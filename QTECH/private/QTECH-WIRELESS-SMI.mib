-- *****************************************************************
-- QTECH-WIRELESS-SMI.mib: Qtech Wireless SMI File
-- 
-- July 2007, Wuzg
-- 
-- Copyright (c) 2007 by Qtech Networks Co.,Ltd.
-- All rights reserved.
-- 
-- *****************************************************************
--

QTECH-WIRELESS-SMI DEFINITIONS ::= BEGIN

IMPORTS
        MODULE-IDENTITY,
        OBJECT-IDENTITY
                FROM SNMPv2-SMI
        products
                FROM QTECH-SMI;
                
wireless        OBJECT IDENTIFIER ::= { products 3 }

wirelessMib MODULE-IDENTITY
        LAST-UPDATED "200707040000Z"
        ORGANIZATION "Qtech Networks Co.,Ltd."
        CONTACT-INFO
                " 
                Tel: 4008-111-000 

                E-mail: service@qtech.com.cn"
        DESCRIPTION
                "The Structure of Management Information for the
                 Qtech enterprise."
        REVISION      "200707040000Z"
        DESCRIPTION
                "Initial version of this MIB module."
        ::= { wireless 1 }        

qtechWirelessProducts OBJECT-IDENTITY
        STATUS  current
        DESCRIPTION
                "qtechWirelessProducts is the root OBJECT IDENTIFIER from
                which sysObjectID values are assigned for wireless product.
                Actual values are defined in QTECH-PRODUCTS-MIB."
        ::= { wirelessMib 1 }

qtechWirelessMgmt OBJECT-IDENTITY
        STATUS  current
        DESCRIPTION
                "qtechWirelessMgmt is the main subtree for those functional mib."
        ::= { wirelessMib 2 }
        
END
