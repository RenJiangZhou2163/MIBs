-- *****************************************************************
-- QTECH-SYSTEM-MIB.mib:  Qtech System MIB file
--
-- Feb 2012, HuangY
--
-- Copyright (c) 2012 by Qtech Networks Co.,Ltd.
-- All rights reserved.
-- 
-- *****************************************************************
--

QTECH-TEMP-FAN-MIB DEFINITIONS ::= BEGIN

IMPORTS
        MODULE-IDENTITY,
        OBJECT-TYPE,
        NOTIFICATION-TYPE,
        Integer32
               FROM SNMPv2-SMI
        MODULE-COMPLIANCE
               FROM SNMPv2-CONF
        qtechMgmt
                FROM QTECH-SMI
        qtechSystemTemperatureCurrent
                FROM QTECH-SYSTEM-MIB;

qtechTempFanMIB MODULE-IDENTITY
        LAST-UPDATED "200203200000Z"
        ORGANIZATION "Qtech Networks Co.,Ltd."
        CONTACT-INFO
                " 
                Tel: 4008-111-000 

                E-mail: service@qtech.com.cn"
        DESCRIPTION
                "This module defines qtech system mibs."
        REVISION      "200203200000Z"
        DESCRIPTION
                "Initial version of this MIB module."
        ::= { qtechMgmt 109}

qtechTempFanTraps OBJECT IDENTIFIER ::= { qtechTempFanMIB 1 }

--Temperature Too High Trap
temperatureTooHighTrap NOTIFICATION-TYPE
        OBJECTS   {qtechSystemTemperatureCurrent}
        STATUS     current
        DESCRIPTION
                "Temperature Too High warning and report the current temperature."
        ::= { qtechTempFanTraps 1 }   
           
--Temperature Too High Recover Trap 
temperTooHighRecovTrap NOTIFICATION-TYPE
        OBJECTS   {qtechSystemTemperatureCurrent}
        STATUS     current
        DESCRIPTION
                "Clear the warning of temperature too high and report the current temperature."
        ::= { qtechTempFanTraps 2 }

--Fan Failure Trap
fanFailure NOTIFICATION-TYPE
        STATUS     current
        DESCRIPTION
                "Fan stopped warning."
        ::= { qtechTempFanTraps 3 }
  
END
