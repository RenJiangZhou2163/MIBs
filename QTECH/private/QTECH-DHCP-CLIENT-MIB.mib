-- *****************************************************************
-- QTECH-DHCP-CLIENT-MIB.mib:  Qtech DHCP client MIB file
--
-- Oct 2015, lushunqin
--
-- Copyright (c) 2015 by Qtech Networks Co.,Ltd.
-- All rights reserved.
-- *****************************************************************
--

QTECH-DHCP-CLIENT-MIB DEFINITIONS ::= BEGIN

IMPORTS
    MODULE-IDENTITY, 
    OBJECT-TYPE,
    IpAddress,
    Integer32,
    Unsigned32
        FROM SNMPv2-SMI

    MODULE-COMPLIANCE,
    OBJECT-GROUP
        FROM SNMPv2-CONF

    TruthValue,
    MacAddress, 
    DisplayString,
    RowStatus
        FROM SNMPv2-TC

    InterfaceIndex
        FROM IF-MIB

    VlanIndex
        FROM Q-BRIDGE-MIB 

    qtechMgmt
        FROM QTECH-SMI;

--********************************************************************
--*  MODULE IDENTITY
--********************************************************************

qtechDhcpClientMIB    MODULE-IDENTITY
       LAST-UPDATED    "201502090000Z"
       ORGANIZATION    "Qtech Networks Co.,Ltd."
       CONTACT-INFO  
                " 
                Tel: 4008-111-000 

                E-mail: service@qtech.com.cn"

        DESCRIPTION             
            "This module defines qtech DHCP Client mibs."
        
        REVISION      "201502090000Z"
        DESCRIPTION
                "Initial version of this MIB module. "
        ::= { qtechMgmt 135 }

qtechDhcpClientMIBObjects OBJECT IDENTIFIER 
    ::= { qtechDhcpClientMIB 0 }
	
qtechDhcpClientConfig OBJECT IDENTIFIER
	::= { qtechDhcpClientMIBObjects 1 }
	
	

--*******************************************************************
--DHCP Client Config :  ip address dhcp on interface
--*******************************************************************

    qtechDhcpClientIntfTable OBJECT-TYPE
         SYNTAX      SEQUENCE OF QtechDhcpClientIntfEntry
         MAX-ACCESS  not-accessible
         STATUS      current
         DESCRIPTION
                     "A table listing the  ip address dhcp 
                     on interface configed for DHCP client."
         ::= { qtechDhcpClientConfig 2 }
   
    qtechDhcpClientIntfEntry OBJECT-TYPE
         SYNTAX      QtechDhcpClientIntfEntry
         MAX-ACCESS  not-accessible
         STATUS      current
         DESCRIPTION
                     "Ip address dhcp entry configed on interface 
                 for DHCP client."
         INDEX       { qtechDhcpIntfClientIndex }
         ::= { qtechDhcpClientIntfTable 1 }
         
    QtechDhcpClientIntfEntry ::= SEQUENCE {
             qtechDhcpIntfClientIndex         InterfaceIndex,
             qtechDhcpClientIpAddrDhcpStatus  INTEGER
             }

    qtechDhcpIntfClientIndex OBJECT-TYPE
         SYNTAX      InterfaceIndex 
         MAX-ACCESS  read-only
         STATUS      current
         DESCRIPTION
                     "Interface DHCP client index."
         ::= { qtechDhcpClientIntfEntry 1 }

    qtechDhcpClientIpAddrDhcpStatus OBJECT-TYPE
         SYNTAX      INTEGER {
                     enable(1),
                     disable(0)
                     }
         MAX-ACCESS  read-create
         STATUS      current
         DESCRIPTION
                     "Ip address dhcp entry configed on interface 
                 for DHCP client. "
         ::= { qtechDhcpClientIntfEntry 2 }

		
qtechDhcpClientMIBConformance OBJECT IDENTIFIER ::= { qtechDhcpClientMIB 2 }
qtechDhcpClientMIBCompliances OBJECT IDENTIFIER ::= { qtechDhcpClientMIBConformance 1 }
qtechDhcpClientMIBGroups      OBJECT IDENTIFIER ::= { qtechDhcpClientMIBConformance 2 }


-- compliance statements

qtechDhcpClientMIBCompliance MODULE-COMPLIANCE
        STATUS  current
        DESCRIPTION
                "The compliance statement for entities which implement
                the Qtech Dhcp Client MIB"
        MODULE  -- this module
                MANDATORY-GROUPS { qtechDhcpClientIntfConfigGroup
                }
        ::= { qtechDhcpClientMIBCompliances 1 }
                
-- units of conformance
        
qtechDhcpClientIntfConfigGroup OBJECT-GROUP
        OBJECTS {
             qtechDhcpClientIpAddrDhcpStatus
        }
        STATUS  current
        DESCRIPTION
                "A collection of objects providing dhcp client config information."
        ::= { qtechDhcpClientMIBGroups 1 } 

END
