-- ****************************************************************
-- Qtech WIFI Configuration and Statistics MIB
--   
-- DEC 2014, Xiongyang
--   
-- Copyright (c) 2014 by Qtech Networks Co.,Ltd.
-- All rights reserved.
--   
-- ****************************************************************


-- Start module
QTECH-ROUTER-WIFI-MIB DEFINITIONS ::= BEGIN

-- Start external defined node
IMPORTS
    MODULE-IDENTITY,
    OBJECT-TYPE,
    Integer32,
    Counter32,
    Gauge32,
    Unsigned32,
    Counter64,
    IpAddress
        FROM SNMPv2-SMI
    MODULE-COMPLIANCE,
    OBJECT-GROUP
        FROM SNMPv2-CONF
    TEXTUAL-CONVENTION,
    DisplayString,
    MacAddress,
    RowStatus,
    TruthValue
        FROM SNMPv2-TC
    InterfaceIndex
        FROM IF-MIB
    qtechMgmt
        FROM QTECH-SMI;
-- End external defined node


-- Start root node
qtechWifiMIB MODULE-IDENTITY
        LAST-UPDATED "201412290000Z"
        ORGANIZATION "Qtech Networks Co.,Ltd."
        CONTACT-INFO
                "E-mail: service@qtech.com.cn"
        DESCRIPTION
                "This module defines qtech wifi mibs."

        REVISION    "201412290000Z"
        DESCRIPTION
                "Initial version of this MIB module."
        ::= { qtechMgmt 133}
        
        QtechEableType ::= TEXTUAL-CONVENTION
          STATUS  current
          DESCRIPTION
             "enable or disable."
          SYNTAX INTEGER {
                     enable(1),
                     disable(2)
                         }

       QtechWlanType ::= TEXTUAL-CONVENTION
          STATUS  current
          DESCRIPTION
             "wlan type."
          SYNTAX INTEGER {
                     ap(1),
                     station(2)
                         }
       
       QtechIsolateType ::= TEXTUAL-CONVENTION
          STATUS  current
          DESCRIPTION
             "wlan ap Isolate type."
          SYNTAX INTEGER {
                     isolate(1),
                     noisolate(2)
                         } 
                         
       QtechAuthenticationType ::= TEXTUAL-CONVENTION
          STATUS  current
          DESCRIPTION
             "authentication type."
          SYNTAX INTEGER {
                     open(1),
                     share-key(2)
                         } 
         
       QtechWapPskCiphersType ::= TEXTUAL-CONVENTION
          STATUS  current
          DESCRIPTION
             "authentication type."
          SYNTAX INTEGER {
                     aes(1),
                     tkip(2),
                     auto(3)
                         }   
                         
       QtechWifiChanWidthType ::= TEXTUAL-CONVENTION
          STATUS  current
          DESCRIPTION
             "Chanle Width type."
          SYNTAX INTEGER {
                     twenty(1),
                     forty(2)
                         }   
       QtechWifiSlotType ::= TEXTUAL-CONVENTION
          STATUS  current
          DESCRIPTION
             "Slot type."
          SYNTAX INTEGER {
                     short(1),
                     long(2)
                         } 
       
       QtechWifiFreChanelType ::= TEXTUAL-CONVENTION
          STATUS  current
          DESCRIPTION
             "Chanle Width type."
          SYNTAX INTEGER {
                     two-point-four(1),
                     five(2)
                         }              
                            
-- End root node
  
        qtechWifiMIBObjects OBJECT IDENTIFIER ::= { qtechWifiMIB 1 } 
     -- WIFI MIB    


-- Node definitions
        qtechWifiDot11radioSupportObjects OBJECT IDENTIFIER ::= { qtechWifiMIBObjects  1 } 
        qtechWifiWlanObjects OBJECT IDENTIFIER ::= { qtechWifiMIBObjects  2 }
        qtechWifiDot11radioIfConfigObjects OBJECT IDENTIFIER ::= { qtechWifiMIBObjects 3 }
--      qtechWifiDot11radioIfApplyObjects OBJECT IDENTIFIER ::= { qtechWifiMIBObjects 4 }
        qtechWifiWlanAssociateObjects OBJECT IDENTIFIER ::= { qtechWifiMIBObjects 4 }        
 
-- Start wifiwlan objects       
        qtechWifiDot11radioSupportTable OBJECT-TYPE  
            SYNTAX SEQUENCE OF QtechWifiDot11radioSupportEntry
            MAX-ACCESS            not-accessible
            STATUS                current
            DESCRIPTION
                "the router support the wifi ability ,
                 include radio index,ap number,station number"
            ::= { qtechWifiDot11radioSupportObjects 1 }
                
        qtechWifiDot11radioSupportEntry OBJECT-TYPE
            SYNTAX QtechWifiDot11radioSupportEntry
            MAX-ACCESS not-accessible
            STATUS current
            DESCRIPTION
                "the router support the wifi ability entry."
            INDEX { qtechWifiDot11radioIndex }
            ::= { qtechWifiDot11radioSupportTable 1 } 
        
        QtechWifiDot11radioSupportEntry::=
            SEQUENCE { 
            	qtechWifiDot11radioIndex
            		Integer32,
                qtechWifiDot11radioApMaxCnt
            		Integer32, 
                qtechWifiDot11radioStationMaxCnt
            		Integer32   
             }                
        
        qtechWifiDot11radioIndex OBJECT-TYPE
            SYNTAX Integer32
            MAX-ACCESS read-only
            STATUS current
            DESCRIPTION
                "the wifi radio interface index."
            ::= { qtechWifiDot11radioSupportEntry 1 }

        qtechWifiDot11radioApMaxCnt OBJECT-TYPE
            SYNTAX Integer32
            MAX-ACCESS read-only
            STATUS current
            DESCRIPTION
                "the wifi radio interface support max ap count."
            ::= { qtechWifiDot11radioSupportEntry 2 } 
        
        qtechWifiDot11radioStationMaxCnt OBJECT-TYPE
            SYNTAX Integer32
            MAX-ACCESS read-only
            STATUS current
            DESCRIPTION
                "the wifi radio interface support max station count."
            ::= { qtechWifiDot11radioSupportEntry 3 }

        qtechWifiWlanIndexNext OBJECT-TYPE
            SYNTAX                INTEGER
            MAX-ACCESS            read-only
            STATUS                current
            DESCRIPTION   "This object contains an appropriate value to be used
                          for qtechWifiWlanIndexNext when creating entries in the
                          qtechWifiWlanTable. The value 0 indicates that no
                          unassigned entries are available."
            ::= { qtechWifiWlanObjects 1 }
        
        qtechWifiVlanIndexNext OBJECT-TYPE
            SYNTAX                INTEGER
            MAX-ACCESS            read-only
            STATUS                current
            DESCRIPTION   "This object contains an appropriate value to be used
                          for qtechWifiVlanIndexNext when creating entries in the
                          qtechWifiWlanTable. The value 0 indicates that no
                          unassigned entries are available."
            ::= { qtechWifiWlanObjects 2 }  
               
        qtechWifiWlanTable OBJECT-TYPE
            SYNTAX SEQUENCE OF QtechWifiWlanEntry
            MAX-ACCESS not-accessible
            STATUS current
            DESCRIPTION
                "A table of wifi wlan templet."
            ::= { qtechWifiWlanObjects 3 }
        
        qtechWifiWlanEntry OBJECT-TYPE
            SYNTAX QtechWifiWlanEntry
            MAX-ACCESS not-accessible
            STATUS current
            DESCRIPTION
                "Wifi wlan temple entry."
            INDEX { qtechWifiWlanIndex }
            ::= { qtechWifiWlanTable 1 }
   
        QtechWifiWlanEntry ::=
            SEQUENCE { 
            	qtechWifiWlanIndex
            		Integer32,
                qtechWifiWlanType
                    QtechWlanType,   
                qtechWifiWlanSsidName
                    DisplayString,
                qtechWifiWlanVlanId
                    Integer32, 
                qtechWifiWlanRowStatus           
                    RowStatus,
                qtechWifiWlanBroadcastSsid
                    QtechEableType,
                qtechWifiWlanIsolate
                    QtechIsolateType,
                qtechWifiWlanBssStaLimit
                    Integer32,  
                rujieWifiWlanSecurityType 
                    BITS, 
                qtechWifiWlanAuthenticationSetKey
                    DisplayString,
                qtechWifiWlanWepAuthenticationType  
                    QtechAuthenticationType, 
                qtechWifiWlanWpaPskCiphersType    
                    QtechWapPskCiphersType, 
                qtechWifiWlanPassphrase 
                    DisplayString,
                qtechWifiWlanDot11RadioIfindex
                    Integer32,
                qtechWifiWlanDot11RadioSubIfindex
                    Integer32
                             }
             
        qtechWifiWlanIndex OBJECT-TYPE
            SYNTAX Integer32(1..15)
            MAX-ACCESS read-only
            STATUS current
            DESCRIPTION
                "The wlan index"
            ::= { qtechWifiWlanEntry 1 }
                    
        qtechWifiWlanType OBJECT-TYPE
            SYNTAX QtechWlanType
            MAX-ACCESS read-write
            STATUS current
            DESCRIPTION
                "Wlan type ap or station."
            ::= { qtechWifiWlanEntry 2 }

        qtechWifiWlanSsidName OBJECT-TYPE
            SYNTAX DisplayString(SIZE (1..32))
            MAX-ACCESS read-write
            STATUS current
            DESCRIPTION
                "Wlan ssid name"
            ::= { qtechWifiWlanEntry 3 }
        
        qtechWifiWlanVlanId OBJECT-TYPE
            SYNTAX Integer32(1..4095)
            MAX-ACCESS read-write
            STATUS current
            DESCRIPTION
                "Wlan vlan id"
            ::= { qtechWifiWlanEntry 4 }   
            
        qtechWifiWlanRowStatus OBJECT-TYPE
            SYNTAX RowStatus
            MAX-ACCESS read-write
            STATUS current
            DESCRIPTION
                "create/modify/delete wlan"
            ::= { qtechWifiWlanEntry 5 }

        
        qtechWifiWlanBroadcastSsid OBJECT-TYPE
            SYNTAX QtechEableType
            MAX-ACCESS read-write
            STATUS current
            DESCRIPTION
                "BroadcastSsid enable or disable"
            ::= { qtechWifiWlanEntry 6}
        
        qtechWifiWlanIsolate OBJECT-TYPE
            SYNTAX QtechIsolateType
            MAX-ACCESS read-write
            STATUS current
            DESCRIPTION
                "Isolate ap"
            ::= { qtechWifiWlanEntry 7 }
        
        qtechWifiWlanBssStaLimit OBJECT-TYPE
            SYNTAX Integer32
            MAX-ACCESS read-write
            STATUS current
            DESCRIPTION
                "the number of user count of bss"
            ::= { qtechWifiWlanEntry 8 }
        
        rujieWifiWlanSecurityType OBJECT-TYPE
            SYNTAX BITS {
               null(0),
               wep(1),
               wpa-psk(2),
               wpa2-psk(3)
            }
            MAX-ACCESS read-write
            STATUS current
            DESCRIPTION
                "wlan security type"
            ::= { qtechWifiWlanEntry 9 }
                        
        qtechWifiWlanAuthenticationSetKey OBJECT-TYPE
            SYNTAX DisplayString
            MAX-ACCESS read-write
            STATUS current
            DESCRIPTION
                "wlan security authentication type"
            ::= { qtechWifiWlanEntry 10 }
        
            
        qtechWifiWlanWepAuthenticationType OBJECT-TYPE
            SYNTAX QtechAuthenticationType
            MAX-ACCESS read-write
            STATUS current
            DESCRIPTION
                "the wep authentication type"
            ::= { qtechWifiWlanEntry 11 }
 
 		qtechWifiWlanWpaPskCiphersType OBJECT-TYPE
            SYNTAX QtechWapPskCiphersType
            MAX-ACCESS read-write
            STATUS current
            DESCRIPTION
                "Wpa-psk ciphers type."
            ::= { qtechWifiWlanEntry 12 }   

        qtechWifiWlanPassphrase OBJECT-TYPE
            SYNTAX DisplayString
            MAX-ACCESS read-write
            STATUS current
            DESCRIPTION
                "The station connect ap setkey ."
            ::= { qtechWifiWlanEntry 13 }   
             
        qtechWifiWlanDot11RadioIfindex OBJECT-TYPE
            SYNTAX Integer32
            MAX-ACCESS read-only
            STATUS current
            DESCRIPTION
                "the ifindex of interface dot11radio"
            ::= { qtechWifiWlanEntry 14 }  
            
        qtechWifiWlanDot11RadioSubIfindex OBJECT-TYPE
            SYNTAX Integer32
            MAX-ACCESS read-only
            STATUS current
            DESCRIPTION
                "the ifindex of subinterface dot11radio"
            ::= { qtechWifiWlanEntry 15 } 
                   
-- End wifi wlan objects         

-- Start Dot11radio interface config objects       
        qtechWifiDot11radioIfConfigTable OBJECT-TYPE
            SYNTAX SEQUENCE OF QtechWifiDot11radioIfConfigEntry
            MAX-ACCESS not-accessible
            STATUS current
            DESCRIPTION
                "A table of wifi Dot11radio interface config."
            ::= { qtechWifiDot11radioIfConfigObjects 1 } 
            
         qtechWifiDot11radioIfConfigEntry OBJECT-TYPE
            SYNTAX QtechWifiDot11radioIfConfigEntry
            MAX-ACCESS not-accessible
            STATUS current
            DESCRIPTION
                "wifi Dot11radio interface config entry."
            INDEX { qtechWifiDot11radioIfConfigIfIndex }
            ::= { qtechWifiDot11radioIfConfigTable 1 }    
            
         
         QtechWifiDot11radioIfConfigEntry ::=
            SEQUENCE { 
            	qtechWifiDot11radioIfConfigIfIndex
            	    Integer32, 
                qtechWifiDot11radioIfConfigRowStatus           
                    RowStatus, 
                qtechWifiDot11radioIfConfigFreBand
                    QtechWifiFreChanelType,
                qtechWifiDot11radioIfConfigChannel
                    Integer32,
                qtechWifiDot11radioIfConfigChanWidth
                    QtechWifiChanWidthType,
                qtechWifiDot11radioIfConfigCountryCode
                    DisplayString,
                qtechWifiDot11radioIfConfigPowerLocal
                    Integer32,
                qtechWifiDot11radioIfConfigWirelessProSupport 
                    BITS,
                qtechWifiDot11radioIfConfigStaLimit
                    Integer32,
                qtechWifiDot11radioIfConfig20ShortGiEnable
                    QtechEableType, 
                qtechWifiDot11radioIfConfig40ShortGiEnable
                    QtechEableType,
                qtechWifiDot11radioIfConfigShortPreambleEnable
                    QtechEableType,
                qtechWifiDot11radioIfConfigSlottime 
                    QtechWifiSlotType,
                qtechWifiDot11radioIfConfigRtsThreshold
                    Integer32, 
                qtechWifiDot11radioIfConfigFragmentThreshold  
                    Integer32, 
                qtechWifiDot11radioIfConfigResponseRssi 
                    Integer32,  
                qtechWifiDot11radioIfConfigEnableQos
                    QtechEableType,
                qtechWifiDot11radioIfConfigEdcaClientBgAifsn
                    Integer32,
                qtechWifiDot11radioIfConfigEdcaClientBgCwmin 
                    Integer32,
                qtechWifiDot11radioIfConfigEdcaClientBgCwmax
                    Integer32,
                qtechWifiDot11radioIfConfigEdcaClientBgTxop
                    Integer32,
                qtechWifiDot11radioIfConfigEdcaClientBeAifsn
                    Integer32,
                qtechWifiDot11radioIfConfigEdcaClientBeCwmin 
                    Integer32,
                qtechWifiDot11radioIfConfigEdcaClientBeCwmax
                    Integer32,
                qtechWifiDot11radioIfConfigEdcaClientBeTxop
                    Integer32,
                qtechWifiDot11radioIfConfigEdcaClientViAifsn
                    Integer32,
                qtechWifiDot11radioIfConfigEdcaClientViCwmin 
                    Integer32,
                qtechWifiDot11radioIfConfigEdcaClientViCwmax
                    Integer32,
                qtechWifiDot11radioIfConfigEdcaClientViTxop
                    Integer32, 
                qtechWifiDot11radioIfConfigEdcaClientVoAifsn
                    Integer32,
                qtechWifiDot11radioIfConfigEdcaClientVoCwmin 
                    Integer32,
                qtechWifiDot11radioIfConfigEdcaClientVoCwmax
                    Integer32,
                qtechWifiDot11radioIfConfigEdcaClientVoTxop
                    Integer32,
                qtechWifiDot11radioIfConfigEdcaRadioBgAifsn
                    Integer32,
                qtechWifiDot11radioIfConfigEdcaRadioBgCwmin 
                    Integer32,
                qtechWifiDot11radioIfConfigEdcaRadioBgCwmax
                    Integer32,
                qtechWifiDot11radioIfConfigEdcaRadioBgTxop
                    Integer32,
                qtechWifiDot11radioIfConfigEdcaRadioBeAifsn
                    Integer32,
                qtechWifiDot11radioIfConfigEdcaRadioBeCwmin 
                    Integer32,
                qtechWifiDot11radioIfConfigEdcaRadioBeCwmax
                    Integer32,
                qtechWifiDot11radioIfConfigEdcaRadioBeTxop
                    Integer32,
                qtechWifiDot11radioIfConfigEdcaRadioViAifsn
                    Integer32,
                qtechWifiDot11radioIfConfigEdcaRadioViCwmin 
                    Integer32,
                qtechWifiDot11radioIfConfigEdcaRadioViCwmax
                    Integer32,
                qtechWifiDot11radioIfConfigEdcaRadioViTxop
                    Integer32, 
                qtechWifiDot11radioIfConfigEdcaRadioVoAifsn
                    Integer32,
                qtechWifiDot11radioIfConfigEdcaRadioVoCwmin 
                    Integer32,
                qtechWifiDot11radioIfConfigEdcaRadioVoCwmax
                    Integer32,
                qtechWifiDot11radioIfConfigEdcaRadioVoTxop
                    Integer32,
                qtechWifiDot11radioIfConfigAntennaTransChainmask
                    Integer32,
                qtechWifiDot11radioIfConfigAntennaReceiveChainmask
                    Integer32,   
                qtechWifiDot11radioIfConfigBeaconDtimPeriod
                    Integer32,
                qtechWifiDot11radioIfConfigBeaconPeriod
                    Integer32, 
                qtechWifiDot11radioIfConfigRetrieShortTime
                    Integer32, 
                qtechWifiDot11radioIfConfigRetrieLongTime
                    Integer32, 
                qtechWifiDot11radioIfConfigStaIdleTimeout
                    Integer32,
                qtechWifiDot11radioIfConfigWlanIdList
                    BITS
                }                             
                             
       qtechWifiDot11radioIfConfigIfIndex OBJECT-TYPE
            SYNTAX Integer32
            MAX-ACCESS read-only
            STATUS current
            DESCRIPTION
                "The Dot11radio interface index ."
            ::= { qtechWifiDot11radioIfConfigEntry 1 }
            
       qtechWifiDot11radioIfConfigRowStatus OBJECT-TYPE
            SYNTAX RowStatus
            MAX-ACCESS read-write
            STATUS current
            DESCRIPTION
                "create/modify/delete ."
            ::= { qtechWifiDot11radioIfConfigEntry 2 }           
                         
       qtechWifiDot11radioIfConfigFreBand OBJECT-TYPE
            SYNTAX QtechWifiFreChanelType
            MAX-ACCESS read-write
            STATUS current
            DESCRIPTION
                "The Dot11radio frequency band  ."
            ::= { qtechWifiDot11radioIfConfigEntry 3 }   
        
        qtechWifiDot11radioIfConfigChannel OBJECT-TYPE
            SYNTAX Integer32
            MAX-ACCESS read-write
            STATUS current
            DESCRIPTION
                "The Dot11radio work Chanel num."
            ::= { qtechWifiDot11radioIfConfigEntry 4 } 
            
        qtechWifiDot11radioIfConfigChanWidth OBJECT-TYPE
            SYNTAX QtechWifiChanWidthType
            MAX-ACCESS read-write
            STATUS current
            DESCRIPTION
                "The Dot11radio Chanel width ."
            ::= { qtechWifiDot11radioIfConfigEntry 5 }   
            
        qtechWifiDot11radioIfConfigCountryCode OBJECT-TYPE
            SYNTAX DisplayString
            MAX-ACCESS read-write
            STATUS current
            DESCRIPTION
                "The Dot11radio country code."
            ::= { qtechWifiDot11radioIfConfigEntry 6 } 
        
         qtechWifiDot11radioIfConfigPowerLocal OBJECT-TYPE
            SYNTAX Integer32(1..100)
            MAX-ACCESS read-write
            STATUS current
            DESCRIPTION
                "The Dot11radio power local percent."
            ::= { qtechWifiDot11radioIfConfigEntry 7 }
                            
        qtechWifiDot11radioIfConfigWirelessProSupport OBJECT-TYPE
             SYNTAX BITS {
               null(0),
               b(1),
               g(2),
               n(3)
            }

            MAX-ACCESS read-write
            STATUS current
            DESCRIPTION
                "The Dot11radio Support wireless protocol ."
            ::= { qtechWifiDot11radioIfConfigEntry 8 } 
                           
        qtechWifiDot11radioIfConfigStaLimit OBJECT-TYPE
            SYNTAX Integer32(1..60)
            MAX-ACCESS read-write
            STATUS current
            DESCRIPTION
                "The Dot11radio Sta Limit ."
            ::= { qtechWifiDot11radioIfConfigEntry 9 }
                    
        qtechWifiDot11radioIfConfig20ShortGiEnable OBJECT-TYPE
            SYNTAX QtechEableType
            MAX-ACCESS read-write
            STATUS current
            DESCRIPTION
                "The Dot11radio 20ShortGi enable."
            ::= { qtechWifiDot11radioIfConfigEntry 10 }
        
        qtechWifiDot11radioIfConfig40ShortGiEnable OBJECT-TYPE
            SYNTAX QtechEableType
            MAX-ACCESS read-write
            STATUS current
            DESCRIPTION
                "The Dot11radio 40ShortGi enable ."
            ::= { qtechWifiDot11radioIfConfigEntry 11 }

                    
        qtechWifiDot11radioIfConfigShortPreambleEnable OBJECT-TYPE
            SYNTAX QtechEableType
            MAX-ACCESS read-write
            STATUS current
            DESCRIPTION
                "The Dot11radio ShortPreamble enable ."
            ::= { qtechWifiDot11radioIfConfigEntry 12 } 
        
        qtechWifiDot11radioIfConfigSlottime OBJECT-TYPE
            SYNTAX QtechWifiSlotType
            MAX-ACCESS read-write
            STATUS current
            DESCRIPTION
                "The Dot11radio slot time ."
            ::= { qtechWifiDot11radioIfConfigEntry 13 } 
    
        qtechWifiDot11radioIfConfigRtsThreshold OBJECT-TYPE
            SYNTAX Integer32(257..2347)
            MAX-ACCESS read-write
            STATUS current
            DESCRIPTION
                "The Dot11radio rts thresholx ."
            ::= { qtechWifiDot11radioIfConfigEntry 14 }
        
        qtechWifiDot11radioIfConfigFragmentThreshold OBJECT-TYPE
            SYNTAX Integer32(256..2346)
            MAX-ACCESS read-write
            STATUS current
            DESCRIPTION
                "The Dot11radio fragment threshold ."
            ::= { qtechWifiDot11radioIfConfigEntry 15 }
        
        qtechWifiDot11radioIfConfigResponseRssi OBJECT-TYPE
            SYNTAX Integer32(0..100)
            MAX-ACCESS read-write
            STATUS current
            DESCRIPTION
                "The Dot11radio response rss ."
            ::= { qtechWifiDot11radioIfConfigEntry 16 }
            
        qtechWifiDot11radioIfConfigEnableQos OBJECT-TYPE
            SYNTAX QtechEableType
            MAX-ACCESS read-write
            STATUS current
            DESCRIPTION
                "The Dot11radio qos enable or disable ."
            ::= { qtechWifiDot11radioIfConfigEntry 17 }
            
        qtechWifiDot11radioIfConfigEdcaClientBgAifsn OBJECT-TYPE
            SYNTAX Integer32(1..15) 
            MAX-ACCESS read-write
            STATUS current
            DESCRIPTION
                "The Dot11radio edca client back-groud aifsn value."
            ::= { qtechWifiDot11radioIfConfigEntry 18 } 
        
        qtechWifiDot11radioIfConfigEdcaClientBgCwmin OBJECT-TYPE
            SYNTAX Integer32(1..15) 
            MAX-ACCESS read-write
            STATUS current
            DESCRIPTION
                "The Dot11radio edca client back-groud cwmin value."
            ::= { qtechWifiDot11radioIfConfigEntry 19 }
        
        qtechWifiDot11radioIfConfigEdcaClientBgCwmax OBJECT-TYPE
            SYNTAX Integer32(1..15) 
            MAX-ACCESS read-write
            STATUS current
            DESCRIPTION
                "The Dot11radio edca client back-groud cwmax value."
            ::= { qtechWifiDot11radioIfConfigEntry 20 }
        
        qtechWifiDot11radioIfConfigEdcaClientBgTxop OBJECT-TYPE
            SYNTAX Integer32(0..255) 
            MAX-ACCESS read-write
            STATUS current
            DESCRIPTION
                "The Dot11radio edca client back-groud txop value."
            ::= { qtechWifiDot11radioIfConfigEntry 21 } 
            
        qtechWifiDot11radioIfConfigEdcaClientBeAifsn OBJECT-TYPE
            SYNTAX Integer32(1..15) 
            MAX-ACCESS read-write
            STATUS current
            DESCRIPTION
                "The Dot11radio edca client best-effort aifsn value."
            ::= { qtechWifiDot11radioIfConfigEntry 22 } 
        
        qtechWifiDot11radioIfConfigEdcaClientBeCwmin OBJECT-TYPE
            SYNTAX Integer32(1..15) 
            MAX-ACCESS read-write
            STATUS current
            DESCRIPTION
                "The Dot11radio edca client best-effort cwmin value."
            ::= { qtechWifiDot11radioIfConfigEntry 23 }
        
        qtechWifiDot11radioIfConfigEdcaClientBeCwmax OBJECT-TYPE
            SYNTAX Integer32(1..15) 
            MAX-ACCESS read-write
            STATUS current
            DESCRIPTION
                "The Dot11radio edca client best-effort cwmax value."
            ::= { qtechWifiDot11radioIfConfigEntry 24 }
        
        qtechWifiDot11radioIfConfigEdcaClientBeTxop OBJECT-TYPE
            SYNTAX Integer32(0..255) 
            MAX-ACCESS read-write
            STATUS current
            DESCRIPTION
                "The Dot11radio edca client best-effort txop value."
            ::= { qtechWifiDot11radioIfConfigEntry 25 }   
        
        qtechWifiDot11radioIfConfigEdcaClientViAifsn OBJECT-TYPE
            SYNTAX Integer32(1..15) 
            MAX-ACCESS read-write
            STATUS current
            DESCRIPTION
                "The Dot11radio edca client video aifsn value."
            ::= { qtechWifiDot11radioIfConfigEntry 26 } 
        
        qtechWifiDot11radioIfConfigEdcaClientViCwmin OBJECT-TYPE
            SYNTAX Integer32(1..15) 
            MAX-ACCESS read-write
            STATUS current
            DESCRIPTION
                "The Dot11radio edca client video cwmin value."
            ::= { qtechWifiDot11radioIfConfigEntry 27 }
        
        qtechWifiDot11radioIfConfigEdcaClientViCwmax OBJECT-TYPE
            SYNTAX Integer32(1..15) 
            MAX-ACCESS read-write
            STATUS current
            DESCRIPTION
                "The Dot11radio edca client video cwmax value."
            ::= { qtechWifiDot11radioIfConfigEntry 28 }
        
        qtechWifiDot11radioIfConfigEdcaClientViTxop OBJECT-TYPE
            SYNTAX Integer32(0..255) 
            MAX-ACCESS read-write
            STATUS current
            DESCRIPTION
                "The Dot11radio edca client video txop value."
            ::= { qtechWifiDot11radioIfConfigEntry 29 }

        qtechWifiDot11radioIfConfigEdcaClientVoAifsn OBJECT-TYPE
            SYNTAX Integer32(1..15) 
            MAX-ACCESS read-write
            STATUS current
            DESCRIPTION
                "The Dot11radio edca client voice aifsn value."
            ::= { qtechWifiDot11radioIfConfigEntry 30 } 
        
        qtechWifiDot11radioIfConfigEdcaClientVoCwmin OBJECT-TYPE
            SYNTAX Integer32(1..15) 
            MAX-ACCESS read-write
            STATUS current
            DESCRIPTION
                "The Dot11radio edca client voice cwmin value."
            ::= { qtechWifiDot11radioIfConfigEntry 31 }
        
        qtechWifiDot11radioIfConfigEdcaClientVoCwmax OBJECT-TYPE
            SYNTAX Integer32(1..15) 
            MAX-ACCESS read-write
            STATUS current
            DESCRIPTION
                "The Dot11radio edca client voice cwmax value."
            ::= { qtechWifiDot11radioIfConfigEntry 32 }
        
        qtechWifiDot11radioIfConfigEdcaClientVoTxop OBJECT-TYPE
            SYNTAX Integer32(0..255) 
            MAX-ACCESS read-write
            STATUS current
            DESCRIPTION
                "The Dot11radio edca client voice txop value."
            ::= { qtechWifiDot11radioIfConfigEntry 33 }
        
        qtechWifiDot11radioIfConfigEdcaRadioBgAifsn OBJECT-TYPE
            SYNTAX Integer32(1..15) 
            MAX-ACCESS read-write
            STATUS current
            DESCRIPTION
                "The Dot11radio edca Radio back-groud aifsn value."
            ::= { qtechWifiDot11radioIfConfigEntry 34 } 
        
        qtechWifiDot11radioIfConfigEdcaRadioBgCwmin OBJECT-TYPE
            SYNTAX Integer32(1..15) 
            MAX-ACCESS read-write
            STATUS current
            DESCRIPTION
                "The Dot11radio edca Radio back-groud cwmin value."
            ::= { qtechWifiDot11radioIfConfigEntry 35 }
        
        qtechWifiDot11radioIfConfigEdcaRadioBgCwmax OBJECT-TYPE
            SYNTAX Integer32(1..15) 
            MAX-ACCESS read-write
            STATUS current
            DESCRIPTION
                "The Dot11radio edca Radio back-groud cwmax value."
            ::= { qtechWifiDot11radioIfConfigEntry 36 }
        
        qtechWifiDot11radioIfConfigEdcaRadioBgTxop OBJECT-TYPE
            SYNTAX Integer32(0..255) 
            MAX-ACCESS read-write
            STATUS current
            DESCRIPTION
                "The Dot11radio edca Radio back-groud txop value."
            ::= { qtechWifiDot11radioIfConfigEntry 37 } 
            
        qtechWifiDot11radioIfConfigEdcaRadioBeAifsn OBJECT-TYPE
            SYNTAX Integer32(1..15) 
            MAX-ACCESS read-write
            STATUS current
            DESCRIPTION
                "The Dot11radio edca Radio best-effort aifsn value."
            ::= { qtechWifiDot11radioIfConfigEntry 38 } 
        
        qtechWifiDot11radioIfConfigEdcaRadioBeCwmin OBJECT-TYPE
            SYNTAX Integer32(1..15) 
            MAX-ACCESS read-write
            STATUS current
            DESCRIPTION
                "The Dot11radio edca Radio best-effort cwmin value."
            ::= { qtechWifiDot11radioIfConfigEntry 39 }
        
        qtechWifiDot11radioIfConfigEdcaRadioBeCwmax OBJECT-TYPE
            SYNTAX Integer32(1..15) 
            MAX-ACCESS read-write
            STATUS current
            DESCRIPTION
                "The Dot11radio edca Radio best-effort cwmax value."
            ::= { qtechWifiDot11radioIfConfigEntry 40 }
        
        qtechWifiDot11radioIfConfigEdcaRadioBeTxop OBJECT-TYPE
            SYNTAX Integer32(0..255) 
            MAX-ACCESS read-write
            STATUS current
            DESCRIPTION
                "The Dot11radio edca Radio best-effort txop value."
            ::= { qtechWifiDot11radioIfConfigEntry 41 }   
        
        qtechWifiDot11radioIfConfigEdcaRadioViAifsn OBJECT-TYPE
            SYNTAX Integer32(1..15) 
            MAX-ACCESS read-write
            STATUS current
            DESCRIPTION
                "The Dot11radio edca Radio video aifsn value."
            ::= { qtechWifiDot11radioIfConfigEntry 42 } 
        
        qtechWifiDot11radioIfConfigEdcaRadioViCwmin OBJECT-TYPE
            SYNTAX Integer32(1..15) 
            MAX-ACCESS read-write
            STATUS current
            DESCRIPTION
                "The Dot11radio edca Radio video cwmin value."
            ::= { qtechWifiDot11radioIfConfigEntry 43 }
        
        qtechWifiDot11radioIfConfigEdcaRadioViCwmax OBJECT-TYPE
            SYNTAX Integer32(1..15) 
            MAX-ACCESS read-write
            STATUS current
            DESCRIPTION
                "The Dot11radio edca Radio video cwmax value."
            ::= { qtechWifiDot11radioIfConfigEntry 44 }
        
        qtechWifiDot11radioIfConfigEdcaRadioViTxop OBJECT-TYPE
            SYNTAX Integer32(0..255) 
            MAX-ACCESS read-write
            STATUS current
            DESCRIPTION
                "The Dot11radio edca Radio video txop value."
            ::= { qtechWifiDot11radioIfConfigEntry 45 }

        qtechWifiDot11radioIfConfigEdcaRadioVoAifsn OBJECT-TYPE
            SYNTAX Integer32(1..15) 
            MAX-ACCESS read-write
            STATUS current
            DESCRIPTION
                "The Dot11radio edca Radio voice aifsn value."
            ::= { qtechWifiDot11radioIfConfigEntry 46 } 
        
        qtechWifiDot11radioIfConfigEdcaRadioVoCwmin OBJECT-TYPE
            SYNTAX Integer32(1..15) 
            MAX-ACCESS read-write
            STATUS current
            DESCRIPTION
                "The Dot11radio edca Radio voice cwmin value."
            ::= { qtechWifiDot11radioIfConfigEntry 47 }
        
        qtechWifiDot11radioIfConfigEdcaRadioVoCwmax OBJECT-TYPE
            SYNTAX Integer32(1..15) 
            MAX-ACCESS read-write
            STATUS current
            DESCRIPTION
                "The Dot11radio edca Radio voice cwmax value."
            ::= { qtechWifiDot11radioIfConfigEntry 48 }
        
        qtechWifiDot11radioIfConfigEdcaRadioVoTxop OBJECT-TYPE
            SYNTAX Integer32(0..255) 
            MAX-ACCESS read-write
            STATUS current
            DESCRIPTION
                "The Dot11radio edca Radio voice txop value."
            ::= { qtechWifiDot11radioIfConfigEntry 49 }
       
        qtechWifiDot11radioIfConfigAntennaTransChainmask  OBJECT-TYPE
            SYNTAX Integer32(1..3) 
            MAX-ACCESS read-write
            STATUS current
            DESCRIPTION
                "The Dot11radio antenna transmit chainmask."
            ::= { qtechWifiDot11radioIfConfigEntry 50 }
            
        qtechWifiDot11radioIfConfigAntennaReceiveChainmask  OBJECT-TYPE
            SYNTAX Integer32(1..3) 
            MAX-ACCESS read-write
            STATUS current
            DESCRIPTION
                "The Dot11radio antenna receive chainmask."
            ::= { qtechWifiDot11radioIfConfigEntry 51 }
                       
        qtechWifiDot11radioIfConfigBeaconDtimPeriod  OBJECT-TYPE
            SYNTAX Integer32(1..255) 
            MAX-ACCESS read-write
            STATUS current
            DESCRIPTION
                "The Dot11radio beacon dtim period ."
            ::= { qtechWifiDot11radioIfConfigEntry 52 }
                  
        qtechWifiDot11radioIfConfigBeaconPeriod  OBJECT-TYPE
            SYNTAX Integer32(200..1000) 
            MAX-ACCESS read-write
            STATUS current
            DESCRIPTION
                "The Dot11radio beacon period."
            ::= { qtechWifiDot11radioIfConfigEntry 53 }
                    
         qtechWifiDot11radioIfConfigRetrieShortTime  OBJECT-TYPE
            SYNTAX Integer32(1..7) 
            MAX-ACCESS read-write
            STATUS current
            DESCRIPTION
                "The Dot11radio short frame retrie times."
            ::= { qtechWifiDot11radioIfConfigEntry 54 }
                     
         qtechWifiDot11radioIfConfigRetrieLongTime  OBJECT-TYPE
            SYNTAX Integer32(1..4) 
            MAX-ACCESS read-write
            STATUS current
            DESCRIPTION
                "The Dot11radio long frame retrie times."
            ::= { qtechWifiDot11radioIfConfigEntry 55 }
                    
          qtechWifiDot11radioIfConfigStaIdleTimeout  OBJECT-TYPE
            SYNTAX Integer32(60..86400) 
            MAX-ACCESS read-write
            STATUS current
            DESCRIPTION
                "The Dot11radio Station idle timeout"
            ::= { qtechWifiDot11radioIfConfigEntry 56 }
                   
          qtechWifiDot11radioIfConfigWlanIdList  OBJECT-TYPE
            SYNTAX BITS {
               w0(0), 
               w1(1),
               w2(2),
               w3(3),
               w4(4),
               w5(5),
               w6(6),
               w7(7),
               w8(8),
               w9(9),
               w10(10),
               w11(11),
               w12(12), 
               w13(13),
               w14(14),
               w15(15)
            }
            MAX-ACCESS read-write
            STATUS current
            DESCRIPTION
                "The Dot11radio Station idle timeout"
            ::= { qtechWifiDot11radioIfConfigEntry 57 }

             
-- End Dot11radio interface config objects                                                                
 
-- Start Dot11radio interface apply objects        
--        qtechWifiDot11radioIfApplyTable OBJECT-TYPE
--            SYNTAX SEQUENCE OF QtechWifiDot11radioIfApplyEntry
--            MAX-ACCESS not-accessible
--            STATUS current
--            DESCRIPTION
--                "A table of wifi Dot11radio interface wlan Apply."
--            ::= { qtechWifiDot11radioIfApplyObjects 1 } 
--            
--         qtechWifiDot11radioIfApplyEntry OBJECT-TYPE
--            SYNTAX QtechWifiDot11radioIfApplyEntry
--            MAX-ACCESS not-accessible
--            STATUS current
--            DESCRIPTION
--                "wifi Dot11radio interface Apply entry."
--            INDEX { qtechWifiDot11radioIfApplyIfIndex }
--            ::= { qtechWifiDot11radioIfApplyTable 1 }    
--            
--         
--        QtechWifiDot11radioIfApplyEntry ::=
--            SEQUENCE { 
--            	qtechWifiDot11radioIfApplyIfIndex
--            		Integer32,  
--                qtechWifiDot11radioIfApplyRowStatus           
--                    RowStatus,  
--                qtechWifiDot11radioIfApplyVlanId
--                    Integer32,  
--                qtechWifiDot11radioIfApplyIpAddress
--                    IpAddress,
--                qtechWifiDot11radioIfApplyMaskAddress
--                    IpAddress, 
--                qtechWifiDot11radioIfApplyStaDhcpEnable
--                    QtechEableType,
--                qtechWifiDot11radioIfApplyStaNatEnable
--                    QtechEableType
--                }                                              
--                   
--         qtechWifiDot11radioIfApplyIfIndex OBJECT-TYPE
--            SYNTAX Integer32
--            MAX-ACCESS not-accessible
--            STATUS current
--            DESCRIPTION
--                "The Dot11radio interface Apply index ."
--            ::= { qtechWifiDot11radioIfApplyEntry 1 } 
--            
--         qtechWifiDot11radioIfApplyRowStatus OBJECT-TYPE
--            SYNTAX RowStatus
--            MAX-ACCESS read-write
--            STATUS current
--            DESCRIPTION
--                "The Dot11radio interface Apply/delete."
--            ::= { qtechWifiDot11radioIfApplyEntry 2 }
--               
--         qtechWifiDot11radioIfApplyVlanId OBJECT-TYPE
--            SYNTAX Integer32
--            MAX-ACCESS read-write
--            STATUS current
--            DESCRIPTION
--                "The Dot11radio interface Apply vlan id."
--            ::= { qtechWifiDot11radioIfApplyEntry 3 }  
--                   
--         qtechWifiDot11radioIfApplyIpAddress OBJECT-TYPE
--            SYNTAX IpAddress
--            MAX-ACCESS read-write
--            STATUS current
--            DESCRIPTION
--                "The Dot11radio interface Apply station ip address ."
--            ::= { qtechWifiDot11radioIfApplyEntry 4 } 
--                                
--         qtechWifiDot11radioIfApplyMaskAddress OBJECT-TYPE
--            SYNTAX IpAddress
--            MAX-ACCESS read-write
--            STATUS current
--            DESCRIPTION
--                "The Dot11radio interface Apply station ip address mask ."
--            ::= { qtechWifiDot11radioIfApplyEntry 5 }
--            
--         qtechWifiDot11radioIfApplyStaDhcpEnable OBJECT-TYPE
--            SYNTAX QtechEableType
--            MAX-ACCESS read-write
--            STATUS current
--            DESCRIPTION
--                "The Dot11radio interface Apply station dhcp enable ."
--            ::= { qtechWifiDot11radioIfApplyEntry 6 }
--         
--         qtechWifiDot11radioIfApplyStaNatEnable OBJECT-TYPE
--            SYNTAX QtechEableType
--            MAX-ACCESS read-write
--            STATUS current
--            DESCRIPTION
--                "The Dot11radio interface Apply station nat enable ."
--            ::= { qtechWifiDot11radioIfApplyEntry 7 }    
-- End Dot11radio interface apply objects 

-- Start Wlan associate objects            
         qtechWifiWlanAssociateTable OBJECT-TYPE
            SYNTAX SEQUENCE OF QtechWifiWlanAssociateEntry
            MAX-ACCESS not-accessible
            STATUS current
            DESCRIPTION
                "A table of wifi wlan associate infromation."
            ::= { qtechWifiWlanAssociateObjects 1 }    
            
          qtechWifiWlanAssociateEntry OBJECT-TYPE
            SYNTAX QtechWifiWlanAssociateEntry
            MAX-ACCESS not-accessible
            STATUS current
            DESCRIPTION
                "wifi wlan associate infromation entry."
            INDEX {qtechWifiWlanAssociateWlanId ,qtechWifiWlanAssociateStaMacAdress}
            ::= { qtechWifiWlanAssociateTable 1 } 
                      
          QtechWifiWlanAssociateEntry ::=
            SEQUENCE { 
            	qtechWifiWlanAssociateWlanId
            	    Integer32, 
                qtechWifiWlanAssociateStaMacAdress
                    DisplayString, 
                qtechWifiWlanAssociateSsidName
                    DisplayString,      
                qtechWifiWlanAssociateStaIpAdress
                    IpAddress,
                qtechWifiWlanAssociateStaMaskAdress
                    IpAddress,
                qtechWifiWlanAssociateStaSigalStrength
                    Integer32,
                qtechWifiWlanAssociateStaConnectTime
                    DisplayString,
                qtechWifiWlanAssociateStaConnectTimeLength
                    DisplayString,
                qtechWifiWlanAssociateStaGate
                    IpAddress,  
                qtechWifiWlanAssociateStaDns
                    IpAddress
                }   
        
        qtechWifiWlanAssociateWlanId OBJECT-TYPE
            SYNTAX Integer32
            MAX-ACCESS read-only
            STATUS current
            DESCRIPTION
                "The Dot11radio wlan id ."
            ::= { qtechWifiWlanAssociateEntry 1 }  
            
        qtechWifiWlanAssociateStaMacAdress OBJECT-TYPE
            SYNTAX DisplayString
            MAX-ACCESS read-only
            STATUS current
            DESCRIPTION
                "The Dot11radio mac address ."
            ::= { qtechWifiWlanAssociateEntry 2 } 
            
        qtechWifiWlanAssociateSsidName OBJECT-TYPE
            SYNTAX DisplayString
            MAX-ACCESS read-only
            STATUS current
            DESCRIPTION
                "The Dot11radio ssid name ."
            ::= { qtechWifiWlanAssociateEntry 3 }
            
        qtechWifiWlanAssociateStaIpAdress OBJECT-TYPE
            SYNTAX IpAddress
            MAX-ACCESS read-only
            STATUS current
            DESCRIPTION
                "The Dot11radio associate station ip ."
            ::= { qtechWifiWlanAssociateEntry 4 } 
        
        qtechWifiWlanAssociateStaMaskAdress OBJECT-TYPE
            SYNTAX IpAddress
            MAX-ACCESS read-only
            STATUS current
            DESCRIPTION
                "The Dot11radio associate station mask address."
            ::= { qtechWifiWlanAssociateEntry 5 }
    
        qtechWifiWlanAssociateStaSigalStrength OBJECT-TYPE
            SYNTAX Integer32
            MAX-ACCESS read-only
            STATUS current
            DESCRIPTION
                "The Dot11radio associate signal strength ."
            ::= { qtechWifiWlanAssociateEntry 6 }  
            
        qtechWifiWlanAssociateStaConnectTime OBJECT-TYPE
            SYNTAX DisplayString
            MAX-ACCESS read-only
            STATUS current
            DESCRIPTION
                "The Dot11radio associate station time ."
            ::= { qtechWifiWlanAssociateEntry 7 } 
        
        qtechWifiWlanAssociateStaConnectTimeLength OBJECT-TYPE
            SYNTAX DisplayString
            MAX-ACCESS read-only
            STATUS current
            DESCRIPTION
                "The Dot11radio associate station time length ."
            ::= { qtechWifiWlanAssociateEntry 8 }  
                    
        qtechWifiWlanAssociateStaGate OBJECT-TYPE
            SYNTAX IpAddress
            MAX-ACCESS read-only
            STATUS current
            DESCRIPTION
                "The Dot11radio associate station gate address ."
            ::= { qtechWifiWlanAssociateEntry 9 } 
            
        qtechWifiWlanAssociateStaDns OBJECT-TYPE
            SYNTAX IpAddress
            MAX-ACCESS read-only
            STATUS current
            DESCRIPTION
                "The Dot11radio associate station dns address ."
            ::= { qtechWifiWlanAssociateEntry 10 }       

-- End Wlan associate objects         
END
-- End module
