-- *******************************************************************
-- RUIJIE-WLAN-QOS-EXTRA-MIB.mib : Ruijie WLAN QOS MIB 
-- 
-- Oct 2009, HUANGTAO
--
-- Copyright (c) 2009 by Ruijie Networks Co.,Ltd.
-- All rights reserved.
-- *******************************************************************


RUIJIE-WLAN-QOS-EXTRA-MIB  DEFINITIONS ::= BEGIN

	IMPORTS	  
	          MODULE-IDENTITY,
	          OBJECT-TYPE
               FROM SNMPv2-SMI
													
            TruthValue
               FROM SNMPv2-TC
            
            MODULE-COMPLIANCE,
            OBJECT-GROUP
               FROM SNMPv2-CONF       
             
            ruijieApCfgRadioId,
            ruijieApgWlanId, 
            ruijieStaMacAddr,
            ruijieApMacAddr
               FROM RUIJIE-AC-MGMT-MIB


            ruijieMgmt 
               FROM RUIJIE-SMI;

--********************************************************************
--*  MODULE IDENTITY
--********************************************************************

ruijieWlanQosExtraMib MODULE-IDENTITY
            LAST-UPDATED    "200909080000Z"
            ORGANIZATION    "Ruijie Networks Co.,Ltd"
			      CONTACT-INFO  
                " 
                Tel: 4008-111-000 

                E-mail: service@ruijie.com.cn"
            DESCRIPTION
                "This MIB is intended to be implemented on all those
                devices operating as Central controllers, that
                terminate the Light Weight Access Point Protocol
                tunnel from Cisco Light-weight LWAPP Access Points.

                Information provided by this MIB is used to study
                the quality of service in the voice and video traffic
                on the WLAN.

                The relationship between CC and the LWAPP APs
                can be depicted as follows:

                      +......+     +......+     +......+
                      +      +     +      +     +      +
                      +  CC  +     +  CC  +     +  CC  +
                      +      +     +      +     +      +
                      +......+     +......+     +......+
                        ..            .             .
                        ..            .             .
                       .  .            .             .
                      .    .            .             .
                     .      .            .             .
                    .        .            .             .
                +......+ +......+     +......+      +......+
                +      + +      +     +      +      +      +
                +  AP  + +  AP  +     +  AP  +      +  AP  +
                +      + +      +     +      +      +      +
                +......+ +......+     +......+      +......+
                           .              .             .
                         .  .              .             .
                        .    .              .             .
                       .      .              .             .
                      .        .              .             .
                   +......+ +......+     +......+      +......+
                   +      + +      +     +      +      +      +
                   +  MN  + +  MN  +     +  MN  +      +  MN  +
                   +      + +      +     +      +      +      +
                   +......+ +......+     +......+      +......+


                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.

                                   GLOSSARY

                Access Point ( AP )

                An entity that contains an 802.11 medium access
                control ( MAC ) and physical layer ( PHY ) interface
                and provides access to the distribution services via
                the wireless medium for associated clients.  

                LWAPP APs encapsulate all the 802.11 frames in
                LWAPP frames and sends them to the controller to which
                it is logically connected.

                Gratuitous Probe Response (GPR)

                The Gratuitous Probe Response feature aids in conserving
                battery power of WLAN-enabled cell phones by providing
                a high rate packet on the order of tens of milliseconds
                such that these kind of phones can wake up and wait at
                predefined intervals, to reduce battery power.  The 
                GPR packet is transmitted from the AP at a predefined
                time interval.
                 

                Light Weight Access Point Protocol ( LWAPP )

                This is a generic protocol that defines the 
                communication between the Access Points and the
                Central Controller. 

                Mobile Node ( MN )

                A roaming 802.11 wireless device in a wireless
                network associated with an access point. Mobile Node 
                and client are used interchangeably. 

                TU

                A measurement of time in units of 1024 microseconds.

                User Priority ( UP )

                Specifies a the priority rules in QOS for handling user 
                priority.

                EDCA
                
                As defined in 802.11e standard, Enhanced distributed
                channel access(EDCA) parameter set element is used 
                by the AP to establish policy, to change policy when
                accepting new clients, or to adapt to changes in 
                offered load. 

                REFERENCE
 
                [1] Wireless LAN Medium Access Control ( MAC ) and
                Physical Layer ( PHY ) Specifications
  
                [2] Draft-obara-capwap-lwapp-00.txt, IETF Light 
                Weight Access Point Protocol "
                
                
                REVISION        "200909080000Z" 
                DESCRIPTION
                        "Initial version of this MIB module."
        ::= { ruijieMgmt 60 }


--********************************************************************
--*  SubMODULE IDENTITY
--********************************************************************


ruijieWlanDeviceWMMObjects OBJECT IDENTIFIER 
        ::= { ruijieWlanQosExtraMib    1 }

ruijieWlanDeviceEDCAObjects OBJECT IDENTIFIER
        ::= { ruijieWlanQosExtraMib    2 }
        
ruijieWlanDevicePrivMappingObjects OBJECT IDENTIFIER
        ::= { ruijieWlanQosExtraMib   3 }

ruijieWlanDeviceRatelimitObjects OBJECT IDENTIFIER
        ::= { ruijieWlanQosExtraMib    4 }
		
ruijieWlanQosMIBConform OBJECT IDENTIFIER 
		::= { ruijieWlanQosExtraMib 5 }



	
--*************************************************
--ruijieWlanDeviceWMMObjects Config
--*************************************************

ruijieWMMStatusTable OBJECT-TYPE 
            SYNTAX          SEQUENCE OF RuijieWMMStatusEntry
            MAX-ACCESS      not-accessible
            STATUS          current
            DESCRIPTION 
                " wmm status for each wlan"
            
        ::= { ruijieWlanDeviceWMMObjects  1 }

ruijieWMMStatusEntry OBJECT-TYPE
			SYNTAX			RuijieWMMStatusEntry
			MAX-ACCESS		not-accessible
			STATUS			current
			DESCRIPTION		
				" "
			INDEX   {
                    ruijieApgWlanId
                }
		::= { ruijieWMMStatusTable 1 }

RuijieWMMStatusEntry ::= 
        SEQUENCE {
            ruijieWMMStatus            TruthValue,
            ruijieAPSDStatus           TruthValue,
            ruijieSMPSStatus           TruthValue                
        }

ruijieWMMStatus OBJECT-TYPE 
            SYNTAX          TruthValue 
            MAX-ACCESS      read-write
            STATUS          current
            DESCRIPTION     
                " the wmm enable WMM or disable WMM
                    "
            DEFVAL          {1}
        ::= { ruijieWMMStatusEntry 1 }



ruijieAPSDStatus OBJECT-TYPE
            SYNTAX          TruthValue
            MAX-ACCESS      read-write
            STATUS          current
            DESCRIPTION     
                "display APSD-Support is enable or disable
                    "
            DEFVAL          {1}
        ::= { ruijieWMMStatusEntry 2 }


ruijieSMPSStatus OBJECT-TYPE
            SYNTAX          TruthValue
            MAX-ACCESS      read-write
            STATUS          current
            DESCRIPTION
                "display the AP's smps-support status
                    "
            DEFVAL          {1}
        ::= { ruijieWMMStatusEntry 3 }


--********************************************************************
--*    EDCA Param set  
--********************************************************************

  
 -- **********************************************************************

 --      SMT EDCA Config TABLE

 -- **********************************************************************

 ruijiedot11EDCATable OBJECT-TYPE

          SYNTAX SEQUENCE OF Ruijiedot11EDCAEntry

          MAX-ACCESS not-accessible

          STATUS current

          DESCRIPTION

               "Conceptual table for EDCA default parameter values at a non-AP

               STA. This table shall contain the four entries of the EDCA

               parameters corresponding to four possible ACs. Index 1 corresponds

               to AC_BK, index 2 to AC_BE, index 3 to AC_VI, and index 4 to AC_VO."

         REFERENCE "IEEE 802.11-2007, 9.1.3.1"

      ::= { ruijieWlanDeviceEDCAObjects 1 }

 ruijiedot11EDCAEntry OBJECT-TYPE

         SYNTAX Ruijiedot11EDCAEntry

         MAX-ACCESS not-accessible

         STATUS current

         DESCRIPTION

           "An Entry (conceptual row) in the EDCA Table.

           ifIndex - Each IEEE 802.11 interface is represented by an ifEntry.

           Interface tables in this MIB module are indexed by ifIndex."
	INDEX {
         ruijieApMacAddr,
         ruijieApCfgRadioId,
         ruijiedot11EDCATableIndex
    }

     ::= { ruijiedot11EDCATable 1 }

 Ruijiedot11EDCAEntry ::=

         SEQUENCE {  ruijiedot11EDCATableIndex        INTEGER,

                     ruijiedot11EDCATableCWmin        INTEGER,

                     ruijiedot11EDCATableCWmax        INTEGER,

                     ruijiedot11EDCATableAIFSN        INTEGER,

                     ruijiedot11EDCATableTXOPLimit    INTEGER,

                     ruijiedot11EDCATableMSDULifetime INTEGER,

                     ruijiedot11EDCATableMandatory    TruthValue }

  
 ruijiedot11EDCATableIndex OBJECT-TYPE

         SYNTAX INTEGER (1..4)

         MAX-ACCESS not-accessible

         STATUS current

         DESCRIPTION

             "The auxiliary variable used to identify instances of the columnar

              objects in the EDCA Table. The value of this variable is

              1) 1, if the value of the AC is AC_BK.

              2) 2, if the value of the AC is AC_BE.

              3) 3, if the value of the AC is AC_VI.

              4) 4, if the value of the AC is AC_VO."

     ::= { ruijiedot11EDCAEntry 1 }

 ruijiedot11EDCATableCWmin OBJECT-TYPE

         SYNTAX INTEGER (0..255)

         MAX-ACCESS read-write

         STATUS current

         DESCRIPTION

              "This attribute shall specify the value of the minimum size of the

              window that shall be used by a STA for a particular AC for

              generating a random number for the backoff. The value of this

              attribute shall be such that it could always be expressed in the

              form of 2X - 1, where X is an integer. The default value for this

              attribute is

              1) aCWmin, if ruijiedot11EDCATableIndex is 1 or 2.

              2) (aCWmin+1)/2 - 1, if ruijiedot11EDCATableIndex is 3.

              3) (aCWmin+1)/4 - 1, if ruijiedot11EDCATableIndex is 4."

     ::= { ruijiedot11EDCAEntry 2 }

 ruijiedot11EDCATableCWmax OBJECT-TYPE

         SYNTAX INTEGER (0..65535)

         MAX-ACCESS read-write

         STATUS current

         DESCRIPTION

              "This attribute shall specify the value of the maximum size of the

              window that shall be used by a STA for a particular AC for

              generating a random number for the backoff. The value of this

              attribute shall be such that it could always be expressed in the

              form of 2X - 1, where X is an integer. The default value for this

              attribute is

              1) aCWmax, if ruijiedot11EDCATableIndex is 1 or 2.

              2) aCWmin, if ruijiedot11EDCATableIndex is 3.

              3) (aCWmin+1)/2 - 1, if ruijiedot11EDCATableIndex is 4."

     ::= { ruijiedot11EDCAEntry 3 }

 ruijiedot11EDCATableAIFSN OBJECT-TYPE

         SYNTAX INTEGER (2..15)

         MAX-ACCESS read-write

         STATUS current

         DESCRIPTION

              "This attribute shall specify the number of slots, after a SIFS

              duration, that the STA, for a particular AC, shall sense the

              medium idle either before transmitting or executing a backoff. The

              default value for this attribute is

              1) 7, if ruijiedot11EDCATableIndex is 1,

              2) 3, if ruijiedot11EDCATableIndex is 2

              3) 2, otherwise."

     ::= { ruijiedot11EDCAEntry 4 }

 ruijiedot11EDCATableTXOPLimit OBJECT-TYPE

         SYNTAX INTEGER (0..65535)

         MAX-ACCESS read-write

         STATUS current

         DESCRIPTION

              "This attribute shall specify the maximum number of microseconds of

              an EDCA TXOP for a given AC at a non-AP STA. The default value for

              this attribute is

              1) 0 for all PHYs, if ruijiedot11EDCATableIndex is 1 or 2; this

              implies that the sender can send one MSDU in an EDCA TXOP,

              2) 3008 microseconds for Clause 17 and Clause 19 PHY and 6016

              microseconds for Clause 18 PHY, if ruijiedot11EDCATableIndex is 3,

              3) 1504 microseconds for Clause 17 and Clause 19 PHY and 3264

              microseconds for Clause 18 PHY, if ruijiedot11EDCATableIndex is 4."

     ::= { ruijiedot11EDCAEntry 5 }

 ruijiedot11EDCATableMSDULifetime OBJECT-TYPE

         SYNTAX INTEGER (0..500)

         MAX-ACCESS read-write

         STATUS current

         DESCRIPTION

              "This attribute shall specify (in TUs) the maximum duration an

              MSDU, for a given AC, would be retained by the MAC before it is

              discarded. The default value for this parameter shall be 500."

     ::= { ruijiedot11EDCAEntry 6 }

 ruijiedot11EDCATableMandatory OBJECT-TYPE

         SYNTAX TruthValue

         MAX-ACCESS read-write

         STATUS current

         DESCRIPTION

             "This attribute, when TRUE, indicates that admission control is

              mandatory for the given AC. When False, this attribute indicates

              that the admission control is not mandatory for the given AC. The

              default value for this parameter shall be FALSE."

     ::= { ruijiedot11EDCAEntry 7 }

 -- **********************************************************************

 --      End of SMT EDCA Config TABLE

 -- **********************************************************************

  
 -- **********************************************************************

 --      SMT AP EDCA Config TABLE

 -- **********************************************************************

 ruijiedot11QAPEDCATable OBJECT-TYPE

          SYNTAX SEQUENCE OF Ruijiedot11QAPEDCAEntry

          MAX-ACCESS not-accessible

          STATUS current

          DESCRIPTION

               "Conceptual table for EDCA default parameter values at the AP.

               This table shall contain the four entries of the EDCA parameters

               corresponding to four possible ACs. Index 1 corresponds to AC_BK,

               index 2 to AC_BE, index 3 to AC_VI, and index 4 to AC_VO."

         REFERENCE "IEEE 802.11-2007, 9.9.1"

      ::= { ruijieWlanDeviceEDCAObjects 2}

 ruijiedot11QAPEDCAEntry OBJECT-TYPE

          SYNTAX Ruijiedot11QAPEDCAEntry

          MAX-ACCESS not-accessible

          STATUS current

          DESCRIPTION

              "An Entry (conceptual row) in the EDCA Table.

              ifIndex - Each IEEE 802.11 interface is represented by an

              ifEntry. Interface tables in this MIB module are indexed

              by ifIndex."

      INDEX {
         ruijieApMacAddr,
         ruijieApCfgRadioId,
         ruijiedot11QAPEDCATableIndex
      }

      ::= { ruijiedot11QAPEDCATable 1 }

 Ruijiedot11QAPEDCAEntry ::=

          SEQUENCE {  ruijiedot11QAPEDCATableIndex            INTEGER,

                      ruijiedot11QAPEDCATableCWmin            INTEGER,

                      ruijiedot11QAPEDCATableCWmax            INTEGER,

                      ruijiedot11QAPEDCATableAIFSN            INTEGER,

                      ruijiedot11QAPEDCATableTXOPLimit        INTEGER,

                      ruijiedot11QAPEDCATableMSDULifetime     INTEGER,

                      ruijiedot11QAPEDCATableMandatory        TruthValue }

  
 ruijiedot11QAPEDCATableIndex OBJECT-TYPE

          SYNTAX INTEGER (1..4)

          MAX-ACCESS not-accessible

          STATUS current

          DESCRIPTION

               "The auxiliary variable used to identify instances of the columnar

               objects in the EDCA Table. The value of this variable is

                1) 1, if the value of the AC is AC_BK.

                2) 2, if the value of the AC is AC_BE.

                3) 3, if the value of the AC is AC_VI.

                4) 4, if the value of the AC is AC_VO."

     ::= { ruijiedot11QAPEDCAEntry 1 }

 ruijiedot11QAPEDCATableCWmin OBJECT-TYPE

         SYNTAX INTEGER (0..255)

         MAX-ACCESS read-write

         STATUS current

         DESCRIPTION

              "This attribute shall specify the value of the minimum size of the

              window that shall be used by an AP for a particular AC for

              generating a random number for the backoff. The value of this

              attribute shall be such that it could always be expressed in the

              form of 2X - 1, where X is an integer. The default value for this

              attribute is

              1) aCWmin, if ruijiedot11QAPEDCATableIndex is 1 or 2.

              2) (aCWmin+1)/2 - 1, if ruijiedot11QAPEDCATableIndex is 3.

              3) (aCWmin+1)/4 - 1, if ruijiedot11QAPEDCATableIndex is 4."

     ::= { ruijiedot11QAPEDCAEntry 2 }

 ruijiedot11QAPEDCATableCWmax OBJECT-TYPE

         SYNTAX INTEGER (0..65535)

         MAX-ACCESS read-write

         STATUS current

         DESCRIPTION

              "This attribute shall specify the value of the maximum size of the

              window that shall be used by an AP for a particular AC for

              generating a random number for the backoff. The value of this

              attribute shall be such that it could always be expressed in the

              form of 2X - 1, where X is an integer. The default value for this

              attribute is

              1) aCWmax, if ruijiedot11QAPEDCATableIndex is 1.

              2) 4*(aCWmin+1) - 1, if ruijiedot11QAPEDCATableIndex is 2.

              3) aCWmin, if ruijiedot11QAPEDCATableIndex is 3.

              4) (aCWmin+1)/2 - 1, if ruijiedot11QAPEDCATableIndex is 4."

     ::= { ruijiedot11QAPEDCAEntry 3 }

 ruijiedot11QAPEDCATableAIFSN OBJECT-TYPE

         SYNTAX INTEGER (1..15)

         MAX-ACCESS read-write

         STATUS current

         DESCRIPTION

              "This attribute shall specify the number of slots, after a SIFS

              duration, that the AP, for a particular AC, shall sense the

              medium idle either before transmitting or executing a backoff. The

              default value for this attribute is

              1) 7, if ruijiedot11QAPEDCATableIndex is 1,

              2) 3, if ruijiedot11QAPEDCATableIndex is 2

              3) 1, otherwise."

     ::= { ruijiedot11QAPEDCAEntry 4 }

 ruijiedot11QAPEDCATableTXOPLimit OBJECT-TYPE

         SYNTAX INTEGER (0..65535)

         MAX-ACCESS read-write

         STATUS current

         DESCRIPTION

              "This attribute shall specify the maximum number of microseconds of

              an EDCA TXOP for a given AC at the AP. The default value for

              this attribute is

              1) 0 for all PHYs, if ruijiedot11QAPEDCATableIndex is 1 or 2; this

              implies that the sender can send one MSDU in an EDCA TXOP,

              2) 3008 microseconds for Clause 17 and Clause 19 PHY and 6016

              microseconds for Clause 18 PHY, if ruijiedot11QAPEDCATableIndex is 3,

              3) 1504 microseconds for Clause 17 and Clause 19 PHY and 3264

               microseconds for Clause 18 PHY, if ruijiedot11QAPEDCATableIndex is 4."

      ::= { ruijiedot11QAPEDCAEntry 5 }

 ruijiedot11QAPEDCATableMSDULifetime OBJECT-TYPE

          SYNTAX INTEGER (0..500)

          MAX-ACCESS read-write

          STATUS current

          DESCRIPTION

               "This attribute shall specify (in TUs) the maximum duration an

               MSDU, for a given AC, would be retained by the MAC at the AP before

               it is discarded. The default value for this parameter shall be

               500."

      ::= { ruijiedot11QAPEDCAEntry 6 }

 ruijiedot11QAPEDCATableMandatory OBJECT-TYPE

          SYNTAX TruthValue

          MAX-ACCESS read-write

          STATUS current

          DESCRIPTION

               "This attribute, when TRUE, indicates that admission control is

               mandatory for the given AC. When False, this attribute indicates

               that the admission control is not mandatory for the given AC. The

               default value for this parameter shall be FALSE."

      ::= { ruijiedot11QAPEDCAEntry 7 }

 -- **********************************************************************

 --      End of SMT AP EDCA Config TABLE

 -- **********************************************************************

 
--********************************************************
--ruijieWlanDeviceEDCAObjects Config
--********************************************************
ruijieWlanEDCATable OBJECT-TYPE
            SYNTAX          SEQUENCE OF RuijieEDCAStatusEntry
            MAX-ACCESS      not-accessible
            STATUS          current
            DESCRIPTION
                "some wmm access catagery's attribution doesn't appeared in stadard MIBS
                so , we add it here
                "    
        ::= { ruijieWlanDeviceEDCAObjects 3 }

ruijieEDCAStatusEntry	OBJECT-TYPE
			SYNTAX		RuijieEDCAStatusEntry
			MAX-ACCESS	not-accessible
			STATUS		current
			DESCRIPTION
				" "
      INDEX {
         ruijieApMacAddr,
         ruijieApCfgRadioId,
         ruijiedot11QAPEDCATableIndex
      }
		::= { ruijieWlanEDCATable 1 }

RuijieEDCAStatusEntry ::= 
        SEQUENCE {
            ruijieQAPEDCAqueuedepth          INTEGER,
            ruijieQAPEDCAcacPolicy           INTEGER,
            ruijieQAPEDCAcacParam            INTEGER
        }

ruijieQAPEDCAqueuedepth OBJECT-TYPE
            SYNTAX          INTEGER  (1..512)
            MAX-ACCESS      read-write
            STATUS          current
            DESCRIPTION     
                "software queue depth for each wmm access catagery"
            DEFVAL      {512}
        ::= { ruijieEDCAStatusEntry 1 }
        

ruijieQAPEDCAcacPolicy OBJECT-TYPE
            SYNTAX          INTEGER {nocac(0), usernum-based(1), channelutilization-based(2)}
            MAX-ACCESS      read-write
            STATUS          current
            DESCRIPTION
                "now  only have two kind of CAC policy , usernum-based (1) and channelutilization-based {2} "

            DEFVAL          {0}
        ::= { ruijieEDCAStatusEntry 2}

ruijieQAPEDCAcacParam OBJECT-TYPE
            SYNTAX          INTEGER  (0..100)
            MAX-ACCESS      read-write
            STATUS          current
            DESCRIPTION     
                "cac param used to determine whether the sta is allowed to be in the high access catagery "
            DEFVAL          {20} -- Used by usernum-based cac policy
        ::= { ruijieEDCAStatusEntry 3}


--********************************************************
--ruijieWlanDevicePrivMappingObjects config
--********************************************************

ruijieWlanDevicePrivMappingWlanDefaultObjects OBJECT IDENTIFIER ::= { ruijieWlanDevicePrivMappingObjects 1 }
        
ruijieWlanDevicePrivMappingAPDefaultObjects OBJECT IDENTIFIER ::= { ruijieWlanDevicePrivMappingObjects 2 }

ruijieWlanDevicePrivMappingTableObjects OBJECT IDENTIFIER ::= { ruijieWlanDevicePrivMappingObjects 3 } 

--********************************************************
--WLAN default WMM AC Config
--********************************************************

ruijieWlanDefaultACTable OBJECT-TYPE
            SYNTAX              SEQUENCE OF RuijieWlanDefaultACEntry
            MAX-ACCESS          not-accessible
            STATUS              current
            DESCRIPTION         
                " this  table used by non-wmm sta, 
                we map the pkt from non-wmm sta to the default WMM access catagery "
            
        ::= { ruijieWlanDevicePrivMappingWlanDefaultObjects 1 }


ruijieWlanDefaultACEntry OBJECT-TYPE
			SYNTAX				RuijieWlanDefaultACEntry
			MAX-ACCESS			not-accessible
			STATUS				current
			DESCRIPTION
				" "
			INDEX    {
                    ruijieApgWlanId
                     }
		::= { ruijieWlanDefaultACTable 1}

RuijieWlanDefaultACEntry ::= 
        SEQUENCE {
            ruijieWlanDefualtACnum          INTEGER,
            ruijieWlanMaxstadot1ptag        INTEGER
        }

ruijieWlanDefualtACnum  OBJECT-TYPE
            SYNTAX          INTEGER
            MAX-ACCESS      read-write
            STATUS          current
            DESCRIPTION 
                " this defines the ap's default WMM AC ,used for non-wmm sta
                    "
        ::= { ruijieWlanDefaultACEntry 1 }

ruijieWlanMaxstadot1ptag  OBJECT-TYPE
            SYNTAX          INTEGER
            MAX-ACCESS      read-write
            STATUS          current
            DESCRIPTION
                " max 802.11e tags a sta in the wlan can use, 
                 all pkt have tag larger than this value will fall in the default AC
                    "
        ::= { ruijieWlanDefaultACEntry 2 }


--********************************************************
-- AP defualt WMM_AC-DSCP, WMM_AC-802DOT1P mapping pairs config
--********************************************************


ruijiePrivMappingAPstatusTable OBJECT-TYPE
            SYNTAX          SEQUENCE OF RuijieAPdefaultStatusMappingEntry
            MAX-ACCESS      not-accessible
            STATUS          current
            DESCRIPTION     
                " when use CAPWAP, we must map pkt belong to certain WMM-AC to a Certian DSCP priv/802.1p pri
                 and as we must encap the pkt ,we must support two kind of mappings - trunnel and inner,
                 you can get the concept in RFC 5416
                    "
        ::= { ruijieWlanDevicePrivMappingAPDefaultObjects 1 }

ruijieAPdefaultStatusMappingEntry		OBJECT-TYPE
			SYNTAX				RuijieAPdefaultStatusMappingEntry
			MAX-ACCESS			not-accessible
			STATUS				current
			DESCRIPTION
				" "
            INDEX   {
                   ruijieApMacAddr
                   }
		::= { ruijiePrivMappingAPstatusTable 1 }

RuijieAPdefaultStatusMappingEntry ::= 
        SEQUENCE {
            ruijiedot1pmappingstatus        INTEGER,
            ruijiedscpmappingstatus         INTEGER
        }

ruijiedot1pmappingstatus OBJECT-TYPE
            SYNTAX          INTEGER
            MAX-ACCESS      read-write
            STATUS          current
            DESCRIPTION     
                "How to set the pkt's 802.1p tag  "
            DEFVAL { 0 }
        ::= { ruijieAPdefaultStatusMappingEntry  1 }

ruijiedscpmappingstatus OBJECT-TYPE
            SYNTAX          INTEGER 
            MAX-ACCESS      read-write
            STATUS          current
            DESCRIPTION
                " how to set the pkt's dscp tag
                    "            
            DEFVAL {0}
        ::= { ruijieAPdefaultStatusMappingEntry 2 }

		
ruijiePrivMappingAPDefaultTable OBJECT-TYPE
            SYNTAX          SEQUENCE OF RuijiePrivMappingAPDefaultEntry
            MAX-ACCESS      not-accessible
            STATUS          current
            DESCRIPTION     
                " when use CAPWAP, we must map pkt belong to certain WMM-AC to a Certian DSCP priv/802.1p pri
                 and as we must encap the pkt ,we must support two kind of mappings - trunnel and inner,
                 you can get the concept in RFC 5416
                    "
        ::= { ruijieWlanDevicePrivMappingAPDefaultObjects 2 }

ruijiePrivMappingAPDefaultEntry		OBJECT-TYPE
			SYNTAX			RuijiePrivMappingAPDefaultEntry
			MAX-ACCESS		not-accessible
			STATUS			current
			DESCRIPTION
				" " 
			INDEX   {
                   ruijieApMacAddr,
                   ruijiedot11QAPEDCATableIndex 
                    }
		::= { ruijiePrivMappingAPDefaultTable 1 }

RuijiePrivMappingAPDefaultEntry ::= 
            SEQUENCE  {
                ruijieAPdefaultDSCPTag      INTEGER,
                ruijieAPdefaultDot1pTag     INTEGER
            }

ruijieAPdefaultDSCPTag OBJECT-TYPE
            SYNTAX          INTEGER (0..63)
            MAX-ACCESS      read-write
            STATUS          current
            DESCRIPTION     
                " DEFAULT dscp tag for certain AC"
        ::= { ruijiePrivMappingAPDefaultEntry 1 }

ruijieAPdefaultDot1pTag OBJECT-TYPE
            SYNTAX          INTEGER
            MAX-ACCESS      read-write
            STATUS          current
            DESCRIPTION     
                " default DOT1P TAG VALUE FOR CERTAIN ac"
        ::= { ruijiePrivMappingAPDefaultEntry 2 }

--********************************************************
-- mapping tables config
-- svp pkt mapping config
--********************************************************
ruijieSVPMappingTable           OBJECT-TYPE
            SYNTAX               SEQUENCE  OF RuijieSVPMappingEntry
            MAX-ACCESS           not-accessible
            STATUS               current
            DESCRIPTION
                " dot11radio-SVP-pkt --> WMM-AC:pkt"
        ::= { ruijieWlanDevicePrivMappingTableObjects 1 }

ruijieSVPMappingEntry   OBJECT-TYPE
            SYNTAX              RuijieSVPMappingEntry
            MAX-ACCESS          not-accessible
            STATUS              current
            DESCRIPTION
                "   svp mapping info
                "
            INDEX   {
                    ruijieApgWlanId
                }
        ::= { ruijieSVPMappingTable 1}



RuijieSVPMappingEntry   ::= 
            SEQUENCE {               
                 ruijieSVPmappingStatus      INTEGER,
                 ruijieSVPmappingAC          INTEGER 
            }

ruijieSVPmappingStatus      OBJECT-TYPE
            SYNTAX          INTEGER {enable(0), disable(1)}            
            MAX-ACCESS      read-write            
            STATUS          current            
            DESCRIPTION               
             " enable or disable the svp mapping "        
        ::= { ruijieSVPMappingEntry 1 }

ruijieSVPmappingAC          OBJECT-TYPE            
            SYNTAX          INTEGER {wmmvo(1), wmmvi(2), wmmbe(3), wmmbk(4)}            
            MAX-ACCESS      read-write            
            STATUS          current            
            DESCRIPTION                
            " MAPPING AC"        
        ::= { ruijieSVPMappingEntry 2 }

--********************************************************
--  ruijieWlanDeviceRatelimitObjects
--  wlan-based info config
--  ap-based info config
--  mac-baesd info config
--********************************************************


ruijieWlanRatelimitTable OBJECT-TYPE
            SYNTAX          SEQUENCE OF RuijieWlanRatelimitEntry
            MAX-ACCESS      not-accessible
            STATUS          current
            DESCRIPTION
                " WLAN-based ratelimit"
        ::= { ruijieWlanDeviceRatelimitObjects 1 } 
		
ruijieWlanRatelimitEntry	OBJECT-TYPE
             SYNTAX             RuijieWlanRatelimitEntry
             MAX-ACCESS         not-accessible
             STATUS             current
             DESCRIPTION 
                       " "
             INDEX { ruijieApgWlanId, ruijieWlanRateLimitDirect }
		::= { ruijieWlanRatelimitTable  1 }

		

RuijieWlanRatelimitEntry ::= 
            SEQUENCE {
                ruijieWlanRateLimitDirect           INTEGER,
                ruijieWlanRatelimitStatus           INTEGER,
                ruijieWlanAverageRate               INTEGER,
                ruijieWlanBurstRate                 INTEGER
            }

ruijieWlanRateLimitDirect OBJECT-TYPE
            SYNTAX          INTEGER (0..1)
            MAX-ACCESS      read-only
            STATUS          current
            DESCRIPTION 
                " direction of the ratelimited stream
                "
        ::= { ruijieWlanRatelimitEntry 1 }

ruijieWlanRatelimitStatus OBJECT-TYPE
            SYNTAX          INTEGER (0..1)
            MAX-ACCESS      read-write
            STATUS          current
            DESCRIPTION
                " enable | diable the ratelimit "
        ::= { ruijieWlanRatelimitEntry 2 }


ruijieWlanAverageRate OBJECT-TYPE
            SYNTAX          INTEGER 
            MAX-ACCESS      read-write
            STATUS          current
            DESCRIPTION
                " average rate of the limited stream "
        ::= { ruijieWlanRatelimitEntry 3 }

ruijieWlanBurstRate OBJECT-TYPE
            SYNTAX          INTEGER
            MAX-ACCESS      read-write
            STATUS          current
            DESCRIPTION
                " burst rate of the limited stream "
        ::= { ruijieWlanRatelimitEntry 4 }
			

ruijieAPRatelimitTable  OBJECT-TYPE
            SYNTAX          SEQUENCE OF RuijieAPRatelimitEntry
            MAX-ACCESS      not-accessible
            STATUS          current
            DESCRIPTION
                " ap-based ratelimit"
        ::= { ruijieWlanDeviceRatelimitObjects 2 } 
		
ruijieAPRatelimitEntry	OBJECT-TYPE
			SYNTAX			RuijieAPRatelimitEntry
			MAX-ACCESS		not-accessible
			STATUS			current
			DESCRIPTION 
				" "
            INDEX   {
                    ruijieApMacAddr,
                    ruijieAPRateLimitDirect
                    }
		::= { ruijieAPRatelimitTable  1 }		
		
		
RuijieAPRatelimitEntry ::= 
            SEQUENCE {
                ruijieAPRateLimitDirect             INTEGER,
                ruijieAPRatelimitStatus             INTEGER,
                ruijieAPAverageRate                 INTEGER,
                ruijieAPBurstRate                   INTEGER
            }		
		

ruijieAPRateLimitDirect OBJECT-TYPE
            SYNTAX          INTEGER (0..1)
            MAX-ACCESS      not-accessible
            STATUS          current
            DESCRIPTION 
                " direction of the ratelimited stream
                "
        ::= { ruijieAPRatelimitEntry 1 }

ruijieAPRatelimitStatus OBJECT-TYPE
            SYNTAX          INTEGER (0..1)
            MAX-ACCESS      read-write
            STATUS          current
            DESCRIPTION
                " enable | diable the ratelimit "
        ::= { ruijieAPRatelimitEntry 2 }


ruijieAPAverageRate OBJECT-TYPE
            SYNTAX          INTEGER 
            MAX-ACCESS      read-write
            STATUS          current
            DESCRIPTION
                " average rate of the limited stream "
        ::= { ruijieAPRatelimitEntry 3 }

ruijieAPBurstRate OBJECT-TYPE
            SYNTAX          INTEGER
            MAX-ACCESS      read-write
            STATUS          current
            DESCRIPTION
                " burst rate of the limited stream "
        ::= { ruijieAPRatelimitEntry 4 }
	
		

ruijieUserRatelimitTable  OBJECT-TYPE
            SYNTAX          SEQUENCE OF RuijieUserRatelimitEntry
            MAX-ACCESS      not-accessible
            STATUS          current
            DESCRIPTION
                " MAC-based ratelimit"
        ::= { ruijieWlanDeviceRatelimitObjects 3 } 
		
ruijieUserRatelimitEntry	OBJECT-TYPE
            SYNTAX          RuijieUserRatelimitEntry
			MAX-ACCESS		not-accessible
			STATUS			current
			DESCRIPTION 
				" "
            INDEX   {
                    ruijieStaMacAddr,
                    ruijieUserRateLimitDirect,
                    ruijieApgWlanId
                    }
		::= { ruijieUserRatelimitTable  1 }

		
RuijieUserRatelimitEntry ::=
            SEQUENCE {
                ruijieUserRateLimitDirect           INTEGER,
                ruijieUserRatelimitStatus           INTEGER,
                ruijieUserAverageRate               INTEGER,
                ruijieUserBurstRate                 INTEGER
            }


ruijieUserRateLimitDirect OBJECT-TYPE
            SYNTAX          INTEGER (0..1)
            MAX-ACCESS      not-accessible
            STATUS          current
            DESCRIPTION 
                " direction of the ratelimited stream
                "
        ::= { ruijieUserRatelimitEntry 1 }

ruijieUserRatelimitStatus OBJECT-TYPE
            SYNTAX          INTEGER (0..1)
            MAX-ACCESS      read-write
            STATUS          current
            DESCRIPTION
                " enable | diable the ratelimit "
        ::= { ruijieUserRatelimitEntry 2 }


ruijieUserAverageRate OBJECT-TYPE
            SYNTAX          INTEGER 
            MAX-ACCESS      read-write
            STATUS          current
            DESCRIPTION
                " average rate of the limited stream "
        ::= { ruijieUserRatelimitEntry 3 }

ruijieUserBurstRate OBJECT-TYPE
            SYNTAX          INTEGER
            MAX-ACCESS      read-write
            STATUS          current
            DESCRIPTION
                " burst rate of the limited stream "
        ::= { ruijieUserRatelimitEntry 4 }
		
		

		
		

--********************************************************************
--*    Compliance statements  
--********************************************************************

ruijieWlanQosMIBCompliances  OBJECT IDENTIFIER  ::= { ruijieWlanQosMIBConform 1 }
ruijieWlanQosMIBGroups  OBJECT IDENTIFIER  ::= { ruijieWlanQosMIBConform 2 }
		
ruijieWlanQosMIBCompliance MODULE-COMPLIANCE
        STATUS  current
        DESCRIPTION
                "The compliance statement for entities which implement
                the Qos module of Ruijie Ac Manager"
        MODULE
                MANDATORY-GROUPS {                
                ruijieWlanQosWMMEDCAConfigGroup,
                ruijieWlanQosRatelimitConfigGroup,
                ruijieWlanQosPriMappingonfigGroup
        }
        ::= { ruijieWlanQosMIBCompliances 1 }
        

--********************************************************************
--*    Units of conformance  
--********************************************************************
ruijieWlanQosWMMEDCAConfigGroup OBJECT-GROUP
        OBJECTS {
		        ruijieWMMStatus ,
            ruijieAPSDStatus,
            ruijieSMPSStatus,   
			      ruijieQAPEDCAqueuedepth,
            ruijieQAPEDCAcacPolicy,
            ruijieQAPEDCAcacParam,
			      ruijieWlanDefualtACnum,
            ruijieWlanMaxstadot1ptag,
			      ruijiedot1pmappingstatus,
            ruijiedscpmappingstatus,
			      ruijieAPdefaultDSCPTag,
            ruijieAPdefaultDot1pTag,
			ruijiedot11EDCATableCWmin,
			ruijiedot11EDCATableCWmax,
			ruijiedot11EDCATableAIFSN,
			ruijiedot11EDCATableTXOPLimit,
			ruijiedot11EDCATableMSDULifetime,
			ruijiedot11EDCATableMandatory,
			ruijiedot11QAPEDCATableCWmin,
			ruijiedot11QAPEDCATableCWmax,
			ruijiedot11QAPEDCATableAIFSN,
			ruijiedot11QAPEDCATableTXOPLimit,
			ruijiedot11QAPEDCATableMSDULifetime,
			ruijiedot11QAPEDCATableMandatory			  
        }
        STATUS     current
        DESCRIPTION
                "This collection of objects represents the 
                WMM quality-of-service parameters  networks. " 
        ::= { ruijieWlanQosMIBGroups 1 }

ruijieWlanQosRatelimitConfigGroup OBJECT-GROUP
        OBJECTS  {
			      ruijieWlanRateLimitDirect,
            ruijieWlanRatelimitStatus,
            ruijieWlanAverageRate,
            ruijieWlanBurstRate,
            ruijieAPRatelimitStatus,
            ruijieAPAverageRate,
            ruijieAPBurstRate,
            ruijieUserRatelimitStatus,
            ruijieUserAverageRate,
            ruijieUserBurstRate
        }
        STATUS     current
        DESCRIPTION
                "This collection of objects represents the 
                 ratelimit parameters 802.11 networks. " 
        ::= { ruijieWlanQosMIBGroups 2 }

ruijieWlanQosPriMappingonfigGroup OBJECT-GROUP
        OBJECTS {
					ruijieSVPmappingStatus,
					ruijieSVPmappingAC
                }
        STATUS     current
        DESCRIPTION
                "This collection of objects represents the 
                pri-mapping parameters 802.11 networks. " 
        ::= { ruijieWlanQosMIBGroups 3 }
		
		
END
