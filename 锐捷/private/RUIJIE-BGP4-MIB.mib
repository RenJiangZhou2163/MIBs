-- *****************************************************************
-- RUIJIE-BGP4-MIB.mib:  RUIJIE BGP4 MIB file
--
-- April 2003, HuangChongbin
--
-- Copyright (c) 2003 by Ruijie Networks Co.,Ltd.
-- All rights reserved.
-- 
-- *****************************************************************

RUIJIE-BGP4-MIB DEFINITIONS ::= BEGIN

IMPORTS
        MODULE-IDENTITY, 
        OBJECT-TYPE, 
        Unsigned32,
        NOTIFICATION-TYPE,
        Counter32
              FROM SNMPv2-SMI
        TruthValue,
        TEXTUAL-CONVENTION
              FROM SNMPv2-TC
        InetAutonomousSystemNumber,
        InetAddressType,
        InetAddress 	
	      FROM INET-ADDRESS-MIB
        AddressFamilyNumbers
          FROM IANA-ADDRESS-FAMILY-NUMBERS-MIB        
        bgpPeerEntry,
        bgpPeerRemoteAddr
              FROM BGP4-MIB
        ruijieMgmt
              FROM RUIJIE-SMI;         

-- BEGIN：MODULE-IDENTITY
ruijieBgp4MIB MODULE-IDENTITY    
        LAST-UPDATED "200304010000Z"
        ORGANIZATION "Ruijie Networks Co.,Ltd."
        CONTACT-INFO
                " 
                Tel: 4008-111-000 
                
                E-mail: service@ruijie.com.cn"
        DESCRIPTION
                "This module defines ruijie bgp4 mibs."
        REVISION      "200304010000Z"
        DESCRIPTION
                "Initial version of this MIB module."
        ::= { ruijieMgmt 38}        
-- END：MODULE-IDENTITY


-- BEGIN：Noun definition 
RuijieBgpID ::= TEXTUAL-CONVENTION
	DISPLAY-HINT "1d."
	STATUS	     current
	DESCRIPTION
	    "The representation of a BGP Identifier.  The BGP
	     Identifier should be represented in the OCTET STRING
	     as with the first OCTET of the string containing
	     the first OCTET of the BGP Identifier received or sent
	     in the OPEN packet and so on.

	     Even though the BGP Identifier is trending away from
	     an IP address it is still displayed as if it was one,
	     even when it would be an illegal IP address."
	SYNTAX OCTET STRING(SIZE (4))                             
-- END：Noun definition 

-- BEGIN： RuijieBgpVrfName definition.
RuijieBgpVrfName ::= TEXTUAL-CONVENTION
   STATUS        current
   DESCRIPTION
       "An identifier that is assigned to each MPLS/BGP VPN and
        is used to uniquely identify it.  This is assigned by the
        system operator or NMS and SHOULD be unique throughout
        the MPLS domain.  If this is the case, then this identifier
        can then be used at any LSR within a specific MPLS domain
        to identify this MPLS/BGP VPN.  It may also be possible to
        preserve the uniqueness of this identifier across MPLS
        domain boundaries, in which case this identifier can then
        be used to uniquely identify MPLS/BGP VPNs on a more global
        basis.  This object MAY be set to the VPN ID as defined in
        RFC 2685."
   REFERENCE
        "RFC 2685 Fox B., et al, 'Virtual Private


         Networks Identifier', September 1999."
   SYNTAX OCTET STRING (SIZE (0..31))
-- END：RuijieBgpVrfName definition 
   
-- BEGIN：ruijieBgpBaseScalars

ruijieBgpBaseScalars
	OBJECT IDENTIFIER ::= { ruijieBgp4MIB 1 }

-- BEGIN：ruijieBgpSupportedCapabilities
-- BGP Capabilities information

ruijieBgpSupportedCapabilities
        OBJECT IDENTIFIER ::= { ruijieBgpBaseScalars 1 }
        
ruijieBgpCapabilitySupportAvailable OBJECT-TYPE
	SYNTAX	   TruthValue
	MAX-ACCESS read-only
	STATUS	   current
	DESCRIPTION
	    "This value is TRUE if capability support is
	     available."
	::= { ruijieBgpSupportedCapabilities 1 }
	
ruijieBgpSupportedCapabilitiesTable OBJECT-TYPE
	SYNTAX	   SEQUENCE OF RuijieBgpSupportedCapabilityEntry
	MAX-ACCESS not-accessible
	STATUS	   current
	DESCRIPTION
	    "Table of supported BGP-4 capabilities."
	::= { ruijieBgpSupportedCapabilities 2 }
	
ruijieBgpSupportedCapabilitiesEntry OBJECT-TYPE
	SYNTAX	   RuijieBgpSupportedCapabilityEntry
	MAX-ACCESS not-accessible
	STATUS	   current
	DESCRIPTION
	    "Information about supported capabilities indexed
	     by capability number."
	INDEX {
	    ruijieBgpSupportedCapabilityCode
	}
	::= { ruijieBgpSupportedCapabilitiesTable 1 }
	
RuijieBgpSupportedCapabilityEntry ::= SEQUENCE {
	ruijieBgpSupportedCapabilityCode
	    Unsigned32,
	ruijieBgpSupportedCapability
	    TruthValue
    }
    
ruijieBgpSupportedCapabilityCode OBJECT-TYPE
	SYNTAX	   Unsigned32 (0..255)
	MAX-ACCESS read-only
	STATUS	   current
	DESCRIPTION
	    "Index of supported capability.  The index directly
	     corresponds with the BGP-4 Capability Advertisement
	     Capability Code."
	::= { ruijieBgpSupportedCapabilitiesEntry 1 }
	
ruijieBgpSupportedCapability OBJECT-TYPE
	SYNTAX	   TruthValue
	MAX-ACCESS read-only
	STATUS	   current
	DESCRIPTION
	    "This value is True if this capability is supported,
	     False otherwise."
	::= { ruijieBgpSupportedCapabilitiesEntry 2 }
	
-- END：ruijieBgpSupportedCapabilities

-- BEGIN：ruijieBgpBaseScalarExtensions
-- BGP Extensions

ruijieBgpBaseScalarExtensions
        OBJECT IDENTIFIER ::= { ruijieBgpBaseScalars 2 }
        
-- Base Scalar Route Reflection Extensions
ruijieBgpBaseScalarRouteReflectExts OBJECT IDENTIFIER ::=
	{ ruijieBgpBaseScalarExtensions 1 }

ruijieBgpRouteReflector OBJECT-TYPE
	SYNTAX	    TruthValue
	MAX-ACCESS  read-only
	STATUS	    current
	DESCRIPTION
	    "This value is TRUE if this implementation supports the
	     BGP Route Reflection Extension and is enabled as a
	     route reflector.  If the BGP Route Reflection extension
	     is not supported this value must be FALSE."
	REFERENCE
	    "RFC 2796 - BGP Route Reflection"
	::= { ruijieBgpBaseScalarRouteReflectExts 1 }

ruijieBgpClusterId OBJECT-TYPE
	SYNTAX	    RuijieBgpID
	MAX-ACCESS  read-only 
	STATUS	    current
	DESCRIPTION
	    "The configured Cluster-ID of the BGP Speaker.  This will
	     default to the BGP Speaker's ruijieBgpIdentifier if this
	     speaker is functioning as a route reflector and an
	     explicit Cluster-ID has not been configured.

	     A value of 0.0.0.0 will be present if Route Reflection is
	     not enabled."
	REFERENCE
	    "RFC 2796 - BGP Route Reflection"
	::= { ruijieBgpBaseScalarRouteReflectExts 2 }

-- Base Scalar AS Confederation Extensions
 
ruijieBgpBaseScalarASConfedExts OBJECT IDENTIFIER ::=
        { ruijieBgpBaseScalarExtensions 2 }

ruijieBgpConfederationRouter OBJECT-TYPE
	SYNTAX	   TruthValue
	MAX-ACCESS read-only
	STATUS	   current
	DESCRIPTION
	    "This value is TRUE if this implementation supports the
	     BGP AS Confederations Extension and this router is
	     configured to be in a confederation."
	REFERENCE
	    "RFC 3065 - Autonomous System Confederations for BGP"
	::= { ruijieBgpBaseScalarASConfedExts 1 }

ruijieBgpConfederationId OBJECT-TYPE
	SYNTAX	   InetAutonomousSystemNumber
	MAX-ACCESS read-only
	STATUS	   current
	DESCRIPTION
	    "The local Confederation Identification Number.
	    
	     This value will be zero (0) if this BGP Speaker is not
	     a confederation router."
	REFERENCE
	    "RFC 3065 - Autonomous System Confederations for BGP"
	    ::= { ruijieBgpBaseScalarASConfedExts 2 }

-- END：ruijieBgpBaseScalarExtensions

ruijieBgpRpkiSession
        OBJECT IDENTIFIER ::= { ruijieBgpBaseScalars 3 }

ruijieBgpRpkiTrap
	OBJECT IDENTIFIER ::= { ruijieBgpRpkiSession 1 }

ruijiebgpRpkiRoaExceed NOTIFICATION-TYPE
    OBJECTS         {
                        ruijieBgpRouteVrfName,
                        ruijieBgpRpkiSessionAddrType,
                        ruijieBgpRpkiSessionAddr,
                        ruijieBgpRpkiSessionRoaLimit

                    }
    STATUS          current
    DESCRIPTION
        "The ruijiebgpRpkiRoaExceed is generated when the 
        number of ROAs received from the session exceeded 
        the alarm number."
   ::= { ruijieBgpRpkiTrap 1 }

ruijiebgpRpkiRoaExceedClear NOTIFICATION-TYPE
    OBJECTS         {
                        ruijieBgpRouteVrfName,
                        ruijieBgpRpkiSessionAddrType,
                        ruijieBgpRpkiSessionAddr,
                        ruijieBgpRpkiSessionRoaLimit

                    }
    STATUS          current
    DESCRIPTION
        "The ruijiebgpRpkiRoaExceedClear is generated when the 
        number of ROAs received from the session decreased below
         the alarm number."
   ::= { ruijieBgpRpkiTrap 2 }   

ruijieBgpRpkiSessionLimit
	OBJECT IDENTIFIER ::= { ruijieBgpRpkiSession 2 }   

ruijieBgpRpkiSessionAddrType  OBJECT-TYPE
        SYNTAX      InetAddressType
        MAX-ACCESS  read-only
        STATUS      current
        DESCRIPTION
                "The BGP rpki session IP address type."
        ::= { ruijieBgpRpkiSessionLimit 1 }

ruijieBgpRpkiSessionAddr OBJECT-TYPE
          SYNTAX InetAddress
          MAX-ACCESS read-only
          STATUS current
          DESCRIPTION
              "The BGP rpki session IP address. "
           ::= { ruijieBgpRpkiSessionLimit 2 } 

ruijieBgpRpkiSessionRoaLimit OBJECT-TYPE
          SYNTAX Unsigned32 (0..4294967295)
          MAX-ACCESS read-only
          STATUS current
          DESCRIPTION
              "The BGP rpki session Roa limit. "
           ::= { ruijieBgpRpkiSessionLimit 3 }              

-- END：ruijieBgpBaseScalars

-- BEGIN：ruijieBgpPeer

ruijieBgpPeer
	OBJECT IDENTIFIER ::= { ruijieBgp4MIB 2 }

-- BEGIN：ruijieBgpPeerPrefixInfoTable

ruijieBgpPeerPrefixInfoTable OBJECT-TYPE
        SYNTAX     SEQUENCE OF RuijieBgpPeerPrefixInfoEntry
        MAX-ACCESS not-accessible
        STATUS     current
        DESCRIPTION
                "This table contains prefix info with peers,
                 One entry per BGP peer ."
        ::= { ruijieBgpPeer 1 }

ruijieBgpPeerPrefixInfoEntry  OBJECT-TYPE
        SYNTAX     RuijieBgpPeerPrefixInfoEntry
        MAX-ACCESS not-accessible
        STATUS     current
        DESCRIPTION
                "Entry containing information about the
                connection with a BGP peer."
        AUGMENTS {
	    bgpPeerEntry
	}
        ::= { ruijieBgpPeerPrefixInfoTable 1 }

RuijieBgpPeerPrefixInfoEntry ::= SEQUENCE {
        ruijieBgpPeerPrefixLimit       Unsigned32,
        ruijieBgpPeerPrefixAccepted    Counter32,
        ruijieBgpPeerPrefixAdvertised  Counter32
        }
    
ruijieBgpPeerPrefixLimit  OBJECT-TYPE
        SYNTAX      Unsigned32 (1..4294967295)
        MAX-ACCESS  read-only
        STATUS      deprecated
        DESCRIPTION
                "Max number of route prefixes accepted on this 
                 connection"
        ::= { ruijieBgpPeerPrefixInfoEntry 1 }
        
ruijieBgpPeerPrefixAccepted  OBJECT-TYPE  
        SYNTAX      Counter32
        MAX-ACCESS  read-only
        STATUS      deprecated
        DESCRIPTION
                "Number of Route prefixes received on this connnection,
                 which are accepted after applying filters. Possible
                 filters are route maps, prefix lists, distributed
                 lists, etc."
        ::= { ruijieBgpPeerPrefixInfoEntry 2 } 

ruijieBgpPeerPrefixAdvertised  OBJECT-TYPE
        SYNTAX      Counter32
        MAX-ACCESS  read-only
        STATUS      deprecated
        DESCRIPTION
                "Counter which gets incremented when a route prefix
                 is advertised on this connection. This object is
                 initialized to zero when the peer is configured or 
                 the router is rebooted"
        ::= { ruijieBgpPeerPrefixInfoEntry 3 }

-- END：ruijieBgpPeerPrefixInfoTable

-- BEGIN：ruijieBgpPeerCapabilities

ruijieBgpPeerCapabilities
	OBJECT IDENTIFIER ::= { ruijieBgpPeer 2 }

-- BEGIN：ruijieBgpPeerCapsAnnouncedTable
-- Announced Capabilities

ruijieBgpPeerCapsAnnouncedTable OBJECT-TYPE
	SYNTAX	   SEQUENCE OF RuijieBgpPeerCapsAnnouncedEntry
	MAX-ACCESS not-accessible
	STATUS	   current
	DESCRIPTION
	    "This table contains the capabilities
	     that are announced to a given peer."
	::= { ruijieBgpPeerCapabilities 1 }

ruijieBgpPeerCapsAnnouncedEntry OBJECT-TYPE
	SYNTAX	   RuijieBgpPeerCapsAnnouncedEntry
	MAX-ACCESS not-accessible
	STATUS	   current
	DESCRIPTION
	    "These entries are keyed by a BGP-4 peer remote
	     address and the BGP Capability Code"
	INDEX {
	    bgpPeerRemoteAddr,
	    ruijieBgpPeerCapAnnouncedCode
	}
	::= { ruijieBgpPeerCapsAnnouncedTable 1 }

RuijieBgpPeerCapsAnnouncedEntry ::= SEQUENCE {
	ruijieBgpPeerCapAnnouncedCode
	    Unsigned32,
	ruijieBgpPeerCapAnnouncedValue
	    OCTET STRING
    }

ruijieBgpPeerCapAnnouncedCode OBJECT-TYPE
	SYNTAX	   Unsigned32 (0..255)
	MAX-ACCESS read-only
	STATUS	   current
	DESCRIPTION
	    "The BGP Capability Advertisement Capability Code."
	::= { ruijieBgpPeerCapsAnnouncedEntry 1 }

ruijieBgpPeerCapAnnouncedValue OBJECT-TYPE
	SYNTAX	   OCTET STRING (SIZE(0..255))
	MAX-ACCESS read-only
	STATUS	   current
	DESCRIPTION
	    "The value of the announced capability."
	::= { ruijieBgpPeerCapsAnnouncedEntry 2 }

-- END：ruijieBgpPeerCapsAnnouncedTable

-- BEGIN：ruijieBgpPeerCapsReceivedTable
-- Received Capabilities

ruijieBgpPeerCapsReceivedTable OBJECT-TYPE
	SYNTAX	   SEQUENCE OF RuijieBgpPeerCapsReceivedEntry
	MAX-ACCESS not-accessible
	STATUS	   current
	DESCRIPTION
	    "This table contains the capabilities
	    that are supported for a given peer."
	::= { ruijieBgpPeerCapabilities 2 }

ruijieBgpPeerCapsReceivedEntry OBJECT-TYPE
	SYNTAX	   RuijieBgpPeerCapsReceivedEntry
	MAX-ACCESS not-accessible
	STATUS	   current
	DESCRIPTION
	    "These entries are keyed by a BGP-4 peer remote
	    address and the BGP Capability Code"
	INDEX {
	    bgpPeerRemoteAddr,
	    ruijieBgpPeerCapReceivedCode
	}
	::= { ruijieBgpPeerCapsReceivedTable 1 }

RuijieBgpPeerCapsReceivedEntry ::= SEQUENCE {
	ruijieBgpPeerCapReceivedCode
	    Unsigned32,
	ruijieBgpPeerCapReceivedValue
	    OCTET STRING
    }

ruijieBgpPeerCapReceivedCode OBJECT-TYPE
	SYNTAX	   Unsigned32 (0..255)
	MAX-ACCESS read-only
	STATUS	   current
	DESCRIPTION
	    "The BGP Capability Received Capability Code."
	::= { ruijieBgpPeerCapsReceivedEntry 1 }

ruijieBgpPeerCapReceivedValue OBJECT-TYPE
	SYNTAX	   OCTET STRING (SIZE(0..255))
	MAX-ACCESS read-only
	STATUS	   current
	DESCRIPTION
	    "The value of the received capability."
	::= { ruijieBgpPeerCapsReceivedEntry 3 }

-- END：ruijieBgpPeerCapsReceivedTable
	
-- END：ruijieBgpPeerCapabilities

-- BEGIN：ruijieBgpPeerExtensions

ruijieBgpPeerExtensions
	OBJECT IDENTIFIER ::= { ruijieBgpPeer 3 }

-- BEGIN：
-- Peer Route Reflection Extensions

ruijieBgpPeerRouteReflectionExts
	OBJECT IDENTIFIER ::= { ruijieBgpPeerExtensions 1 }

ruijieBgpPeerReflectorClientTable OBJECT-TYPE
	SYNTAX	   SEQUENCE OF RuijieBgpPeerReflectorClientEntry
	MAX-ACCESS not-accessible
	STATUS	   current
	DESCRIPTION
	    "Table of route reflection client settings on a per-peer
	     basis."
	REFERENCE
	    "RFC 2796 - BGP Route Reflection"
	::= { ruijieBgpPeerRouteReflectionExts 1 }

ruijieBgpPeerReflectorClientEntry OBJECT-TYPE
	SYNTAX	   RuijieBgpPeerReflectorClientEntry
	MAX-ACCESS not-accessible
	STATUS	   current
	DESCRIPTION
	    "Entry containing data on a per-peer basis on whether
	     the peer is configured as a route reflector client."
	REFERENCE
	    "RFC 2796 - BGP Route Reflection"
	AUGMENTS {
	    bgpPeerEntry
	}
	::= { ruijieBgpPeerReflectorClientTable 1 }

RuijieBgpPeerReflectorClientEntry ::= SEQUENCE {
	ruijieBgpPeerReflectorClient
	    INTEGER
    }

ruijieBgpPeerReflectorClient OBJECT-TYPE
	SYNTAX	  INTEGER {
	    nonClient(0),
	    client(1),
	    meshedClient(2)
	}
	MAX-ACCESS  read-only
	STATUS	    current
	DESCRIPTION
	    "This value indicates whether the given peer is a
	     reflector client of this router, or not.  A value of
	     nonClient indicates that this peer is not a reflector
	     client.  A value of client indicates that this peer is a
	     reflector client that is not fully meshed with other
	     reflector clients.	 A value of meshedClient indicates
	     that the peer is a reflector client and is fully meshed
	     with all other reflector clients.

	     This value must be nonClient (0) for BGP external peers."
	REFERENCE
	    "RFC 2796 - BGP Route Reflection"
	::= { ruijieBgpPeerReflectorClientEntry 1 }

-- Peer AS Confederations Extensions

ruijieBgpPeerASConfederationExts
	OBJECT IDENTIFIER ::= { ruijieBgpPeerExtensions 2 }

ruijieBgpPeerConfedMemberTable OBJECT-TYPE
	SYNTAX	   SEQUENCE OF RuijieBgpPeerConfedMemberEntry
	MAX-ACCESS not-accessible
	STATUS	   current
	DESCRIPTION
	    "Table of confederation member settings on a per-peer
	     basis."
	REFERENCE
	    "RFC 3065 - BGP Confederations"
	::= { ruijieBgpPeerASConfederationExts 1 }

ruijieBgpPeerConfedMemberEntry OBJECT-TYPE
	SYNTAX	   RuijieBgpPeerConfedMemberEntry
	MAX-ACCESS not-accessible
	STATUS	   current
	DESCRIPTION
	    "Entry containing data on a per-peer basis on whether
	     the peer is configured as a BGP confederation member."
	REFERENCE
	    "RFC 3065 - BGP Confederations"
	AUGMENTS {
	    bgpPeerEntry
	}
	::= { ruijieBgpPeerConfedMemberTable 1 }

RuijieBgpPeerConfedMemberEntry ::= SEQUENCE {
	ruijieBgpPeerConfedMember
	    TruthValue
    }
    
ruijieBgpPeerConfedMember OBJECT-TYPE
	SYNTAX	    TruthValue
	MAX-ACCESS  read-only
	STATUS	    current
	DESCRIPTION
	    "This value indicates whether the given peer is in our
	     confederation or not."
	REFERENCE
	    "RFC 3065 - BGP Confederations"
	::= { ruijieBgpPeerConfedMemberEntry 1 }
	
-- END：ruijieBgpPeerExtensions	 

-- Notifications
ruijieBgpPeerTrap
	OBJECT IDENTIFIER ::= { ruijieBgpPeer 4 }

ruijiebgpEstablished NOTIFICATION-TYPE
    OBJECTS         {
                        ruijiebgpPeerLastError,
                        ruijiebgpPeerState
                    }
    STATUS          current
    DESCRIPTION
        "The BGP rjbgpFsmStateChange notification is generated
        for every BGP FSM state change. The bgpPeerRemoteAddr
        value is attached to the notification object ID."
   ::= { ruijieBgpPeerTrap 1 }

ruijiebgpBackwardTransition NOTIFICATION-TYPE
    OBJECTS         {
                        ruijiebgpPeerLastError,
                        ruijiebgpPeerState
                    }
    STATUS          current
    DESCRIPTION
        "The rjbgpBackwardTransition Event is generated when the
        BGP FSM moves from a higher numbered state to a lower
        numbered state. The bgpPeerRemoteAddr value is attached
        to the notification object ID."
   ::= { ruijieBgpPeerTrap 2 }

ruijiebgpRouteThresholdExceed NOTIFICATION-TYPE
    OBJECTS {
                ruijieBgpAddressFamilyAfi,
                ruijieBgpAddressFamilySafi,
                ruijieBgpPeerType,
                ruijieBgpPeerRemoteAddr,
                ruijieBgpRouteLimitNum,
                ruijieBgpRouteLimitThreshold
            }
    STATUS          current
    DESCRIPTION
        "The ruijiebgpRouteThresholdExceed is generated when the 
        number of routes received from the BGP peer exceeded the
         alarm threshold."
   ::= { ruijieBgpPeerTrap 3 }   

ruijiebgpRouteThresholdClear NOTIFICATION-TYPE
    OBJECTS {
                ruijieBgpAddressFamilyAfi,
                ruijieBgpAddressFamilySafi,
                ruijieBgpPeerType,
                ruijieBgpPeerRemoteAddr,
                ruijieBgpRouteLimitNum,
                ruijieBgpRouteLimitThreshold
            }
    STATUS          current
    DESCRIPTION
        "The ruijiebgpRouteThresholdClear is generated when the 
        number of routes received from the BGP peer decreased 
        below the alarm threshold."
   ::= { ruijieBgpPeerTrap 4 }   

ruijiebgpRouteExceed NOTIFICATION-TYPE
    OBJECTS {
                ruijieBgpAddressFamilyAfi,
                ruijieBgpAddressFamilySafi,
                ruijieBgpPeerType,
                ruijieBgpPeerRemoteAddr,
                ruijieBgpRouteLimitNum,
                ruijieBgpRouteLimitThreshold
            }
    STATUS          current
    DESCRIPTION
        "The ruijiebgpRouteExceed is generated when the
        number of routes received from the BGP peer 
        exceeded the alarm number."
   ::= { ruijieBgpPeerTrap 5 }  

ruijiebgpRouteExceedClear NOTIFICATION-TYPE
    OBJECTS {
                ruijieBgpAddressFamilyAfi,
                ruijieBgpAddressFamilySafi,
                ruijieBgpPeerType,
                ruijieBgpPeerRemoteAddr,
                ruijieBgpRouteLimitNum,
                ruijieBgpRouteLimitThreshold
            }
    STATUS          current
    DESCRIPTION
        "The ruijiebgpRouteClear is generated when the
        number of routes received from the BGP peer 
        decreased below the alarm number."
   ::= { ruijieBgpPeerTrap 6 }  

ruijiebgpVrfRouteExceed NOTIFICATION-TYPE
    OBJECTS {
                ruijieBgpRouteVrfName,
                ruijieBgpRouteLimitNum,
                ruijieBgpRouteLimitCurrentNum
            }
    STATUS          current
    DESCRIPTION
        "The ruijiebgpVrfRouteExceed is generated when the
        number of routes in the VPN instance reached the 
        alarm threshould."
   ::= { ruijieBgpPeerTrap 7 }  

ruijiebgpVrfRouteExceedClear NOTIFICATION-TYPE
    OBJECTS {
                ruijieBgpRouteVrfName,
                ruijieBgpRouteLimitNum,
                ruijieBgpRouteLimitCurrentNum
            }
    STATUS          current
    DESCRIPTION
        "The ruijiebgpVrfRouteClear is generated when the
        number of routes in the VPN instance fell below 
        the clear alarm threshold."
   ::= { ruijieBgpPeerTrap 8 }                

-- END：ruijieBgpPeerTrap 

-- BEGIN：ruijieBgpPeerExtensions

-- ruijieBGP Peer table.  This table contains, one entry per
-- BGP peer, information about the BGP peer.

ruijieBgpPeerTable OBJECT-TYPE
    SYNTAX     SEQUENCE OF RuijieBgpPeerEntry
    MAX-ACCESS not-accessible
    STATUS     current
    DESCRIPTION
            "BGP peer table.  This table contains,
            one entry per BGP peer, information about
            the connections with BGP peers."
    ::= { ruijieBgpPeer 5 }

ruijieBgpPeerEntry OBJECT-TYPE
    SYNTAX     RuijieBgpPeerEntry
    MAX-ACCESS not-accessible
    STATUS     current
    DESCRIPTION
            "Entry containing information about the
            connection with a BGP peer."
    INDEX { ruijieBgpPeerVrfName,
            ruijieBgpPeerType,
            ruijieBgpPeerRemoteAddr      
        }
    ::= { ruijieBgpPeerTable 1 }

RuijieBgpPeerEntry ::= SEQUENCE {
        ruijieBgpPeerVrfName                    RuijieBgpVrfName,
        ruijieBgpPeerType                       InetAddressType,
        ruijieBgpPeerRemoteAddr                 InetAddress,
        ruijiebgpPeerLastError                  OCTET STRING,
        ruijiebgpPeerState                      INTEGER
        }

ruijieBgpPeerVrfName OBJECT-TYPE
   SYNTAX        RuijieBgpVrfName
   MAX-ACCESS    read-only
   STATUS        current
   DESCRIPTION
       "The human-readable name of this VPN.  This MAY
        be equivalent to the [RFC2685] VPN-ID, but may
        also vary.  If it is set to the VPN ID, it MUST
        be equivalent to the value of mplsL3VpnVrfVpnId.
        It is strongly recommended that all sites supporting
        VRFs that are part of the same VPN use the same
        naming convention for VRFs as well as the same VPN
        ID."
   REFERENCE
       "[RFC2685]"
   ::= { ruijieBgpPeerEntry 1 }        
  
ruijieBgpPeerType OBJECT-TYPE
          SYNTAX InetAddressType
          MAX-ACCESS read-only
          STATUS current
          DESCRIPTION
              "This attribute shall specify the address family of the peer's address. "
           ::= { ruijieBgpPeerEntry 2 }

ruijieBgpPeerRemoteAddr OBJECT-TYPE
          SYNTAX InetAddress
          MAX-ACCESS read-only
          STATUS current
          DESCRIPTION
              "This attribute shall specify the address of the peer. "
           ::= { ruijieBgpPeerEntry 3 }   

ruijiebgpPeerLastError OBJECT-TYPE
    SYNTAX          OCTET STRING (SIZE  (2))
    MAX-ACCESS      read-only
    STATUS          current
    DESCRIPTION
        "The last error code and subcode seen by this
        peer on this connection.  If no error has
        occurred, this field is zero.  Otherwise, the
        first byte of this two byte OCTET STRING
        contains the error code, and the second byte
        contains the subcode."
    REFERENCE       "RFC 4271, Section 4.5." 
    ::= { ruijieBgpPeerEntry 4 }
           
ruijiebgpPeerState OBJECT-TYPE
          SYNTAX   INTEGER  {
                        none(0),
                        idle(1),
                        connect(2),
                        active(3),
                        opensent(4),
                        openconfirm(5),
                        established(6)
                    }
    MAX-ACCESS      read-only
    STATUS          current
    DESCRIPTION
        "The BGP peer connection previous state."
    REFERENCE
        "RFC 1771, Section 8, A Border Gateway Protocol 4
         (BGP-4)." 
    ::= { ruijieBgpPeerEntry 5 }
  
    
-- END：rjbgpPeerTable
    
ruijieBgpPeerRouteLimit OBJECT IDENTIFIER ::= { ruijieBgpPeer 6 }

ruijieBgpAddressFamilyAfi OBJECT-TYPE
    SYNTAX     AddressFamilyNumbers
    MAX-ACCESS read-only
    STATUS     current
    DESCRIPTION
            "BGP peer address family afi."
    ::= { ruijieBgpPeerRouteLimit 1 }

ruijieBgpAddressFamilySafi OBJECT-TYPE
    SYNTAX   INTEGER  {
        unicast(1),
        multicast(2),
        unicast-multicast(3),
        mpls-label(4),
        static-multicast(5),
        mdt-map(6),
        vpls(65),
        mdt(66),
        evpn(70),
        bgp-ls(71),
        sr-policy(73),
        mpls-vpn(128),
        vr-labeled(129),
        flowspec(133),
        flowspec-vpn(134),
        vr-unlabeled(140)
    }
    MAX-ACCESS read-only
    STATUS     current
    DESCRIPTION
            "BGP peer subsequent address family."
    ::= { ruijieBgpPeerRouteLimit 2 }

ruijieBgpRouteLimitNum OBJECT-TYPE
    SYNTAX     Unsigned32
    MAX-ACCESS read-only
    STATUS     current
    DESCRIPTION
            "BGP peer route limit."
    ::= { ruijieBgpPeerRouteLimit 3 }

ruijieBgpRouteLimitThreshold OBJECT-TYPE
    SYNTAX     INTEGER(1..100)
    MAX-ACCESS read-only
    STATUS     current
    DESCRIPTION
            "BGP peer route limit threshold."
    ::= { ruijieBgpPeerRouteLimit 4 }    

ruijieBgpRouteLimitCurrentNum OBJECT-TYPE
    SYNTAX     Unsigned32
    MAX-ACCESS read-only
    STATUS     current
    DESCRIPTION
            "BGP peer current route number."
    ::= { ruijieBgpPeerRouteLimit 5 } 

ruijieBgpRouteVrfName OBJECT-TYPE
    SYNTAX     RuijieBgpVrfName
    MAX-ACCESS read-only
    STATUS     current
    DESCRIPTION
            "BGP VRF name."
    ::= { ruijieBgpPeerRouteLimit 6 }          

-- END：ruijieBgpPeer

-- BEGIN：Conformance Information

ruijieBgpConformance
	OBJECT IDENTIFIER ::= { ruijieBgp4MIB 3 }

ruijieBgpMIBCompliances OBJECT IDENTIFIER ::=
	{ ruijieBgpConformance 1 }
ruijieBgpMIBGroups	OBJECT IDENTIFIER ::=
	{ ruijieBgpConformance 2 }

-- END：Conformance Information

END
