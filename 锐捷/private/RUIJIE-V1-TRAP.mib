-- *****************************************************************
-- RUIJIE-V1-TRAP.mib:  Ruijie Switch SNMPv1 Trap MIB
--
-- November 2002, Wuzg
--
-- Copyright (c) 2002 by Ruijie Networks Co.,Ltd.
-- All rights reserved.
-- 
-- *****************************************************************
--

RUIJIE-V1-TRAP DEFINITIONS ::= BEGIN

IMPORTS
    ruijieMacNotiHisMacChangedMsg
        FROM RUIJIE-ADDRESS-MIB
    ruijieSystemHardChangeDesc
        FROM RUIJIE-SYSTEM-MIB    
    stormViolationAlarmType
        FROM RUIJIE-TRAFFIC-CTRL-MIB
    ruijieSystemHwPower,
    ruijieSystemHwFan                
	FROM RUIJIE-SYSTEM-MIB
    ruijieIgmpInterfaceIfIndex,
    ruijieIgmpInterfaceVersion,
    ruijieIgmpInterfaceHostVersion
        FROM RUIJIE-IGMP-MIB
    ruijieEntityStateChgDesc,
    ruijieTemperatureWarningDesc
        FROM RUIJIE-ENTITY-MIB
    -- scMemberOperStatus
    --     FROM RUIJIE-CLUSTER-MIB
    ruijieSMPSwitchIP,
    ruijieSMPSwitchInterfaceID,
    ruijieSMPSwitchInterfaceVLANID,
    ruijieSMPFrameContentLength,
    ruijieSMPFrameContent,
    ruijieSMPArpAttackSubnetIP,
    ruijieSMPArpAttackSubnetIPNum,
    ruijieSMPArpAttackInterfaceSlot,
    ruijieSMPArpAttackInterfacePort,
    ruijieSMPArpAttackInterfaceVlanID,
    ruijieSMPArpAttackFrameContent,
    ruijieSMPArpAttackStatus,
    ruijieSMPArpAttackCriticalStatus,
    ruijieSMPArpAttackMac,
    ruijieSMPArpAttackInterfaceIndex
        FROM RUIJIE-SMP-MIB
    lineDetectStatus,
    lineDetectPosition
        FROM RUIJIE-INTERFACE-MIB
    -- userIpaddr
    --     FROM RUIJIE-AUTH-GATEWAY-MIB
    ruijieUrpfIfDropRate
        FROM RUIJIE-URPF-MIB
    TRAP-TYPE
        FROM RFC-1215
    ifIndex
        FROM RFC1213-MIB
    switch
        FROM RUIJIE-SMI;

 --
 -- snmpv1-trap definitions 
 --
          
 sysHardChangeDetected TRAP-TYPE
   	ENTERPRISE switch
   	VARIABLES  { ruijieSystemHardChangeDesc }
   	DESCRIPTION
         "System hardware has changed include number of devices or number of modules 
          or the place or type of the module is change."
     ::= 1

 portSecurityViolate TRAP-TYPE
     ENTERPRISE switch
     VARIABLES  { ifIndex }
     DESCRIPTION
         "the port security violate trap indicates that port security rule 
          is violated when port security of this port is opened."
     ::= 2
     
 stormViolationAlarm TRAP-TYPE
     ENTERPRISE switch
     VARIABLES  { ifIndex,stormViolationAlarmType}
     DESCRIPTION
         "while the storm threshold has been set, if more broadcast 
         is send to the port, then this trap will be sent."
     ::= 3

 macNotification TRAP-TYPE
   	ENTERPRISE switch
   	VARIABLES  { ruijieMacNotiHisMacChangedMsg }
   	DESCRIPTION
          "This notification is generated when there is enough MAC
           address information to fully occupy a maximum size SNMP trap
           message. This notification is also generated when there
           is at least one MAC address changed or removed and the amount
           of time elapsed from the previous notification is greater
           than the maximum wait time denoted by ruijieMacNotificationInterval object. 
   
           If there are more MAC addresses information than can fit into
           one ruijieMacNotiHisMacChangedMsg object, then multiple notifications
           will be generated."
     ::= 4
     
 powerStateChange TRAP-TYPE
     ENTERPRISE switch
     VARIABLES  { ruijieSystemHwPower}
     DESCRIPTION
         "while the state of power changed, then this trap will be sent."
     ::= 5
     
 fanStateChange TRAP-TYPE
     ENTERPRISE switch
     VARIABLES  { ruijieSystemHwFan}
     DESCRIPTION
         "while the state of fan changed, then this trap will be sent."
     ::= 6

pimNeighborLoss TRAP-TYPE
     ENTERPRISE switch
     VARIABLES  {ifIndex }
     DESCRIPTION
        "A pimNeighborLoss trap signifies the loss of an adjacency
         with a neighbor.  This trap should be generated when the
         neighbor timer expires, and the router has no other
         neighbors on the same interface with a lower IP address than
         itself."
    ::= 7
    
  igmpVersionConflicted TRAP-TYPE
     ENTERPRISE switch
     VARIABLES  {ruijieIgmpInterfaceIfIndex,
                 ruijieIgmpInterfaceVersion,
                 ruijieIgmpInterfaceHostVersion }
     DESCRIPTION
        "A igmpVersionErr trap signifies version is 
         different in the interface with host.This trap 
         should be generated when interface run  version 
         IGMPV1 and reported by host which run version IGMPV2.
         also when interface run version IGMPV2 and reported 
         by host which run version IGMPV1."        
    ::= 8
    
  dvmrpRouteInformation TRAP-TYPE
     ENTERPRISE switch     
     DESCRIPTION
        "A dvmrpRouteInformation trap signifies the
        Number of routes is more than The limit of 
        ruijieDvmrpRoutehogNotification in one minute,
        then the trap should be generated."
    ::= 9
 
 entityNotification TRAP-TYPE
     ENTERPRISE switch
     VARIABLES  { ruijieEntityStateChgDesc}
     DESCRIPTION
         "while the state of entity changed or some failure happened, this trap will be sent."
     ::= 10
     
 -- clusterMemberStateChange TRAP-TYPE
 --     ENTERPRISE switch
 --     VARIABLES  {scMemberOperStatus}
 --     DESCRIPTION
 --         "while the state of member switch changed, then this trap will be sent.
 --          either state of member switch change from active to inactive or from
 --          inactive to active."
 --     ::= 11
                                                              
 temperatureWarning TRAP-TYPE
     ENTERPRISE switch
     VARIABLES  { ruijieTemperatureWarningDesc }
     DESCRIPTION
         "while the temperature of one of modules reach warning temperature, then this trap will be sent."
     ::= 12
                                                              
 lineDetect TRAP-TYPE
     ENTERPRISE switch
     VARIABLES  { ifIndex, lineDetectStatus,lineDetectPosition }
     DESCRIPTION
         "Notifications of the detection of short circuit or broken circuit, or restoring the line to normal state."
     ::= 13     

  smpFrameRelay TRAP-TYPE
     ENTERPRISE switch
     VARIABLES  {ruijieSMPSwitchIP,ruijieSMPSwitchInterfaceID,ruijieSMPSwitchInterfaceVLANID,
      			  ruijieSMPFrameContentLength,ruijieSMPFrameContent}
      DESCRIPTION
              "Trap message includes:
               IP address for the switch receiving specified messages;
               Port receving the messages;
               Message length;
               Message content." 
      ::= 14


 smpArpAttack TRAP-TYPE
     ENTERPRISE switch
     VARIABLES  { ruijieSMPArpAttackSubnetIP, ruijieSMPArpAttackSubnetIPNum, ruijieSMPArpAttackInterfaceSlot,
               ruijieSMPArpAttackInterfacePort, ruijieSMPArpAttackInterfaceVlanID, ruijieSMPArpAttackFrameContent,
               ruijieSMPArpAttackStatus, ruijieSMPArpAttackCriticalStatus, ruijieSMPArpAttackMac, 
               ruijieSMPArpAttackInterfaceIndex }
     DESCRIPTION
         "Send warning to SMP when detecting the ARP attack."  
     ::= 15    
     
     
 -- authGatewayUserLeave TRAP-TYPE
 --     ENTERPRISE switch
 --     VARIABLES  {userIpaddr}
 --     DESCRIPTION
 --         "Sending Trap when the user is offline."
 --     ::= 16
     
     
 urpfIfDropRateNotify TRAP-TYPE
     ENTERPRISE switch
     VARIABLES  {ruijieUrpfIfDropRate}
     DESCRIPTION
         "This notification is generated when 
         ruijieUrpfIfDropRateNotifyEnable is set to true and
         the calculated URPF drop rate (ruijieUrpfIfDropRate) 
         exceeds the notification threshold drop rate 
         (ruijieUrpfIfNotifyDropRateThreshold). Note the 
         exceptional value of 0 for threshold allows notification 
         generation if any drop events occur in an interval.
 
         After generating this notification, another such
         notification will not be sent out for a minimum of five 
         minutes (note the exception to this provided by 
         ruijieUrpfIfNotifyDrHoldDownReset).

         The object value present in the notification is the 
         the drop rate that exceeded the threshold."  
     ::= 17
     
END
