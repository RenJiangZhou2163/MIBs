-- *****************************************************************
-- RUIJIE-CAPWAP-MULTICAST-MIB.mib:  Ruijie CAPWAP MULTICAST MIB file
--
-- Oct 2009, xieweiwu
--
-- Copyright (c) 2009 by Ruijie Networks Co.,Ltd.
-- All rights reserved.
-- 
-- *****************************************************************
--

RUIJIE-CAPWAP-MULTICAST-MIB DEFINITIONS ::= BEGIN

IMPORTS
        MODULE-IDENTITY,
        OBJECT-TYPE,
        IpAddress
                FROM SNMPv2-SMI
        MODULE-COMPLIANCE,
        OBJECT-GROUP
                FROM SNMPv2-CONF
        ruijieMgmt
                FROM RUIJIE-SMI;

ruijieCapwapMulticastMIB MODULE-IDENTITY
        LAST-UPDATED "200910220000Z"
        ORGANIZATION "Ruijie Networks Co.,Ltd."
        CONTACT-INFO
                " 
                Tel: 4008-111-000 

                E-mail: service@ruijie.com.cn"
        DESCRIPTION
                "This module defines ruijie Capwap Multicast mibs."
        REVISION      "200910220000Z"
        DESCRIPTION
                "Initial version of this MIB module."
        ::= { ruijieMgmt 59}

ruijieCapwapMulticastMIBObjects OBJECT IDENTIFIER ::= { ruijieCapwapMulticastMIB 1 }


--capwap multicast mode
ruijieCapwapMulticastWorkingMode OBJECT-TYPE
        SYNTAX INTEGER {
            unicast(1),    -- Working in capwap unicast(1),
            multicast(2)    -- Working in capwap multicast(2)
        }
        MAX-ACCESS read-write
        STATUS current
        DESCRIPTION
            "System Multicast working mode:
             unicast(1):
                Working in capwap unicast.
             multicast(2):
                Working in capwap multicast."
        DEFVAL { unicast }
        ::= { ruijieCapwapMulticastMIBObjects 1 }

--show capwap multicast group address
ruijieCapwapMulticastGroup OBJECT-TYPE
        SYNTAX IpAddress
        MAX-ACCESS read-write
        STATUS current
        DESCRIPTION
            "the address of capwap multicast"
        ::= { ruijieCapwapMulticastMIBObjects 2 }

ruijieCapwapMulticastMIBConformance OBJECT IDENTIFIER ::= { ruijieCapwapMulticastMIB 2 }
ruijieCapwapMulticastMIBCompliances OBJECT IDENTIFIER ::= { ruijieCapwapMulticastMIBConformance 1 }
ruijieCapwapMulticastMIBGroups      OBJECT IDENTIFIER ::= { ruijieCapwapMulticastMIBConformance 2 }


-- compliance statements

ruijieCapwapMulticastMIBCompliance MODULE-COMPLIANCE
        STATUS  current
        DESCRIPTION
                "The compliance statement for entities which implement
                the Ruijie Capwap Multicast MIB"
        MODULE  -- this module
                MANDATORY-GROUPS { ruijieCapwapMulticastMIBGroup
                 }
        ::= { ruijieCapwapMulticastMIBCompliances 1 }
                
-- units of conformance

ruijieCapwapMulticastMIBGroup OBJECT-GROUP
        OBJECTS {
           ruijieCapwapMulticastWorkingMode,
           ruijieCapwapMulticastGroup
        }
        STATUS  current
        DESCRIPTION
                "A collection of objects providing CapwapMulticast configure ."
        ::= { ruijieCapwapMulticastMIBGroups 1 }
        
END
