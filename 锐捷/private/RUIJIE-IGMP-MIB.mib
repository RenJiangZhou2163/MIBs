--*****************************************************************
-- RUIJIE-IGMP-MIB.mib: This mib was extracted from rfc2933
--
-- January 2003, zhenggao
--
-- Copyright (c) 2003 by Ruijie Networks Co.,Ltd.
-- All rights reserved.
-- 
-- *****************************************************************

RUIJIE-IGMP-MIB DEFINITIONS ::= BEGIN
IMPORTS
    MODULE-IDENTITY,
    NOTIFICATION-TYPE,
    OBJECT-TYPE, 
    Counter32, 
    Gauge32,
    Integer32,
    Unsigned32, 
    IpAddress, 
    TimeTicks  
        FROM SNMPv2-SMI
    RowStatus, 
    DisplayString          
        FROM SNMPv2-TC
    EnabledStatus            
         FROM P-BRIDGE-MIB 
    ruijieMgmt                
        FROM RUIJIE-SMI
    InterfaceIndexOrZero,    
    InterfaceIndex        
        FROM IF-MIB
    MODULE-COMPLIANCE, 
    OBJECT-GROUP  
        FROM SNMPv2-CONF;
 
ruijieIgmpMIB MODULE-IDENTITY
    LAST-UPDATED "200301200000Z"
    ORGANIZATION "Ruijie Networks Co.,Ltd."
    CONTACT-INFO
        "
        Tel: 4008-111-000 
        
        E-mail: service@ruijie.com.cn"
    DESCRIPTION
        "This module defines ruijie igmp mibs."
    REVISION      "200301200000Z"
    DESCRIPTION
        "Initial version of this MIB module."
    ::= { ruijieMgmt 26}

ruijieIgmpMIBObjects OBJECT IDENTIFIER ::= { ruijieIgmpMIB 1 }  
ruijieIgmpTraps      OBJECT IDENTIFIER ::= { ruijieIgmpMIBObjects 3 }
--
--  The RUIJIE-IGMP Interface Table
--
ruijieIgmpInterfaceTable OBJECT-TYPE
    SYNTAX     SEQUENCE OF RuijieIgmpInterfaceEntry
    MAX-ACCESS not-accessible
    STATUS     current
    DESCRIPTION
        "The (conceptual) table listing the interfaces on
         which IGMP is enabled."
    ::= {  ruijieIgmpMIBObjects 1 }

ruijieIgmpInterfaceEntry OBJECT-TYPE
    SYNTAX     RuijieIgmpInterfaceEntry
    MAX-ACCESS not-accessible
    STATUS     current
    DESCRIPTION
        "An entry (conceptual row) representing an
         interface on which IGMP is enabled."
    INDEX      { ruijieIgmpInterfaceIfIndex }
    ::= { ruijieIgmpInterfaceTable 1 }
              
RuijieIgmpInterfaceEntry ::= SEQUENCE {
    ruijieIgmpInterfaceIfIndex		               InterfaceIndex ,
    ruijieIgmpInterfaceQueryInterval	            Unsigned32,
	 ruijieIgmpInterfaceVersion		               Unsigned32,
	 ruijieIgmpInterfaceQuerier		               IpAddress,
	 ruijieIgmpInterfaceQueryMaxResponseTime      Unsigned32,
	 ruijieIgmpInterfaceQuerierUpTime             TimeTicks,
    ruijieIgmpInterfaceQuerierExpiryTime         TimeTicks,
    ruijieIgmpInterfaceVersion1QuerierTimer      TimeTicks,
    ruijieIgmpInterfaceWrongVersionQueries       Counter32,
    ruijieIgmpInterfaceJoins		               Counter32,
    ruijieIgmpInterfaceProxyIfIndex              InterfaceIndexOrZero,
    ruijieIgmpInterfaceGroups                    Gauge32,            
    ruijieIgmpInterfaceRobustness                Unsigned32,
	 ruijieIgmpInterfaceLastMembQueryIntvl        Unsigned32,
	 ruijieIgmpInterfaceQuerierPresentTimeout     Integer32,           	
	 ruijieIgmpInterfaceLeaves		               Counter32,		   
	 ruijieIgmpInterfaceAccessGroupAclName        DisplayString,
	 ruijieIgmpInterfaceEnabled                   EnabledStatus,
	 ruijieIgmpInterfaceHostVersion               Unsigned32	                          
    }
 
ruijieIgmpInterfaceIfIndex OBJECT-TYPE
    SYNTAX     InterfaceIndex
    MAX-ACCESS not-accessible
    STATUS     current
    DESCRIPTION
        "The ifIndex value of the interface for which IGMP is
         enabled."
    ::= { ruijieIgmpInterfaceEntry 1 }

ruijieIgmpInterfaceQueryInterval OBJECT-TYPE
    SYNTAX     Unsigned32(1..65535)
    UNITS      "seconds"
    MAX-ACCESS read-write
    STATUS     current
    DESCRIPTION
        "The frequency at which IGMP Host-Query packets are
         transmitted on this interface."
    DEFVAL     { 125 }  
    ::= { ruijieIgmpInterfaceEntry 2 }
    
ruijieIgmpInterfaceVersion OBJECT-TYPE
    SYNTAX     Unsigned32
    MAX-ACCESS read-write
    STATUS     current
    DESCRIPTION
        "The version of IGMP which is running on this interface.
         This object can be used to configure a router capable of
         running either value.  For IGMP to function correctly, all
         routers on a LAN must be configured to run the same version
         of IGMP on that LAN."
    DEFVAL     { 2 }
    ::= { ruijieIgmpInterfaceEntry 3 }  
    
ruijieIgmpInterfaceQuerier OBJECT-TYPE
    SYNTAX     IpAddress
    MAX-ACCESS read-only
    STATUS     current
    DESCRIPTION
        "The address of the IGMP Querier on the IP subnet to which           
         this interface is attached."
    ::= { ruijieIgmpInterfaceEntry 4 }
        
ruijieIgmpInterfaceQueryMaxResponseTime OBJECT-TYPE
    SYNTAX     Unsigned32 (10..250)
    UNITS      "tenths of seconds"
    MAX-ACCESS read-write
    STATUS     current
    DESCRIPTION
        "The maximum query response time advertised in IGMPv2
         queries on this interface."
    DEFVAL     { 100 }
    ::= { ruijieIgmpInterfaceEntry 5 }   

ruijieIgmpInterfaceQuerierUpTime OBJECT-TYPE
    SYNTAX     TimeTicks
    MAX-ACCESS read-only
    STATUS     current
    DESCRIPTION
        "The time since starIgmpInterfaceQuerier was last changed."
    ::= { ruijieIgmpInterfaceEntry 6 }

ruijieIgmpInterfaceQuerierExpiryTime OBJECT-TYPE
    SYNTAX     TimeTicks
    MAX-ACCESS read-only
    STATUS     current
    DESCRIPTION
        "The amount of time remaining before the Other Querier
         Present Timer expires.  If the local system is the querier,
         the value of this object is zero."
    ::= { ruijieIgmpInterfaceEntry 7 }
    
ruijieIgmpInterfaceVersion1QuerierTimer OBJECT-TYPE
    SYNTAX     TimeTicks
    MAX-ACCESS read-only
    STATUS     current
    DESCRIPTION
        "The time remaining until the host assumes that there are no
         IGMPv1 routers present on the interface.  While this is non-
         zero, the host will reply to all queries with version 1
         membership reports."
    ::= { ruijieIgmpInterfaceEntry 8} 
 
ruijieIgmpInterfaceWrongVersionQueries OBJECT-TYPE
    SYNTAX     Counter32
    MAX-ACCESS read-only
    STATUS     current
    DESCRIPTION 
        "The number of queries received whose IGMP version does not
         match igmpInterfaceVersion, over the lifetime of the row
         entry.  IGMP requires that all routers on a LAN be
         configured to run the same version of IGMP.  Thus, if any
         queries are received with the wrong version, this indicates
         a configuration error."
    ::= { ruijieIgmpInterfaceEntry 9 }

ruijieIgmpInterfaceJoins OBJECT-TYPE
    SYNTAX     Counter32
    MAX-ACCESS read-only
    STATUS     current
    DESCRIPTION
        "The number of times a group membership has been added on
         this interface; that is, the number of times an entry for
         this interface has been added to the Cache Table.  This
         object gives an indication of the amount of IGMP activity
         over the lifetime of the row entry."
    ::= { ruijieIgmpInterfaceEntry 10 } 

ruijieIgmpInterfaceProxyIfIndex OBJECT-TYPE
    SYNTAX     InterfaceIndexOrZero
    MAX-ACCESS read-only
    STATUS     obsolete
    DESCRIPTION
        "Some devices implement a form of IGMP proxying whereby
         memberships learned on the interface represented by this
         row, cause IGMP Host Membership Reports to be sent on the
         interface whose ifIndex value is given by this object.  Such
         a device would implement the igmpV2RouterMIBGroup only on
         its router interfaces (those interfaces with non-zero
         igmpInterfaceProxyIfIndex).  Typically, the value of this
         object is 0, indicating that no proxying is being done."
    DEFVAL     { 0 }
    ::= { ruijieIgmpInterfaceEntry 11 } 

ruijieIgmpInterfaceGroups OBJECT-TYPE
    SYNTAX     Gauge32
    MAX-ACCESS read-only
    STATUS     current
    DESCRIPTION
        "The current number of entries for this interface in the
         Cache Table."
    ::= { ruijieIgmpInterfaceEntry 12 }
     
ruijieIgmpInterfaceRobustness OBJECT-TYPE
    SYNTAX     Unsigned32 (1..255)
    MAX-ACCESS read-write     
    STATUS     current
    DESCRIPTION
        "The Robustness Variable allows tuning for the expected
         packet loss on a subnet.  If a subnet is expected to be
         lossy, the Robustness Variable may be increased.  IGMP is
         robust to (Robustness Variable-1) packet losses."
    DEFVAL     { 2 }
    ::= { ruijieIgmpInterfaceEntry 13 }
  
ruijieIgmpInterfaceLastMembQueryIntvl OBJECT-TYPE
    SYNTAX     Unsigned32 (1..655)
    UNITS      "tenths of seconds"
    MAX-ACCESS read-write
    STATUS     current
    DESCRIPTION
        "The Last Member Query Interval is the Max Response Time
         inserted into Group-Specific Queries sent in response to
         Leave Group messages, and is also the amount of time between
         Group-Specific Query messages.  This value may be tuned to
         modify the leave latency of the network.  A reduced value
         results in reduced time to detect the loss of the last
         member of a group.  The value of this object is irrelevant
         if igmpInterfaceVersion is 1."
    DEFVAL     { 10 }
    ::= { ruijieIgmpInterfaceEntry 14 }    
 
ruijieIgmpInterfaceQuerierPresentTimeout OBJECT-TYPE
      SYNTAX     Integer32(60..300)
      UNITS      "seconds"
      MAX-ACCESS read-write
      STATUS     current
      DESCRIPTION
          "A timeout interval.  If no IGMPv2 queries are heard on this
	        interface within this timeout interval, the local router
	        will take over the Querier on the IP subnet to which this
	        interface is attached."
      DEFVAL     { 265 }
      ::= { ruijieIgmpInterfaceEntry 15 }

ruijieIgmpInterfaceLeaves OBJECT-TYPE
      SYNTAX     Counter32
      MAX-ACCESS read-only
      STATUS     current
      DESCRIPTION
          "The number of times a group membership has been removed
	        from this interface; that is, the number of times an entry
	        for this interface has been deleted from the Cache Table."
      ::= { ruijieIgmpInterfaceEntry 16 }

ruijieIgmpInterfaceAccessGroupAclName   OBJECT-TYPE    
      SYNTAX     DisplayString
      MAX-ACCESS read-write
      STATUS     current
      DESCRIPTION
          "To control the multicast groups that hosts on the subnet 
           serviced by an interface can join,Defalut value means 
           allow all multicast groups can join."
      DEFVAL {""}
      ::= { ruijieIgmpInterfaceEntry 17 }

ruijieIgmpInterfaceEnabled    OBJECT-TYPE
    SYNTAX    EnabledStatus
    MAX-ACCESS read-only
    STATUS current
    DESCRIPTION
        "Evaluates to Enable if  this interface are
         running IGMP."    
    ::= { ruijieIgmpInterfaceEntry 18 }

ruijieIgmpInterfaceHostVersion OBJECT-TYPE
    SYNTAX     Unsigned32
    MAX-ACCESS read-only
    STATUS     current
    DESCRIPTION
        "The version of Host which is running on this interface."   
    ::= { ruijieIgmpInterfaceEntry 19 }  

--
--ruijie igmp interface static Table
--
ruijieIgmpInterfaceStaticTable OBJECT-TYPE
    SYNTAX     SEQUENCE OF RuijieIgmpInterfaceStaticEntry
    MAX-ACCESS not-accessible
    STATUS     current
    DESCRIPTION
        "The (conceptual) table listing the interfaces on
         which IGMP is enabled."
    ::= {  ruijieIgmpMIBObjects 2 }

ruijieIgmpInterfaceStaticEntry OBJECT-TYPE
    SYNTAX     RuijieIgmpInterfaceStaticEntry
    MAX-ACCESS not-accessible
    STATUS     current
    DESCRIPTION
        "An entry (conceptual row) representing an
         interface on which IGMP is enabled."
    INDEX      { ruijieIgmpInterfaceStaticInterface,
                 ruijieIgmpInterfaceStaticGroupAddress }
    ::= { ruijieIgmpInterfaceStaticTable 1 }

RuijieIgmpInterfaceStaticEntry  ::= SEQUENCE {
    ruijieIgmpInterfaceStaticInterface       InterfaceIndex,
    ruijieIgmpInterfaceStaticGroupAddress    IpAddress,       
    ruijieIgmpInterfaceStaticStatus          RowStatus
    }

ruijieIgmpInterfaceStaticInterface   OBJECT-TYPE    
    SYNTAX     InterfaceIndex
    MAX-ACCESS not-accessible
    STATUS     current
    DESCRIPTION
        "The index of interface."    
    ::= { ruijieIgmpInterfaceStaticEntry 1 }

ruijieIgmpInterfaceStaticGroupAddress   OBJECT-TYPE    
    SYNTAX     IpAddress
    MAX-ACCESS not-accessible
    STATUS     current
    DESCRIPTION
        "configed the static group address, the multilayer switch 
         does not accept the packets itself, but only forwards them."    
    ::= { ruijieIgmpInterfaceStaticEntry 2 }

ruijieIgmpInterfaceStaticStatus OBJECT-TYPE
    SYNTAX     RowStatus
    MAX-ACCESS read-create
    STATUS     current
    DESCRIPTION
        "The status of this entry.  Creating the entry enables Igmp static table; 
         destroying the entry disables Igmp static table."
    ::= { ruijieIgmpInterfaceStaticEntry 3}

--
-- Notification 
--
ruijieIgmpVersionConflicted    NOTIFICATION-TYPE
    OBJECTS {
       ruijieIgmpInterfaceIfIndex,
       ruijieIgmpInterfaceVersion,
       ruijieIgmpInterfaceHostVersion
    }
    STATUS             current
    DESCRIPTION
        "A ruijieIgmpVersionErr trap signifies version is 
         different in the interface with host.This trap 
         should be generated when interface run  version 
         IGMPV1 and reported by host which run version IGMPV2.
         also when interface run version IGMPV2 and reported 
         by host which run version IGMPV1."
    ::= { ruijieIgmpTraps 1 }

-- units of conformance

ruijieIgmpMIBConformance OBJECT IDENTIFIER ::= { ruijieIgmpMIB 2 }
ruijieIgmpMIBCompliances OBJECT IDENTIFIER ::= { ruijieIgmpMIBConformance 1 }
ruijieIgmpMIBGroups      OBJECT IDENTIFIER ::= { ruijieIgmpMIBConformance 2 }

-- compliance statements
ruijieIgmpMIBCompliance MODULE-COMPLIANCE
    STATUS  current
    DESCRIPTION
        "The compliance statement for entities which implement
         the Ruijie IGMP MIB"
    MODULE  -- this module
    MANDATORY-GROUPS {
        ruijieIgmpInterfaceMIBGroup,    
        ruijieIgmpInterfaceStaticMIBGroup
        }
    ::= { ruijieIgmpMIBCompliances 1 }

-- conformance information

ruijieIgmpInterfaceMIBGroup OBJECT-GROUP
    OBJECTS {
    ruijieIgmpInterfaceQueryInterval,
	 ruijieIgmpInterfaceVersion,
	 ruijieIgmpInterfaceQuerier,
	 ruijieIgmpInterfaceQueryMaxResponseTime,
	 ruijieIgmpInterfaceQuerierUpTime,
    ruijieIgmpInterfaceQuerierExpiryTime,
    ruijieIgmpInterfaceVersion1QuerierTimer,
    ruijieIgmpInterfaceWrongVersionQueries,
    ruijieIgmpInterfaceJoins,
    ruijieIgmpInterfaceProxyIfIndex,
    ruijieIgmpInterfaceGroups,            
    ruijieIgmpInterfaceRobustness,
	 ruijieIgmpInterfaceLastMembQueryIntvl,
	 ruijieIgmpInterfaceQuerierPresentTimeout,           	
	 ruijieIgmpInterfaceLeaves,		   
	 ruijieIgmpInterfaceAccessGroupAclName,
	 ruijieIgmpInterfaceEnabled,
	 ruijieIgmpInterfaceHostVersion	 
    }
    STATUS  current
    DESCRIPTION
        "A collection of IGMP interface managment."
    ::= { ruijieIgmpMIBGroups 1 }

ruijieIgmpInterfaceStaticMIBGroup OBJECT-GROUP
    OBJECTS {
    ruijieIgmpInterfaceStaticStatus
    }
    STATUS  current
    DESCRIPTION
        "A collection of IGMP interface static managment."
    ::= { ruijieIgmpMIBGroups 2 }
    
-- -------------------------------------------------------------
-- Compliance statements
-- -------------------------------------------------------------
igmpExternCompliance MODULE-COMPLIANCE
    STATUS      current
    DESCRIPTION
        "The compliance statement for device support of IGMP
         services."
         
    MODULE
        OBJECT           ruijieIgmpInterfaceQueryInterval
        SYNTAX           Unsigned32(1..65535)
        DESCRIPTION     "The Scope is 1-65535."
         
        OBJECT           ruijieIgmpInterfaceQueryMaxResponseTime
        SYNTAX           Unsigned32(10..250)
        DESCRIPTION     "The Scope is 10-250."         
        
        OBJECT           ruijieIgmpInterfaceLastMembQueryIntvl
        SYNTAX           Unsigned32(1..655)
        DESCRIPTION     "The Scope is 1-655." 
        
        OBJECT           ruijieIgmpInterfaceQuerierPresentTimeout
        SYNTAX           Unsigned32(60..300)
        DESCRIPTION      "The Scope is 60-300."                 
                             
    ::= { ruijieIgmpMIBCompliances 2 }


END
