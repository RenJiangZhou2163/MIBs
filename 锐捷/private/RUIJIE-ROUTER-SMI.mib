-- *****************************************************************
-- RUIJIE-ROUTER-SMI.mib: Ruijie Router SMI File
-- 
-- Jan. 2005, Wuzg
--
-- Copyright (c) 2005 by Ruijie Networks Co.,Ltd.
-- All rights reserved.
-- 
-- *****************************************************************
--

RUIJIE-ROUTER-SMI DEFINITIONS ::= BEGIN

IMPORTS
        MODULE-IDENTITY,
        OBJECT-IDENTITY
                FROM SNMPv2-SMI
        products
                FROM RUIJIE-SMI;
                
router          OBJECT IDENTIFIER ::= { products 2 }

routerMib MODULE-IDENTITY
        LAST-UPDATED "200501060000Z"
        ORGANIZATION "Ruijie Networks Co.,Ltd."
        CONTACT-INFO
                " 
                Tel: 4008-111-000 

                E-mail: service@ruijie.com.cn"
        DESCRIPTION
                "The Structure of Management Information for the
                 Ruijie enterprise."
        REVISION      "200501060000Z"
        DESCRIPTION
                "Initial version of this MIB module."
        ::= { router 1 }        

ruijieRouterProducts OBJECT-IDENTITY
        STATUS  current
        DESCRIPTION
                "ruijieRouterProducts is the root OBJECT IDENTIFIER from
                which sysObjectID values are assigned for router.  Actual
                values are defined in RUIJIE-PRODUCTS-MIB."
        ::= { routerMib 1 }
        
END
