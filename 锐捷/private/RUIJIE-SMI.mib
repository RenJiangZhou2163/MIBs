-- *****************************************************************
-- RUIJIE-SMI.mib: RUIJIE-SMI
--                Ruijie Enterprise Structure of Management Information
--
-- March 2002, Wuzg
-- 
-- Copyright (c) 2002 by Ruijie Networks Co.,Ltd.
-- All rights reserved.
-- 
-- *****************************************************************
--

RUIJIE-SMI DEFINITIONS ::= BEGIN

IMPORTS
        MODULE-IDENTITY,
        OBJECT-IDENTITY,
        enterprises
                FROM SNMPv2-SMI;

-- Ruijie Snmpagent Enterprise Specific Objects
   ruijie          OBJECT IDENTIFIER ::= { enterprises 4881 }

   products        OBJECT IDENTIFIER ::= { ruijie 1 }

   switch          OBJECT IDENTIFIER ::= { products 1 }
   
switchMib MODULE-IDENTITY
        LAST-UPDATED "200203190000Z"
        ORGANIZATION "Ruijie Networks Co.,Ltd."
        CONTACT-INFO
                " 
                Tel: 4008-111-000 

                E-mail: service@ruijie.com.cn"
        DESCRIPTION
                "The Structure of Management Information for the
                 Ruijie enterprise."
        REVISION      "200203190000Z"
        DESCRIPTION
                "Initial version of this MIB module."
        ::= { switch 10 }        

ruijieSwitchProducts OBJECT-IDENTITY
        STATUS  current
        DESCRIPTION
                "ruijieSwitchProducts is the root OBJECT IDENTIFIER from
                which sysObjectID values are assigned for switch.  Actual
                values are defined in RUIJIE-PRODUCTS-MIB."
        ::= { switchMib 1 }

ruijieMgmt OBJECT-IDENTITY
        STATUS  current
        DESCRIPTION
                "ruijieMgmt is the main subtree for those functional mib."
        ::= { switchMib 2 }

ruijieAgentCapability OBJECT-IDENTITY
        STATUS  current
        DESCRIPTION
                "ruijieAgentCapability provides a root object identifier
                from which AGENT-CAPABILITIES values may be assigned."
        ::= { switchMib 3 }

ruijieModules OBJECT-IDENTITY
        STATUS  current
        DESCRIPTION
                "ruijieModules provides a root object identifier
                from which MODULE-IDENTITY values may be assigned."
        ::= { switchMib 4 }
        
ruijieExperiment OBJECT-IDENTITY
        STATUS  current
        DESCRIPTION
                "ruijieExperiment provides a root object identifier
                from which experimental mibs may be temporarily
                based.  mibs are typicially based here if they
                fall in one of two categories
                1) are IETF work-in-process mibs which have not
                been assigned a permanent object identifier by
                the IANA.
                2) are ruijie work-in-process which has not been
                assigned a permanent object identifier by the
                ruijie assigned number authority, typicially because
                the mib is not ready for deployment.

                NOTE WELL:  support for mibs in the ruijieExperiment
                subtree will be deleted when a permanent object
                identifier assignment is made."
        ::= { switchMib 5 }
 
END
