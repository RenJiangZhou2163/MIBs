-- *****************************************************************
-- RUIJIE-MPLSOAM-MIB.mib:  Ruijie MPLSOAM MIB file
--
-- $Copyright$
-- 
-- *****************************************************************
--

	RUIJIE-MPLSOAM-MIB DEFINITIONS ::= BEGIN
 
		IMPORTS
			ruijieMgmt			
				FROM RUIJIE-SMI			
			IpAddress, Integer32, Unsigned32, OBJECT-TYPE, MODULE-IDENTITY, 
			NOTIFICATION-TYPE			
				FROM SNMPv2-SMI
			DisplayString, TruthValue, TimeStamp, RowStatus, TEXTUAL-CONVENTION       
				FROM SNMPv2-TC;
	
	
--  1.3.6.1.4.1.2011.5.12.7
-- January 04, 2011 at 13:27 GMT
		-- 1.3.6.1.4.1.2011.5.12.7
		ruijieMplsOam MODULE-IDENTITY 
			LAST-UPDATED "201101041327Z"		-- January 04, 2011 at 13:27 GMT
			ORGANIZATION 
				"Ruijie Networks Co.,Ltd."
			CONTACT-INFO
                "
                Tel: 4008-111-000

                E-mail: service@ruijie.com.cn"
			DESCRIPTION 
			    "Copyright (C) Ruijie Networks.
	            This MIB module contains managed object definitions
	            for the Operation, Administration and Maintenance (OAM) as in [Y.1711].
	
	            The MPLS OAM is Operation Administration and Maintenance mechanism for MPLS network."
			::= { ruijieMgmt 93 }

		
	
--
-- Node definitions
--
	
--  Node definitions
-- 
-- 1.3.6.1.4.1.2011.5.12.7.1
		-- 1.3.6.1.4.1.2011.5.12.7.1
		ruijieMplsOamPs OBJECT IDENTIFIER ::= { ruijieMplsOam 1 }

		
--  1.3.6.1.4.1.2011.5.12.7.1.1
		-- 1.3.6.1.4.1.2011.5.12.7.1.1
		ruijieMplsOamObjects OBJECT IDENTIFIER ::= { ruijieMplsOamPs 1 }

		
--  1.3.6.1.4.1.2011.5.12.7.1.1.1
		-- 1.3.6.1.4.1.2011.5.12.7.1.1.1
		ruijieMplsOamCapability OBJECT-TYPE
			SYNTAX Unsigned32 (0..1)
			MAX-ACCESS read-write
			STATUS current
			DESCRIPTION
				"Whether OAM is enabled globally.
				1: enable;
				0: disable;
				The default value is disabled globally."
			::= { ruijieMplsOamObjects 1 }

		
--  1.3.6.1.4.1.2011.5.12.7.1.1.3
		-- 1.3.6.1.4.1.2011.5.12.7.1.1.2
		ruijieMplsOamIgrTable OBJECT-TYPE
			SYNTAX SEQUENCE OF RuijieMplsOamIgrEntry
			MAX-ACCESS not-accessible
			STATUS current
			DESCRIPTION
				"This table specifies information for configuring
                and monitoring LSP(or te tunnel)."
			::= { ruijieMplsOamObjects 2 }

		
--  1.3.6.1.4.1.2011.5.12.7.1.1.3.1
		-- 1.3.6.1.4.1.2011.5.12.7.1.1.3.1
		ruijieMplsOamIgrEntry OBJECT-TYPE
			SYNTAX RuijieMplsOamIgrEntry
			MAX-ACCESS not-accessible
			STATUS current
			DESCRIPTION
				"A row in this table represents information for configuring
				and monitoring LSP(or te tunnel). It is indexed by
            	ruijieMplsOamIgrIndex, which uniquely identifies a single LSP(or te tunnel)."
			INDEX { ruijieMplsOamIgrIndex }
			::= { ruijieMplsOamIgrTable 1 }

		
		RuijieMplsOamIgrEntry ::=
			SEQUENCE { 
				ruijieMplsOamIgrIndex
					Unsigned32,
				ruijieMplsOamIgrLspName
			    	OCTET STRING,
			    ruijieMplsOamIgrLspId
			 		Integer32,
				ruijieMplsOamIgrDetType
					INTEGER,
				ruijieMplsOamIgrDetFreq
					INTEGER,
				ruijieMplsOamIgrRevType
					INTEGER,
				ruijieMplsOamIgrRevLspName
					OCTET STRING,
				ruijieMplsOamIgrEnable
					INTEGER,
			    ruijieMplsOamIgrValid
			    	Integer32,
				ruijieMplsOamIgrAvaState
					Integer32,
				ruijieMplsOamIgrDefectType
					Integer32,
				ruijieMplsOamIgrRowStatus
					RowStatus
			 }


--  1.3.6.1.4.1.2011.5.12.7.1.1.3.1.1
		-- 1.3.6.1.4.1.2011.5.12.7.1.1.3.1.1
		ruijieMplsOamIgrIndex OBJECT-TYPE
			SYNTAX Unsigned32
			MAX-ACCESS read-only
			STATUS current
			DESCRIPTION
				"This is a unique index in the ingress table."
			::= { ruijieMplsOamIgrEntry 1 }

		
--  1.3.6.1.4.1.2011.5.12.7.1.1.3.1.6
		-- 1.3.6.1.4.1.2011.5.12.7.1.1.3.1.2
	    ruijieMplsOamIgrLspName  OBJECT-TYPE
			SYNTAX OCTET STRING
			MAX-ACCESS read-create
			STATUS current
			DESCRIPTION
		 		"The name of an LSP(or te tunnel)."
			::= { ruijieMplsOamIgrEntry 2 }


		ruijieMplsOamIgrLspId OBJECT-TYPE
			SYNTAX Integer32 (1..65535)
			MAX-ACCESS read-create
			STATUS current
			DESCRIPTION
			 	"The ID of an LSP."
			::= { ruijieMplsOamIgrEntry 3 }
			
			
--  1.3.6.1.4.1.2011.5.12.7.1.1.3.1.3
		-- 1.3.6.1.4.1.2011.5.12.7.1.1.3.1.3
		ruijieMplsOamIgrDetType OBJECT-TYPE     
			SYNTAX INTEGER {                                            
			           cv(1),
                       ffd(2)
            }
			MAX-ACCESS read-create
			STATUS current
			DESCRIPTION
				"The OAM defect detection function is based on the periodic transmission 
				of CV or FFD packets from ingress to egress of an LSP. Each CV and FFD packet 
				carries a unique TTSI (Trail Termination Source Identifier), which is composed 
				of the source LSR identifier, and the LSP identifier.
				1: CV;
				2: FFD."
			::= { ruijieMplsOamIgrEntry 4 }

		
--  1.3.6.1.4.1.2011.5.12.7.1.1.3.1.4
		-- 1.3.6.1.4.1.2011.5.12.7.1.1.3.1.4
		ruijieMplsOamIgrDetFreq OBJECT-TYPE
			SYNTAX INTEGER {                   
			    cv1000ms(0),                     
				ffd50ms2(1),
				ffd100ms3(2),
				ffd200ms4(3),
				ffd500ms5(4)
			}
			MAX-ACCESS read-create
			STATUS current
			DESCRIPTION
				"For CV: the frequency is 1s.
				For FFD: the frequency is one of 
				50ms,100ms,200ms,500ms.
				0: 1s(only for cv);
				1: 50ms;
				2: 100ms;
				3: 200ms;
				4: 500ms."
			::= { ruijieMplsOamIgrEntry 5 }

		
--  1.3.6.1.4.1.2011.5.12.7.1.1.3.1.5
		-- 1.3.6.1.4.1.2011.5.12.7.1.1.3.1.5
		ruijieMplsOamIgrRevType OBJECT-TYPE
			SYNTAX INTEGER {  
			     private(1),
			     share(2)
			}   		
			MAX-ACCESS read-create
			STATUS current
			DESCRIPTION
				"The BDI flow is injected on a return path (such as a return LSP) to inform the upstream LSR
				(which is the source of the forward LSP) that there is a defect at the downstream LSP's LSR sink
				point.BDI and loopback transactions use a return path. A return path could be:
				1: A dedicated return LSP;
				2: A shared return LSP, which is shared between many forward LSPs."
			::= { ruijieMplsOamIgrEntry 6 }

		
		-- 1.3.6.1.4.1.2011.5.12.7.1.1.3.1.6
		ruijieMplsOamIgrRevLspName OBJECT-TYPE
			SYNTAX OCTET STRING
			MAX-ACCESS read-create
			STATUS current
			DESCRIPTION
				"The name of a return LSP."
			::= { ruijieMplsOamIgrEntry 7 }

		
--  1.3.6.1.4.1.2011.5.12.7.1.1.3.1.15
		-- 1.3.6.1.4.1.2011.5.12.7.1.1.3.1.9
		ruijieMplsOamIgrEnable OBJECT-TYPE
			SYNTAX INTEGER {
			    disable(0),
			    enable(1)		
			}
			MAX-ACCESS read-create
			STATUS current
			DESCRIPTION
				"The detection of OAM is enabled/disabled on the ingress of an LSP.
				0: The OAM detection is disabled on the ingress;
				1: The OAM detection is enabled on the ingress."
			::= { ruijieMplsOamIgrEntry 8 }

		
		-- 1.3.6.1.4.1.2011.5.12.7.1.1.3.1.10
		ruijieMplsOamIgrValid OBJECT-TYPE
			SYNTAX Integer32 (0..1)
			MAX-ACCESS read-only
			STATUS current
			DESCRIPTION
				"0: stop detection of OAM;
				 1: start detection of OAM."
			::= { ruijieMplsOamIgrEntry 9 }

		
--  1.3.6.1.4.1.2011.5.12.7.1.1.3.1.16
		-- 1.3.6.1.4.1.2011.5.12.7.1.1.3.1.11
		ruijieMplsOamIgrAvaState OBJECT-TYPE
			SYNTAX Integer32 (0..1)
			MAX-ACCESS read-only
			STATUS current
			DESCRIPTION
				"If the LSP Timer (T3) expires, then the LSP enters the 
				Unavailable state. The start point of the Unavailable state 
				is deemed to be at the entry into the LSP defect state.
				An LSP re-enters the Available state after first exiting the LSP defect state. 
				0: available state;
				1: unavailable state."
			::= { ruijieMplsOamIgrEntry 10 }

		
--  1.3.6.1.4.1.2011.5.12.7.1.1.3.1.17
		-- 1.3.6.1.4.1.2011.5.12.7.1.1.3.1.12
		ruijieMplsOamIgrDefectType OBJECT-TYPE
			SYNTAX Integer32 (0..7)
			MAX-ACCESS read-only
			STATUS current
			DESCRIPTION
				"There are 6 types of defect in total, among which there are 4 MPLS layer user-plane
				defects(i.e., dLOCV, dTTSI_Mismatch, dTTSI_Mismerge and dExcess), 1 Server layer defect,
				1 peer maintenance entity defect:
				0: no defect;
				1: dServer, Any server layer defect arising below the MPLS layer network;
				2: dPeerMe, Any peer maintenance entity defect arising outside the MPLS subnetwork;
				3: dLOCV, Loss of Connectivity Verification defect;
				4: dTTSI-Mismatch, Trail Termination Source Identifier Mismatch defect;
				5: dTTSI-Mismerge, Trail Termination Source Identifier Mismerge defect;
				6: dExcess, Excess rate of CV/FFD defect;
				7: dUnknown, Unknown defect in the MPLS network."
			::= { ruijieMplsOamIgrEntry 11 }

		
--  1.3.6.1.4.1.2011.5.12.7.1.1.3.1.18
		-- 1.3.6.1.4.1.2011.5.12.7.1.1.3.1.13
		ruijieMplsOamIgrRowStatus OBJECT-TYPE
			SYNTAX RowStatus
			MAX-ACCESS read-create
			STATUS current
			DESCRIPTION
				"It is used to create and
                 		delete a row in this table."
			::= { ruijieMplsOamIgrEntry 12 }

		
		-- 1.3.6.1.4.1.2011.5.12.7.1.1.3
		ruijieMplsOamEgrTable OBJECT-TYPE
			SYNTAX SEQUENCE OF RuijieMplsOamEgrEntry
			MAX-ACCESS not-accessible
			STATUS current
			DESCRIPTION
				"This table specifies information for configuring
                and monitoring LSP(or te tunnel)."
			::= { ruijieMplsOamObjects 3 }

		
		-- 1.3.6.1.4.1.2011.5.12.7.1.1.4.1
		ruijieMplsOamEgrEntry OBJECT-TYPE
			SYNTAX RuijieMplsOamEgrEntry
			MAX-ACCESS not-accessible
			STATUS current
			DESCRIPTION
				"A row in this table represents information for configuring
				and monitoring LSP(or te tunnel). It is indexed by
            	ruijieMplsOamEgrIndex, which uniquely identifies a single LSP(or te tunnel)."
			INDEX { ruijieMplsOamEgrIndex }
			::= { ruijieMplsOamEgrTable 1 }

		
		RuijieMplsOamEgrEntry ::=
			SEQUENCE {
				ruijieMplsOamEgrIndex
					Unsigned32,
				ruijieMplsOamEgrLspName
					OCTET STRING,
				ruijieMplsOamEgrLsrId
					IpAddress,
				ruijieMplsOamEgrLspId
			 		Integer32,
				ruijieMplsOamEgrDetType
					INTEGER,
				ruijieMplsOamEgrDetFreq
					INTEGER,
				ruijieMplsOamEgrRevType
					INTEGER,
			 	ruijieMplsOamEgrRevLspName
			 		OCTET STRING,
				ruijieMplsOamEgrAutoEn
					INTEGER,
				ruijieMplsOamEgrAutoOvertime
					Integer32,
				ruijieMplsOamEgrBDIFreq
					INTEGER,
				ruijieMplsOamEgrEnable
					INTEGER,
				ruijieMplsOamEgrValid
					INTEGER,
				ruijieMplsOamEgrAvaState
					Integer32,
				ruijieMplsOamEgrDefectType
					Integer32,
				ruijieMplsOamEgrRowStatus
					RowStatus
			 }

		-- 1.3.6.1.4.1.2011.5.12.7.1.1.4.1.1
		ruijieMplsOamEgrIndex OBJECT-TYPE
			SYNTAX Unsigned32
			MAX-ACCESS read-only
			STATUS current
			DESCRIPTION
				"This is a unique index in the egress table."
			::= { ruijieMplsOamEgrEntry 1 }
			
			
		-- 1.3.6.1.4.1.2011.5.12.7.1.1.4.1.2
		ruijieMplsOamEgrLspName OBJECT-TYPE
			SYNTAX OCTET STRING
			MAX-ACCESS read-create
			STATUS current
			DESCRIPTION
				"The name of static LSP at egress."
			::= { ruijieMplsOamEgrEntry 2 }

		
		-- 1.3.6.1.4.1.2011.5.12.7.1.1.4.1.3
		ruijieMplsOamEgrLsrId OBJECT-TYPE
			SYNTAX IpAddress
			MAX-ACCESS read-create
			STATUS current
			DESCRIPTION
				"The Ingress LSR ID of an LSP."
			::= { ruijieMplsOamEgrEntry 3 }

		
		-- 1.3.6.1.4.1.2011.5.12.7.1.1.4.1.4
		   ruijieMplsOamEgrLspId OBJECT-TYPE
			SYNTAX Integer32 (1..65535)
			MAX-ACCESS read-create
			STATUS current
			DESCRIPTION
			 	"The ID of an LSP."
			::= { ruijieMplsOamEgrEntry 4 }

		
		-- 1.3.6.1.4.1.2011.5.12.7.1.1.4.1.5
		ruijieMplsOamEgrDetType OBJECT-TYPE
			SYNTAX INTEGER {
			       adaptability(0),
			       cv(1),
			       ffd(2)
	     	}
			MAX-ACCESS read-create
			STATUS current
			DESCRIPTION
				"0: adaptability;
				 1: CV;
				 2: FFD."
			::= { ruijieMplsOamEgrEntry 5 }

		
		-- 1.3.6.1.4.1.2011.5.12.7.1.1.4.1.6
		ruijieMplsOamEgrDetFreq OBJECT-TYPE
			SYNTAX INTEGER{ 
			    cv1000ms(0),                     
				ffd50ms2(1),
				ffd100ms3(2),
				ffd200ms4(3),
				ffd500ms5(4),
			 	invalid6(5)      
			}
			MAX-ACCESS read-create
			STATUS current
			DESCRIPTION
				"0: 1000ms(only for cv);
			 	 1: 50ms;
				 2: 100ms;
				 3: 200ms;
				 4: 500ms;
				 5: invalid."
			::= { ruijieMplsOamEgrEntry 6 }

		
		-- 1.3.6.1.4.1.2011.5.12.7.1.1.4.1.7
		ruijieMplsOamEgrRevType OBJECT-TYPE
			SYNTAX INTEGER {
			     private(0),
			     share(1) 
		    }
			MAX-ACCESS read-create
			STATUS current
			DESCRIPTION
				"The BDI flow is injected on a return path (such as a return LSP) to inform the upstream LSR
				(which is the source of the forward LSP) that there is a defect at the downstream LSP's LSR sink
				point.BDI and loopback transactions use a return path. A return path could be:
				1: A dedicated return LSP;
				2: A shared return LSP, which is shared between many forward LSPs."
			::= { ruijieMplsOamEgrEntry 7 }

		
		-- 1.3.6.1.4.1.2011.5.12.7.1.1.4.1.8
	 --	ruijieMplsOamEgrRevTunnName OBJECT-TYPE
		ruijieMplsOamEgrRevLspName OBJECT-TYPE
			SYNTAX OCTET STRING
			MAX-ACCESS read-create
			STATUS current
			DESCRIPTION
				"The name of a return LSP."
			::= { ruijieMplsOamEgrEntry 8 }

		
		-- 1.3.6.1.4.1.2011.5.12.7.1.1.4.1.9
		ruijieMplsOamEgrAutoEn OBJECT-TYPE
			SYNTAX INTEGER { 
			       disable(0),
				   enable(1)
            }
			MAX-ACCESS read-create
			STATUS current
			DESCRIPTION
				"The adaptability is enabled/disabled.
				0: disable;
				1: enable."
			::= { ruijieMplsOamEgrEntry 9 }

		
		-- 1.3.6.1.4.1.2011.5.12.7.1.1.4.1.10
		ruijieMplsOamEgrAutoOvertime OBJECT-TYPE
			SYNTAX Integer32 (0..255)
			MAX-ACCESS read-create
			STATUS current
			DESCRIPTION
				"The wait-time of adaptability."
			::= { ruijieMplsOamEgrEntry 10 }

		
		-- 1.3.6.1.4.1.2011.5.12.7.1.1.4.1.11
		ruijieMplsOamEgrBDIFreq OBJECT-TYPE
			SYNTAX INTEGER { 
			    cv1000ms(0),
				ffd50ms2(1),
				ffd100ms3(2),
				ffd200ms4(3),
				ffd500ms5(4)         
            }
			MAX-ACCESS read-create
			STATUS current
			DESCRIPTION
				"For CV: the frequency is 1s.
				For FFD: the frequency is one of 
				50ms,100ms,200ms,500ms.
				0: 1000ms(only for cv);
				1: 50ms;
				2: 100ms;
				3: 200ms;
				4: 500ms."
			::= { ruijieMplsOamEgrEntry 11 }

		
		-- 1.3.6.1.4.1.2011.5.12.7.1.1.4.1.12
		ruijieMplsOamEgrEnable OBJECT-TYPE
			SYNTAX INTEGER {
			    disable(0),
			    enable(1)		
			}
			MAX-ACCESS read-create
			STATUS current
			DESCRIPTION
				"The detection of OAM is enabled/disabled on the egress of an LSP.
				0: The OAM detection is disabled on the egress;
				1: The OAM detection is enabled on the egress."
			::= { ruijieMplsOamEgrEntry 12 }

		
		-- 1.3.6.1.4.1.2011.5.12.7.1.1.4.1.13
		ruijieMplsOamEgrValid OBJECT-TYPE
			SYNTAX INTEGER { 
				stop(1),
			    start(2)
			}
			MAX-ACCESS read-only
			STATUS current
			DESCRIPTION
				"1: stop detection of OAM;
				 2: start detection of OAM."
			::= { ruijieMplsOamEgrEntry 13 }

		
		-- 1.3.6.1.4.1.2011.5.12.7.1.1.4.1.14
		ruijieMplsOamEgrAvaState OBJECT-TYPE
			SYNTAX Integer32 (0..1)
			MAX-ACCESS read-only
			STATUS current
			DESCRIPTION
				"If the LSP Timer (T1) expires, then the LSP enters the 
				Unavailable state. The start point of the Unavailable state 
				is deemed to be at the entry into the LSP defect state.
				An LSP re-enters the Available state after the LSP Defect State.
				first exists.
				T1 defines the length of time the LSP is in the Defect state 
				before declaring an LSP Unavailable or returning to defect 
				free state
				0: available state;
				1: unavailable state."
			::= { ruijieMplsOamEgrEntry 14 }

		
		-- 1.3.6.1.4.1.2011.5.12.7.1.1.4.1.15
		ruijieMplsOamEgrDefectType OBJECT-TYPE
			SYNTAX Integer32 (0..7)
			MAX-ACCESS read-only
			STATUS current
			DESCRIPTION
				"There are 6 types of defect in total, among which there are 4 MPLS layer user-plane
				defects(i.e., dLOCV, dTTSI_Mismatch, dTTSI_Mismerge and dExcess), 1 Server layer defect,
				1 peer maintenance entity defect:
				0: no defect;
				1: dServer, Any server layer defect arising below the MPLS layer network;
				2: dPeerMe, Any peer maintenance entity defect arising outside the MPLS subnetwork;
				3: dLOCV, Loss of Connectivity Verification defect;
				4: dTTSI-Mismatch, Trail Termination Source Identifier Mismatch defect;
				5: dTTSI-Mismerge, Trail Termination Source Identifier Mismerge defect;
				6: dExcess, Excess rate of CV/FFD defect;
				7: dUnknown, Unknown defect in the MPLS network."
			::= { ruijieMplsOamEgrEntry 15 }

		
		-- 1.3.6.1.4.1.2011.5.12.7.1.1.4.1.16
		ruijieMplsOamEgrRowStatus OBJECT-TYPE
            SYNTAX RowStatus
            MAX-ACCESS read-create
			STATUS current
			DESCRIPTION
				"It is used to create and
                 delete a row in this table."
			::= { ruijieMplsOamEgrEntry 16 }

				
		-- 1.3.6.1.4.1.2011.5.12.7.1.1.5
		ruijieMplsOamTrapOpen OBJECT-TYPE
			SYNTAX Unsigned32 (0..1)
			MAX-ACCESS read-write
			STATUS current
			DESCRIPTION
				"0: disable                 
				 1: enable"                
			::= { ruijieMplsOamObjects 4 }

		
--  1.3.6.1.4.1.2011.5.12.7.1.3
		-- 1.3.6.1.4.1.2011.5.12.7.1.2
		ruijieMplsOamNotifications OBJECT IDENTIFIER ::= { ruijieMplsOamPs 2 }

		
--  1.3.6.1.4.1.2011.5.12.7.1.3.1
		-- 1.3.6.1.4.1.2011.5.12.7.1.2.1
		ruijieMplsOamIgrLSPOutDefect NOTIFICATION-TYPE
			OBJECTS { ruijieMplsOamIgrIndex, ruijieMplsOamIgrLspName, ruijieMplsOamIgrAvaState, ruijieMplsOamIgrDefectType }
			STATUS current
			DESCRIPTION 
				"This notification is generated when the LSP exits 
				defect state at the LSP ingress."
			::= { ruijieMplsOamNotifications 1 }

		
--  1.3.6.1.4.1.2011.5.12.7.1.3.2
		-- 1.3.6.1.4.1.2011.5.12.7.1.2.2
		ruijieMplsOamIgrLSPInDefect NOTIFICATION-TYPE
			OBJECTS { ruijieMplsOamIgrIndex, ruijieMplsOamIgrLspName, ruijieMplsOamIgrAvaState, ruijieMplsOamIgrDefectType }
			STATUS current
			DESCRIPTION 
				"This notification is generated when the LSP enters
				defect state at the LSP ingress."
			::= { ruijieMplsOamNotifications 2 }

		
--  1.3.6.1.4.1.2011.5.12.7.1.3.3
		-- 1.3.6.1.4.1.2011.5.12.7.1.2.3
		ruijieMplsOamIgrLSPAva NOTIFICATION-TYPE
			OBJECTS { ruijieMplsOamIgrIndex, ruijieMplsOamIgrLspName, ruijieMplsOamIgrAvaState, ruijieMplsOamIgrDefectType }
			STATUS current
			DESCRIPTION 
				"This notification is generated when the LSP enters
				available state at the LSP ingress."
			::= { ruijieMplsOamNotifications 3 }

		
--  1.3.6.1.4.1.2011.5.12.7.1.3.4
		-- 1.3.6.1.4.1.2011.5.12.7.1.2.4
		ruijieMplsOamIgrLSPUnAva NOTIFICATION-TYPE
			OBJECTS { ruijieMplsOamIgrIndex, ruijieMplsOamIgrLspName, ruijieMplsOamIgrAvaState, ruijieMplsOamIgrDefectType }
			STATUS current
			DESCRIPTION 
				"This notification is generated when the LSP enters
				unavailable state at the LSP ingress."
			::= { ruijieMplsOamNotifications 4 }

		
		-- 1.3.6.1.4.1.2011.5.12.7.1.2.5
		ruijieMplsOamEgrLSPOutDefect NOTIFICATION-TYPE
			OBJECTS { ruijieMplsOamEgrIndex, ruijieMplsOamEgrLspName, ruijieMplsOamEgrLsrId, ruijieMplsOamEgrLspId, ruijieMplsOamEgrAvaState, ruijieMplsOamEgrDefectType
				 }
			STATUS current
			DESCRIPTION 
				"This notification is generated when the LSP exits
				defect state at the LSP egress."
			::= { ruijieMplsOamNotifications 5 }

		
		-- 1.3.6.1.4.1.2011.5.12.7.1.2.6
		ruijieMplsOamEgrLSPInDefect NOTIFICATION-TYPE
		 	OBJECTS { ruijieMplsOamEgrIndex, ruijieMplsOamEgrLspName, ruijieMplsOamEgrLsrId, ruijieMplsOamEgrLspId, ruijieMplsOamEgrAvaState, ruijieMplsOamEgrDefectType
				 }
			STATUS current
			DESCRIPTION 
				"This notification is generated when the LSP enters
				defect state at the LSP egress."
			::= { ruijieMplsOamNotifications 6 }

		
		-- 1.3.6.1.4.1.2011.5.12.7.1.2.7
		ruijieMplsOamEgrLSPAva NOTIFICATION-TYPE
		 	OBJECTS { ruijieMplsOamEgrIndex, ruijieMplsOamEgrLspName, ruijieMplsOamEgrLsrId, ruijieMplsOamEgrLspId, ruijieMplsOamEgrAvaState, ruijieMplsOamEgrDefectType
				 }
			STATUS current
			DESCRIPTION 
				"This notification is generated when the LSP enters
				available state at the LSP egress."
			::= { ruijieMplsOamNotifications 7 }

		
		-- 1.3.6.1.4.1.2011.5.12.7.1.2.8
		ruijieMplsOamEgrLSPUnAva NOTIFICATION-TYPE
			OBJECTS { ruijieMplsOamEgrIndex, ruijieMplsOamEgrLspName, ruijieMplsOamEgrLsrId, ruijieMplsOamEgrLspId, ruijieMplsOamEgrAvaState, ruijieMplsOamEgrDefectType
				 }
			STATUS current
			DESCRIPTION 
				"This notification is generated when the LSP enters
				unavailable state at the LSP egress."
			::= { ruijieMplsOamNotifications 8 }

		
		-- 1.3.6.1.4.1.2011.5.12.7.1.2.9
		ruijieMplsOamEgrFirstPkt NOTIFICATION-TYPE
			OBJECTS { ruijieMplsOamEgrIndex, ruijieMplsOamEgrLspName, ruijieMplsOamEgrLsrId, ruijieMplsOamEgrLspId, ruijieMplsOamEgrDetType, ruijieMplsOamEgrDetFreq
				 }
			STATUS current
			DESCRIPTION 
				"If adaptability is enabled, this notification is generated when 
				the LSP egress receives the first CV/FFD packet."
			::= { ruijieMplsOamNotifications 9 }

		
		-- 1.3.6.1.4.1.2011.5.12.7.1.2.10
		ruijieMplsOamEgrAutoProFDI NOTIFICATION-TYPE
		 	OBJECTS { ruijieMplsOamEgrIndex, ruijieMplsOamEgrLspName, ruijieMplsOamEgrLsrId, ruijieMplsOamEgrLspId, ruijieMplsOamEgrEnable 
		         }
			STATUS current
			DESCRIPTION 
				"The FDI is sent downstream from the upstream node in an LSP 
				to inform the downstream end of an LSP of a upstream defect.
				It is also generated when the adaptability is enabled."
			::= { ruijieMplsOamNotifications 10 }
			
			
		ruijieMplsPsObjects OBJECT IDENTIFIER ::= { ruijieMplsOamPs 3 }

        
        ruijieMplsPsTable OBJECT-TYPE
            SYNTAX SEQUENCE OF RuijieMplsPsEntry
            MAX-ACCESS not-accessible
            STATUS current
            DESCRIPTION
                "This table specifies information for configuring
                and monitoring LSP protection group(or te tunnel protection group)."
            ::= { ruijieMplsPsObjects 1 }

        
        ruijieMplsPsEntry OBJECT-TYPE
            SYNTAX RuijieMplsPsEntry
            MAX-ACCESS not-accessible
            STATUS current
            DESCRIPTION
                "A row in this table represents information for configuring
				and monitoring LSP protection group(or te tunnel protection group). It is indexed by
            	ruijieMplsPsIndex, which uniquely identifies a single LSP protection group(or te tunnel protection group)."
            INDEX { ruijieMplsPsIndex }
            ::= { ruijieMplsPsTable 1 }

        
        RuijieMplsPsEntry ::=
            SEQUENCE { 
                ruijieMplsPsIndex
                    Unsigned32,
                ruijieMplsPsGroupName
                	OCTET STRING,
                ruijieMplsPsType
                    Integer32,
                ruijieMplsPsWorkLspName
                    OCTET STRING,
                ruijieMplsPsWorkLspId
                    Integer32,
                ruijieMplsPsProtectLspName
                    OCTET STRING,
                ruijieMplsPsProtectLspId
                    Integer32,
                ruijieMplsPsRevertiveMode
                    Integer32,
                ruijieMplsPsWTR
                    Integer32,
                ruijieMplsPsHoldOff
                    Integer32,
                ruijieMplsPsSwitchCondition
                    Integer32,
                ruijieMplsPsWorkLspState
                    Integer32,
                ruijieMplsPsProtLspState
                    Integer32,
                ruijieMplsPsSwitchResult
                    Integer32,
                ruijieMplsPsRowStatus
                    RowStatus
             }


        ruijieMplsPsIndex OBJECT-TYPE
            SYNTAX Unsigned32
            MAX-ACCESS read-only
            STATUS current
            DESCRIPTION
                "This is a unique index in the protection group table."
            ::= { ruijieMplsPsEntry 1 }


        ruijieMplsPsGroupName OBJECT-TYPE
            SYNTAX OCTET STRING
            MAX-ACCESS read-only
            STATUS current
            DESCRIPTION
                "The protection group name."
            ::= { ruijieMplsPsEntry 2 }
            
        
        ruijieMplsPsType OBJECT-TYPE
            SYNTAX Integer32 (1..4)
            MAX-ACCESS read-only
            STATUS current
            DESCRIPTION
                "The MPLS PS architecture can be a 1+1 type, a 1:1 type, a shared mesh type,
				or a packet 1+1 type.
				1. In the 1+1 architecture type, a protection LSP is dedicated to each working
				   LSP with the working LSP bridged onto the protection LSP at the source of
				   the protection domain.
				2. In the 1:1 architecture type, a protection LSP is dedicated to each working LSP.
				3. In the shared mesh architecture type, possible sharing of protection capacity
				   between disjoint link, node, or SRG failures in the network is achieved while
				   guaranteeing recovery from a single failure. For each link in the network, it
				   keeps track of all the working paths whose traffic will be switched onto it
				   after a given failure. By keeping track of this, it only needs to reserve the
				   maximum of the protection capacity required to protect a single failure in the
				   network.
				4. In the packet 1+1 architecture type, the traffic is transmitted simultaneously
				   onto two possibly disjoint routed LSPs to the sink of the protection domain. 
				   Each pair of duplicate transmitted packets is assigned the same identifier(sequence number)
				   but distinct from the other pairs of duplicate packets. At the sink of the 
				   protection domain, packet level selection mechanism is employed to select one
				   of the two possibly received copies of each packet. The following list provides
				   principles for MPLS protection architectures and mechanisms development.
				1: 1:1 protection switching;
				2: 1+1 protection switching;
				3: shared mesh protection swiching;
				4: packet 1+1 protection switching."
            ::= { ruijieMplsPsEntry 3 }

        
        ruijieMplsPsWorkLspName OBJECT-TYPE
            SYNTAX OCTET STRING
            MAX-ACCESS read-only
            STATUS current
            DESCRIPTION
                "The name of work-lsp(or work-tunnel)."
            ::= { ruijieMplsPsEntry 4 }

        
        ruijieMplsPsWorkLspId OBJECT-TYPE
            SYNTAX Integer32 (1..65535)
            MAX-ACCESS read-only
            STATUS current
            DESCRIPTION
                "The ID of work-lsp(or work-tunnel)."
            ::= { ruijieMplsPsEntry 5 }

        
        ruijieMplsPsProtectLspName OBJECT-TYPE
            SYNTAX OCTET STRING
            MAX-ACCESS read-only
            STATUS current
            DESCRIPTION
                "The name of protect-lsp."
            ::= { ruijieMplsPsEntry 6 }

        
        ruijieMplsPsProtectLspId OBJECT-TYPE
            SYNTAX Integer32 (1..65535)
            MAX-ACCESS read-only
            STATUS current
            DESCRIPTION
                "The ID of protect-lsp(or protect-tunnel)."
            ::= { ruijieMplsPsEntry 7 }

        
        ruijieMplsPsRevertiveMode OBJECT-TYPE
            SYNTAX Integer32 (1..2)
            MAX-ACCESS read-only
            STATUS current
            DESCRIPTION
                "The protection group revertive mode can be non-revertive and revertive
				protection switching.
				1. In revertive mode of operation, under conditions where working traffic
				   is being transmitted via the protection LSP and when the working LSP
				   is restored, if local protection switching requests have been previously
				   active and now become inactive, a local wait to restore state is entered.
				2. When the failed LSP is no longer in an SF condition, and no other
				   externally initiated commands are present, a no request state is entered.
				   During this state, switching does not occur.
				1: revertive;
				2: non-revertive."
            ::= { ruijieMplsPsEntry 8 }

        
        ruijieMplsPsWTR OBJECT-TYPE
            SYNTAX Integer32 (0..60)
            MAX-ACCESS read-only
            STATUS current
            DESCRIPTION
                "Wait to restore is only applicable for the revertive mode and
				applies to a working LSP. It prevents reversion back to select
				the working LSP until the wait to restore timer has expired.
				The wait to restore time may be configured by the operator
				in 1 minute steps between 1 and 30 minutes; the default value is
				12 minutes."
            ::= { ruijieMplsPsEntry 9 }

        
        ruijieMplsPsHoldOff OBJECT-TYPE
            SYNTAX Integer32 (0..100)
            MAX-ACCESS read-only
            STATUS current
            DESCRIPTION
                "In general, if lower layer(e.g., SDH or optical) protection
				mechanisms are being utilized in conjunction with MPLS layer
				protection mechanisms, then the lower layers should have a
				chance to restore working traffic before the MPLS layer initiates
				protection actions(e.g., using a hold-off timer). The objective
				here is to avoid duplicated protection switching in different
				layer networks. The default value is 0ms; the maximum value is 10s."
            ::= { ruijieMplsPsEntry 10 }

        
        ruijieMplsPsSwitchCondition OBJECT-TYPE
            SYNTAX Integer32 (1..9)
            MAX-ACCESS read-only
            STATUS current
            DESCRIPTION
                "The following switch initiation criteria exist:
				1. an externally initiated command(clear, lockout of protection, 
				   forced switch, manual switch);
				2. an automatically initiated command(signal fail) associated with
				   a protection domain; or
				3. a state (wait to restore, no request) of the protection switching
				   function.
				The followings are switch request priority:
				1. clear: This command clears all of the externally initiated switch commands
				   listed below.
				2. lockout of protection(LoP): Fix the selector position on the working LSP.
				   Prevents the selector from switching to the protection LSP when it is
				   selecting the working LSP. Switches the selector from the protection to
				   the working LSP when it is selecting the protection LSP.
				3. forced switch(FS) for working LSP: Switches the selector from the working
				   LSP to the protection LSP (unless a higher priority switch request(i.e., LoP)
				   is in effect).
				4. signal fail: Signal fail(SF) is declared when the source of the protection
				   domain enters the LSP defect state by receiving a BDI packet from the return
				   LSP or out of band.
				5. manual switch(MS): Switches the selector from the working LSP to the
				   protection LSP (unless an equal or higher priority switch request
				   (i.e., LoP, FS, SF or MS) is in effect). Switches the selector from
				   the protection LSP to the working LSP (unless an equal or higher
				   priority switch request(i.e., LoP, FS, SF or MS) is in effect).
				6. WTR: Wait to restore is only applicable for the revertive mode and applies
				   to a working LSP.
				7. no request."
            ::= { ruijieMplsPsEntry 11 }

        
        ruijieMplsPsWorkLspState OBJECT-TYPE
            SYNTAX Integer32 (1..2)
            MAX-ACCESS read-only
            STATUS current
            DESCRIPTION
                "The state of working lsp state lists below:
                1: defect state;
                2: non-defect state."
            ::= { ruijieMplsPsEntry 12 }

        
        ruijieMplsPsProtLspState OBJECT-TYPE
            SYNTAX Integer32 (1..2)
            MAX-ACCESS read-only
            STATUS current
            DESCRIPTION
                "The state of protection lsp state lists below:
                1: defect state;
                2: non-defect state."
            ::= { ruijieMplsPsEntry 13 }

        
        ruijieMplsPsSwitchResult OBJECT-TYPE
            SYNTAX Integer32 (1..2)
            MAX-ACCESS read-only
            STATUS current
            DESCRIPTION
                "Which lsp is user traffic being transmitted:
                1: working-lsp;
                2: protection-lsp."
            ::= { ruijieMplsPsEntry 14 }

                
        ruijieMplsPsRowStatus OBJECT-TYPE
            SYNTAX RowStatus
            MAX-ACCESS read-only
            STATUS current
            DESCRIPTION
                "It is used to create and
                delete a row in this table.
                1: active;
                2: notInService;
                3: notReady;
                4: createAndGo;
                5: createAndWait;
                6: destroy."
            ::= { ruijieMplsPsEntry 15 }

        
        ruijieMplsPsTrapOpen OBJECT-TYPE
            SYNTAX Unsigned32 (1..2)
            MAX-ACCESS read-write
            STATUS current
            DESCRIPTION
                "1:enable;
                2:disable."
            ::= { ruijieMplsPsObjects 2 }

        
        ruijieMplsPsNotifications OBJECT IDENTIFIER ::= { ruijieMplsOamPs 4 }

        
        ruijieMplsPsSwitchPtoW NOTIFICATION-TYPE
            OBJECTS { ruijieMplsPsWorkLspName, ruijieMplsPsWorkLspId, ruijieMplsPsProtectLspName, ruijieMplsPsProtectLspId, ruijieMplsPsSwitchResult
                 }
            STATUS current
            DESCRIPTION 
                "This notification is generated when switching traffic from
                protection-lsp to working-lsp."
            ::= { ruijieMplsPsNotifications 1 }

        
        ruijieMplsPsSwitchWtoP NOTIFICATION-TYPE
            OBJECTS { ruijieMplsPsWorkLspName, ruijieMplsPsWorkLspId, ruijieMplsPsProtectLspName, ruijieMplsPsProtectLspId, ruijieMplsPsSwitchResult
                 }
            STATUS current
            DESCRIPTION 
                "This notification is generated when switching traffic from woking-lsp
                to protection-lsp."
            ::= { ruijieMplsPsNotifications 2 }

        
        ruijieMplsOamPsConformance OBJECT IDENTIFIER ::= { ruijieMplsOamPs 5 }

        
        ruijieMplsOamPsCompliances OBJECT IDENTIFIER ::= { ruijieMplsOamPsConformance 1 }

        
        ruijieMplsOamPsGroupCompliance MODULE-COMPLIANCE
            STATUS current
            DESCRIPTION 
                "The compliance statement for mpls oam protection group."
            MODULE -- this module
             	MANDATORY-GROUPS { ruijieMplsPsGroup }
            ::= { ruijieMplsOamPsCompliances 1 }

        
        ruijieMplsOamPsGroups OBJECT IDENTIFIER ::= { ruijieMplsOamPsConformance 2 }  				
        
        ruijieMplsPsGroup OBJECT-GROUP
            OBJECTS {
            	ruijieMplsPsGroupName,
                ruijieMplsPsType,
                ruijieMplsPsWorkLspName,
                ruijieMplsPsWorkLspId,
                ruijieMplsPsProtectLspName,
                ruijieMplsPsProtectLspId,
                ruijieMplsPsRevertiveMode,
                ruijieMplsPsWTR,
                ruijieMplsPsHoldOff,
                ruijieMplsPsSwitchCondition,
                ruijieMplsPsWorkLspState, 
                ruijieMplsPsProtLspState,
                ruijieMplsPsSwitchResult,
                ruijieMplsPsRowStatus,
                ruijieMplsPsIndex
                }
            STATUS current
            DESCRIPTION 
                "The compliance statement for mpls oam protection group management."
            ::= { ruijieMplsOamPsGroups 1 }

        
        ruijieMplsPsNotificationGroup NOTIFICATION-GROUP
            NOTIFICATIONS { ruijieMplsPsSwitchPtoW, ruijieMplsPsSwitchWtoP }
            STATUS current
            DESCRIPTION 
                "Description."
			::= { ruijieMplsOamPsGroups 2 }
		
	
	END

--
-- RUIJIE-MPLSOAM-MIB.mib
--
