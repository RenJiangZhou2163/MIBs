-- *******************************************************************
-- RUIJIE-IP-PRIVATE-MIB.mib : Ruijie AC IP MIB file
-- May 2010, humin; April 2019, zhangzh
--
-- Copyright (c) 2009 by Ruijie Networks Co.,Ltd.
-- All rights reserved.
-- *******************************************************************
--
RUIJIE-IP-PRIVATE-MIB DEFINITIONS ::= BEGIN

IMPORTS
        IpAddress,
        OBJECT-TYPE,
        MODULE-IDENTITY,
        NOTIFICATION-TYPE,
        Counter32
                        FROM SNMPv2-SMI
		Ipv6Address
		        FROM IPV6-TC
        IfIndex
                FROM RUIJIE-TC
        MacAddress,
        DisplayString,
        RowStatus
                FROM SNMPv2-TC
        MODULE-COMPLIANCE,
        NOTIFICATION-GROUP,
        OBJECT-GROUP
                FROM SNMPv2-CONF
        ruijieMgmt
                FROM RUIJIE-SMI; 
	
ruijieIPPrivateMgmt MODULE-IDENTITY
	LAST-UPDATED "200909180000Z"
    ORGANIZATION "Ruijie Networks Co.,Ltd."
    CONTACT-INFO
        " 
    Tel: 4008-111-000

    E-mail: service@ruijie.com.cn"
    DESCRIPTION
        "This module defines ac management mibs."
	REVISION      "200909180000Z"
    DESCRIPTION
        "Initial version of this MIB module."
    ::= { ruijieMgmt 73}

-- ******** define the notify nodes *************
ruijieIPPrivateAcNotificationsMIBObjects OBJECT IDENTIFIER ::= { ruijieIPPrivateMgmt 1 }
ruijieIPPrivateAcNtfObjects              OBJECT IDENTIFIER ::= { ruijieIPPrivateAcNotificationsMIBObjects 1 }
ruijieIPPrivateAcNotifications           OBJECT IDENTIFIER ::= { ruijieIPPrivateAcNotificationsMIBObjects 2 }

-- ****************************************
--
--               Notify nodes
--
-- ****************************************
ruijieIPPrivateAcNotifyIpv4AddressChangeType OBJECT-TYPE
    SYNTAX      INTEGER
    MAX-ACCESS  accessible-for-notify
    STATUS      current
    DESCRIPTION
        "Represents the AC Ipv4 address change operation, 0-del,1-add."
    ::= { ruijieIPPrivateAcNtfObjects 1 }

ruijieIPPrivateAcNotifyIpv4ChangeAddress OBJECT-TYPE
    SYNTAX      IpAddress
    MAX-ACCESS  accessible-for-notify
    STATUS      current
    DESCRIPTION
        "Represents the AC Ipv4 address which is changing."
    ::= { ruijieIPPrivateAcNtfObjects 2 }

ruijieIPPrivateAcNotifyIpv4ChangeAddressMask OBJECT-TYPE
    SYNTAX      IpAddress
    MAX-ACCESS  accessible-for-notify
    STATUS      current
    DESCRIPTION
        "Represents the AC Ipv4 address's mask which is changing."
    ::= { ruijieIPPrivateAcNtfObjects 3 }

ruijieIPPrivateAcNotifyIpv4ChangeIfIndex OBJECT-TYPE
    SYNTAX      INTEGER
    MAX-ACCESS  accessible-for-notify
    STATUS      current
    DESCRIPTION
        "Represents the AC Ipv4 address change on which interface."
    ::= { ruijieIPPrivateAcNtfObjects 4 }

ruijieIPPrivateNotifyArpFilterInfo OBJECT-TYPE
    SYNTAX      DisplayString
    MAX-ACCESS  accessible-for-notify
    STATUS      current
    DESCRIPTION
        "Represents the filtered ARP information."
    ::= { ruijieIPPrivateAcNtfObjects 5 }

ruijieIPPrivateAcNotifyChangeIpv4AddressAlarm NOTIFICATION-TYPE
    OBJECTS     {
                  ruijieIPPrivateAcNotifyIpv4AddressChangeType,
                  ruijieIPPrivateAcNotifyIpv4ChangeAddress,
                  ruijieIPPrivateAcNotifyIpv4ChangeAddressMask,
                  ruijieIPPrivateAcNotifyIpv4ChangeIfIndex
                }
    STATUS      current
    DESCRIPTION
        "This notification is sent by the AC when an AC's Ipv4 address is changed."
    ::= { ruijieIPPrivateAcNotifications 1 }

ruijieIPPrivateNotifyArpFilter NOTIFICATION-TYPE
    OBJECTS     {
                    ruijieIPPrivateNotifyArpFilterInfo
                }
    STATUS      current
    DESCRIPTION
        "This notification is sent when arp packet is filtered."
    ::= { ruijieIPPrivateAcNotifications 2 }
    
--********************************************************************
--                                                                  **
--                ac query ap's ip information	                    **
--                                                                  **
--********************************************************************    
ruijieIPPrivateAcQueryApMIBObject OBJECT IDENTIFIER ::= { ruijieIPPrivateAcNotificationsMIBObjects 3 }
ruijieIPPrivateAcQueryApInfo      OBJECT IDENTIFIER ::= { ruijieIPPrivateAcQueryApMIBObject 1}

--********************************************************************
--                                                                  **
--            table about ac query ap's ip information              **
--                                                                  **
--******************************************************************** 
ruijieIPPrivateAcQueryApMIBTable OBJECT-TYPE
    SYNTAX  SEQUENCE OF RuijieIPPrivateApInfoEntry
    MAX-ACCESS  not-accessible
    STATUS  current
    DESCRIPTION
            "The Ap IP information."
    ::= { ruijieIPPrivateAcQueryApInfo 1 }

ruijieIPPrivateApInfoEntry OBJECT-TYPE
    SYNTAX  RuijieIPPrivateApInfoEntry
    MAX-ACCESS  not-accessible
    STATUS  current
    DESCRIPTION
        "Get the Ap IP information."
    INDEX   { ruijieIPPrivateAcApMacAddr,
              ruijieIPPrivateAcApIp}
    ::= { ruijieIPPrivateAcQueryApMIBTable 1 }

RuijieIPPrivateApInfoEntry ::=
    SEQUENCE {
        ruijieIPPrivateAcApMacAddr                 MacAddress,
        ruijieIPPrivateAcApIp                      IpAddress,
        ruijieIPPrivateAcApMask                    IpAddress,
        ruijieIPPrivateAcApGateway                 IpAddress						
    }

ruijieIPPrivateAcApMacAddr OBJECT-TYPE
    SYNTAX  MacAddress
    MAX-ACCESS  read-only
    STATUS  current
    DESCRIPTION
            "The AP's ethernet mac address."
    ::= { ruijieIPPrivateApInfoEntry 1}
    
ruijieIPPrivateAcApIp OBJECT-TYPE
    SYNTAX  IpAddress
    MAX-ACCESS  read-only
    STATUS  current
    DESCRIPTION
        "The AP's IP address."
    ::= { ruijieIPPrivateApInfoEntry 2}
		
ruijieIPPrivateAcApMask OBJECT-TYPE
    SYNTAX  IpAddress	   
    MAX-ACCESS  read-only
    STATUS  current
    DESCRIPTION
    	"The AP's MASK address."
    ::= { ruijieIPPrivateApInfoEntry 3}				
    
ruijieIPPrivateAcApGateway OBJECT-TYPE
    SYNTAX  IpAddress	   
    MAX-ACCESS  read-only
    STATUS  current
    DESCRIPTION
    	"The AP's Gateway address."
    ::= { ruijieIPPrivateApInfoEntry 4}


--********************************************************************
--                                                                  **
--           conformance information                                **
--                                                                  **
--********************************************************************
ruijieIPPrivateMIBConformance OBJECT IDENTIFIER ::= { ruijieIPPrivateMgmt 2 }
ruijieIPPrivateMIBCompliances OBJECT IDENTIFIER ::= { ruijieIPPrivateMIBConformance 1 }
ruijieIPPrivateMIBGroups      OBJECT IDENTIFIER ::= { ruijieIPPrivateMIBConformance 2 }


--********************************************************************
--                                                                  **
--           compliance statements                                  **
--                                                                  **
--********************************************************************
ruijieIPPrivateMIBCompliance MODULE-COMPLIANCE
        STATUS  current
        DESCRIPTION
                "The compliance statement for entities which implement
                the Ruijie Ac Manager Ac"
        MODULE  -- this module
                MANDATORY-GROUPS { ruijieIPPrivateMIBGroup, ruijieIPPrivateTrapGroup }
        ::= { ruijieIPPrivateMIBCompliances 1 }
        

--********************************************************************
--                                                                  **
--           units of conformance                                   **
--                                                                  **
--********************************************************************
ruijieIPPrivateMIBGroup OBJECT-GROUP
        OBJECTS {
            ruijieIPPrivateAcNotifyIpv4AddressChangeType,
            ruijieIPPrivateAcNotifyIpv4ChangeAddress,
            ruijieIPPrivateAcNotifyIpv4ChangeAddressMask,
            ruijieIPPrivateAcNotifyIpv4ChangeIfIndex,
            ruijieIPPrivateAcApMacAddr,
            ruijieIPPrivateAcApIp,
            ruijieIPPrivateAcApMask,
            ruijieIPPrivateAcApGateway 
        }
        STATUS  current
        DESCRIPTION
                "A collection of objects providing ac manager (echo) ability to a
                Ruijie agent."
        ::= { ruijieIPPrivateMIBGroups 1 }

ruijieIPPrivateTrapGroup NOTIFICATION-GROUP
    NOTIFICATIONS {
        ruijieIPPrivateAcNotifyChangeIpv4AddressAlarm
    }
    STATUS  current
    DESCRIPTION
        "A collection of traps providing ac manager (echo) ability to a
         Ruijie agent."
    ::= { ruijieIPPrivateMIBGroups 2 }


--********************************************************************
--                                                                  **
--           device interface ip/ipv6 information                   **
--                                                                  **
--********************************************************************    
ruijieIfIPMIBObjects OBJECT IDENTIFIER ::= { ruijieIPPrivateMgmt 3 }

--********************************************************************
--                                                                  **
--            table about device interface ip information           **
--                                                                  **
--******************************************************************** 

ruijieIfIPTable OBJECT-TYPE
    SYNTAX  SEQUENCE OF RuijieIfIPEntry
    MAX-ACCESS  not-accessible
    STATUS  current
    DESCRIPTION
            "The Interface IP information."
    ::= { ruijieIfIPMIBObjects 1 }

ruijieIfIPEntry OBJECT-TYPE
    SYNTAX  RuijieIfIPEntry
    MAX-ACCESS  not-accessible
    STATUS  current
    DESCRIPTION
        "Get the Interface IP information."
    INDEX   { ruijieIfIndex
              }
    ::= { ruijieIfIPTable 1 }

RuijieIfIPEntry ::=
    SEQUENCE {
        ruijieIfIndex                    IfIndex,
        ruijieIfIPPriIp                  IpAddress,
        ruijieIfIP2ndIp1                 IpAddress,
        ruijieIfIP2ndIp2              	 IpAddress,
        ruijieIfIP2ndIp3            	 IpAddress,
        ruijieIfIP2ndIp4            	 IpAddress				
    }

ruijieIfIndex OBJECT-TYPE
    SYNTAX  IfIndex
    MAX-ACCESS  not-accessible
    STATUS  current
    DESCRIPTION
            "The Interface's index."
    ::= { ruijieIfIPEntry 1}
    
 ruijieIfIPPriIp OBJECT-TYPE
    SYNTAX  IpAddress
    MAX-ACCESS  read-only
    STATUS  current
    DESCRIPTION
        "The Interface's Primary IP address."
    ::= { ruijieIfIPEntry 2}
		
ruijieIfIP2ndIp1 OBJECT-TYPE
    SYNTAX  IpAddress	   
    MAX-ACCESS  read-only
    STATUS  current
    DESCRIPTION
    	"The Interface's Second IP address."
    ::= { ruijieIfIPEntry 3}				
    
ruijieIfIP2ndIp2 OBJECT-TYPE
    SYNTAX  IpAddress	   
    MAX-ACCESS  read-only
    STATUS  current
    DESCRIPTION
    	"The Interface's Third IP address."
    ::= { ruijieIfIPEntry 4}

ruijieIfIP2ndIp3 OBJECT-TYPE
    SYNTAX  IpAddress	   
    MAX-ACCESS  read-only
    STATUS  current
    DESCRIPTION
    	"The Interface's Fourth IP address."
    ::= { ruijieIfIPEntry 5}	
	
ruijieIfIP2ndIp4 OBJECT-TYPE
    SYNTAX  IpAddress	   
    MAX-ACCESS  read-only
    STATUS  current
    DESCRIPTION
    	"The Interface's Fifth IP address."
    ::= { ruijieIfIPEntry 6}		
	

--********************************************************************
--                                                                  **
--            table about device interface ipv6 information           **
--                                                                  **
--******************************************************************** 

ruijieIfIPv6Table OBJECT-TYPE
    SYNTAX  SEQUENCE OF RuijieIfIPv6Entry
    MAX-ACCESS  not-accessible
    STATUS  current
    DESCRIPTION
            "The Interface IPv6 information."
    ::= { ruijieIfIPMIBObjects 2 }

ruijieIfIPv6Entry OBJECT-TYPE
    SYNTAX  RuijieIfIPv6Entry
    MAX-ACCESS  not-accessible
    STATUS  current
    DESCRIPTION
        "Get the Interface IPv6 information."
    INDEX   { ruijieIfIPv6Index}
    ::= { ruijieIfIPv6Table 1 }

RuijieIfIPv6Entry ::=
    SEQUENCE {
        ruijieIfIPv6Index                 IfIndex,
        ruijieIfIPv6LinkLocalIp           Ipv6Address,
        ruijieIfIPv6Ip1                   Ipv6Address,
        ruijieIfIPv6Ip2              	  Ipv6Address,
        ruijieIfIPv6Ip3              	  Ipv6Address,
        ruijieIfIPv6Ip4              	  Ipv6Address				
    }
 ruijieIfIPv6Index OBJECT-TYPE
    SYNTAX  IfIndex
    MAX-ACCESS  not-accessible
    STATUS  current
    DESCRIPTION
            "The Interface's index."
    ::= { ruijieIfIPv6Entry 1}
    
 ruijieIfIPv6LinkLocalIp  OBJECT-TYPE
    SYNTAX  Ipv6Address
    MAX-ACCESS  read-only
    STATUS  current
    DESCRIPTION
        "The Interface's IPv6 Linklocal address."
    ::= { ruijieIfIPv6Entry 2}
		
ruijieIfIPv6Ip1 OBJECT-TYPE
    SYNTAX  Ipv6Address	   
    MAX-ACCESS  read-only
    STATUS  current
    DESCRIPTION
    	"The Interface's First IPv6 address."
    ::= { ruijieIfIPv6Entry 3}				
    
ruijieIfIPv6Ip2 OBJECT-TYPE
    SYNTAX  Ipv6Address	   
    MAX-ACCESS  read-only
    STATUS  current 
    DESCRIPTION
    	"The Interface's Second IPv6 address."
    ::= { ruijieIfIPv6Entry 4}

ruijieIfIPv6Ip3 OBJECT-TYPE
    SYNTAX  Ipv6Address	   
    MAX-ACCESS  read-only
    STATUS  current
    DESCRIPTION
    	"The Interface's Third IPv6 address."
    ::= { ruijieIfIPv6Entry 5}	
	
ruijieIfIPv6Ip4 OBJECT-TYPE
    SYNTAX  Ipv6Address	   
    MAX-ACCESS  read-only
    STATUS  current
    DESCRIPTION
    	"The Interface's Fourth IPv6 address."
    ::= { ruijieIfIPv6Entry 6}				
    
END
