-- *****************************************************************
-- RUIJIE-EEE-MIB.mib:  Ruijie EEE MIB file
--
-- Feb 2012, linzhihong
--
-- Copyright (c) 2012 by Ruijie Networks Co.,Ltd.
-- All rights reserved.
-- 
-- *****************************************************************
--

RUIJIE-EEE-MIB DEFINITIONS ::= BEGIN

IMPORTS
        MODULE-IDENTITY,
        OBJECT-TYPE,
        NOTIFICATION-TYPE,
        Integer32,
        OBJECT-TYPE
                FROM SNMPv2-SMI
        ruijieMgmt
                FROM RUIJIE-SMI;

ruijieEEEMIB MODULE-IDENTITY
        LAST-UPDATED "201210160000Z"
        ORGANIZATION "Ruijie Networks Co.,Ltd."
        CONTACT-INFO
                " 
                Tel: 4008-111-000 

                E-mail: service@ruijie.com.cn"
        DESCRIPTION
                "This module defines ruijie EEE mibs."
        REVISION      "201210160000Z"
        DESCRIPTION
                "Add a table about EEE."
        REVISION      "201210160000Z"
        DESCRIPTION
                "Initial version of this MIB module."
        ::= { ruijieMgmt 119 }

ruijieEEEConfigMIBObjects OBJECT IDENTIFIER ::= { ruijieEEEMIB 1 }

ruijieEEETable OBJECT-TYPE
        SYNTAX 			SEQUENCE OF RuijieEEEEntry
        MAX-ACCESS 	not-accessible
        STATUS 			current
        DESCRIPTION
            " "
        ::= { ruijieEEEConfigMIBObjects 1 }

   
ruijieEEEEntry OBJECT-TYPE
        SYNTAX 			RuijieEEEEntry
        MAX-ACCESS 	not-accessible
        STATUS 			current
        DESCRIPTION
            " "
        INDEX { ruijieEEEifIndex }
        ::= { ruijieEEETable 1 }

RuijieEEEEntry ::=
        SEQUENCE {
            ruijieEEEifIndex 		 Integer32,
            ruijieEEEAdminEnable INTEGER,
            ruijieEEEOperEnable  INTEGER
        }
       
ruijieEEEifIndex OBJECT-TYPE
        SYNTAX 			Integer32 (1..2147483647)
        MAX-ACCESS 	read-only
        STATUS 			current
        DESCRIPTION
            " "
        ::= { ruijieEEEEntry 1 }
   
           
ruijieEEEAdminEnable OBJECT-TYPE
        SYNTAX INTEGER {
            enabled(1),
            disabled(2)
        }
        MAX-ACCESS read-write
        STATUS current
        DESCRIPTION
            " "
        ::= { ruijieEEEEntry 2 }
    
ruijieEEEOperEnable OBJECT-TYPE
        SYNTAX INTEGER {
            enabled(1),
            disabled(2)
        }
        MAX-ACCESS read-only
        STATUS current
        DESCRIPTION
            " "
        ::= { ruijieEEEEntry 3 }                             
        
END
