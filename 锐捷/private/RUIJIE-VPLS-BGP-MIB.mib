RUIJIE-VPLS-BGP-MIB DEFINITIONS ::= BEGIN
      IMPORTS
      MODULE-IDENTITY, OBJECT-TYPE,
       Unsigned32, transmission
         FROM SNMPv2-SMI                    -- RFC2578

      MODULE-COMPLIANCE, OBJECT-GROUP
         FROM SNMPv2-CONF                   -- RFC2580

      RowStatus, StorageType,  TEXTUAL-CONVENTION
         FROM SNMPv2-TC                     -- RFC2579

      SnmpAdminString
         FROM SNMP-FRAMEWORK-MIB            -- RFC3411

      ruijievplsConfigIndex, ruijievplsPwBindIndex
         FROM RUIJIE-VPLS-GENERIC-MIB
      ruijieMgmt
         FROM RUIJIE-SMI
      ;

   ruijievplsBgpDraft01MIB MODULE-IDENTITY
      LAST-UPDATED "201004281200Z"  -- 28 April 2010 12:00:00 GMT
      ORGANIZATION "Ruijie Networks Co.,Ltd."
      CONTACT-INFO
                "
                Tel: 4008-111-000

                E-mail: service@ruijie.com.cn"

      DESCRIPTION
          "Copyright (C) Ruijie Networks (2010).

           This MIB module contains managed object definitions for
           BGP signalled Virtual Private LAN Services as in
           [RFC4761]

           This MIB module enables the use of any underlying PseudoWire
           network. "

      -- Revision history.
      REVISION
          "201004281200Z"  -- 28 April 2010 12:00:00 GMT
      DESCRIPTION "Initial version published as part of Ruijie private MIB."
         ::= { ruijieMgmt 79 }

   -- VPLS BGP specific Textual Conventions.
   RuijieVplsBgpRouteDistinguisher ::= TEXTUAL-CONVENTION
      STATUS        current
      DESCRIPTION
          "Syntax for a route distinguisher. For a complete
           definition of a route distinguisher, see [RFC4364].
           For more details on use of a route distinguisher
           for a VPLS service, see [RFC4761]"
      REFERENCE
          "[RFC4364]"
      SYNTAX  OCTET STRING(SIZE (0..256))

   RuijieVplsBgpRouteTarget ::= TEXTUAL-CONVENTION
      STATUS        current
      DESCRIPTION
          "Syntax for a route target. For a complete
           definition of a route target, see [RFC4364]."
      REFERENCE
          "[RFC4364]"
      SYNTAX  OCTET STRING(SIZE (0..256))

   -- Top-level components of this MIB.

   -- Tables, Scalars
   ruijievplsBgpObjects       OBJECT IDENTIFIER
                                 ::= { ruijievplsBgpDraft01MIB 1 }
   -- Conformance
   ruijievplsBgpConformance   OBJECT IDENTIFIER
                                 ::= { ruijievplsBgpDraft01MIB 2 }

     -- Vpls Edge Device (VE) Identifier Table

     ruijievplsBgpVETable OBJECT-TYPE
         SYNTAX        SEQUENCE OF RuijieVplsBgpVEEntry
         MAX-ACCESS    not-accessible
         STATUS        current
         DESCRIPTION
            "This table associates VPLS Edge devices to a VPLS instance"
         ::= { ruijievplsBgpObjects 1 }

     ruijievplsBgpVEEntry OBJECT-TYPE
         SYNTAX        RuijieVplsBgpVEEntry
         MAX-ACCESS    not-accessible
         STATUS        current
         DESCRIPTION
            "An entry in this table is created for each VE Id
             configured on a PE for a particular VPLS service
             instance."
         INDEX  { ruijievplsConfigIndex, ruijievplsBgpVEindex }
         ::= { ruijievplsBgpVETable 1 }

     RuijieVplsBgpVEEntry ::= SEQUENCE {
          ruijievplsBgpVEindex        Unsigned32,
          ruijievplsBgpVEId           Unsigned32,
          ruijievplsBgpRangeSize      Unsigned32,
          ruijievplsBgpVEPreference   Unsigned32,
          ruijievplsBgpVERowStatus    RowStatus
        }

      ruijievplsBgpVEindex  OBJECT-TYPE
          SYNTAX          Unsigned32  (1..2147483647)
          MAX-ACCESS      not-accessible
          STATUS          current
          DESCRIPTION
               "Unique index for the conceptual row identifying
                VE in a VPLS instance."
          ::= { ruijievplsBgpVEEntry 1 }

     ruijievplsBgpVEId OBJECT-TYPE
        SYNTAX        Unsigned32 (1..256)
        MAX-ACCESS    read-create
        STATUS        current
        DESCRIPTION
            "A secondary index identifying a VE within an
             instance of a VPLS service."
        ::= { ruijievplsBgpVEEntry 2 }

     ruijievplsBgpRangeSize OBJECT-TYPE
        SYNTAX        Unsigned32 (1..256)
        MAX-ACCESS    read-create
        STATUS        current
        DESCRIPTION
            "Specifies the range size for the given VE ID."
        DEFVAL           { 16 }
        ::= { ruijievplsBgpVEEntry 3}

     ruijievplsBgpVEPreference OBJECT-TYPE
        SYNTAX        Unsigned32 (0..256)
        MAX-ACCESS    read-only
        STATUS        current
        DESCRIPTION
            "Specifies the preference of the VE Id on this PE
             if the site is multi-homed and VE Id is re-used.

             Set this 0 if the site is NOT dual-homed or multi-homed."
        DEFVAL           { 0 }
        ::= { ruijievplsBgpVEEntry 4}

     ruijievplsBgpVERowStatus OBJECT-TYPE
        SYNTAX        RowStatus
        MAX-ACCESS    read-create
        STATUS        current
        DESCRIPTION
            "This variable is used to create, modify, and/or
             delete a row in this table.  When a row in this
             table is in active(1) state, no objects in that row
             can be modified except ruijievplsBgpSiteRowStatus."
        ::= { ruijievplsBgpVEEntry 5 }

      -- VPLS BGP PW Binding Table

      ruijievplsBgpPwBindTable OBJECT-TYPE
          SYNTAX          SEQUENCE OF RuijieVplsBgpPwBindEntry
          MAX-ACCESS      not-accessible
          STATUS          current
          DESCRIPTION
               "This table provides BGP specific information for
                an association between a VPLS service and the
                corresponding Pseudo Wires. A service can have more
                than one Pseudo Wire association. Pseudo Wires are
                defined in the pwTable."
          ::= { ruijievplsBgpObjects 2 }

      ruijievplsBgpPwBindEntry OBJECT-TYPE
          SYNTAX          RuijieVplsBgpPwBindEntry
          MAX-ACCESS      not-accessible
          STATUS          current
          DESCRIPTION
               "Each row represents an association between a
                VPLS instance and one or more Pseudo Wires
                defined in the pwTable. Each index is unique
                in describing an entry in this table. However
                both indexes are required to define the one
                to many association of service to pseudowire.

                An entry in this table in instantiated only when
                BGP signalling is used to configure VPLS service.

                Each entry in this table provides BGP specific
                information for the VPlS represented by
                ruijievplsConfigIndex."
          INDEX  { ruijievplsConfigIndex, ruijievplsPwBindIndex }
          ::= { ruijievplsBgpPwBindTable 1 }

      RuijieVplsBgpPwBindEntry ::=
          SEQUENCE {
              ruijievplsBgpPwBindLocalVEId    Unsigned32,
              ruijievplsBgpPwBindRemoteVEId   Unsigned32
          }

      ruijievplsBgpPwBindLocalVEId   OBJECT-TYPE
           SYNTAX          Unsigned32 (1..256)
           MAX-ACCESS      read-only
           STATUS          current
           DESCRIPTION
                "Identifies the local VE that this Pseudo Wire
                 is associated with."
          ::= { ruijievplsBgpPwBindEntry 1 }

      ruijievplsBgpPwBindRemoteVEId   OBJECT-TYPE
           SYNTAX          Unsigned32 (1..256)
           MAX-ACCESS      read-only
           STATUS          current
           DESCRIPTION
                "Identifies the remote VE that this Pseudo Wire
                 is associated with."
          ::= { ruijievplsBgpPwBindEntry 2 }

   -- Compliance requirement for read-only implementations.

   ruijievplsBgpCompliances
     OBJECT IDENTIFIER ::= { ruijievplsBgpConformance 1 }

   ruijievplsBgpModuleFullCompliance MODULE-COMPLIANCE
      STATUS current
      DESCRIPTION
           "Compliance requirement for implementations that
            provide full support for VPLS-BGP-DRAFT-01-MIB.
            Such devices can then be monitored and configured using
            this MIB module."

      MODULE -- this module

          MANDATORY-GROUPS {
               -- ruijievplsBgpConfigGroup,
               ruijievplsBgpVEGroup,
               ruijievplsBgpPwBindGroup
           }
      ::= { ruijievplsBgpCompliances 1 }


   ruijievplsBgpModuleReadOnlyCompliance MODULE-COMPLIANCE
      STATUS current
      DESCRIPTION
           "Compliance requirement for implementations that only
            provide read-only support for VPLS-BGP-DRAFT-01-MIB.
            Such devices can then be monitored but cannot be
            configured using this MIB modules."

      MODULE -- this module

          MANDATORY-GROUPS {
               -- ruijievplsBgpConfigGroup,
               ruijievplsBgpVEGroup,
               ruijievplsBgpPwBindGroup
           }

           -- OBJECT          ruijievplsBgpConfigRouteDistinguisher
           -- MIN-ACCESS      read-only
           -- DESCRIPTION
           --     "Write access is not required."

           -- OBJECT          ruijievplsBgpConfigRouteTarget
           -- MIN-ACCESS      read-only
           -- DESCRIPTION
           --     "Write access is not required."

           -- OBJECT          ruijievplsBgpVEName
           -- MIN-ACCESS      read-only
           -- DESCRIPTION
           --     "Write access is not required."

      ::= { ruijievplsBgpCompliances 2 }

-- Units of conformance.

      ruijievplsBgpGroups
        OBJECT IDENTIFIER ::= { ruijievplsBgpConformance 2 }


      ruijievplsBgpVEGroup OBJECT-GROUP
          OBJECTS {
              ruijievplsBgpVEPreference
          }
          STATUS          current
          DESCRIPTION
               "The group of objects supporting management of VPLS
                Edge devices for L2VPN VPLS services using BGP"
          ::= { ruijievplsBgpGroups 2 }

      ruijievplsBgpPwBindGroup OBJECT-GROUP
          OBJECTS {
              ruijievplsBgpPwBindLocalVEId,
              ruijievplsBgpPwBindRemoteVEId
          }
          STATUS          current
          DESCRIPTION
               "The group of objects supporting management of
                Pseudo Wires for L2VPN VPLS services using BGP"
          ::= { ruijievplsBgpGroups 3 }

END
