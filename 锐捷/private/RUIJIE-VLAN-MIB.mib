-- *****************************************************************
-- RUIJIE-VLAN-MIB.mib:  Ruijie VLAN MIB file
--
-- March 2002, Wuzg
--
-- Copyright (c) 2002 by Ruijie Networks Co.,Ltd.
-- All rights reserved.
-- 
-- *****************************************************************
--

RUIJIE-VLAN-MIB DEFINITIONS ::= BEGIN

IMPORTS
        MODULE-IDENTITY,
        OBJECT-TYPE,
        Integer32
                FROM SNMPv2-SMI
        VlanId,
        PortList
                FROM Q-BRIDGE-MIB
        DisplayString,
        TEXTUAL-CONVENTION
                FROM SNMPv2-TC
        MODULE-COMPLIANCE,
        OBJECT-GROUP
                FROM SNMPv2-CONF
        ConfigStatus,
        MemberMap,
        IfIndex
                FROM RUIJIE-TC
        ruijieMgmt
                FROM RUIJIE-SMI;

ruijieVlanMIB MODULE-IDENTITY
        LAST-UPDATED "200203200000Z"
        ORGANIZATION "Ruijie Networks Co.,Ltd."
        CONTACT-INFO
                " 
                Tel: 4008-111-000 

                E-mail: service@ruijie.com.cn"
        DESCRIPTION
                "This module defines ruijie vlan mibs."
        REVISION      "200203200000Z"
        DESCRIPTION
                "Initial version of this MIB module."
        ::= { ruijieMgmt 9}

ruijieVlanMIBObjects OBJECT IDENTIFIER ::= { ruijieVlanMIB 1 }

VlanList ::= TEXTUAL-CONVENTION
    STATUS      current
    DESCRIPTION
        "Each octet within this value specifies a set of eight
        vlans, with the first octet specifying vlans 1 through
        8, the second octet specifying vlans 9 through 16, etc.
        Within each octet, the most significant bit represents
        the lowest numbered vlan, and the least significant bit
        represents the highest numbered vlan.  Thus, each vlan
        of the bridge is represented by a single bit within the
        value of this object.  If that bit has a value of '1',
        then that vlan is included in the set of vlans; the vlan
        is not included if its bit has a value of '0'."
    SYNTAX      OCTET STRING
    
ruijieVlanMaxNumber OBJECT-TYPE
        SYNTAX Integer32
        MAX-ACCESS read-only
        STATUS current
        DESCRIPTION
            "Number of MAX vlans this system supported."
        ::= { ruijieVlanMIBObjects 1 }

ruijieVlanCurrentNumber OBJECT-TYPE
        SYNTAX Integer32
        MAX-ACCESS read-only
        STATUS current
        DESCRIPTION
            "Number of current vlans this system have."
        ::= { ruijieVlanMIBObjects 2 }
    
ruijieSystemMaxVID OBJECT-TYPE
        SYNTAX Integer32
        MAX-ACCESS read-only
        STATUS current
        DESCRIPTION
            "Max vlans of VID this system supported."
        ::= { ruijieVlanMIBObjects 3 }    

-- ruijieVlanIfConfigTable from the 10.3(4b3) has been abandoned. 
ruijieVlanIfConfigTable OBJECT-TYPE
        SYNTAX SEQUENCE OF RuijieVlanIfConfigEntry
        MAX-ACCESS not-accessible
        STATUS obsolete
        DESCRIPTION
            "vlan table."
        ::= { ruijieVlanMIBObjects 4 }
    
ruijieVlanIfConfigEntry OBJECT-TYPE
        SYNTAX RuijieVlanIfConfigEntry
        MAX-ACCESS not-accessible
        STATUS obsolete
        DESCRIPTION
            "list of vlan and it's port group table."
        INDEX { ruijieVlanIfConfigIfIndex}
        ::= { ruijieVlanIfConfigTable 1 }
    
RuijieVlanIfConfigEntry ::=
        SEQUENCE {
        ruijieVlanIfConfigIfIndex IfIndex,
        ruijieVlanIfAccessVlan   VlanId,
        ruijieVlanIfNativeVlan   VlanId,
        ruijieVlanIfAllowedVlanList OCTET STRING
        }    
    
ruijieVlanIfConfigIfIndex OBJECT-TYPE
        SYNTAX IfIndex
        MAX-ACCESS not-accessible
        STATUS obsolete
        DESCRIPTION
            " "
        ::= { ruijieVlanIfConfigEntry 1 }  

ruijieVlanIfAccessVlan OBJECT-TYPE
        SYNTAX VlanId
        MAX-ACCESS read-write
        STATUS obsolete
        DESCRIPTION
            "The value indicate the VID of the vlan which that this port 
             belong to. This field is effective for only access port."
        ::= { ruijieVlanIfConfigEntry 2 }          

ruijieVlanIfNativeVlan OBJECT-TYPE
        SYNTAX VlanId
        MAX-ACCESS read-write
        STATUS obsolete
        DESCRIPTION
            "The value indicate the VID of the native vlan of that this port .
             This field is effective for only trunk port."
        ::= { ruijieVlanIfConfigEntry 3 }                 
        
ruijieVlanIfAllowedVlanList OBJECT-TYPE
        SYNTAX OCTET STRING(SIZE(512))
        MAX-ACCESS read-write
        STATUS obsolete
        DESCRIPTION
            "Each bit in every octet in octet string assigned to a vlan, the value of
             the bit indicates that if the vlan is belong to allowed vlan list of this 
             interface. It indicates that assigned vlan is member of allowed vlan list
             of this interface if value of the bit is 1. The lowest bit of first byte 
             correspond to vlan 1 and the lowest bit of second byte correspond to vlan 9
             vlan. This field is effective for only trunk port."
        ::= { ruijieVlanIfConfigEntry 4 }        

 
--  ruijieVlanTable from the 10.3(4b3) has been abandoned.   
ruijieVlanTable OBJECT-TYPE
        SYNTAX SEQUENCE OF RuijieVlanEntry
        MAX-ACCESS not-accessible
        STATUS obsolete
        DESCRIPTION
            "vlan table."
        ::= { ruijieVlanMIBObjects 5 }
    
ruijieVlanEntry OBJECT-TYPE
        SYNTAX RuijieVlanEntry
        MAX-ACCESS not-accessible
        STATUS obsolete
        DESCRIPTION
            "list of vlan and it's distribution table."
        INDEX { ruijieVlanVID }
        ::= { ruijieVlanTable 1 }
    
RuijieVlanEntry ::=
        SEQUENCE {
        ruijieVlanVID VlanId,
        ruijieVlanPortMemberAction MemberMap,
        ruijieVlanApMemberAction MemberMap,
        ruijieVlanAlias DisplayString,
        ruijieVlanEntryStatus ConfigStatus
        }
    
ruijieVlanVID OBJECT-TYPE
        SYNTAX VlanId
        MAX-ACCESS read-only
        STATUS obsolete
        DESCRIPTION
            "VID of vlan ."
        ::= { ruijieVlanEntry 1 }
 
ruijieVlanPortMemberAction OBJECT-TYPE
        SYNTAX MemberMap
        MAX-ACCESS read-only
        STATUS obsolete
        DESCRIPTION
            "Each octet in member map assigned to a physical port, the value of
             the octect indicates the action of a physical port in the
             vlan. Drop(1) indicate that the vlan doesn't include this physical port, 
             Add(2) indicate that the vlan include this physical port."
        ::= { ruijieVlanEntry 2 }
        
ruijieVlanApMemberAction OBJECT-TYPE
        SYNTAX MemberMap
        MAX-ACCESS read-only
        STATUS obsolete
        DESCRIPTION
            "Each octet in member map assigned to a aggreate port, the value of
             the octect indicates the action of a aggreate port in the
            vlan. Drop(1) indicate that the vlan doesn't include this physical port, 
             Add(2) indicate that the vlan include this physical port."
        ::= { ruijieVlanEntry 3 }        
        
ruijieVlanAlias OBJECT-TYPE
        SYNTAX DisplayString (SIZE (0..32))
        MAX-ACCESS read-create
        STATUS obsolete
        DESCRIPTION
            "Vlan's alias ."
        DEFVAL{""}   
        ::= { ruijieVlanEntry 4 }
                
ruijieVlanEntryStatus OBJECT-TYPE
        SYNTAX ConfigStatus
        MAX-ACCESS read-create
        STATUS obsolete
        DESCRIPTION
            "Status of this entry, set this object to valid will creat a vlan of this entry,
             and set its value to invalid will delete the vlan of this entry."
        ::= { ruijieVlanEntry 5 }

-- ruijieVlanPortConfigTable from the 10.3(4b3) was started to support.   
--The table of VLAN members    
ruijieVlanPortConfigTable OBJECT-TYPE
        SYNTAX SEQUENCE OF RuijieVlanPortConfigEntry
        MAX-ACCESS not-accessible
        STATUS current
        DESCRIPTION
            "The table of VLAN members."
        ::= { ruijieVlanMIBObjects 6 }
    
ruijieVlanPortConfigEntry OBJECT-TYPE
        SYNTAX RuijieVlanPortConfigEntry
        MAX-ACCESS not-accessible
        STATUS current
        DESCRIPTION
            "list of ports."
        INDEX { ruijieVlanPortConfigIndex}
        ::= { ruijieVlanPortConfigTable 1 }
    
RuijieVlanPortConfigEntry ::=
        SEQUENCE {
        ruijieVlanPortConfigIndex IfIndex,
        ruijieVlanPortConfigMode INTEGER,
        ruijieVlanPortAccessVlan   VlanId,
        ruijieVlanPortNativeVlan   VlanId,
        ruijieVlanPortAllowedVlanList VlanList,
        ruijieIfVlanID Integer32
        }
        
--the index of port    
ruijieVlanPortConfigIndex OBJECT-TYPE
        SYNTAX IfIndex
        MAX-ACCESS not-accessible
        STATUS current
        DESCRIPTION
            "port index"
        ::= { ruijieVlanPortConfigEntry 1 }
        
--The port mode, read-only, in RUIJIE-INTERFACE-MIB.mib can be set up.       
ruijieVlanPortConfigMode OBJECT-TYPE
        SYNTAX INTEGER {
            access(1), -- the mode of interface is access port
            trunk(2),  -- the mode of interface is trunk port
            dot1q-tunnel(3),   --  the mode of interface is 802.1q tunnel port
            hybrid(4), -- the mode of interface is hybrid port
		  		  other(5), -- the mode of interface is unknow port
		  		  uplink(6), -- the mode of interface is uplink port
		  		  host(7),  -- the mode of interface is private host port
		  		  promiscuous(8) -- the mode of interface is private promiscuous port
        }
        MAX-ACCESS read-only
        STATUS current
        DESCRIPTION
            "Port mode, indicates that port is an 
             access(1), trunk(2), dot1q-tunnel(3), 
             hybrid(4), other(5), uplink(6), 
		  		   host(7) or promiscuous(8) port."
        ::= { ruijieVlanPortConfigEntry 2 }
        
ruijieVlanPortAccessVlan OBJECT-TYPE
        SYNTAX VlanId
        MAX-ACCESS read-write
        STATUS current
        DESCRIPTION
            "The value indicate the VID of the vlan which that this port 
             belong to. This field is effective for only access port."
        ::= { ruijieVlanPortConfigEntry 3 }

ruijieVlanPortNativeVlan OBJECT-TYPE
        SYNTAX VlanId
        MAX-ACCESS read-write
        STATUS current
        DESCRIPTION
            "The value indicate the VID of the native vlan of that this port .
             This field is effective for only trunk,hybrid,uplink and dot1q_tunnel port."
        ::= { ruijieVlanPortConfigEntry 4 }
    
ruijieVlanPortAllowedVlanList OBJECT-TYPE
        SYNTAX VlanList
        MAX-ACCESS read-write
        STATUS current
        DESCRIPTION
            "Each octet within this value specifies a set of eight
             vlans, with the first octet specifying vlans 0 through
             7, the second octet specifying vlans 8 through 15, etc.
             Within each octet, the most significant bit represents
             the lowest numbered vlan, and the least significant bit
             represents the highest numbered vlan.  Thus, each vlan
             of the bridge is represented by a single bit within the
             value of this object.  If that bit has a value of '1',
             then that vlan is included in the set of vlans; the vlan
             is not included if its bit has a value of '0'"
        ::= { ruijieVlanPortConfigEntry 5 }

ruijieIfVlanID OBJECT-TYPE
        SYNTAX Integer32
        MAX-ACCESS read-write
        STATUS current
        DESCRIPTION
            "The value indicates the VID of the vlan which that this port 
             belong to or of the native vlan of this port. 
	     This field is effective for only access, trunk, 
	     hybrid, uplink and dot1q_tunnel port."
        ::= { ruijieVlanPortConfigEntry 6 }

-- ruijieVlanConfigTable from the 10.3(4b3) was started to support.        
ruijieVlanConfigTable OBJECT-TYPE
        SYNTAX SEQUENCE OF RuijieVlanConfigEntry
        MAX-ACCESS not-accessible
        STATUS current
        DESCRIPTION
            "vlan table."
        ::= { ruijieVlanMIBObjects 7 }
    
ruijieVlanConfigEntry OBJECT-TYPE
        SYNTAX RuijieVlanConfigEntry
        MAX-ACCESS not-accessible
        STATUS current
        DESCRIPTION
            "list of vlan and it's distribution table."
        INDEX { ruijieVlanConfigVID }
        ::= { ruijieVlanConfigTable 1 }
    
RuijieVlanConfigEntry ::=
        SEQUENCE {
        ruijieVlanConfigVID VlanId,
        ruijieVlanConfigAction Integer32,
        ruijieVlanConfigName DisplayString,
        ruijieVlanConfigPortMember PortList
        }
   
ruijieVlanConfigVID OBJECT-TYPE
        SYNTAX VlanId
        MAX-ACCESS read-only
        STATUS current
        DESCRIPTION
            "VID of vlan ."
        ::= { ruijieVlanConfigEntry 1 }
      
ruijieVlanConfigAction OBJECT-TYPE
        SYNTAX Integer32
        MAX-ACCESS read-write
        STATUS current
        DESCRIPTION
            "The value 1 to create a vlan, 0 to delete a vlan."
        ::= { ruijieVlanConfigEntry 2 }
      
ruijieVlanConfigName OBJECT-TYPE
        SYNTAX DisplayString
        MAX-ACCESS read-write
        STATUS current
        DESCRIPTION
            "vlan name."
        ::= { ruijieVlanConfigEntry 3 }
 
ruijieVlanConfigPortMember OBJECT-TYPE
        SYNTAX PortList
        MAX-ACCESS read-only
        STATUS current
        DESCRIPTION
            "Each octet within this value specifies a set of eight
             ports, with the first octet specifying ports 1 through
             8, the second octet specifying ports 9 through 16, etc.
             Within each octet, the most significant bit represents
             the lowest numbered port, and the least significant bit
             represents the highest numbered port.  Thus, each port
             of the bridge is represented by a single bit within the
             value of this object.  If that bit has a value of '1',
             then that port is included in the set of ports; the port
             is not included if its bit has a value of '0'."
        ::= { ruijieVlanConfigEntry 4 }


ruijieVlanMIBConformance OBJECT IDENTIFIER ::= { ruijieVlanMIB 2 }
ruijieVlanMIBCompliances OBJECT IDENTIFIER ::= { ruijieVlanMIBConformance 1 }
ruijieVlanMIBGroups      OBJECT IDENTIFIER ::= { ruijieVlanMIBConformance 2 }


-- compliance statements

ruijieVlanMIBCompliance MODULE-COMPLIANCE
        STATUS  current
        DESCRIPTION
                "The compliance statement for entities which implement
                the Ruijie Vlan MIB"
        MODULE  -- this module
                MANDATORY-GROUPS { ruijieVlanMIBGroup
                 }
        ::= { ruijieVlanMIBCompliances 1 }
                
-- units of conformance

ruijieVlanMIBGroup OBJECT-GROUP
        OBJECTS {
           ruijieVlanMaxNumber,
           ruijieVlanCurrentNumber,
           ruijieSystemMaxVID,
--           ruijieVlanIfConfigIfIndex,
           ruijieVlanIfAccessVlan,
           ruijieVlanIfNativeVlan,
           ruijieVlanIfAllowedVlanList,
           ruijieVlanVID,
           ruijieVlanApMemberAction,
           ruijieVlanPortMemberAction,
           ruijieVlanAlias,
           ruijieVlanEntryStatus,  
--           ruijieManageVlanVID,
--           ruijiePortDefaultVIDPortIndex,
--           ruijiePortDefaultVID,
--           ruijieVlanPortConfigIndex,
           ruijieVlanPortConfigMode,
           ruijieVlanPortAccessVlan,
           ruijieVlanPortNativeVlan,
           ruijieVlanPortAllowedVlanList,
           ruijieIfVlanID,
           ruijieVlanConfigVID,
           ruijieVlanConfigAction,
           ruijieVlanConfigName,
           ruijieVlanConfigPortMember                    
        }
        STATUS  current
        DESCRIPTION
                "A collection of objects providing vlan configure ."
        ::= { ruijieVlanMIBGroups 1 }         
END
