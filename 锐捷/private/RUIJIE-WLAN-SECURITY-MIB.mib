-- *******************************************************************
-- RUIJIE-WLAN-SECURITY-MIB.mib : Ruijie WLAN DHCP MIB
--
-- Oct 2009, luolc
--
-- Copyright (c) 2009 by Ruijie Networks Co.,Ltd.
-- All rights reserved.
-- *******************************************************************
RUIJIE-WLAN-SECURITY-MIB DEFINITIONS ::= BEGIN
    IMPORTS
        MODULE-IDENTITY,
        OBJECT-TYPE,
        Integer32,
        Unsigned32
            FROM SNMPv2-SMI
        TruthValue,
        DisplayString,
        MacAddress,
        RowStatus
            FROM SNMPv2-TC
        MODULE-COMPLIANCE,
        NOTIFICATION-GROUP,
        OBJECT-GROUP
            FROM SNMPv2-CONF
        ruijieApgWlanId
            FROM RUIJIE-AC-MGMT-MIB
        ruijieMgmt
            FROM RUIJIE-SMI;


-- **********************************************
-- * MODULE IDENTITY
-- **********************************************
ruijieWLANsecurityMIB MODULE-IDENTITY
    LAST-UPDATED    "200910280000Z"
    ORGANIZATION
        "Ruijie Networks Co.,Ltd."
    CONTACT-INFO
        "Tel: 4008-111-000
           E-mail: service@ruijie.com.cn "

    DESCRIPTION
       "
       Wlan security software private MIB for Ruijie SNC.
       This is AC device manage MIB.
       "
    REVISION      "200910280000Z"
    DESCRIPTION
       "Initial version of this MIB module."

    ::= { ruijieMgmt  61 }


-- ***************************************************************************
-- * Major sections
-- ***************************************************************************
ruijieWLANsecurityMIBObjects OBJECT IDENTIFIER  ::= { ruijieWLANsecurityMIB 1 }


--***************************************************************************
--* AP agent MIB object
--***************************************************************************

ruijieAPworkmode OBJECT-TYPE
      SYNTAX  INTEGER { fitap(1), fatap(2) }
      MAX-ACCESS read-write
      STATUS current
      DESCRIPTION
        "This Attribute present AP device work mode ,
        Value 1 means Fit AP , Value 2 means Fat AP."
      DEFVAL { 1 }
      ::= { ruijieWLANsecurityMIBObjects 1}

--***************************************************************************
--* ruijieWLANsecurityConfig Table
--***************************************************************************

ruijieWLANsecurityConfigTable OBJECT-TYPE
    SYNTAX SEQUENCE OF RuijieWLANsecurityConfigEntry
    MAX-ACCESS not-accessible
    STATUS current
    DESCRIPTION
      "RuiJie Private WLAN security MIB"
    ::={ ruijieWLANsecurityMIBObjects 2 }


ruijieWLANsecurityConfigEntry  OBJECT-TYPE
    SYNTAX RuijieWLANsecurityConfigEntry
    MAX-ACCESS not-accessible
    STATUS current
    DESCRIPTION
      "An agent MAY process one or more WLAN security , which is identifed by ruijieApgWlanId.
      In other words, wlan ID is the index of this MIB table."
    INDEX { ruijieApgWlanId }
    ::={ ruijieWLANsecurityConfigTable 1 }


RuijieWLANsecurityConfigEntry ::=
    SEQUENCE {
        ruijieWLANsecrymode                 INTEGER,
        ruijiestaticweplength               INTEGER,
        ruijie8021xweplength                INTEGER,
        ruijieWPAenabled                    TruthValue,
        ruijieWPAPairwisecipher             INTEGER,
        ruijieWPAakmmode                    INTEGER,
        ruijieWPApskPassPhrase              DisplayString,
        ruijieWLANsecry80211i               TruthValue,
        ruijieWAPIasuIpaddress              Unsigned32,
        ruijieWAPIcertificateformat         INTEGER,
        ruijieWAPImsrekeyClientoff          TruthValue,
        ruijieWAPIimportcertificate         INTEGER,
        ruijieWAPIcacertificatename         DisplayString,
        ruijieWAPIlocalcertificatename      DisplayString,
        ruijieWAPIascertificatename         DisplayString,
        ruijieRSNenabled                    TruthValue,
        ruijieRSNPairwisecipher             INTEGER,
        ruijieRSNakmmode                    INTEGER,
        ruijieRSNpskPassPhrase              DisplayString,
        ruijieWEPAuthenAlgorithm            INTEGER,
        ruijieWLANsecurityStatus            RowStatus,
        ruijieACauthenMethodsupport         INTEGER,
        ruijieWLANEAPAuthenSupport          INTEGER
    }

ruijieWLANsecrymode OBJECT-TYPE
    SYNTAX INTEGER {open(1),staticwep(2), wep8021x(3),wpanone(4),wpapsk(5),wpa8021x(6),tsn(7) }
    MAX-ACCESS read-write
    STATUS current
    DESCRIPTION
      "This attribute present wlan security mode. Value 1 means open,
      Value 2 means static-wep,Value 3 means 802.1x-wep,Value 4 means WPA-PSK,
      Value 5 means WPA-802.1x,Value 6 means TSN(Hybrid)"
    ::= { ruijieWLANsecurityConfigEntry 1}

ruijiestaticweplength OBJECT-TYPE
    SYNTAX INTEGER  { wep40(1),wep104(2),wep128(3)}
    MAX-ACCESS read-write
    STATUS current
    DESCRIPTION
      "Static WEP key length,1 means WEP-40,
      2 means WEP-104, 3 means WEP-128,default is 2."
    DEFVAL { 2 }
    ::= { ruijieWLANsecurityConfigEntry 2}


ruijie8021xweplength OBJECT-TYPE
    SYNTAX INTEGER  { wep40(1),wep104(2),wep128(3)}
    MAX-ACCESS read-write
    STATUS current
    DESCRIPTION
      "IEEE802.1x WEP key length,1 means WEP-40,
      2 means WEP-104, 3 means WEP-128,default is 2."
    DEFVAL { 2 }
    ::= { ruijieWLANsecurityConfigEntry 3}

ruijieWPAenabled OBJECT-TYPE
    SYNTAX TruthValue
    MAX-ACCESS read-write
    STATUS current
    DESCRIPTION
      "Does this WLAN open WPA1 (it is not RSNA) support. "
    DEFVAL { false }
    ::= { ruijieWLANsecurityConfigEntry 4}


ruijieWPAPairwisecipher OBJECT-TYPE
    SYNTAX INTEGER { tkip(1),aes(2), tkiporaes(3) }
    MAX-ACCESS read-write
    STATUS current
    DESCRIPTION
      "WPA1 cipher mode default is TKIP(1)."
    DEFVAL { 1 }
    ::= { ruijieWLANsecurityConfigEntry 5}


ruijieWPAakmmode OBJECT-TYPE
    SYNTAX INTEGER { ieee8021x(1), psk(2), pskor8021x(3) }
    MAX-ACCESS read-write
    STATUS current
    DESCRIPTION
      "WPA1 AKM mode ,default is 802.1x."
    DEFVAL { 1 }
    ::= { ruijieWLANsecurityConfigEntry 6}


ruijieWPApskPassPhrase OBJECT-TYPE
    SYNTAX DisplayString
    MAX-ACCESS read-write
    STATUS current
    DESCRIPTION
      "WPA1 PSK password ,it is write-only.
      Any try to read it return FAIL."
    ::= { ruijieWLANsecurityConfigEntry 7 }


ruijieWLANsecry80211i  OBJECT-TYPE
    SYNTAX TruthValue
    MAX-ACCESS read-write
    STATUS current
    DESCRIPTION
      "IEEE802.11i or WAPI security mode.
       true means IEEE802.11i, false means WAPI."
    DEFVAL { true}
    ::= { ruijieWLANsecurityConfigEntry 8 }


ruijieWAPIasuIpaddress OBJECT-TYPE
    SYNTAX Unsigned32 (1..4294967295)
    MAX-ACCESS read-write
    STATUS current
    DESCRIPTION
      "WAPI ASU IP address."
    ::= { ruijieWLANsecurityConfigEntry 9 }


ruijieWAPIcertificateformat OBJECT-TYPE
    SYNTAX INTEGER { x509v3(1), wapigbw(2) }
    MAX-ACCESS read-write
    STATUS current
    DESCRIPTION
        "WAPI certificate format ,1 means x509v3,
        2 means WAPI-GBW. Now we only support x509v3."
    DEFVAL { 1 }
    ::= { ruijieWLANsecurityConfigEntry 10 }


ruijieWAPImsrekeyClientoff OBJECT-TYPE
    SYNTAX TruthValue
    MAX-ACCESS read-write
    STATUS current
    DESCRIPTION
      "When one user off line, deos the WAPI sure update group keys,
      default is false."
    DEFVAL { false }
    ::= { ruijieWLANsecurityConfigEntry 11 }


ruijieWAPIimportcertificate OBJECT-TYPE
    SYNTAX INTEGER { ca(1),local(2),as(3) }
    MAX-ACCESS read-write
    STATUS current
    DESCRIPTION
      "Import WAPI certificate,this is write-only."
    ::= { ruijieWLANsecurityConfigEntry 12 }


ruijieWAPIcacertificatename OBJECT-TYPE
    SYNTAX DisplayString
    MAX-ACCESS read-write
    STATUS current
    DESCRIPTION
      "WAPI CA certificate file name, default is wapi_ca.cer."
    ::= { ruijieWLANsecurityConfigEntry 13 }

ruijieWAPIlocalcertificatename OBJECT-TYPE
    SYNTAX DisplayString
    MAX-ACCESS read-write
    STATUS current
    DESCRIPTION
      "WAPI Local certificate file name, default is wapi_local.cer."
    ::= { ruijieWLANsecurityConfigEntry 14 }

ruijieWAPIascertificatename OBJECT-TYPE
    SYNTAX DisplayString
    MAX-ACCESS read-write
    STATUS current
    DESCRIPTION
      "WAPI ASU certificate file name, default is wapi_as.cer."
    ::= { ruijieWLANsecurityConfigEntry 15 }

ruijieRSNenabled OBJECT-TYPE
    SYNTAX TruthValue
    MAX-ACCESS read-write
    STATUS current
    DESCRIPTION
      "RSNA (WPA2) enable or disable"
    ::= { ruijieWLANsecurityConfigEntry 16 }

ruijieRSNPairwisecipher OBJECT-TYPE
    SYNTAX INTEGER { tkip(1), aes(2), tkiporaes(3) }
    MAX-ACCESS read-write
    STATUS current
    DESCRIPTION
      "WPA2 cipher mode."
    DEFVAL { 2 }
    ::= { ruijieWLANsecurityConfigEntry 17 }

ruijieRSNakmmode OBJECT-TYPE
    SYNTAX INTEGER { ieee8021x(1), psk(2), pskor8021x(3) }
    MAX-ACCESS read-write
    STATUS current
    DESCRIPTION
      "WPA2 authen key manage mode."
    DEFVAL { 1 }
    ::= { ruijieWLANsecurityConfigEntry 18 }

ruijieRSNpskPassPhrase OBJECT-TYPE
    SYNTAX DisplayString
    MAX-ACCESS read-write
    STATUS current
    DESCRIPTION
      "WPA2 PSK password ,it is write-only.
      Any try to read it return FAIL."
    ::= { ruijieWLANsecurityConfigEntry 19 }

ruijieWEPAuthenAlgorithm OBJECT-TYPE
    SYNTAX INTEGER { openSystem(1), sharedKey(2) }
    MAX-ACCESS read-only
    STATUS current
    DESCRIPTION
        "authentication algorithms supported by the Authencator.
         The following are the values and the associated algorithm.
         Value = 1: Open System
         Value = 2: Shared Key"
    ::= { ruijieWLANsecurityConfigEntry 20 }

ruijieWLANsecurityStatus OBJECT-TYPE
    SYNTAX RowStatus
    MAX-ACCESS read-write
    STATUS current
    DESCRIPTION
        "The status column used for creating and
         deleting instances of the columnar objects in the
         default WEP key Table."
    ::= { ruijieWLANsecurityConfigEntry 21 }

ruijieACauthenMethodsupport OBJECT-TYPE
    SYNTAX INTEGER
    MAX-ACCESS read-write
    STATUS current
    DESCRIPTION
        "authentication method supported by the AC, including the 
        EAP-SIM authentication, WEP authentication, EAP-MD5 
        authentication."
    ::= { ruijieWLANsecurityConfigEntry 22 }
    
ruijieWLANEAPAuthenSupport OBJECT-TYPE
    SYNTAX INTEGER
    {
    enableEAPAuthentication(0),
    disableEAPAuthentication(1),
    notSupportingEAPAuthentication(2)
    }
    MAX-ACCESS read-write
    STATUS current
    DESCRIPTION
        "Whether the current ap or ac enables or diables the EAP authentication."
    ::= { ruijieWLANsecurityConfigEntry 23 }
--********************************************************************
-- * dot11WEPDefaultKeys TABLE
--********************************************************************

ruijieWEPDefaultKeysTable OBJECT-TYPE
      SYNTAX SEQUENCE OF RuijieWEPDefaultKeysEntry
      MAX-ACCESS not-accessible
      STATUS current
      DESCRIPTION
          "Conceptual table for WEP default keys. "
      REFERENCE
          "IEEE Std 802.11-2007, 8.3.2"
      ::= { ruijieWLANsecurityMIBObjects 3 }

ruijieWEPDefaultKeysEntry OBJECT-TYPE
      SYNTAX RuijieWEPDefaultKeysEntry
      MAX-ACCESS not-accessible
      STATUS current
      DESCRIPTION
         "An Entry (conceptual row) in the WEP Default Keys Table."
      INDEX { ruijieApgWlanId,
              ruijieWEPDefaultKeyIndex }
      ::= { ruijieWEPDefaultKeysTable 1 }

RuijieWEPDefaultKeysEntry ::=
      SEQUENCE {
               ruijieWEPDefaultKeyIndex INTEGER,
               ruijieWEPDefaultKeyValue OCTET STRING,
               ruijieWEPDefaultKeyLength INTEGER
               }

ruijieWEPDefaultKeyIndex OBJECT-TYPE
      SYNTAX INTEGER (1..4)
      MAX-ACCESS not-accessible
      STATUS current
      DESCRIPTION
          "The auxiliary variable used to identify instances
          of the columnar objects in the WEP Default Keys Table.
          The value of this variable is equal to the
          WEPDefaultKeyID + 1"
      ::= { ruijieWEPDefaultKeysEntry 1 }

ruijieWEPDefaultKeyValue OBJECT-TYPE
      SYNTAX OCTET STRING
      MAX-ACCESS read-write
      STATUS current
      DESCRIPTION
          "A WEP default secret key value."
      ::= { ruijieWEPDefaultKeysEntry 2 }

ruijieWEPDefaultKeyLength OBJECT-TYPE
      SYNTAX INTEGER { wep40(1),wep104(2),wep128(3) }
      MAX-ACCESS read-write
      STATUS current
      DESCRIPTION
          "A WEP default secret key length."
      ::= { ruijieWEPDefaultKeysEntry 3 }

--********************************************************************
-- * End of dot11WEPDefaultKeys TABLE
--********************************************************************

--********************************************************************
--*    Compliance statements
--********************************************************************
ruijieWlansecurityMIBConform OBJECT IDENTIFIER  ::= { ruijieWLANsecurityMIB 2 }

ruijieWlansecurityMIBCompliances OBJECT IDENTIFIER ::= { ruijieWlansecurityMIBConform 1 }

ruijieWlansecurityMIBGroups      OBJECT IDENTIFIER ::= { ruijieWlansecurityMIBConform 2 }

ruijieWlansecurityMIBCompliance MODULE-COMPLIANCE
    STATUS  current
    DESCRIPTION
        "The compliance statement for entities which implement
        the wlan security module of Ruijie Ac device Manager"
    MODULE
    MANDATORY-GROUPS {
        ruijieWlansecuritycofigGroup,
        ruijieWEPDefaultKeysGroup,
        ruijieWlansecurityTrapGroup
    }
    ::= { ruijieWlansecurityMIBCompliances 1 }

--********************************************************************
--*    Units of conformance
--********************************************************************

ruijieWlansecuritycofigGroup OBJECT-GROUP
        OBJECTS {
            ruijieAPworkmode,
            ruijieWLANsecrymode ,
            ruijiestaticweplength,
            ruijie8021xweplength,
            ruijieWPAenabled,
            ruijieWPAPairwisecipher,
            ruijieWPAakmmode,
            ruijieWPApskPassPhrase,
            ruijieWLANsecry80211i,
            ruijieWAPIasuIpaddress,
            ruijieWAPIcertificateformat,
            ruijieWAPImsrekeyClientoff,
            ruijieWAPIimportcertificate,
            ruijieWAPIcacertificatename,
            ruijieWAPIlocalcertificatename,
            ruijieWAPIascertificatename,
            ruijieRSNenabled,
            ruijieRSNPairwisecipher,
            ruijieRSNakmmode,
            ruijieRSNpskPassPhrase,
            ruijieWEPAuthenAlgorithm,
            ruijieWLANsecurityStatus,
            ruijieACauthenMethodsupport,
            ruijieWLANEAPAuthenSupport,
            ruijieWlansecurityWepDecrytEnableTrapVar,
            ruijieWlansecurityDeviceMAC
        }
        STATUS     current
        DESCRIPTION
                "This collection of objects represents the
                 WLAN security private MIB "
        ::= { ruijieWlansecurityMIBGroups 1 }

ruijieWEPDefaultKeysGroup OBJECT-GROUP
        OBJECTS {
            ruijieWEPDefaultKeyValue,
            ruijieWEPDefaultKeyLength
        }
        STATUS     current
        DESCRIPTION
                "This collection of objects represents the
                 WLAN WEP default keys."
        ::= { ruijieWlansecurityMIBGroups 2 }

ruijieWlansecurityTrapGroup NOTIFICATION-GROUP
        NOTIFICATIONS {
            ruijieWlansecurityWepDecrytErr   
        }
        STATUS     current
        DESCRIPTION
                "This collection of objects represents the
                 wlan wep traps private MIB "
        ::= { ruijieWlansecurityMIBGroups 3 }
        
--***********************************************************
--*     variable of trap
--***********************************************************
ruijieWlansecurityTrapvar OBJECT IDENTIFIER ::= { ruijieWLANsecurityMIB 3 }

ruijieWlansecurityWepDecrytEnableTrapVar OBJECT-TYPE
    SYNTAX      Integer32
    MAX-ACCESS  read-write
    STATUS      current
    DESCRIPTION
        "Tell the host whether need to send the trap."
    ::= { ruijieWlansecurityTrapvar 1 }

ruijieWlansecurityDeviceMAC OBJECT-TYPE
    SYNTAX      MacAddress
    MAX-ACCESS  read-write
    STATUS      current
    DESCRIPTION
        "MAC address of the device."
    ::= { ruijieWlansecurityTrapvar 2 }
--***********************************************************
--*     wep decryt error trap
--***********************************************************
ruijieWLANsecurityTraps OBJECT IDENTIFIER ::= { ruijieWLANsecurityMIB 0 }

ruijieWlansecurityWepDecrytErr NOTIFICATION-TYPE
    OBJECTS {
        ruijieApgWlanId,
        ruijieWlansecurityDeviceMAC
    }
    STATUS  current
    DESCRIPTION
            "The information of an event of a wep decrytion error."
    ::= { ruijieWLANsecurityTraps 1 }


END
