-- *****************************************************************
-- RUIJIE-TIME-MIB.mib:  Ruijie Time MIB file
--
-- March 2002, Wuzg
--
-- Copyright (c) 2002 by Ruijie Networks Co.,Ltd.
-- All rights reserved.
-- 
-- *****************************************************************
--

RUIJIE-TIME-MIB DEFINITIONS ::= BEGIN

IMPORTS
        MODULE-IDENTITY,
        OBJECT-TYPE,
        Integer32
                FROM SNMPv2-SMI
        DisplayString,
        RowStatus,
        DateAndTime
                FROM SNMPv2-TC
        MODULE-COMPLIANCE,
        OBJECT-GROUP
                FROM SNMPv2-CONF
        ruijieMgmt
                FROM RUIJIE-SMI;

ruijieTimeMIB MODULE-IDENTITY
        LAST-UPDATED "200203200000Z"
        ORGANIZATION "Ruijie Networks Co.,Ltd."
        CONTACT-INFO
                " 
                Tel: 4008-111-000 

                E-mail: service@ruijie.com.cn"
        DESCRIPTION
                "This module defines ruijie time mibs."
        REVISION      "200203200000Z"
        DESCRIPTION
                "Initial version of this MIB module."
        ::= { ruijieMgmt 15}

ruijieTimeMIBObjects OBJECT IDENTIFIER ::= { ruijieTimeMIB 1 }

ruijieClockDateAndTime OBJECT-TYPE
    SYNTAX      DateAndTime
    MAX-ACCESS  read-write
    STATUS      current
    DESCRIPTION
        "The current local date and time for the system.

        Setting this object is equivalent to setting an automated
        clock and calendar.  The value of the object will track the
        date and time from the value set.  Note that due to hardware
        limitations some systems may not be able to preserve such
        meaning across reboots of the system, as indicated by
        csyClockLostOnReboot.

        A constant value of all zeros and length 8 indicates the
        system is not aware of the present date and time."
    ::= { ruijieTimeMIBObjects 1 }

ruijieClockWeek OBJECT-TYPE
    SYNTAX      INTEGER(1..7)
    MAX-ACCESS  read-only
    STATUS      current
    DESCRIPTION
        "This value indicate that which day currunt time of system indicate. e.g. 
         1 indicate Monday，7 indicate Sunday"
    ::= { ruijieTimeMIBObjects 2 }    
    

ruijieTimeRangeMIBObjects OBJECT IDENTIFIER ::= { ruijieTimeMIB 2}

--
-- Time/scheduling range filter table
--

ruijieTimeRangeTable OBJECT-TYPE
    SYNTAX      SEQUENCE OF RuijieTimeRangeEntry
    MAX-ACCESS  not-accessible
    STATUS      current
    DESCRIPTION
        "Defines a table of filters which can be used to effectively
         enable or disable policies based on a valid time range."
    ::= { ruijieTimeRangeMIBObjects 1}

ruijieTimeRangeEntry OBJECT-TYPE
    SYNTAX      RuijieTimeRangeEntry
    MAX-ACCESS  not-accessible
    STATUS      current
    DESCRIPTION
        "A row describing a given time range for which a policy may be
         filtered on to place the rule active or inactive."
    INDEX   { ruijieTimeRangeName }
    ::= { ruijieTimeRangeTable 1 }

RuijieTimeRangeEntry ::= SEQUENCE {
    ruijieTimeRangeName                 DisplayString,
    ruijieTimeRangePeriodRuijie          DateAndTime,
    ruijieTimeRangePeriodEnd            DateAndTime,
    ruijieTimeRangeRowStatus            RowStatus
}

ruijieTimeRangeName OBJECT-TYPE
    SYNTAX      DisplayString(SIZE (1..32))
    MAX-ACCESS  not-accessible
    STATUS      current
    DESCRIPTION
        "An administratively assigned name for this time range.
         This value is unique for every entry
         When this string be used as an index,Value of a sub-identifier equal 
         ASCII value of corresponding character(first sub-identifier corresponds
         first character of string). The number of sub-identifiers of this string
         must be 32,If length of string is less than 32 the sub-identifier(0x0) 
         will be filled in tail."
    ::= { ruijieTimeRangeEntry 1 }


ruijieTimeRangePeriodRuijie OBJECT-TYPE
    SYNTAX      DateAndTime
    MAX-ACCESS  read-create
    STATUS      current
    DESCRIPTION
        "The ruijieing time period for this filter.  In addition to a
         normal DateAndTime string, this object may be set to the
         OCTET STRING value THISANDPRIOR which indicates that the
         filter is valid from any time before now up until (at least)
         now."
    DEFVAL { '0000010100000000'H }
    ::= { ruijieTimeRangeEntry 2 }

ruijieTimeRangePeriodEnd OBJECT-TYPE
    SYNTAX      DateAndTime
    MAX-ACCESS  read-create
    STATUS      current
    DESCRIPTION
        "The ending time period for this filter.  In addition to a
         normal DateAndTime string, this object may be set to the
         OCTET STRING value THISANDFUTURE which indicates that the
         filter is valid without an ending date and/or time."
    DEFVAL { '9999123123595909'H }
    ::= { ruijieTimeRangeEntry 3 }

ruijieTimeRangeRowStatus OBJECT-TYPE
    SYNTAX      RowStatus
    MAX-ACCESS  read-create
    STATUS      current
    DESCRIPTION
        "This object indicates the conceptual status of this row."
    ::= { ruijieTimeRangeEntry 4 }


--
-- Time range periodic filter table
--

ruijieTimeRangePeriodicTable OBJECT-TYPE
    SYNTAX      SEQUENCE OF RuijieTimeRangePeriodicEntry
    MAX-ACCESS  not-accessible
    STATUS      current
    DESCRIPTION
        "Defines a table of periodic time filters in the time-range."
    ::= { ruijieTimeRangeMIBObjects 2 }

ruijieTimeRangePeriodicEntry OBJECT-TYPE
    SYNTAX      RuijieTimeRangePeriodicEntry
    MAX-ACCESS  not-accessible
    STATUS      current
    DESCRIPTION
        "A row describing a given periodic time limit for the time-range."
    INDEX   { ruijieTimeRangePeriodicTRName }
    ::= { ruijieTimeRangePeriodicTable 1 }

RuijieTimeRangePeriodicEntry ::= SEQUENCE {
    ruijieTimeRangePeriodicTRName               DisplayString,
    ruijieTimeRangePeriodicIndex                Integer32,
    ruijieTimeRangePeriodicType                 INTEGER, 
    ruijieTimeRangePeriodicRuijieWeekDay            OCTET STRING,
    ruijieTimeRangePeriodicEndWeekDay           INTEGER,
    ruijieTimeRangePeriodicTimeOfDayRuijie          DateAndTime,
    ruijieTimeRangePeriodicTimeOfDayEnd         DateAndTime,
    ruijieTimeRangePeriodicRowStatus            RowStatus
}

ruijieTimeRangePeriodicTRName OBJECT-TYPE
    SYNTAX      DisplayString (SIZE(1..32))
    MAX-ACCESS  not-accessible
    STATUS      current
    DESCRIPTION
        "Time-range name which this periodic time filter belong to.
         This value is unique for every entry
         When this string be used as an index,Value of a sub-identifier equal 
         ASCII value of corresponding character(first sub-identifier corresponds
         first character of string). The number of sub-identifiers of this string
         must be 32,If length of string is less than 32 the sub-identifier(0x0) 
         will be filled in tail."
    ::= { ruijieTimeRangePeriodicEntry 1 }

ruijieTimeRangePeriodicIndex OBJECT-TYPE
        SYNTAX Integer32(1..65535)
        MAX-ACCESS read-only
        STATUS current
        DESCRIPTION
               "Object which specifies a unique entry in the ruijieTimeRangePeriodicTable. 
                A management station wishing to initiate a entry operation should use a
                pseudo-random value for this object when creating
                or modifying an instance of a entry.
                
                The RowStatus semantics of the entry object will prevent access conflicts."
        ::= { ruijieTimeRangePeriodicEntry 2 }
        
ruijieTimeRangePeriodicType OBJECT-TYPE
        SYNTAX INTEGER{
              fixed-segment(1),   -- Fixed time period, defined by the entry, which is in one or several days. 
              unfixed-segment(2)  -- Unfixed time period, defined by the entry, which is one or several days in a week. 
        }
        MAX-ACCESS read-create
        STATUS current
        DESCRIPTION
               "Type defined by the time period in the entry." 
        ::= { ruijieTimeRangePeriodicEntry 3 }        

ruijieTimeRangePeriodicRuijieWeekDay OBJECT-TYPE
    SYNTAX      OCTET STRING (SIZE(1))
    MAX-ACCESS  read-create
    STATUS      current
    DESCRIPTION
         "The start day in a week of the time period. Every bit in this byte stands for one day in 
          a week. The lowest bit(the 1st bit from the right) stands for monday. One by one to the left 
          Tuesday, wednesday,thursday, friday,saturday, sunday are. The highest bit(the 1st bit from the left)
          always be 0. 1 means the day represented by the bit is included."
    DEFVAL {'fe'H}
    ::= { ruijieTimeRangePeriodicEntry 4 }

ruijieTimeRangePeriodicEndWeekDay OBJECT-TYPE
    SYNTAX      INTEGER{
                       monday(1), tuesday(2), wednesday(3),
                       thursday(4), friday(5), saturday(6),
                       sunday(7)                            
                }
    MAX-ACCESS  read-create
    STATUS      current
    DESCRIPTION
        "The end day in a week of the time period. When ruijieTimeRangePeriodicType is 'fixed-segment',
         this field is insignificant."
    ::= { ruijieTimeRangePeriodicEntry 5 }
    
ruijieTimeRangePeriodicTimeOfDayRuijie OBJECT-TYPE
    SYNTAX      DateAndTime
    MAX-ACCESS  read-create
    STATUS      current
    DESCRIPTION
        "The start time of the time period. In fact, only time in DateAndTime is meaningful."
    ::= { ruijieTimeRangePeriodicEntry 6 }

ruijieTimeRangePeriodicTimeOfDayEnd OBJECT-TYPE
    SYNTAX      DateAndTime
    MAX-ACCESS  read-create
    STATUS      current
    DESCRIPTION
        "The end time of the time period. In fact, only time in DateAndTime is meaningful."
     ::= { ruijieTimeRangePeriodicEntry 7 }

ruijieTimeRangePeriodicRowStatus OBJECT-TYPE
    SYNTAX      RowStatus
    MAX-ACCESS  read-create
    STATUS      current
    DESCRIPTION
        "This object indicates the conceptual status of this row"
    ::= { ruijieTimeRangePeriodicEntry 8 }

ruijieTimeMIBConformance OBJECT IDENTIFIER ::= { ruijieTimeMIB 3 }
ruijieTimeMIBCompliances OBJECT IDENTIFIER ::= { ruijieTimeMIBConformance 1 }
ruijieTimeMIBGroups      OBJECT IDENTIFIER ::= { ruijieTimeMIBConformance 2 }


-- compliance statements

ruijieTimeMIBCompliance MODULE-COMPLIANCE
        STATUS  current
        DESCRIPTION
                "The compliance statement for entities which implement
                the Ruijie Time MIB"
        MODULE  -- this module
                GROUP ruijieTimeMIBGroup
                DESCRIPTION
                  "This group is mandatory for device which support RTC."                  
                GROUP ruijieTimeRangeMIBGroup
                DESCRIPTION
                  "This group is mandatory for device which support RTC or NTP/SNTP."                
                
        ::= { ruijieTimeMIBCompliances 1 }
                
-- units of conformance

ruijieTimeMIBGroup OBJECT-GROUP
        OBJECTS {
               ruijieClockDateAndTime, 
               ruijieClockWeek
        }
        STATUS  current
        DESCRIPTION
                "A collection of objects providing time information."
        ::= { ruijieTimeMIBGroups 1 } 
        
ruijieTimeRangeMIBGroup OBJECT-GROUP
        OBJECTS {
          ruijieTimeRangePeriodicIndex          ,
          ruijieTimeRangePeriodicType           ,
          ruijieTimeRangePeriodicRuijieWeekDay   ,
          ruijieTimeRangePeriodicEndWeekDay     ,
          ruijieTimeRangePeriodicTimeOfDayRuijie ,
          ruijieTimeRangePeriodicTimeOfDayEnd   ,
          ruijieTimeRangePeriodicRowStatus       
        }
        STATUS  current
        DESCRIPTION
                "A collection of objects providing time-range function."
        ::= { ruijieTimeMIBGroups 2 }        
  
END
