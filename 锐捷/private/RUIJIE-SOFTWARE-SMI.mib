-- *****************************************************************
-- RUIJIE-SOFTWARE-SMI.mib: Ruijie SOFTWARE SMI File
-- 
-- Aug. 2014, panshiyong
--
-- Copyright (c) 2014 by Ruijie Networks Co.,Ltd.
-- All rights reserved.
-- 
-- *****************************************************************
--

RUIJIE-SOFTWARE-SMI DEFINITIONS ::= BEGIN

IMPORTS
        MODULE-IDENTITY,
        OBJECT-IDENTITY
                FROM SNMPv2-SMI
        products
                FROM RUIJIE-SMI;
                
software OBJECT IDENTIFIER ::= { products 7 }

softwareMib MODULE-IDENTITY
        LAST-UPDATED "201408190000Z"
        ORGANIZATION "Ruijie Networks Co.,Ltd."
        CONTACT-INFO
                " 
                Tel: 4008-111-000 

                E-mail: service@ruijie.com.cn"
        DESCRIPTION
                "The Structure of Management Information for the
                 Ruijie enterprise."
        REVISION      "201005250000Z"
        DESCRIPTION
                "Initial version of this MIB module."
        ::= { software 1 }        

ruijieSoftwareProducts OBJECT-IDENTITY
        STATUS  current
        DESCRIPTION
                "ruijieSoftwareProducts is the root OBJECT IDENTIFIER from
                 which sysObjectID values are assigned for software.  Actual
                 values are defined in RUIJIE-PRODUCTS-MIB."
        ::= { softwareMib 1 }
        
END
