-- *****************************************************************
-- RUIJIE-ROUTE-MIB.mib:  Ruijie Route MIB file
--
-- March 2002, Wuzg
--
-- Copyright (c) 2002 by Ruijie Networks Co.,Ltd.
-- All rights reserved.
-- 
-- *****************************************************************
--

RUIJIE-ROUTE-MIB DEFINITIONS ::= BEGIN

IMPORTS
        MODULE-IDENTITY,
        OBJECT-TYPE,
        NOTIFICATION-TYPE,
        TimeTicks,
        Unsigned32,
        Integer32,
        IpAddress
                FROM SNMPv2-SMI
        AddressFamilyNumbers
                FROM IANA-ADDRESS-FAMILY-NUMBERS-MIB
        TruthValue,
        DisplayString,
        RowStatus,
        TEXTUAL-CONVENTION
                FROM SNMPv2-TC
        MODULE-COMPLIANCE,
        OBJECT-GROUP
                FROM SNMPv2-CONF
        ConfigStatus,
        IfIndex
                FROM RUIJIE-TC
        EnabledStatus 
                FROM P-BRIDGE-MIB
        ruijieMgmt
                FROM RUIJIE-SMI
        mplsL3VpnVrfPerfCurrNumRoutes
                FROM MPLS-L3VPN-STD-MIB
        mplsL3VpnVrfConfMidRteThresh
                FROM MPLS-L3VPN-STD-MIB;

ruijieRouteMIB MODULE-IDENTITY
        LAST-UPDATED "200203200000Z"
        ORGANIZATION "Ruijie Networks Co.,Ltd."
        CONTACT-INFO
                " 
                Tel: 4008-111-000 

                E-mail: service@ruijie.com.cn"
        DESCRIPTION
                "This module defines ruijie route mibs."
        REVISION      "200203200000Z"
        DESCRIPTION
                "Initial version of this MIB module."
        ::= { ruijieMgmt 20}

RuijieRouteProtoType ::= TEXTUAL-CONVENTION        
   STATUS current                          
   DESCRIPTION                             
            "Routing protocol type." 
   SYNTAX INTEGER {                        
            other(1),  --notspecified
            local(2),  --localinterface
            netmgmt(3),  --staticroute
            icmp(4),  --resultofICMPRedirect
            egp(5),  --ExteriorGatewayProtocol
            ggp(6),  --Gateway-GatewayProtocol
            hello(7),  --FuzzBallHelloSpeak
            rip(8),  --BerkeleyRIPorRIP-II
            isis(9),  --DualIS-IS
            esis(10),  --ISO9542
            ciscoigrp(11),  --CiscoIGRP
            bbnspfigp(12),  --BBNSPFIGP
            ospf(13),  --OpenShortestPathFirst
            bgp(14),  --BorderGatewayProtocol
            idpr(15),  --InterDomainPolicyRouting
            ciscoeigrp(16),  --CiscoEIGRP
            max(17)  --MAXTYPE                        
            }                                

ruijieRouteMIBObjects OBJECT IDENTIFIER ::= { ruijieRouteMIB 1 }

ruijieRouteServiceStatus OBJECT-TYPE
    SYNTAX  EnabledStatus
    MAX-ACCESS read-write
    STATUS current
    DESCRIPTION
              "Route management function status"
         ::={ ruijieRouteMIBObjects 1 }
         
ruijieRoutingProtoInfoTable OBJECT-TYPE
     SYNTAX   SEQUENCE OF RuijieRoutingProtoInfoEntry
     MAX-ACCESS   not-accessible
     STATUS   current
     DESCRIPTION
        "The routing protocol infomation ."
    ::= { ruijieRouteMIBObjects  2 }

ruijieRoutingProtoInfoEntry OBJECT-TYPE
    SYNTAX   RuijieRoutingProtoInfoEntry
    MAX-ACCESS   not-accessible
    STATUS   current
    DESCRIPTION
       "the entry of this table."
   INDEX {   ruijieRoutingProtoInfoProtoType,
             ruijieRoutingProtoInfoGateWay
          }
   ::= { ruijieRoutingProtoInfoTable 1 }
   
RuijieRoutingProtoInfoEntry ::=
  SEQUENCE{
     ruijieRoutingProtoInfoProtoType
         RuijieRouteProtoType,
     ruijieRoutingProtoInfoGateWay    
         IpAddress,
     ruijieRoutingProtoInfoDistance 
         Unsigned32,
     ruijieRoutingProtoInfoLastUpdate   
         TimeTicks
     }
  
ruijieRoutingProtoInfoProtoType   OBJECT-TYPE
     SYNTAX   RuijieRouteProtoType
     MAX-ACCESS   read-only
     STATUS   current
     DESCRIPTION
        "The routing protocol type"
    ::= { ruijieRoutingProtoInfoEntry 1 }  
             
ruijieRoutingProtoInfoGateWay OBJECT-TYPE 
     SYNTAX   IpAddress
     MAX-ACCESS   read-only
     STATUS   current
     DESCRIPTION
        "For rip ,the gateway is this router's neighbor.
         for ospf ,the gateway is  the router Id of this router,
         New entry will be addded when router ID is changed."
    ::= { ruijieRoutingProtoInfoEntry 2 }
    
ruijieRoutingProtoInfoDistance OBJECT-TYPE 
     SYNTAX   Unsigned32
     MAX-ACCESS   read-only
     STATUS   current
     DESCRIPTION
        "The routing protocol distance."
    ::= { ruijieRoutingProtoInfoEntry 3 }
    
ruijieRoutingProtoInfoLastUpdate OBJECT-TYPE 
     SYNTAX   TimeTicks
     MAX-ACCESS   read-only
     STATUS   current
     DESCRIPTION
        "The last update time of the neighbor that be found.
         or  router ID that it last change ."
    ::= { ruijieRoutingProtoInfoEntry 4 }


ruijieDefRoutingCfgTable OBJECT-TYPE
     SYNTAX SEQUENCE OF RuijieDefRoutingCfgEntry
     MAX-ACCESS not-accessible
     STATUS current
     DESCRIPTION
         "Default routing configuration."
 ::= { ruijieRouteMIBObjects 3}
 
ruijieDefRoutingCfgEntry OBJECT-TYPE
     SYNTAX RuijieDefRoutingCfgEntry
     MAX-ACCESS not-accessible
     STATUS current
     DESCRIPTION
         "The entry define one routing protocol's default
          routing configurate,if in rip routing configuration
          only route map is valid to this default route parameter"
     INDEX { ruijieDefRoutingCfgRoutingProtoType}
 ::= { ruijieDefRoutingCfgTable 1 }

 
RuijieDefRoutingCfgEntry ::=
     SEQUENCE {
     ruijieDefRoutingCfgRoutingProtoType 
             RuijieRouteProtoType,
     ruijieDefRoutingCfgAlways  
             TruthValue,
     ruijieDefRoutingCfgMetric
             Unsigned32,
     ruijieDefRoutingCfgMetricType  --only use in ospf
             INTEGER,
     ruijieDefRoutingCfgRouteMap
             DisplayString,
     ruijieDefRoutingCfgStatus
             RowStatus
              }
ruijieDefRoutingCfgRoutingProtoType  OBJECT-TYPE
     SYNTAX   RuijieRouteProtoType
     MAX-ACCESS   read-only
     STATUS   current
     DESCRIPTION
        "index indicate that which routing protocol configuration mode is current mode."
    ::= { ruijieDefRoutingCfgEntry 1 } 
    
ruijieDefRoutingCfgAlways OBJECT-TYPE
     SYNTAX   TruthValue
     MAX-ACCESS   read-create
     STATUS   current
     DESCRIPTION
        "Setting the value to TRUE indicates that always advertise default route."
     DEFVAL{false}
    ::= { ruijieDefRoutingCfgEntry 2 }  
             
ruijieDefRoutingCfgMetric OBJECT-TYPE
     SYNTAX   Unsigned32(1..16777214) 
     MAX-ACCESS   read-create
     STATUS   current
     DESCRIPTION
        "Set  ospf default metric value."
     DEFVAL {10}
    ::= { ruijieDefRoutingCfgEntry 3 }
                             
ruijieDefRoutingCfgMetricType OBJECT-TYPE
     SYNTAX   INTEGER{                        
                     type1(1),
                     type2(2)
                     }
                   
     MAX-ACCESS   read-create
     STATUS   current
     DESCRIPTION
        "Set  OSPF Link State type,this value is only 
         valid in ospf configuration"
     DEFVAL {type2}
    ::= { ruijieDefRoutingCfgEntry 4 } 
           
ruijieDefRoutingCfgRouteMap OBJECT-TYPE
     SYNTAX   DisplayString(SIZE(0..32))
     MAX-ACCESS   read-create
     STATUS   current
     DESCRIPTION
        "Set  route's Route-map reference.Null string indicate that no any route-map
        reference."
     DEFVAL {""}
    ::= { ruijieDefRoutingCfgEntry 5 }   
          
ruijieDefRoutingCfgStatus OBJECT-TYPE
     SYNTAX   RowStatus
     MAX-ACCESS   read-create
     STATUS   current
     DESCRIPTION
        "if this value is change to destroy,
         this entry will be deleted"       
    ::= { ruijieDefRoutingCfgEntry 6 }           


         
--Route map group
ruijieRouteMapMIBObjects OBJECT IDENTIFIER ::= { ruijieRouteMIB 2 }         

--ruijieRouteMapTable
ruijieRouteMapTable OBJECT-TYPE
     SYNTAX   SEQUENCE OF RuijieRouteMapEntry
     MAX-ACCESS   not-accessible
     STATUS   current
     DESCRIPTION
        "the route map table."
    ::= { ruijieRouteMapMIBObjects  1 }

ruijieRouteMapEntry OBJECT-TYPE
    SYNTAX   RuijieRouteMapEntry
    MAX-ACCESS   not-accessible
    STATUS   current
    DESCRIPTION
       "the entry of this table."
   INDEX {
            ruijieRouteMapName,
            ruijieRouteMapSequenceNumber
          }
   ::= { ruijieRouteMapTable 1 }
   
RuijieRouteMapEntry ::=
  SEQUENCE{
     ruijieRouteMapName
         DisplayString,
     ruijieRouteMapSequenceNumber
         Unsigned32,
     ruijieRouteMapOperType   
         INTEGER,
     ruijieRouteMapMatchMetric  
         Unsigned32,
     ruijieRouteMapMatchRouteType 
         INTEGER,
     ruijieRouteMapMetricValueType    
         INTEGER,
     ruijieRouteMapSetMetric  
         Unsigned32,      
    ruijieRouteMapSetLevel  
         INTEGER,
     ruijieRouteMapSetMetricType 
         INTEGER,
     ruijieRouteMapSetNexthopSt
         ConfigStatus,          
     ruijieRouteMapSetNexthop
         IpAddress,
     ruijieRouteMapStatus
         RowStatus             
           }   
ruijieRouteMapName   OBJECT-TYPE  
     SYNTAX   DisplayString(SIZE(1..32))
     MAX-ACCESS   read-only
     STATUS   current
     DESCRIPTION
        "The route map name  ,A meaningful name for the route map. The
        redistribute router configuration command uses this
        name to reference the route map. Multiple route maps
        might share the same map tag name.
        
        When this string be used as an index,Value of a sub-identifier equal 
        ASCII value of corresponding character(first sub-identifier corresponds
        first character of string). The number of sub-identifiers of this string
        must be 32,If length of string is less than 32 the sub-identifier(0x0) 
        will be filled in tail."
    ::= { ruijieRouteMapEntry 1 }    
         
ruijieRouteMapSequenceNumber   OBJECT-TYPE
     SYNTAX   Unsigned32(0..65535)
     MAX-ACCESS   read-only
     STATUS   current
     DESCRIPTION
        "Number that indicates the position of a new route map in the 
         list of route maps already configured with the same name."
     DEFVAL {10}
    ::= { ruijieRouteMapEntry 2 }    

ruijieRouteMapOperType   OBJECT-TYPE
     SYNTAX   INTEGER
                    { permit(1),
                      deny(2)
                     }
     MAX-ACCESS   read-only
     STATUS   current
     DESCRIPTION
        " If permit is specified and the match criteria are
        met for this route map, the route is redistributed as
        controlled by the set actions. If deny is specified, the route
        is not redistributed.  "
     DEFVAL {permit}
    ::= { ruijieRouteMapEntry 3 }      
    
ruijieRouteMapMatchMetric   OBJECT-TYPE  
     SYNTAX   Unsigned32(0..2147483647) 
     MAX-ACCESS   read-create
     STATUS   current
     DESCRIPTION
        " Match the specified route metric. The metric-value can be
          an IGRP 5-part metric with a value from 1 to 255.
          0 indicate that this item will not be matched."
     DEFVAL {0}
    ::= { ruijieRouteMapEntry 4 }       
    
ruijieRouteMapMatchRouteType   OBJECT-TYPE  
     SYNTAX   INTEGER{
                	 notMatch(0),
               	 internal(1),
               	 external(2),
                	 external-type1(3),
                	 external-type2(4)                   	
                	} 
     MAX-ACCESS   read-create
     STATUS   current
     DESCRIPTION
        "  the route type value which route-map match,
           internal: OSPF intra-area and interarea routes or EIGRP internal routes,
           external: OSPF external routes(Type 1 or Type 2)or EIGRP external routes,
           external-type1: OSPF external routes Type 1 
           external-type2: OSPF external routes Type 2
           'notMatch' indicate that this item will not be matched."
     DEFVAL {notMatch}
    ::= { ruijieRouteMapEntry 5}      

ruijieRouteMapMetricValueType   OBJECT-TYPE  
     SYNTAX INTEGER{
           noOper(0),
     		  replace(1),
     		  add(2), 
     		  reduce(3)
     		} 
     MAX-ACCESS   read-create
     STATUS   current
     DESCRIPTION
        " How to modify old metric vlaue.
          'noOper':  metric value will not be modified.
          'replace': old metric value will be replaced by  ruijieRouteMapSetMetric.
          'add': new metric value will equal 'old metric vlaue + ruijieRouteMapSetMetric'
          'reduce': new metric value will equal 'old metric vlaue - ruijieRouteMapSetMetric'"
     DEFVAL {noOper}
    ::= { ruijieRouteMapEntry 6 } 
           
ruijieRouteMapSetMetric   OBJECT-TYPE  
     SYNTAX   Unsigned32(1..2147483647)
     MAX-ACCESS   read-create
     STATUS   current
     DESCRIPTION
        " Set the metric value to the given redistributed routes (for
         any protocol except IGRP or EIGRP). The metric value is
         an integer from 1 to 255.
         
         ruijieRouteMapMetricValueType will decide real operation.  The value of
         ruijieRouteMapSetMetric is invalid in ruijieRouteMapMetricValueType is 
         'noOper'."
     DEFVAL {1}
    ::= { ruijieRouteMapEntry 7 }
    
ruijieRouteMapSetLevel   OBJECT-TYPE  
     SYNTAX   INTEGER{
     		  all(0),
     		  stubarea(1), -- OSPF NSSA
     		  backbone(2)  -- OSPF backbone areas
     		} 
     MAX-ACCESS   read-create
     STATUS   current
     DESCRIPTION
        "Set the level for routes that are advertised into the
         specified area of the routing domain.
         'all'indicate that routes will be advertised into all type area."
     DEFVAL {all}
    ::= { ruijieRouteMapEntry 8 }       
    
ruijieRouteMapSetMetricType   OBJECT-TYPE  
     SYNTAX   INTEGER{
                 	 noOper(0),
               	 internal(1),
                	 external(2),
                	 type1(3),
                	 type2(4)
                	} 
     MAX-ACCESS   read-create
     STATUS   current
     DESCRIPTION
        " set metric type,
         'external' means   IS-IS external metric;
         'internal' means   Use IGP metric as the MED for BGP;
         'type-1  ' means  OSPF external type 1 metric;
         'type-2 '  means  OSPF external type 2 metric.
         'noOper'indicate that no any opertion will be done for this item."
     DEFVAL {noOper}
    ::= { ruijieRouteMapEntry 9}    

ruijieRouteMapSetNexthopSt   OBJECT-TYPE  
     SYNTAX ConfigStatus
     MAX-ACCESS   read-create
     STATUS   current
     DESCRIPTION
        " How to modify nexthop vlaue.
          'invalid': nexthop value will not be modified.
          'valid':  nexthop value will be modified to ruijieRouteMapSetNexthop.
          Setting this value to 'valid' have no any effect.This value will be changed 
          to 'valid' when setting 'ruijieRouteMapSetNexthop'"
     DEFVAL {invalid}
    ::= { ruijieRouteMapEntry 10 } 
           
ruijieRouteMapSetNexthop   OBJECT-TYPE  
     SYNTAX   IpAddress
     MAX-ACCESS   read-create
     STATUS   current
     DESCRIPTION
        " Set the nexthop value to give the redistributed routes"
    ::= { ruijieRouteMapEntry 11 }

ruijieRouteMapStatus   OBJECT-TYPE  
     SYNTAX   RowStatus
     MAX-ACCESS   read-create
     STATUS   current
     DESCRIPTION
        " if this value is destroy,the entry will be delete."
    ::= { ruijieRouteMapEntry 12 }    


--ruijieRouteMapMatchIpAddressTable

ruijieRouteMapMatchIpAddressTable OBJECT-TYPE
     SYNTAX   SEQUENCE OF RuijieRouteMapMatchIpAddressEntry 
     MAX-ACCESS   not-accessible
     STATUS   current
     DESCRIPTION
        "the match ip address item of the route map ."
    ::= { ruijieRouteMapMIBObjects  2 }

ruijieRouteMapMatchIpAddressEntry OBJECT-TYPE
    SYNTAX   RuijieRouteMapMatchIpAddressEntry
    MAX-ACCESS   not-accessible
    STATUS   current
    DESCRIPTION
       "Match a standard access list by specifying the Acl name "
   INDEX {
            ruijieRouteMapName,      
            ruijieRouteMapSequenceNumber, 
            ruijieRouteMapMatchType,  
            ruijieRouteMapMatchIpAddressAclName
          }
   ::= { ruijieRouteMapMatchIpAddressTable 1 }
   
RuijieRouteMapMatchIpAddressEntry ::=
  SEQUENCE{
     ruijieRouteMapMatchType
         INTEGER,    
     ruijieRouteMapMatchIpAddressAclName  
         DisplayString,         
     ruijieRouteMapMatchIpAddressStatus
         RowStatus
           }   

ruijieRouteMapMatchType   OBJECT-TYPE  
     SYNTAX   INTEGER{
             destination(1),
             nextHop(2),
             source(3)
     }
     MAX-ACCESS   read-only
     STATUS   current
     DESCRIPTION
        "destination(1):match route destination ip address 
         nextHop(2):match route nextHop ip address
         source(3):match route source ip address
        "
    ::= { ruijieRouteMapMatchIpAddressEntry 1 }
                  
ruijieRouteMapMatchIpAddressAclName   OBJECT-TYPE  
     SYNTAX   DisplayString(SIZE(1..32)) 
     MAX-ACCESS   read-only
     STATUS   current
     DESCRIPTION
        "The acl name apply to ip address.
        
        When this string be used as an index,Value of a sub-identifier equal 
        ASCII value of corresponding character(first sub-identifier corresponds
        first character of string). The number of sub-identifiers of this string
        must be 32,If length of string is less than 32 the sub-identifier(0x0) 
        will be filled in tail."
    ::= { ruijieRouteMapMatchIpAddressEntry 2 }
             
ruijieRouteMapMatchIpAddressStatus  OBJECT-TYPE
     SYNTAX   RowStatus                      
     MAX-ACCESS   read-create
     STATUS   current
     DESCRIPTION
        "The entry status,if the value is destroy ,the 
          entry will be deleted."
    ::= { ruijieRouteMapMatchIpAddressEntry 3 }       
    
--ruijieRouteMapMatchTagTable

ruijieRouteMapMatchTagTable OBJECT-TYPE
     SYNTAX   SEQUENCE OF RuijieRouteMapMatchTagEntry
     MAX-ACCESS   not-accessible
     STATUS   current
     DESCRIPTION
        "Match a tag value item of route map "
    ::= { ruijieRouteMapMIBObjects  3 }

ruijieRouteMapMatchTagEntry OBJECT-TYPE
    SYNTAX   RuijieRouteMapMatchTagEntry
    MAX-ACCESS   not-accessible
    STATUS   current
    DESCRIPTION
       "Match the specified tag value in a list of one or more route
        tag values. Each can be an integer from 0 to 4294967295. "
   INDEX {
            ruijieRouteMapName,     
            ruijieRouteMapSequenceNumber,
            ruijieRouteMapMatchTagValue 
          }
   ::= { ruijieRouteMapMatchTagTable 1 }
   
RuijieRouteMapMatchTagEntry ::=
  SEQUENCE{
     ruijieRouteMapMatchTagValue  
         Unsigned32,
     ruijieRouteMapMatchTagStatus
         RowStatus
           }   
ruijieRouteMapMatchTagValue   OBJECT-TYPE  
     SYNTAX   Unsigned32(0..2147483647) 
     MAX-ACCESS   read-only
     STATUS   current
     DESCRIPTION
        "  Match the specified tag value."
    ::= { ruijieRouteMapMatchTagEntry 1 }   
    
ruijieRouteMapMatchTagStatus   OBJECT-TYPE
     SYNTAX   RowStatus
     MAX-ACCESS   read-create
     STATUS   current
     DESCRIPTION
        "  the entry status,if the value is destroy ,the 
        entry will be deleted."
    ::= { ruijieRouteMapMatchTagEntry 2 }


--ruijieRouteMapMatchInterfaceTable

ruijieRouteMapMatchInterfaceTable OBJECT-TYPE
     SYNTAX   SEQUENCE OF RuijieRouteMapMatchInterfaceEntry
     MAX-ACCESS   not-accessible
     STATUS   current
     DESCRIPTION
        "Match Interface item of route map ."
    ::= { ruijieRouteMapMIBObjects  4 }

ruijieRouteMapMatchInterfaceEntry OBJECT-TYPE
    SYNTAX   RuijieRouteMapMatchInterfaceEntry
    MAX-ACCESS   not-accessible
    STATUS   current
    DESCRIPTION
       "Match the specified next hop route out one of the specified
       interfaces. "
   INDEX {
            ruijieRouteMapName,    
            ruijieRouteMapSequenceNumber,  
            ruijieRouteMapMatchInterfaceIfIndex                  
          }
   ::= { ruijieRouteMapMatchInterfaceTable 1 }
   
RuijieRouteMapMatchInterfaceEntry ::=
  SEQUENCE{
     ruijieRouteMapMatchInterfaceIfIndex
            IfIndex,
     ruijieRouteMapMatchInterfaceStatus
            RowStatus
           }   
           
ruijieRouteMapMatchInterfaceIfIndex   OBJECT-TYPE  
     SYNTAX   IfIndex 
     MAX-ACCESS   read-only
     STATUS   current
     DESCRIPTION
        "  The ifTable's ifIndex."
    ::= { ruijieRouteMapMatchInterfaceEntry 1 }   
    
ruijieRouteMapMatchInterfaceStatus  OBJECT-TYPE
     SYNTAX   RowStatus
     MAX-ACCESS   read-create
     STATUS   current
     DESCRIPTION
        "  the entry status,if the value is destroy ,the 
        entry will be deleted."
    ::= { ruijieRouteMapMatchInterfaceEntry 2 }
         
--Route redistribute group
ruijieRouteRedistributeMIBObjects OBJECT IDENTIFIER ::= { ruijieRouteMIB 3 }

--Routing Redistribute table
ruijieRouteRedistributeTable OBJECT-TYPE
        SYNTAX   SEQUENCE OF RuijieRouteRedistributeEntry
        MAX-ACCESS   not-accessible
        STATUS   current
        DESCRIPTION
           " this table descripts the redistributing methods."
       ::= { ruijieRouteRedistributeMIBObjects  1 }

ruijieRouteRedistributeEntry OBJECT-TYPE
       SYNTAX   RuijieRouteRedistributeEntry
       MAX-ACCESS   not-accessible
       STATUS   current
       DESCRIPTION
          "each entry descripts the methord,when Redistribute routes 
           from one routing protocol to another routing protocol."
      INDEX {ruijieRouteRedistributeProtocolCfg, 
             ruijieRouteRedistributeProtocol
            }
      ::= { ruijieRouteRedistributeTable 1 }
      
RuijieRouteRedistributeEntry ::=
     SEQUENCE{
         ruijieRouteRedistributeProtocolCfg
            RuijieRouteProtoType,
         ruijieRouteRedistributeProtocol
            RuijieRouteProtoType,
         ruijieRouteRedistributeMetricValue
            Unsigned32,
         ruijieRouteRedistributeMetricType
            INTEGER,
         ruijieRouteRedistributeTagValue
            Unsigned32,
         ruijieRouteRedistributeRouteMapName
            DisplayString,
         ruijieRouteRedistributeStatus
            RowStatus
              }

ruijieRouteRedistributeProtocolCfg OBJECT-TYPE
       SYNTAX   RuijieRouteProtoType                       
       MAX-ACCESS   read-only
       STATUS   current
       DESCRIPTION 
           "The protocol which the redistributing will be setted in."  
       ::={ruijieRouteRedistributeEntry 1}  
       
ruijieRouteRedistributeProtocol OBJECT-TYPE
       SYNTAX   RuijieRouteProtoType
       MAX-ACCESS   read-only
       STATUS   current
       DESCRIPTION 
           "The protocol which routing will redistribute to ."  
       ::={ruijieRouteRedistributeEntry 2}         
          
ruijieRouteRedistributeMetricValue OBJECT-TYPE
        SYNTAX   Unsigned32(1..16777214)
        MAX-ACCESS   read-create
        STATUS   current
        DESCRIPTION
           "0 indicate that redistributing metric value will equal 
            ruijieOspfRouteRedisDefMetricVal for OSPF or 
            ruijieRipOffsetMetric for RIP. Other value indicate that
            ruijieRouteRedistributeMetricValue will be set for new metric value
            for redistribute routes,for rip this value only can be from 1 to 16."
        DEFVAL {0}   
        ::= { ruijieRouteRedistributeEntry 3 }   
       
ruijieRouteRedistributeMetricType  OBJECT-TYPE
        SYNTAX   INTEGER{  
                     type1(1),
                     type2(2)
                   }                        
        MAX-ACCESS   read-create
        STATUS   current
        DESCRIPTION
           " Metric type  value ."
        DEFVAL {type2}   
        ::= { ruijieRouteRedistributeEntry 4 }    
       
ruijieRouteRedistributeTagValue  OBJECT-TYPE
        SYNTAX   Unsigned32(0..4294967295)
        MAX-ACCESS   read-create
        STATUS   current
        DESCRIPTION
           "  Set tag for routes redistributed into OSPF."
        DEFVAL {0}             
        ::= { ruijieRouteRedistributeEntry 5 } 
              
ruijieRouteRedistributeRouteMapName  OBJECT-TYPE
        SYNTAX   DisplayString(SIZE(0..32))
        MAX-ACCESS   read-create
        STATUS   current
        DESCRIPTION
           "Set  route's Route-map reference.Null string indicate that no any route-map
            reference."
        DEFVAL {""}
       ::= { ruijieRouteRedistributeEntry 6 }         
           
ruijieRouteRedistributeStatus  OBJECT-TYPE
        SYNTAX   RowStatus        
        MAX-ACCESS   read-create
        STATUS   current
        DESCRIPTION
           "  the entry status,if the value is destroy ,then 
              disable this redistribute."
       ::= { ruijieRouteRedistributeEntry 7 } 

ruijieRouteFilteringMIBObjects OBJECT IDENTIFIER ::= { ruijieRouteMIB 4 }
--ip prefix-list table
ruijieIpPrefixListTable OBJECT-TYPE
        SYNTAX   SEQUENCE OF RuijieIpPrefixListEntry
        MAX-ACCESS   not-accessible
        STATUS   current
        DESCRIPTION
           " this table descripts the ip prefix list."
       ::= { ruijieRouteFilteringMIBObjects  1 }

ruijieIpPrefixListEntry OBJECT-TYPE
       SYNTAX   RuijieIpPrefixListEntry
       MAX-ACCESS   not-accessible
       STATUS   current
       DESCRIPTION
          "each entry descripts a prefix list"
      INDEX {ruijieIpPrefixListName, 
             ruijieIpPrefixListSequence
            }
      ::= { ruijieIpPrefixListTable 1 }
      
RuijieIpPrefixListEntry ::=
     SEQUENCE{
         ruijieIpPrefixListName
            DisplayString,
         ruijieIpPrefixListSequence
            Unsigned32,
         ruijieIpPrefixListOperMethod
            INTEGER,
         ruijieIpPrefixListIpAddress
            IpAddress,
         ruijieIpPrefixListMaskLength
            Unsigned32,
         ruijieIpPrefixListMinimumPrefixLength
            Unsigned32,
         ruijieIpPrefixListMaximumPrefixLength
            Unsigned32,
         ruijieIpPrefixListStatus
            RowStatus
              }

ruijieIpPrefixListName OBJECT-TYPE
       SYNTAX   DisplayString(SIZE(1..32))                       
       MAX-ACCESS   read-only
       STATUS   current
       DESCRIPTION 
           "name of ip prefix-list name."  
       ::={ruijieIpPrefixListEntry 1}
       
ruijieIpPrefixListSequence OBJECT-TYPE
       SYNTAX   Unsigned32(0..2147483647)                       
       MAX-ACCESS   read-only
       STATUS   current
       DESCRIPTION 
           "sequence can be set either automatically or manually. 
           if 0 is seted,that means sequence will be created automatically.
           In the case that sequential numbers are set manually, the
           user may pick any number less than 2147483647 and more than 1. 
           In the case that sequential number are set automatically, the sequential 
           number will increase by a unit of five (5) per list. If a list
           with no specified sequential number is created after a list
           with a specified sequential number, the list will 
           automatically pick the next multiple of five (5) as the 
           list number. For example, if a list with number 2 already 
           exists and a new list with no specified number is created,
           the next list will be numbered 5. If lists 2 and 7 already
           exist and a new list with no specified number is created, 
           the new list will be numbered 10."  
       ::={ruijieIpPrefixListEntry 2}
       
ruijieIpPrefixListOperMethod OBJECT-TYPE
       SYNTAX   INTEGER{
                         permit(1),
                         deny(2)
                       }                       
       MAX-ACCESS   read-create
       STATUS   current
       DESCRIPTION 
           "this field specifies whether the prefix for this entry 
           is to permit or deny the listed prefix."  
       ::={ruijieIpPrefixListEntry 3}
       
ruijieIpPrefixListIpAddress OBJECT-TYPE
       SYNTAX   IpAddress                    
       MAX-ACCESS   read-create
       STATUS   current
       DESCRIPTION 
           "ip prefix-list ip address."  
       ::={ruijieIpPrefixListEntry 4}
       
ruijieIpPrefixListMaskLength OBJECT-TYPE
       SYNTAX  Unsigned32(0..32)                       
       MAX-ACCESS   read-create
       STATUS   current
       DESCRIPTION 
           "ip prefix-list mask length."  
       ::={ruijieIpPrefixListEntry 5}
       
ruijieIpPrefixListMinimumPrefixLength OBJECT-TYPE
       SYNTAX  Unsigned32(0..32)                       
       MAX-ACCESS   read-create
       STATUS   current
       DESCRIPTION 
           "this field specifies prefix length. The prefix list
            will be applied if the prefix length is greater than 
            or equal to ruijieIpPrefixListMinimumPrefixLength.
            value '0' means that this parameter has no effect.
            
            The condition 'ruijieIpPrefixListMaximumPrefixLength 
            >= ruijieIpPrefixListMinimumPrefixLength > ruijieIpPrefixListMaskLength'
            must be satisfied when this value is not '0' "  
       ::={ruijieIpPrefixListEntry 6}
       
ruijieIpPrefixListMaximumPrefixLength OBJECT-TYPE
       SYNTAX Unsigned32(0..32)                         
       MAX-ACCESS   read-create
       STATUS   current
       DESCRIPTION 
           "this field specifies prefix length. The prefix list 
            will be applied if the prefix length is less than or 
            equal to ruijieIpPrefixListMaximumPrefixLength.
            value '0' means that this parameter has no effect.
            
            The condition 'ruijieIpPrefixListMaximumPrefixLength 
            >= ruijieIpPrefixListMinimumPrefixLength > ruijieIpPrefixListMaskLength'
            must be satisfied when this value is not '0' "  
       ::={ruijieIpPrefixListEntry 7}
       
ruijieIpPrefixListStatus OBJECT-TYPE
       SYNTAX   RowStatus                    
       MAX-ACCESS   read-create
       STATUS   current
       DESCRIPTION 
           "the entry status,if the value is destroy ,then 
            delete this ip prefix-list."  
       ::={ruijieIpPrefixListEntry 8}  
       
       
--distribute-list table
--distribute-list is used for Filtering both input and output of the routing information
ruijieDistributeListTable OBJECT-TYPE
        SYNTAX   SEQUENCE OF RuijieDistributeListEntry
        MAX-ACCESS   not-accessible
        STATUS   current
        DESCRIPTION
           " this table descripts the distribute list."
       ::= { ruijieRouteFilteringMIBObjects  2 }

ruijieDistributeListEntry OBJECT-TYPE
       SYNTAX   RuijieDistributeListEntry
       MAX-ACCESS   not-accessible
       STATUS   current
       DESCRIPTION
          "distribute-list can be applied to both incoming
           and outgoing routing information,Permit or deny 
           routes from being advertised in routing updates
           depending upon the action listed in the access list or ip prefix list."
      INDEX {ruijieDistributeListCfgProtoType, 
             ruijieDistributeListIfIndex,
             ruijieDistributeListDirection,
             ruijieDistributeListFilteringProtocol
            }
      ::= { ruijieDistributeListTable 1 }
      
RuijieDistributeListEntry ::=
     SEQUENCE{
         ruijieDistributeListCfgProtoType 
             RuijieRouteProtoType,
         ruijieDistributeListIfIndex
             Unsigned32,
         ruijieDistributeListDirection 
            INTEGER,             
         ruijieDistributeListFilteringProtocol
            Unsigned32,
         ruijieDistributeListFilterType
            INTEGER,
         ruijieDistributeListAclName
            DisplayString,
         ruijieDistributeListGateWayIpPrefixName
            DisplayString,
         ruijieDistributeListPrefixIpPrefixName
            DisplayString,      
         ruijieDistributeListStatus
            RowStatus
              }

ruijieDistributeListCfgProtoType OBJECT-TYPE
       SYNTAX   RuijieRouteProtoType                      
       MAX-ACCESS   read-only
       STATUS   current
       DESCRIPTION 
        "This index indicate that which routing protocol
         configuration mode is current mode."
       ::={ruijieDistributeListEntry 1}
       
ruijieDistributeListIfIndex OBJECT-TYPE
       SYNTAX   Unsigned32                       
       MAX-ACCESS   read-only
       STATUS   current
       DESCRIPTION 
          "The interface that this distribute list apply to.
           If this value is 0,it indicate that this distribute list apply in all 
           interfaces.
           Other value is equal to TEXTUAL-CONVENTION 'IfIndex' meaning."
       ::={ruijieDistributeListEntry 2}

ruijieDistributeListDirection OBJECT-TYPE
       SYNTAX  INTEGER{
                         out(1),
                         in(2)
                       }                        
       MAX-ACCESS   read-only
       STATUS   current
       DESCRIPTION 
           "If direct is 'in' the distribute list is applied to input packets，
            If direct is 'out' the distribute list is applied to output packets."
       ::={ruijieDistributeListEntry 3}

ruijieDistributeListFilteringProtocol OBJECT-TYPE
       SYNTAX Unsigned32              
       MAX-ACCESS read-only
       STATUS   current
       DESCRIPTION 
           "If this value is 0,it indicate that this distribute list will apply on 
            all protocol.
            
            Other value is equal to TEXTUAL-CONVENTION 'RuijieRouteProtoType' meaning,
            it indicate the protocol which this distribute list apply on."   
       ::={ruijieDistributeListEntry 4}
                     
ruijieDistributeListFilterType OBJECT-TYPE
       SYNTAX   INTEGER{
                         acl(1),
                         gateway(2),
                         prefix(3),
                         prefix-gateway(4)
                       }                       
       MAX-ACCESS   read-create
       STATUS   current
       DESCRIPTION 
           "this field defines the filtering type which
            distribute-list used ,
            'acl' means filtering destination ip address of  route 
              information in incoming or outing packets;
            'gateway' means filtering source ip address and mask of incoming packets;
            'prefix' means filtering destination ip address and mask of route
             information in incoming or outing packets;
            'prefix-gateway' means that firstly filtering  destination 
             ip address and mask of route information in incoming or outing packets,
             secondly filtering source ip address and mask of incoming packets.
             if Prefix-list filter is configed,Access-list filter can not be configed;
             if  Access-list filter is configed,Prefix-list filter can not be configed."  
       ::={ruijieDistributeListEntry 5}
       
ruijieDistributeListAclName OBJECT-TYPE
       SYNTAX DisplayString(SIZE (0..32))
       MAX-ACCESS   read-create
       STATUS   current
       DESCRIPTION 
           " This field is valid when the field ruijieDistributeListFilterType's value
             is 'acl',it's access list name that distribute-list reference to.
             Null string indicate that the distribute list will not reference any ACL"
       ::={ruijieDistributeListEntry 6}
       
ruijieDistributeListGateWayIpPrefixName OBJECT-TYPE
       SYNTAX DisplayString(SIZE (0..32))
       MAX-ACCESS   read-create
       STATUS   current
       DESCRIPTION 
           " this field is valid when the field ruijieDistributeListFilterType's value
             is 'gateway',it's ip prefix list name that distribute-list source ip and mask
             reference to.
             
             Null string indicate that the distribute list source ip and mask 
             will not reference any ip prefix list." 
       ::={ruijieDistributeListEntry 7}
       
ruijieDistributeListPrefixIpPrefixName OBJECT-TYPE
       SYNTAX DisplayString(SIZE (0..32))
       MAX-ACCESS   read-create
       STATUS   current
       DESCRIPTION 
           " this field is valid when the field ruijieDistributeListFilterType's value
             is 'gateway',it's ip prefix list name that distribute-list destination 
             ip and mask reference to.
             
             Null string indicate that the distribute list destination ip and mask 
             will not reference any ip prefix list."   
       ::={ruijieDistributeListEntry 8}
              
ruijieDistributeListStatus OBJECT-TYPE
       SYNTAX   RowStatus        
       MAX-ACCESS   read-create
       STATUS   current
       DESCRIPTION 
           "the entry status,if the value is destroy ,then 
            delete this distribute-list."  
       ::={ruijieDistributeListEntry 9}
                     
ruijieipCidrRouteExtendMIBObjects OBJECT IDENTIFIER ::= { ruijieRouteMIB 5 }    
ruijieipCidrRouteTable OBJECT-TYPE
    SYNTAX   SEQUENCE OF RuijieIpCidrRouteEntry
    MAX-ACCESS not-accessible
    STATUS   current
    DESCRIPTION
       "This entity's IP Routing table."
    REFERENCE
       "RFC 1213 Section 6.6, The IP Group"
    ::= { ruijieipCidrRouteExtendMIBObjects 1 }

ruijieipCidrRouteEntry OBJECT-TYPE
    SYNTAX   RuijieIpCidrRouteEntry
    MAX-ACCESS not-accessible
    STATUS   current
    DESCRIPTION
       "A particular route to  a  particular  destina-
       tion, under a particular policy."
    INDEX {
        ruijieipCidrRouteDest,
        ruijieipCidrRouteMask,
        ruijieipCidrRouteTos,
        ruijieipCidrRouteNextHop
        }
    ::= { ruijieipCidrRouteTable 1 }

RuijieIpCidrRouteEntry ::=
    SEQUENCE {
        ruijieipCidrRouteDest
            IpAddress,
        ruijieipCidrRouteMask
            IpAddress,
        ruijieipCidrRouteTos
             Integer32,
        ruijieipCidrRouteNextHop
            IpAddress,
        ruijieipCidrRouteIfIndex
            Integer32,
        ruijieipCidrRouteType
            INTEGER,
        ruijieipCidrRouteProto
            INTEGER,
        ruijieipCidrRouteAge
            Integer32,
        ruijieipCidrRouteInfo
            OBJECT IDENTIFIER,
        ruijieipCidrRouteNextHopAS
            Integer32,
        ruijieipCidrRouteMetric1
            Integer32,
        ruijieipCidrRouteMetric2
            Integer32,
        ruijieipCidrRouteMetric3
            Integer32,
        ruijieipCidrRouteMetric4
            Integer32,
        ruijieipCidrRouteMetric5
            Integer32,
        ruijieipCidrRouteStatus
            RowStatus,
        ruijieipCidrOspfRouteType
            INTEGER
    }

ruijieipCidrRouteDest OBJECT-TYPE
    SYNTAX   IpAddress
    MAX-ACCESS read-only
    STATUS   current
    DESCRIPTION
       "The destination IP address of this route.

       This object may not take a Multicast (Class  D)
       address value.

       Any assignment (implicit or  otherwise)  of  an
       instance  of  this  object to a value x must be
       rejected if the bitwise logical-AND of  x  with
       the  value of the corresponding instance of the
       ipCidrRouteMask object is not equal to x."
    ::= { ruijieipCidrRouteEntry 1 }

ruijieipCidrRouteMask OBJECT-TYPE
    SYNTAX   IpAddress
    MAX-ACCESS read-only
    STATUS   current
    DESCRIPTION
       "Indicate the mask to be logical-ANDed with the
       destination  address  before  being compared to
       the value  in  the  ipCidrRouteDest  field.   For
       those  systems  that  do  not support arbitrary
       subnet masks, an agent constructs the value  of
       the  ipCidrRouteMask  by  reference to the IP Ad-
       dress Class.

       Any assignment (implicit or  otherwise)  of  an
       instance  of  this  object to a value x must be
       rejected if the bitwise logical-AND of  x  with
       the  value of the corresponding instance of the
       ipCidrRouteDest object is not equal to ipCidrRoute-
       Dest."
    ::= { ruijieipCidrRouteEntry 2 }

-- The following convention is included for specification
-- of TOS Field contents.  At this time, the Host Requirements
-- and the Router Requirements documents disagree on the width
-- of the TOS field.  This mapping describes the Router
-- Requirements mapping, and leaves room to widen the TOS field
-- without impact to fielded systems.

ruijieipCidrRouteTos OBJECT-TYPE
    SYNTAX   Integer32
    MAX-ACCESS read-only
    STATUS   current
    DESCRIPTION
       "The policy specifier is the IP TOS Field.  The encoding
       of IP TOS is as specified  by  the  following convention.
       Zero indicates the default path if no more  specific
       policy applies.

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy
           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22
           1 1 0 0  ==>  24      1 1 0 1  ==>  26
           1 1 1 0  ==>  28      1 1 1 1  ==>  30"
    ::= { ruijieipCidrRouteEntry 3 }

ruijieipCidrRouteNextHop OBJECT-TYPE
    SYNTAX   IpAddress
    MAX-ACCESS read-only
    STATUS   current
    DESCRIPTION
       "On remote routes, the address of the next sys-
       tem en route; Otherwise, 0.0.0.0."
    ::= { ruijieipCidrRouteEntry 4 }

ruijieipCidrRouteIfIndex OBJECT-TYPE
    SYNTAX   Integer32
    MAX-ACCESS read-create
    STATUS   current
    DESCRIPTION
       "The ifIndex value which identifies  the  local
       interface  through  which  the next hop of this
       route should be reached."
    DEFVAL { 0 }
    ::= { ruijieipCidrRouteEntry 5 }

ruijieipCidrRouteType OBJECT-TYPE
    SYNTAX   INTEGER {
                other    (1), -- not specified by this MIB
                reject   (2), -- route which discards traffic
                local    (3), -- local interface
                remote   (4)  -- remote destination
             }
    MAX-ACCESS read-create
    STATUS   current
    DESCRIPTION
       "The type of route.  Note that local(3)  refers
       to  a route for which the next hop is the final
       destination; remote(4) refers to  a  route  for
       which  the  next  hop is not the final destina-
       tion.

       Routes which do not result in traffic forwarding or
       rejection should not be displayed even if the
       implementation keeps them stored internally.


       reject (2) refers to a route which, if matched, discards
       the message as unreachable. This is used in some
       protocols as a means of correctly aggregating routes."
    ::= { ruijieipCidrRouteEntry 6 }

ruijieipCidrRouteProto OBJECT-TYPE
    SYNTAX   INTEGER {
                other     (1),  -- not specified
                local     (2),  -- local interface
                netmgmt   (3),  -- static route
                icmp      (4),  -- result of ICMP Redirect

                        -- the following are all dynamic
                        -- routing protocols
                egp        (5),  -- Exterior Gateway Protocol
                ggp        (6),  -- Gateway-Gateway Protocol
                hello      (7),  -- FuzzBall HelloSpeak
                rip        (8),  -- Berkeley RIP or RIP-II
                isIs       (9),  -- Dual IS-IS
                esIs       (10), -- ISO 9542
                ciscoIgrp  (11), -- Cisco IGRP
                bbnSpfIgp  (12), -- BBN SPF IGP
                ospf       (13), -- Open Shortest Path First
                bgp        (14), -- Border Gateway Protocol
                idpr       (15), -- InterDomain Policy Routing
                ciscoEigrp (16), -- Cisco EIGRP
                policy     (17)  -- Ruijie private policy-route
                
             }
    MAX-ACCESS read-only
    STATUS   current
    DESCRIPTION
       "The routing mechanism via which this route was
       learned.  Inclusion of values for gateway rout-
       ing protocols is not  intended  to  imply  that
       hosts should support those protocols."
    ::= { ruijieipCidrRouteEntry 7 }

ruijieipCidrRouteAge OBJECT-TYPE
    SYNTAX   Integer32
    MAX-ACCESS read-only
    STATUS   current
    DESCRIPTION
       "The number of seconds  since  this  route  was
       last  updated  or  otherwise  determined  to be
       correct.  Note that no semantics of  `too  old'
       can  be implied except through knowledge of the
       routing  protocol  by  which  the   route   was
       learned."
    DEFVAL  { 0 }
    ::= { ruijieipCidrRouteEntry 8 }

ruijieipCidrRouteInfo OBJECT-TYPE
    SYNTAX   OBJECT IDENTIFIER
    MAX-ACCESS read-create
    STATUS   current
    DESCRIPTION
       "A reference to MIB definitions specific to the
       particular  routing protocol which is responsi-
       ble for this route, as determined by the  value
       specified  in the route's ipCidrRouteProto value.
       If this information is not present,  its  value
       should be set to the OBJECT IDENTIFIER { 0 0 },
       which is a syntactically valid object  identif-
       ier, and any implementation conforming to ASN.1
       and the Basic Encoding Rules must  be  able  to
       generate and recognize this value."
    ::= { ruijieipCidrRouteEntry 9 }

ruijieipCidrRouteNextHopAS OBJECT-TYPE
    SYNTAX   Integer32
    MAX-ACCESS read-create
    STATUS   current
    DESCRIPTION
       "The Autonomous System Number of the Next  Hop.
       The  semantics of this object are determined by
       the routing-protocol specified in  the  route's
       ipCidrRouteProto  value. When  this object is
       unknown or not relevant its value should be set
       to zero."
    DEFVAL { 0 }
    ::= { ruijieipCidrRouteEntry 10 }

ruijieipCidrRouteMetric1 OBJECT-TYPE
    SYNTAX   Integer32
    MAX-ACCESS read-create
    STATUS   current
    DESCRIPTION
       "The primary routing  metric  for  this  route.
       The  semantics of this metric are determined by
       the routing-protocol specified in  the  route's
       ipCidrRouteProto  value.   If  this metric is not
       used, its value should be set to -1."
    DEFVAL { -1 }
    ::= { ruijieipCidrRouteEntry 11 }

ruijieipCidrRouteMetric2 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ruijieipCidrRouteEntry 12 }

ruijieipCidrRouteMetric3 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ruijieipCidrRouteEntry 13 }

ruijieipCidrRouteMetric4 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ruijieipCidrRouteEntry 14 }

ruijieipCidrRouteMetric5 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ruijieipCidrRouteEntry 15 }

ruijieipCidrRouteStatus OBJECT-TYPE
    SYNTAX   RowStatus
    MAX-ACCESS read-create
    STATUS   current
    DESCRIPTION
       "The row status variable, used according to
       row installation and removal conventions."
    ::= { ruijieipCidrRouteEntry 16 }
    
ruijieipCidrOspfRouteType OBJECT-TYPE
    SYNTAX   INTEGER
             {
               ospf-route    (0), --ospf intra area route 
               ospf-ia-route (1), --ospf inter area route
	       ospf-n1-route (2), --ospf nssa external type 1 route
	       ospf-n2-route (3), --ospf nssa external type 2 route
	       ospf-e1-route (4), --ospf external type 1 route 
	       ospf-e2-route (5)  --OSPF external type 2 route
             }
    MAX-ACCESS read-only
    STATUS   current
    DESCRIPTION
       "this field describles the ospf route entry's type,
        it's valid when this route was learned by ospf protocol."
    ::= { ruijieipCidrRouteEntry 17 }                     
              
ruijieRouteMIBConformance OBJECT IDENTIFIER ::= { ruijieRouteMIB 6 }
ruijieRouteMIBCompliances OBJECT IDENTIFIER ::= { ruijieRouteMIBConformance 1 }
ruijieRouteMIBGroups      OBJECT IDENTIFIER ::= { ruijieRouteMIBConformance 2 }


-- compliance statements

ruijieRouteMIBCompliance MODULE-COMPLIANCE
        STATUS  current
        DESCRIPTION
                "The compliance statement for entities which implement
                the Ruijie Route MIB"
        MODULE  -- this module
                MANDATORY-GROUPS { 
                        ruijieRouteMIBGroup,
                        ruijieRouteInfoMIBGroup,
                        ruijieRouteMapMIBGroup,
                        ruijieRouteRedistributeMIBGroup ,
                        ruijieRouteFilteringMibGroup,
                        ruijieipCidrRouteMibGroup
                 }
        ::= { ruijieRouteMIBCompliances 1 }
                
-- units of conformance
        
ruijieRouteMIBGroup OBJECT-GROUP
        OBJECTS {
             ruijieRouteServiceStatus
        }
        STATUS  current
        DESCRIPTION
                "A collection of objects providing route managment."
        ::= { ruijieRouteMIBGroups 1 }        

ruijieRouteInfoMIBGroup OBJECT-GROUP
        OBJECTS {
           ruijieRoutingProtoInfoProtoType,
           ruijieRoutingProtoInfoGateWay    ,
           ruijieRoutingProtoInfoDistance ,
           ruijieRoutingProtoInfoLastUpdate,
           
           ruijieDefRoutingCfgRoutingProtoType,
           ruijieDefRoutingCfgAlways  ,
           ruijieDefRoutingCfgMetric,
           ruijieDefRoutingCfgMetricType,
           ruijieDefRoutingCfgRouteMap,
           ruijieDefRoutingCfgStatus              
        }
        STATUS  current
        DESCRIPTION
                "A collection of objects providing route information for all routing protocol."
        ::= { ruijieRouteMIBGroups 2}
                
ruijieRouteMapMIBGroup OBJECT-GROUP
        OBJECTS {
           ruijieRouteMapName,
           ruijieRouteMapSequenceNumber,
           ruijieRouteMapOperType   ,
           ruijieRouteMapMatchMetric  ,
           ruijieRouteMapMatchRouteType ,
           ruijieRouteMapMetricValueType    ,
           ruijieRouteMapSetMetric  ,      
           ruijieRouteMapSetLevel  ,
           ruijieRouteMapSetMetricType ,
           ruijieRouteMapSetNexthopSt,
           ruijieRouteMapSetNexthopSt,
           ruijieRouteMapStatus,
           
           ruijieRouteMapMatchIpAddressAclName,
           ruijieRouteMapMatchType,    
           ruijieRouteMapMatchIpAddressStatus,
           
           ruijieRouteMapMatchTagValue  ,
           ruijieRouteMapMatchTagStatus,
         
           ruijieRouteMapMatchInterfaceIfIndex,
           ruijieRouteMapMatchInterfaceStatus
        }
        STATUS  current
        DESCRIPTION
                "A collection of objects providing route managment."
        ::= { ruijieRouteMIBGroups 3 }   
        
ruijieRouteRedistributeMIBGroup OBJECT-GROUP
        OBJECTS {
--         ruijieRouteRedistributeDefMetricVal,
        
         ruijieRouteRedistributeProtocolCfg,
         ruijieRouteRedistributeProtocol,
         ruijieRouteRedistributeMetricValue,
         ruijieRouteRedistributeMetricType,
         ruijieRouteRedistributeTagValue,
         ruijieRouteRedistributeRouteMapName,
         ruijieRouteRedistributeStatus
        }
        STATUS  current
        DESCRIPTION
                "A collection of objects providing route Redistributting."
        ::= { ruijieRouteMIBGroups 4 }   
        
ruijieRouteFilteringMibGroup  OBJECT-GROUP
        OBJECTS { 
                  ruijieIpPrefixListName,
                  ruijieIpPrefixListSequence,
                  ruijieIpPrefixListOperMethod,
                  ruijieIpPrefixListIpAddress,
                  ruijieIpPrefixListMaskLength,
                  ruijieIpPrefixListMinimumPrefixLength,
                  ruijieIpPrefixListMaximumPrefixLength,
                  ruijieIpPrefixListStatus,
                  
                  ruijieDistributeListCfgProtoType ,
                  ruijieDistributeListIfIndex,
                  ruijieDistributeListFilterType,
                  ruijieDistributeListDirection ,
                  ruijieDistributeListAclName,
                  ruijieDistributeListGateWayIpPrefixName,
                  ruijieDistributeListPrefixIpPrefixName,
                  ruijieDistributeListFilteringProtocol,
                  ruijieDistributeListStatus     
                }
        STATUS  current
        DESCRIPTION
                "A collection of objects providing route distribute-list."
        ::= { ruijieRouteMIBGroups 5 }    
        
ruijieipCidrRouteMibGroup  OBJECT-GROUP
        OBJECTS { 
        ruijieipCidrRouteDest,
        ruijieipCidrRouteMask,
        ruijieipCidrRouteTos,
        ruijieipCidrRouteNextHop,
        ruijieipCidrRouteIfIndex,
        ruijieipCidrRouteType,
        ruijieipCidrRouteProto,
        ruijieipCidrRouteAge,
        ruijieipCidrRouteInfo,
        ruijieipCidrRouteNextHopAS,
        ruijieipCidrRouteMetric1,
        ruijieipCidrRouteMetric2,
        ruijieipCidrRouteMetric3,
        ruijieipCidrRouteMetric4,
        ruijieipCidrRouteMetric5,
        ruijieipCidrRouteStatus,
        ruijieipCidrOspfRouteType
                }
        STATUS  current
        DESCRIPTION
                "A collection of objects providing CIDR Route Table."
        ::= { ruijieRouteMIBGroups 6 }

-- Notifications
ruijieRouteTrap  OBJECT IDENTIFIER ::= { ruijieRouteMIB 7 }
ruijieVrfRouteThresholdExceed NOTIFICATION-TYPE
    OBJECTS {
                ruijieRouteVrfName,
                ruijieAddressFamilyAfi,
                ruijieRouteLimitNum,
                ruijieRouteLimitThreshold,
                ruijieRouteLimitCurrentNum
            }
    STATUS          current
    DESCRIPTION
        "The ruijieRouteThresholdExceed is generated when the 
        number of routes in the VPN instance received from the alarm threshold."
   ::= { ruijieRouteTrap 1 }
ruijieVrfRouteThresholdClear NOTIFICATION-TYPE
    OBJECTS {
                ruijieRouteVrfName,
                ruijieAddressFamilyAfi,
                ruijieRouteLimitNum,
                ruijieRouteLimitThreshold,
                ruijieRouteLimitCurrentNum
            }
    STATUS          current
    DESCRIPTION
        "The ruijieVrfRouteThresholdClear is generated when the 
        number of routes received in the VPN instance decreased 
        below the alarm threshold."
   ::= { ruijieRouteTrap 2 }
ruijieVrfRouteExceed NOTIFICATION-TYPE
    OBJECTS {
                ruijieRouteVrfName,
                ruijieAddressFamilyAfi,
                ruijieRouteLimitNum,
                ruijieRouteLimitCurrentNum
            }
    STATUS          current
    DESCRIPTION
        "The ruijieRouteExceed is generated when the
        number of routes in the VPN instance reached the 
        alarm threshould."
   ::= { ruijieRouteTrap 3 }

ruijieVrfRouteExceedClear NOTIFICATION-TYPE
    OBJECTS {
                ruijieRouteVrfName,
                ruijieAddressFamilyAfi,
                ruijieRouteLimitNum,
                ruijieRouteLimitCurrentNum
            }
    STATUS          current
    DESCRIPTION
        "The ruijieVrfRouteExceedClear is generated when the
        number of routes received in the VPN instance 
        decreased below the alarm number."
   ::= { ruijieRouteTrap 4 }

ruijieRouteVrfName OBJECT-TYPE
    SYNTAX     DisplayString(SIZE(0..64))
    MAX-ACCESS read-only
    STATUS     current
    DESCRIPTION
            "VPN instance name."
    ::= { ruijieRouteTrap 5 }     
ruijieAddressFamilyAfi OBJECT-TYPE
    SYNTAX     AddressFamilyNumbers
    MAX-ACCESS read-only
    STATUS     current
    DESCRIPTION
            "The destination IP address family afi."
    ::= { ruijieRouteTrap 6 }

ruijieRouteLimitNum OBJECT-TYPE
    SYNTAX     Unsigned32
    MAX-ACCESS read-only
    STATUS     current
    DESCRIPTION
            "Route limit."
    ::= { ruijieRouteTrap 7 }
ruijieRouteLimitThreshold OBJECT-TYPE
    SYNTAX     INTEGER(1..100)
    MAX-ACCESS read-only
    STATUS     current
    DESCRIPTION
            "Route limit threshold."
    ::= { ruijieRouteTrap 8 }    

ruijieRouteLimitCurrentNum OBJECT-TYPE
    SYNTAX     Unsigned32
    MAX-ACCESS read-only
    STATUS     current
    DESCRIPTION
            "Current route number."
    ::= { ruijieRouteTrap 9 } 

ruijieVrfMplsL3VpnRouteMidClear NOTIFICATION-TYPE
    OBJECTS {
                mplsL3VpnVrfPerfCurrNumRoutes,
                mplsL3VpnVrfConfMidRteThresh
            }
    STATUS          current
    DESCRIPTION
        "The ruijieVrfMplsL3VpnRouteMidClear is generated when the 
        number of routes received in the VPN instance decreased 
        below the alarm threshold."
   ::= { ruijieRouteTrap 10 }

END
