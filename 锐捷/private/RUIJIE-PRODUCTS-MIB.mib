-- *****************************************************************
-- RUIJIE-PRODUCTS-MIB.mib:  Ruijie Product Object Identifier Assignments
--
-- March 2002, Wuzg
--
-- Copyright (c) 2002 by Ruijie Networks Co.,Ltd.
-- All rights reserved.
-- 
-- *****************************************************************
--

RUIJIE-PRODUCTS-MIB DEFINITIONS ::= BEGIN

IMPORTS
        MODULE-IDENTITY
                FROM SNMPv2-SMI
        ruijieModules,        
        ruijieSwitchProducts
                FROM RUIJIE-SMI
        ruijieRouterProducts
                FROM RUIJIE-ROUTER-SMI
        ruijieGatewayProducts                                         
                FROM RUIJIE-GATEWAY-SMI
        ruijieWirelessProducts
                FROM RUIJIE-WIRELESS-SMI
        ruijieSoftwareProducts
                FROM RUIJIE-SOFTWARE-SMI
        ruijieSmartClassProducts
                FROM RUIJIE-SMARTCLASS-SMI;

ruijieProductsMIB MODULE-IDENTITY
        LAST-UPDATED "200203200000Z"
        ORGANIZATION "Ruijie Networks Co.,Ltd."
        CONTACT-INFO
                " 
                Tel: 4008-111-000 

                E-mail: service@ruijie.com.cn"
        DESCRIPTION
                "This module defines the object identifiers that are
            		assigned to various hardware platforms, and hence are
            		returned as values for sysObjectID"
        REVISION      "200203200000Z"
        DESCRIPTION
                "Initial version of this MIB module."
        ::= { ruijieModules 1}

-- devices return a sysObjectID value that corresponds to the
-- device model number

-- ****************************** switch ***********************************

s2126G   OBJECT IDENTIFIER ::= { ruijieSwitchProducts 1 }

s2126GL3 OBJECT IDENTIFIER ::= { ruijieSwitchProducts 2 }

s2150G   OBJECT IDENTIFIER ::= { ruijieSwitchProducts 3 }

s2150GL3 OBJECT IDENTIFIER ::= { ruijieSwitchProducts 4 }

s4909 OBJECT IDENTIFIER ::= { ruijieSwitchProducts 5 }

s3550-12G OBJECT IDENTIFIER ::= { ruijieSwitchProducts 6 }

s3550-24G OBJECT IDENTIFIER ::= { ruijieSwitchProducts 8 }        

s21-STACKING OBJECT IDENTIFIER ::= { ruijieSwitchProducts 11 }

s3550-24 OBJECT IDENTIFIER ::= { ruijieSwitchProducts 12 }

s3550-48 OBJECT IDENTIFIER ::= { ruijieSwitchProducts 13 }

s3550-12SFP-GT OBJECT IDENTIFIER ::= { ruijieSwitchProducts 15 }

s6806 OBJECT IDENTIFIER ::= { ruijieSwitchProducts 16 }

s6810 OBJECT IDENTIFIER ::= { ruijieSwitchProducts 17 }

s2126S OBJECT IDENTIFIER ::= { ruijieSwitchProducts 18 }

s2126S-STACKING OBJECT IDENTIFIER ::= { ruijieSwitchProducts 19 }

s1908PLUS OBJECT IDENTIFIER ::= { ruijieSwitchProducts 20 }

s1916PLUS OBJECT IDENTIFIER ::= { ruijieSwitchProducts 21 }

s6506 OBJECT IDENTIFIER ::= { ruijieSwitchProducts 22 }

s2126S-08  OBJECT IDENTIFIER ::= { ruijieSwitchProducts 23 }

s2126S-16  OBJECT IDENTIFIER ::= { ruijieSwitchProducts 24 }

s6806E OBJECT IDENTIFIER ::= { ruijieSwitchProducts 25 }

s6810E OBJECT IDENTIFIER ::= { ruijieSwitchProducts 26 }

s2026G OBJECT IDENTIFIER ::= { ruijieSwitchProducts 27 }

s3750-24 OBJECT IDENTIFIER ::= { ruijieSwitchProducts 28 }

s3750-48 OBJECT IDENTIFIER ::= { ruijieSwitchProducts 29 }

s2126    OBJECT IDENTIFIER ::= { ruijieSwitchProducts 30 }

s2126-STACKING    OBJECT IDENTIFIER ::= { ruijieSwitchProducts 31 }

-- s2026F OBJECT IDENTIFIER ::= { ruijieSwitchProducts 32 }

s2026F OBJECT IDENTIFIER ::= { ruijieSwitchProducts 33 }

s3760-12SFP-GT OBJECT IDENTIFIER ::= { ruijieSwitchProducts 34 }

s4009 OBJECT IDENTIFIER ::= { ruijieSwitchProducts 35 }            

s3526 OBJECT IDENTIFIER ::= { ruijieSwitchProducts 36 }

s3512G OBJECT IDENTIFIER ::= { ruijieSwitchProducts 37 }

hcl-12GCS-L3 OBJECT IDENTIFIER ::= { ruijieSwitchProducts 38 }

hcl-24GS-L3 OBJECT IDENTIFIER ::= { ruijieSwitchProducts 39 }

hcl-48TMS-2S-S OBJECT IDENTIFIER ::= { ruijieSwitchProducts 40 }

s5750-24GT-12SFP OBJECT IDENTIFIER ::= { ruijieSwitchProducts 41 }

s5750P-24GT-12SFP OBJECT IDENTIFIER ::= { ruijieSwitchProducts 42 }

s8606 OBJECT IDENTIFIER ::= { ruijieSwitchProducts 43 }

s8610 OBJECT IDENTIFIER ::= { ruijieSwitchProducts 44 }

s8606B OBJECT IDENTIFIER ::= { ruijieSwitchProducts 45 }

s9620 OBJECT IDENTIFIER ::= { ruijieSwitchProducts 46 }

s2924G OBJECT IDENTIFIER ::= { ruijieSwitchProducts 47 }

s3760-24 OBJECT IDENTIFIER ::= { ruijieSwitchProducts 48 }

s3760-48 OBJECT IDENTIFIER ::= { ruijieSwitchProducts 49 }

s3750E-24 OBJECT IDENTIFIER ::= { ruijieSwitchProducts 50 }

s3750E-48 OBJECT IDENTIFIER ::= { ruijieSwitchProducts 51 }

--s3750E-12SFP-GT OBJECT IDENTIFIER ::= { ruijieSwitchProducts 52 }

s5750S-24GT-12SFP OBJECT IDENTIFIER ::= { ruijieSwitchProducts 53 }

s2128G OBJECT IDENTIFIER ::= { ruijieSwitchProducts 54 }

s2927XG OBJECT IDENTIFIER ::= { ruijieSwitchProducts 55 }

s3512GPLUS OBJECT IDENTIFIER ::= { ruijieSwitchProducts 56 }

s7604 OBJECT IDENTIFIER ::= { ruijieSwitchProducts 57 }

s7606 OBJECT IDENTIFIER ::= { ruijieSwitchProducts 58 }

s7610 OBJECT IDENTIFIER ::= { ruijieSwitchProducts 59 }

s5750-24SFP-12GT OBJECT IDENTIFIER ::= { ruijieSwitchProducts 60 }

s5750-48GT-4SFP OBJECT IDENTIFIER ::= { ruijieSwitchProducts 61 }

s5750S-48GT-4SFP OBJECT IDENTIFIER ::= { ruijieSwitchProducts 62 }

s3250-24 OBJECT IDENTIFIER ::= { ruijieSwitchProducts 63 }

s3250-48 OBJECT IDENTIFIER ::= { ruijieSwitchProducts 64 }

s2724G OBJECT IDENTIFIER ::= { ruijieSwitchProducts 65 }

s2951XG OBJECT IDENTIFIER ::= { ruijieSwitchProducts 66 }

s3750-24-UB OBJECT IDENTIFIER ::= { ruijieSwitchProducts 67 }

s3750-48-UB OBJECT IDENTIFIER ::= { ruijieSwitchProducts 68 }

scg5510  OBJECT IDENTIFIER ::= { ruijieSwitchProducts 69 }

s2052G  OBJECT IDENTIFIER ::= { ruijieSwitchProducts 70 }

s2328G  OBJECT IDENTIFIER ::= { ruijieSwitchProducts 71 }

s8614  OBJECT IDENTIFIER ::= { ruijieSwitchProducts 72 }

s5760-24GT-4SFP  OBJECT IDENTIFIER ::= { ruijieSwitchProducts 73 }

--s5650-27XG  OBJECT IDENTIFIER ::= { ruijieSwitchProducts 74 }

s5760-48GT-4SFP  OBJECT IDENTIFIER ::= { ruijieSwitchProducts 75 }

--s5450-28GT  OBJECT IDENTIFIER ::= { ruijieSwitchProducts 76 }

s3250P-24  OBJECT IDENTIFIER ::= { ruijieSwitchProducts 78 }

--s2928G  OBJECT IDENTIFIER ::= { ruijieSwitchProducts 79 }

--s2952G  OBJECT IDENTIFIER ::= { ruijieSwitchProducts 80 }

--s2028G  OBJECT IDENTIFIER ::= { ruijieSwitchProducts 81 }

s2628G  OBJECT IDENTIFIER ::= { ruijieSwitchProducts 82 }

s2652G  OBJECT IDENTIFIER ::= { ruijieSwitchProducts 83 }

--s5750R-48GT-4SFP OBJECT IDENTIFIER ::= { ruijieSwitchProducts 84 }

s5750P-48GT-4SFP OBJECT IDENTIFIER ::= { ruijieSwitchProducts 85 }

--s5750R-24GT-4SFP OBJECT IDENTIFIER ::= { ruijieSwitchProducts 86 }

--s5750P-24GT-4SFP OBJECT IDENTIFIER ::= { ruijieSwitchProducts 87 }

--s5750-24GT-4SFP OBJECT IDENTIFIER ::= { ruijieSwitchProducts 88 }

--s5750S-24GT-4SFP OBJECT IDENTIFIER ::= { ruijieSwitchProducts 89 }

s5750-48GT-4SFP-A OBJECT IDENTIFIER ::= { ruijieSwitchProducts 92 }

s5750-48GT-4SFP-AP OBJECT IDENTIFIER ::= { ruijieSwitchProducts 93 }

s2352G OBJECT IDENTIFIER ::= { ruijieSwitchProducts 94 }

--nm2-24esw OBJECT IDENTIFIER ::= { ruijieSwitchProducts 95 }

--nmx-24esw OBJECT IDENTIFIER ::= { ruijieSwitchProducts 95 }

--nm2-16esw OBJECT IDENTIFIER ::= { ruijieSwitchProducts 96 }

--s5750E-24SFP-12GT OBJECT IDENTIFIER ::= { ruijieSwitchProducts 97 }

s3760E-24 OBJECT IDENTIFIER ::= { ruijieSwitchProducts 98 }

s3760E-48 OBJECT IDENTIFIER ::= { ruijieSwitchProducts 99 }

s3250E-24 OBJECT IDENTIFIER ::= { ruijieSwitchProducts 100 }

s2628G-P OBJECT IDENTIFIER ::= { ruijieSwitchProducts 101 }

s3250E-48 OBJECT IDENTIFIER ::= { ruijieSwitchProducts 102 }

s2652G-P OBJECT IDENTIFIER ::= { ruijieSwitchProducts 103 }

S3760E-24P OBJECT IDENTIFIER ::= { ruijieSwitchProducts 104 }

S3760E-48P OBJECT IDENTIFIER ::= { ruijieSwitchProducts 105 }

s2628G-E OBJECT IDENTIFIER ::= { ruijieSwitchProducts 106 }

s2652G-E OBJECT IDENTIFIER ::= { ruijieSwitchProducts 107 }

S5750-24GT/8SFP-E OBJECT IDENTIFIER ::= { ruijieSwitchProducts 111 }

S5750-24GT/8SFP-P OBJECT IDENTIFIER ::= { ruijieSwitchProducts 112 }

S5750-48GT/4SFP-E OBJECT IDENTIFIER ::= { ruijieSwitchProducts 113 }

S5750-48GT/4SFP-P OBJECT IDENTIFIER ::= { ruijieSwitchProducts 114 }

S2928G-E OBJECT IDENTIFIER ::= { ruijieSwitchProducts 117 }

S2952G-E OBJECT IDENTIFIER ::= { ruijieSwitchProducts 118 }

S2924GT/8SFP-XS-P OBJECT IDENTIFIER ::= { ruijieSwitchProducts 120 }

S6200-48XS OBJECT IDENTIFIER ::= { ruijieSwitchProducts 123 }

S2628G-I OBJECT IDENTIFIER ::= { ruijieSwitchProducts 126 }

S2652G-I OBJECT IDENTIFIER ::= { ruijieSwitchProducts 127 }

S6000-48GT4XS OBJECT IDENTIFIER ::= { ruijieSwitchProducts 128 }

S6210-32XS8QXS OBJECT IDENTIFIER ::= { ruijieSwitchProducts 129}

S6210-48XS OBJECT IDENTIFIER ::= { ruijieSwitchProducts 130}

S15010 OBJECT IDENTIFIER ::= { ruijieSwitchProducts 131 }

S12006 OBJECT IDENTIFIER ::= { ruijieSwitchProducts 132 }

S12010 OBJECT IDENTIFIER ::= { ruijieSwitchProducts 133 }

S5750-28GT-L OBJECT IDENTIFIER ::= { ruijieSwitchProducts 137 }

S5750-52GT-L OBJECT IDENTIFIER ::= { ruijieSwitchProducts 138 }

S5750-24SFP/8GT-E OBJECT IDENTIFIER ::= { ruijieSwitchProducts 139 }

S6000-86GT10XS OBJECT IDENTIFIER ::= { ruijieSwitchProducts 141 }

S2928G-S OBJECT IDENTIFIER ::= { ruijieSwitchProducts 142 }

S2950G-S OBJECT IDENTIFIER ::= { ruijieSwitchProducts 143 }

S5750-28GT-S OBJECT IDENTIFIER ::= { ruijieSwitchProducts 144 }

S2628G-S OBJECT IDENTIFIER ::= { ruijieSwitchProducts 146 }

S2652G-S OBJECT IDENTIFIER ::= { ruijieSwitchProducts 147 }

S6220-24XS OBJECT IDENTIFIER ::= { ruijieSwitchProducts 148 }

S6220-48XS4QXS OBJECT IDENTIFIER ::= { ruijieSwitchProducts 150 }

S6220-48XT4QXS OBJECT IDENTIFIER ::= { ruijieSwitchProducts 151 }

S6000-24GT/8SFP OBJECT IDENTIFIER ::= { ruijieSwitchProducts 153 }

S6000-48GT/4SFP OBJECT IDENTIFIER ::= { ruijieSwitchProducts 154 }

S2928G-24P OBJECT IDENTIFIER ::= { ruijieSwitchProducts 155 }

S2928G-12P OBJECT IDENTIFIER ::= { ruijieSwitchProducts 156 }

S5750-24GT/8SFP-S OBJECT IDENTIFIER ::= { ruijieSwitchProducts 157 }

S5750-48GT/4SFP-S OBJECT IDENTIFIER ::= { ruijieSwitchProducts 158 }

RG-S7805E OBJECT IDENTIFIER ::= { ruijieSwitchProducts 159 }

RG-S7807E OBJECT IDENTIFIER ::= { ruijieSwitchProducts 160 }

RG-S7810E OBJECT IDENTIFIER ::= { ruijieSwitchProducts 161 }

RG-S8605E OBJECT IDENTIFIER ::= { ruijieSwitchProducts 162 }

RG-S8607E OBJECT IDENTIFIER ::= { ruijieSwitchProducts 163 }

RG-S8610E OBJECT IDENTIFIER ::= { ruijieSwitchProducts 164 }

RG-N18010 OBJECT IDENTIFIER ::= { ruijieSwitchProducts 165 }

RG-N18014 OBJECT IDENTIFIER ::= { ruijieSwitchProducts 166 }

S2528G-24P OBJECT IDENTIFIER ::= { ruijieSwitchProducts 169 }

RG-N18007 OBJECT IDENTIFIER ::= { ruijieSwitchProducts 170 }

S2910-24GT4XS-E OBJECT IDENTIFIER ::= { ruijieSwitchProducts 174 }

S2910-48GT4XS-E OBJECT IDENTIFIER ::= { ruijieSwitchProducts 175 }

S2910C-24GT2XS-P-E OBJECT IDENTIFIER ::= { ruijieSwitchProducts 176 }

S2910C-24GT2XS-HP-E OBJECT IDENTIFIER ::= { ruijieSwitchProducts 177 }

S2910C-48GT2XS-HP-E OBJECT IDENTIFIER ::= { ruijieSwitchProducts 178 }

S5750-24GT4XS-L OBJECT IDENTIFIER ::= { ruijieSwitchProducts 179 }

S5750-48GT4XS-L OBJECT IDENTIFIER ::= { ruijieSwitchProducts 180 }

S6220-48XS6QXS-H OBJECT IDENTIFIER ::= { ruijieSwitchProducts 184 }

S6220-48XT6QXS-H OBJECT IDENTIFIER ::= { ruijieSwitchProducts 185 }

S2910-24GT4SFP-UP-H OBJECT IDENTIFIER ::= { ruijieSwitchProducts 186 }

S5750-48GT/4SFP-P V5.0 OBJECT IDENTIFIER ::= { ruijieSwitchProducts 188 }

S5750-24GT4XS-H OBJECT IDENTIFIER ::= { ruijieSwitchProducts 190 }

S5750-48GT4XS-H OBJECT IDENTIFIER ::= { ruijieSwitchProducts 191 }

S5750C-28GT4XS-H OBJECT IDENTIFIER ::= { ruijieSwitchProducts 192 }

S5750C-28SFP4XS-H OBJECT IDENTIFIER ::= { ruijieSwitchProducts 193 }

S5750C-48GT4XS-H OBJECT IDENTIFIER ::= { ruijieSwitchProducts 194 }

S5750C-28GT4XS-HP-H OBJECT IDENTIFIER ::= { ruijieSwitchProducts 195 }

S5750C-48GT4XS-HP-H OBJECT IDENTIFIER ::= { ruijieSwitchProducts 196 }

S6000C-28GT4XS-E OBJECT IDENTIFIER ::= { ruijieSwitchProducts 197 }

S6000C-48GT4XS-E OBJECT IDENTIFIER ::= { ruijieSwitchProducts 198 }

RG-S7808C OBJECT IDENTIFIER ::= { ruijieSwitchProducts 199}

S2320G-P OBJECT IDENTIFIER ::= { ruijieSwitchProducts 202 }

NBS5552XG OBJECT IDENTIFIER ::= { ruijieSwitchProducts 206 }

NBS2009G-P OBJECT IDENTIFIER ::= { ruijieSwitchProducts 208 }

NBS5628XG OBJECT IDENTIFIER ::= { ruijieSwitchProducts 210 }

NBS5652XG OBJECT IDENTIFIER ::= { ruijieSwitchProducts 211 }

RG-AS224T OBJECT IDENTIFIER ::= { ruijieSwitchProducts 220 }

RG-AS248T OBJECT IDENTIFIER ::= { ruijieSwitchProducts 221 }

RG-AS224GT OBJECT IDENTIFIER ::= { ruijieSwitchProducts 222 }

RG-AS224GT-P OBJECT IDENTIFIER ::= { ruijieSwitchProducts 223 }

RG-AS248GT OBJECT IDENTIFIER ::= { ruijieSwitchProducts 224 }

RG-AS324GT OBJECT IDENTIFIER ::= { ruijieSwitchProducts 225 }

RG-AS324GF OBJECT IDENTIFIER ::= { ruijieSwitchProducts 226 }

RG-AS348GT OBJECT IDENTIFIER ::= { ruijieSwitchProducts 227 }

RG-AS216T OBJECT IDENTIFIER ::= { ruijieSwitchProducts 228 }

RG-AS216GT OBJECT IDENTIFIER ::= { ruijieSwitchProducts 229 }

NBS228F OBJECT IDENTIFIER ::= { ruijieSwitchProducts 232 }

NBS252F OBJECT IDENTIFIER ::= { ruijieSwitchProducts 233 }

RG-N18010-X OBJECT IDENTIFIER ::= { ruijieSwitchProducts 235 }

RG-N18018-X OBJECT IDENTIFIER ::= { ruijieSwitchProducts 234 }

S2910-10GT2SFP-P-E OBJECT IDENTIFIER ::= { ruijieSwitchProducts 238 }

S2910-10GT2SFP-UP-H OBJECT IDENTIFIER ::= { ruijieSwitchProducts 239 }

S6220-32QXS-H OBJECT IDENTIFIER ::= { ruijieSwitchProducts 241 }

S2910-24GT4XS-UP-H OBJECT IDENTIFIER ::= { ruijieSwitchProducts 286 }

S2710G-P OBJECT IDENTIFIER ::= { ruijieSwitchProducts 294 }

SF2900-8GT2SFP-S OBJECT IDENTIFIER ::= { ruijieSwitchProducts 827 }

SF2900-8GT2SFP-P-S OBJECT IDENTIFIER ::= { ruijieSwitchProducts 828 }

S2900-18GT2SFP-L OBJECT IDENTIFIER ::= { ruijieSwitchProducts 826 }

S2900-8GT2SFP-L OBJECT IDENTIFIER ::= { ruijieSwitchProducts 822 }

S2900-8GT2SFP-P-L OBJECT IDENTIFIER ::= { ruijieSwitchProducts 824 }

S2900-24GT4SFP/2GT-L OBJECT IDENTIFIER ::= { ruijieSwitchProducts 825 }

S2900-24GT4SFP/2GT-P-L OBJECT IDENTIFIER ::= { ruijieSwitchProducts 823 }

-- ****************************** router ***********************************

r2620 OBJECT IDENTIFIER ::= { ruijieRouterProducts 1 }

r2624 OBJECT IDENTIFIER ::= { ruijieRouterProducts 2 }

r2690 OBJECT IDENTIFIER ::= { ruijieRouterProducts 3 }

r2692 OBJECT IDENTIFIER ::= { ruijieRouterProducts 4 }

r3642 OBJECT IDENTIFIER ::= { ruijieRouterProducts 5 }

r3662 OBJECT IDENTIFIER ::= { ruijieRouterProducts 6 }

nbr1000 OBJECT IDENTIFIER ::= { ruijieRouterProducts 7 }

nbr200  OBJECT IDENTIFIER ::= { ruijieRouterProducts 8 }

secvpn100 OBJECT IDENTIFIER ::= { ruijieRouterProducts 9 }

r2632 OBJECT IDENTIFIER ::= { ruijieRouterProducts 10 }

r1762 OBJECT IDENTIFIER ::= { ruijieRouterProducts 11 }

rcms OBJECT IDENTIFIER ::= { ruijieRouterProducts 12 }

hcl-r1762 OBJECT IDENTIFIER ::= { ruijieRouterProducts 13 }

hcl-r2632 OBJECT IDENTIFIER ::= { ruijieRouterProducts 14 }

hcl-r2692 OBJECT IDENTIFIER ::= { ruijieRouterProducts 15 }

hcl-r3642 OBJECT IDENTIFIER ::= { ruijieRouterProducts 16 }

hcl-r3662 OBJECT IDENTIFIER ::= { ruijieRouterProducts 17 }

r3740 OBJECT IDENTIFIER ::= { ruijieRouterProducts 18 }

nbr2000 OBJECT IDENTIFIER ::= { ruijieRouterProducts 19 }

nbr300 OBJECT IDENTIFIER ::= { ruijieRouterProducts 20 }

nbr1200 OBJECT IDENTIFIER ::= { ruijieRouterProducts 21 }

nbr1500 OBJECT IDENTIFIER ::= { ruijieRouterProducts 22 }

r2716 OBJECT IDENTIFIER ::= { ruijieRouterProducts 23 }

r2724 OBJECT IDENTIFIER ::= { ruijieRouterProducts 24 }

r3802 OBJECT IDENTIFIER ::= { ruijieRouterProducts 25 }

r3804 OBJECT IDENTIFIER ::= { ruijieRouterProducts 26 }

rsr50-20 OBJECT IDENTIFIER ::= { ruijieRouterProducts 27 }

rsr50-40 OBJECT IDENTIFIER ::= { ruijieRouterProducts 28 }

rsr50-80 OBJECT IDENTIFIER ::= { ruijieRouterProducts 29 }

npe50-20 OBJECT IDENTIFIER ::= { ruijieRouterProducts 30 }

rsr10-02 OBJECT IDENTIFIER ::= { ruijieRouterProducts 31 }

rsr20-04 OBJECT IDENTIFIER ::= { ruijieRouterProducts 32 }

vpn120 OBJECT IDENTIFIER ::= { ruijieRouterProducts 33 }

rsr20-24 OBJECT IDENTIFIER ::= { ruijieRouterProducts 35 }

--nmx-24esw-l2 OBJECT IDENTIFIER ::= { ruijieRouterProducts 39 }

--nmx-24esw-3gel3 OBJECT IDENTIFIER ::= { ruijieRouterProducts 40 }

rsr20-14 OBJECT IDENTIFIER ::= { ruijieRouterProducts 41 }

rsr30-44 OBJECT IDENTIFIER ::= { ruijieRouterProducts 42 }

r2700v2v3 OBJECT IDENTIFIER ::= { ruijieRouterProducts 43 }

r2700v5 OBJECT IDENTIFIER ::= { ruijieRouterProducts 44 }

npe50-40 OBJECT IDENTIFIER ::= { ruijieRouterProducts 45 }

rsr20-18 OBJECT IDENTIFIER ::= { ruijieRouterProducts 46 }

rsr50E-80 OBJECT IDENTIFIER ::= { ruijieRouterProducts 47 }

npe50e-80 OBJECT IDENTIFIER ::= { ruijieRouterProducts 49 }

rsr7708 OBJECT IDENTIFIER ::= { ruijieRouterProducts 50 }

dnmx-48esw OBJECT IDENTIFIER ::= { ruijieRouterProducts 51 }

rsr7704 OBJECT IDENTIFIER ::= { ruijieRouterProducts 52 }

rsr7716 OBJECT IDENTIFIER ::= { ruijieRouterProducts 53 }

rsr20-14e OBJECT IDENTIFIER ::= { ruijieRouterProducts 54 }

rsr20-14f OBJECT IDENTIFIER ::= { ruijieRouterProducts 55 }

rsr10-01g-w OBJECT IDENTIFIER ::= { ruijieRouterProducts 56 }

rsr10-01g-c OBJECT IDENTIFIER ::= { ruijieRouterProducts 57 }

rsr10-01g-td OBJECT IDENTIFIER ::= { ruijieRouterProducts 58 }

rsr50e-40 OBJECT IDENTIFIER ::= { ruijieRouterProducts 66 }


--*******************wireless*************************************
WS5708-V10 OBJECT IDENTIFIER ::= { ruijieWirelessProducts 1 }

AP220-SE-V10 OBJECT IDENTIFIER ::= { ruijieWirelessProducts 2 }

WS5302-V10 OBJECT IDENTIFIER ::= { ruijieWirelessProducts 3 }

AP220-E-V10 OBJECT IDENTIFIER ::= { ruijieWirelessProducts 4 }

AP620-H-V10 OBJECT IDENTIFIER ::= { ruijieWirelessProducts 5 }

AP220-SH-V10 OBJECT IDENTIFIER ::= { ruijieWirelessProducts 8 }

M8600-WS-V10 OBJECT IDENTIFIER ::= { ruijieWirelessProducts 14 }

AP620-H-S-V10 OBJECT IDENTIFIER ::= { ruijieWirelessProducts 17 }

AP220-SH-V20 OBJECT IDENTIFIER ::= { ruijieWirelessProducts 18 }

AP220-E-V11 OBJECT IDENTIFIER ::= { ruijieWirelessProducts 19 }

AP220-SE-V11 OBJECT IDENTIFIER ::= { ruijieWirelessProducts 20 }

AP220-SH-V11 OBJECT IDENTIFIER ::= { ruijieWirelessProducts 23 }

AP220-E-V20 OBJECT IDENTIFIER ::= { ruijieWirelessProducts 24 }

AP220-SE-V20 OBJECT IDENTIFIER ::= { ruijieWirelessProducts 25 }

AP220-E-V199 OBJECT IDENTIFIER ::= { ruijieWirelessProducts 26 }

AP220-I-V10 OBJECT IDENTIFIER ::= { ruijieWirelessProducts 27 }

AP220-SI-V10 OBJECT IDENTIFIER ::= { ruijieWirelessProducts 28 }

AP220-E-M-V15 OBJECT IDENTIFIER ::= { ruijieWirelessProducts 29 }

AP220-SH-V30 OBJECT IDENTIFIER ::= { ruijieWirelessProducts 30 }

AP620-H-V20 OBJECT IDENTIFIER ::= { ruijieWirelessProducts 31 }

AP220-E-V30 OBJECT IDENTIFIER ::= { ruijieWirelessProducts 34 }

AP220-E-M-V20 OBJECT IDENTIFIER ::= { ruijieWirelessProducts 35 }


--********************gateway*************************************
EG1000S OBJECT IDENTIFIER ::= { ruijieGatewayProducts 1 }
EG1000C OBJECT IDENTIFIER ::= { ruijieGatewayProducts 2 }
EG1000M OBJECT IDENTIFIER ::= { ruijieGatewayProducts 3 }
EG1000E OBJECT IDENTIFIER ::= { ruijieGatewayProducts 5 }

NPE40   OBJECT IDENTIFIER ::= { ruijieGatewayProducts 6 }
NPE50E  OBJECT IDENTIFIER ::= { ruijieGatewayProducts 7 }
NPE60   OBJECT IDENTIFIER ::= { ruijieGatewayProducts 8 }
NPE80   OBJECT IDENTIFIER ::= { ruijieGatewayProducts 9 }

NBR2000G   OBJECT IDENTIFIER ::= { ruijieGatewayProducts 10 }
NBR2500G   OBJECT IDENTIFIER ::= { ruijieGatewayProducts 11 }

NPE60E  OBJECT IDENTIFIER ::= { ruijieGatewayProducts 13 }

NBR1300G OBJECT IDENTIFIER ::= { ruijieGatewayProducts 18 }
NBR1500G OBJECT IDENTIFIER ::= { ruijieGatewayProducts 19 }
EG1000L  OBJECT IDENTIFIER ::= { ruijieGatewayProducts 20 }
EG2000K  OBJECT IDENTIFIER ::= { ruijieGatewayProducts 21 }
NBR2000D OBJECT IDENTIFIER ::= { ruijieGatewayProducts 22 }
NBR1000G OBJECT IDENTIFIER ::= { ruijieGatewayProducts 23 }
EG2000D  OBJECT IDENTIFIER ::= { ruijieGatewayProducts 24 }
EG2000T  OBJECT IDENTIFIER ::= { ruijieGatewayProducts 25 }
EG2000G  OBJECT IDENTIFIER ::= { ruijieGatewayProducts 26 }
EG2000X  OBJECT IDENTIFIER ::= { ruijieGatewayProducts 27 }
EG2000XE OBJECT IDENTIFIER ::= { ruijieGatewayProducts 28 }
EG2000CE OBJECT IDENTIFIER ::= { ruijieGatewayProducts 29 }
EG2000SE OBJECT IDENTIFIER ::= { ruijieGatewayProducts 30 }
EG2000GE OBJECT IDENTIFIER ::= { ruijieGatewayProducts 31 }
NBR2020G OBJECT IDENTIFIER ::= { ruijieGatewayProducts 33 }
EG2000P  OBJECT IDENTIFIER ::= { ruijieGatewayProducts 35 }
EG2000UE OBJECT IDENTIFIER ::= { ruijieGatewayProducts 36 }
DDI3000  OBJECT IDENTIFIER ::= { ruijieGatewayProducts 67 }
DDI2000  OBJECT IDENTIFIER ::= { ruijieGatewayProducts 74 }

--********************software*************************************
RG-ESS1000 OBJECT IDENTIFIER ::= { ruijieSoftwareProducts 1 }
RG-eLog2 OBJECT IDENTIFIER ::= { ruijieSoftwareProducts 2 }

--********************smartclass***********************************
RG-SCC600 OBJECT IDENTIFIER ::=  {ruijieSmartClassProducts 1}

RG-ITC1000 OBJECT IDENTIFIER ::=  {ruijieSmartClassProducts 100}

END
