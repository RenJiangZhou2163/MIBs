-- *****************************************************************
-- RUIJIE-CAPWAP-MULTICAST6-MIB.mib:  Ruijie CAPWAP MULTICAST6 MIB file
--
-- May 2010, xieweiwu
--
-- Copyright (c) 2010 by Ruijie Networks Co.,Ltd.
-- All rights reserved.
-- 
-- *****************************************************************
--

RUIJIE-CAPWAP-MULTICAST6-MIB DEFINITIONS ::= BEGIN

IMPORTS
        MODULE-IDENTITY,
        OBJECT-TYPE
                FROM SNMPv2-SMI
		    InetAddress
		            FROM INET-ADDRESS-MIB
        MODULE-COMPLIANCE,
        OBJECT-GROUP
                FROM SNMPv2-CONF
        ruijieMgmt
                FROM RUIJIE-SMI;

ruijieCapwapMulticast6MIB MODULE-IDENTITY
        LAST-UPDATED "201005200000Z"
        ORGANIZATION "Ruijie Networks Co.,Ltd."
        CONTACT-INFO
                " 
                Tel: 4008-111-000 

                E-mail: service@ruijie.com.cn"
        DESCRIPTION
                "This module defines ruijie Capwap Multicast6 mibs."
        REVISION      "201005200000Z"
        DESCRIPTION
                "Initial version of this MIB module."
        ::= { ruijieMgmt 85}

ruijieCapwapMulticast6MIBObjects OBJECT IDENTIFIER ::= { ruijieCapwapMulticast6MIB 1 }


--capwap multicast6 mode
ruijieCapwapMulticast6WorkingMode OBJECT-TYPE
        SYNTAX INTEGER {
            disabled(1),   -- Multicast6 mode disable
            unicast(2),    -- Working in capwap unicast(2),
            multicast(3)    -- Working in capwap multicast(3)
        }
        MAX-ACCESS read-write
        STATUS current
        DESCRIPTION
            "System Multicast6 working mode:
             disabled(1):
                Multicast6 mode disable, and all MLD report or leave
                message will be discard.
             unicast(2):
                Working in capwap unicast.
             multicast(3):
                Working in capwap multicast."
        DEFVAL { disabled }
        ::= { ruijieCapwapMulticast6MIBObjects 1 }

--show capwap multicast6 group address
ruijieCapwapMulticast6Group OBJECT-TYPE
        SYNTAX InetAddress
        MAX-ACCESS read-write
        STATUS current
        DESCRIPTION
            "the address of capwap multicast"
        ::= { ruijieCapwapMulticast6MIBObjects 2 }

ruijieCapwapMulticast6MIBConformance OBJECT IDENTIFIER ::= { ruijieCapwapMulticast6MIB 2 }
ruijieCapwapMulticast6MIBCompliances OBJECT IDENTIFIER ::= { ruijieCapwapMulticast6MIBConformance 1 }
ruijieCapwapMulticast6MIBGroups      OBJECT IDENTIFIER ::= { ruijieCapwapMulticast6MIBConformance 2 }


-- compliance statements

ruijieCapwapMulticast6MIBCompliance MODULE-COMPLIANCE
        STATUS  current
        DESCRIPTION
                "The compliance statement for entities which implement
                the Ruijie Capwap Multicast6 MIB"
        MODULE  -- this module
                MANDATORY-GROUPS { ruijieCapwapMulticast6MIBGroup
                 }
        ::= { ruijieCapwapMulticast6MIBCompliances 1 }
                
-- units of conformance

ruijieCapwapMulticast6MIBGroup OBJECT-GROUP
        OBJECTS {
           ruijieCapwapMulticast6WorkingMode,
           ruijieCapwapMulticast6Group
        }
        STATUS  current
        DESCRIPTION
                "A collection of objects providing CapwapMulticast6 configure ."
        ::= { ruijieCapwapMulticast6MIBGroups 1 }
        
END
