-- *****************************************************************
-- RUIJIE-BFD-MIB.mib:  Ruijie BFD MIB file
--
-- 2012-12-26 Wangxiaoyang@ruijie.com.cn
--
-- Copyright (c) 2012 by Ruijie Networks Co.,Ltd.
-- All rights reserved.
-- 
-- *****************************************************************
--

RUIJIE-BFD-MIB DEFINITIONS ::= BEGIN

IMPORTS
    MODULE-IDENTITY, OBJECT-TYPE, NOTIFICATION-TYPE,
        mib-2, Integer32, Unsigned32, Counter32, Counter64
        FROM SNMPv2-SMI

    TEXTUAL-CONVENTION, TruthValue, RowStatus, StorageType, TimeStamp
        FROM SNMPv2-TC

    MODULE-COMPLIANCE, OBJECT-GROUP, NOTIFICATION-GROUP
        FROM SNMPv2-CONF

    InterfaceIndexOrZero
        FROM IF-MIB

    InetAddress, InetAddressType, InetPortNumber
        FROM INET-ADDRESS-MIB
        
    ruijieMgmt
        FROM RUIJIE-SMI;

-- TEXTUAL-CONVENTION
    RuijieBfdSessIndexTC ::= TEXTUAL-CONVENTION
    DISPLAY-HINT   "d"
    STATUS         current
    DESCRIPTION
        "An index used to uniquely identify BFD sessions."
    SYNTAX Unsigned32 (1..4294967295)

    RuijieBfdIntervalTC ::= TEXTUAL-CONVENTION
    DISPLAY-HINT  "d"
    STATUS        current
    DESCRIPTION
        "The BFD interval in microseconds."
    SYNTAX Unsigned32 (0..4294967295)

    RuijieBfdMultiplierTC ::= TEXTUAL-CONVENTION
    DISPLAY-HINT    "d"
    STATUS          current
    DESCRIPTION
        "The BFD failure detection multiplier."
    SYNTAX Unsigned32 (1..255)

    RuijieBfdDiagTC ::= TEXTUAL-CONVENTION
    STATUS       current
    DESCRIPTION
        "A common BFD diagnostic code."
    SYNTAX INTEGER {
        noDiagnostic(0),
        controlDetectionTimeExpired(1),
        echoFunctionFailed(2),
        neighborSignaledSessionDown(3),
        forwardingPlaneReset(4),
        pathDown(5),
        concatenatedPathDown(6),
        administrativelyDown(7),
        reverseConcatenatedPathDown(8)
    }

    RuijieBfdSessTypeTC ::= TEXTUAL-CONVENTION
    STATUS        current
    DESCRIPTION
        "BFD session type"
    REFERENCE
        "Katz, D. and D. Ward, Bidirectional Forwarding
              Detection (BFD), RFC 5880, June 2010.

         Katz, D. and D. Ward, Bidirectional Forwarding
              Detection (BFD) for IPv4 and IPv6 (Single Hop),
              RFC 5881, June 2010. 

         Katz, D. and D. Ward, Bidirectional Forwarding
              Detection (BFD) for Multihop Paths, RFC 5883,
              June 2010."
    SYNTAX INTEGER {
        singleHop(1),
        multiHopTotallyArbitraryPaths(2),
        multiHopOutOfBandSignaling(3),
        multiHopUnidirectionalLinks(4),
        multiPointHead(5),
        multiPointTail(6)
    }

    RuijieBfdSessOperModeTC ::= TEXTUAL-CONVENTION
    STATUS            current
    DESCRIPTION
        "BFD session operating mode"
    REFERENCE
        "Katz, D. and D. Ward, Bidirectional Forwarding Detection (BFD), RFC 5880, June 2010."
    SYNTAX INTEGER {
        asyncModeWEchoFunction(1),
        asynchModeWOEchoFunction(2),
        demandModeWEchoFunction(3),
        demandModeWOEchoFunction(4)
    }

    RuijieBfdCtrlDestPortNumberTC ::= TEXTUAL-CONVENTION
    DISPLAY-HINT            "d"
    STATUS                  current
    DESCRIPTION
        "UDP destination port number of BFD control packets.
         3784 represents single hop BFD session.
         4784 represents multi hop BFD session.
         However, syntax is left open to wider range of values
         purposely for two reasons:
         1. implementation uses non-compliant port number for
            valid proprietary reason.
         2. potential future extension drafts."
    REFERENCE
        "Use of port 3784 from Katz, D. and D. Ward, 
              Bidirectional Forwarding
              Detection (BFD) for IPv4 and IPv6 (Single Hop),
              RFC 5881, June 2010.

         Use of port 4784 from Katz, D. and D. Ward, Bidirectional 
              Forwarding Detection (BFD) for IPv4 and IPv6 
              (Single Hop), RFC 5881, June 2010."
    SYNTAX Unsigned32 (0..65535)

    RuijieBfdCtrlSourcePortNumberTC ::= TEXTUAL-CONVENTION
    DISPLAY-HINT              "d"
    STATUS                    current
    DESCRIPTION
        "UDP source port number of BFD control packets.
         However, syntax is left open to wider range of values
         purposely for two reasons:
         1. implementation uses non-compliant port number for
            valid proprietary reason.
         2. potential future extension drafts."
    REFERENCE
        "Port 49152..65535 (RFC5881)"
    SYNTAX Unsigned32 (0..65535)

    RuijieBfdSessStateTC ::= TEXTUAL-CONVENTION
    STATUS         current
    DESCRIPTION
        "BFD session state. State failing(5) is only applicable if
         corresponding session is running in BFD version 0."
    REFERENCE
        "RFC 5880 - Bidirectional Forwarding Detection (BFD), Katz, 
         D., Ward, D., June 2010."
    SYNTAX INTEGER {
        adminDown(1),
        down(2),
        init(3),
        up(4),
        failing(5)
    }

    RuijieBfdSessAuthenticationTypeTC ::= TEXTUAL-CONVENTION
    STATUS                      current
    DESCRIPTION
        "BFD authentication type"
    REFERENCE
        "Sections 4.2 - 4.4 from Katz, D. and D. Ward, 
         Bidirectional Forwarding Detection (BFD), 
         RFC 5880, June 2010."
    SYNTAX INTEGER {
        noAuthentication(-1),
        reserved(0),
        simplePassword(1),
        keyedMD5(2),
        meticulousKeyedMD5(3),
        keyedSHA1(4),
        meticulousKeyedSHA1(5)
    }

    RuijieBfdSessionAuthenticationKeyTC ::= TEXTUAL-CONVENTION
    DISPLAY-HINT                  "1x "
    STATUS                        current
    DESCRIPTION
        "BFD authentication key type.

         A RuijieBfdSessionAuthenticationKeyTC is always interpreted within
         the context of an RuijieBfdSessAuthenticationTypeTC value.  Every
         usage of the RuijieBfdSessionAuthenticationTypeTC textual
         convention is required to specify the the
         RuijieBfdSessionAuthenticationKeyTC object that provides the
         context.  It is suggested that the
         RuijieBfdSessionAuthentcationTypeTC object be logically registered
         before the object(s) that use the
         RuijieBfdSessionAuthenticationKeyTC textual convention, if they
         appear in the same logical row.

         The value of a RuijieBfdSessionAuthenticationKeyTC must always be
         consistent with the value of the associated
         RuijieBfdSessionAuthencationTypeTC object.  Attempts to set a
         RuijieBfdSessionAuthenticationKeyTC object to a value inconsistent
         with the associated RuijieBfdSessionAuthenticationTypeTC must fail
         with an inconsistentValue error.

         The following size constraints for a
         RuijieBfdSessionAuthenticationKeyTC object are defined for the
         associated RuijieBfdSessionAuthenticationTypeTC values show below:

         noAuthentication(-1): SIZE(0)
         reserved(0): SIZE(0)
         simplePassword(1): SIZE(1..16)
         keyedMD5(2): SIZE(16)
         meticulousKeyedMD5(3): SIZE(16)
         keyedSHA1(4): SIZE(20)
         meticulousKeyedSHA1(5): SIZE(20)

         When this textual convention is used as the syntax of an
         index object, there may be issues with the limit of 128
         sub-identifiers specified in SMIv2, STD 58.  In this case,
         the object definition MUST include a 'SIZE' clause to limit
         the number of potential instance sub-identifiers; otherwise
         the applicable constraints MUST be stated in the appropriate
         conceptual row DESCRIPTION clauses, or in the surrounding
         documentation if there is no single DESCRIPTION clause that
         is appropriate."
    REFERENCE
        "RFC5880, Sections 4.2 - 4.4"
    SYNTAX OCTET STRING(SIZE(0..252))
    
    
-- ruijie bfd mib 


ruijieBfdMIB MODULE-IDENTITY
    LAST-UPDATED "201204141200Z"
    ORGANIZATION "Ruijie Networks Co.,Ltd."
    CONTACT-INFO
            " 
            Tel: 4008-111-000 

            E-mail: service@ruijie.com.cn"
    DESCRIPTION
            "This module defines ruijie BFD mibs."
    REVISION      "201204141200Z"
    DESCRIPTION
            "Initial version of this MIB module."
                
-- RFC Ed.: RFC-editor pls fill in xxxx
    ::= { ruijieMgmt 48 }
-- RFC Ed.: assigned by IANA, see section 7.1 for details

-- Top level components of this MIB module.

ruijieBfdNotifications OBJECT IDENTIFIER ::= { ruijieBfdMIB 0 }

ruijieBfdObjects       OBJECT IDENTIFIER ::= { ruijieBfdMIB 1 }

ruijieBfdConformance   OBJECT IDENTIFIER ::= { ruijieBfdMIB 2 }

ruijieBfdScalarObjects OBJECT IDENTIFIER ::= { ruijieBfdObjects 1 }

-- BFD General Variables

-- These parameters apply globally to the Systems'
-- BFD Process.

ruijieBfdAdminStatus OBJECT-TYPE
    SYNTAX     INTEGER {
        enabled(1),
        disabled(2)
    }
    MAX-ACCESS read-write
    STATUS     current
    DESCRIPTION
        "The global administrative status of BFD in this device.
         The value 'enabled' denotes that the BFD Process is
         active on at least one interface; 'disabled' disables
         it on all interfaces."
    DEFVAL { enabled }
    ::= { ruijieBfdScalarObjects 1 }

ruijieBfdSessNotificationsEnable OBJECT-TYPE
    SYNTAX     TruthValue
    MAX-ACCESS read-write
    STATUS     current
    DESCRIPTION
        "If this object is set to true(1), then it enables
         the emission of ruijieBfdSessUp and ruijieBfdSessDown
         notifications; otherwise these notifications are not
         emitted."
    REFERENCE
        "See also RFC3413 for explanation that
         notifications are under the ultimate control of the
         MIB modules in this document."
    DEFVAL { false }
    ::= { ruijieBfdScalarObjects 2 }

-- BFD Session Table
-- The BFD Session Table specifies BFD session specific
-- information.

ruijieBfdSessTable OBJECT-TYPE
    SYNTAX     SEQUENCE OF RuijieBfdSessEntry
    MAX-ACCESS not-accessible
    STATUS     current
    DESCRIPTION
        "The BFD Session Table describes the BFD sessions."
    REFERENCE
        "Katz, D. and D. Ward, Bidirectional Forwarding
          Detection (BFD), RFC 5880, June 2012."
    ::= { ruijieBfdObjects 2 }

ruijieBfdSessEntry OBJECT-TYPE
    SYNTAX     RuijieBfdSessEntry
    MAX-ACCESS not-accessible
    STATUS     current
    DESCRIPTION
        "The BFD Session Entry describes BFD session."
    INDEX { ruijieBfdSessIndex }
    ::= { ruijieBfdSessTable 1 }

RuijieBfdSessEntry ::= SEQUENCE {
    ruijieBfdSessIndex                    RuijieBfdSessIndexTC,
    ruijieBfdSessVersionNumber            Unsigned32,
    ruijieBfdSessType                     RuijieBfdSessTypeTC,
    ruijieBfdSessDiscriminator            Unsigned32,
    ruijieBfdSessRemoteDiscr              Unsigned32,
    ruijieBfdSessDestinationUdpPort       RuijieBfdCtrlDestPortNumberTC,
    ruijieBfdSessSourceUdpPort            RuijieBfdCtrlSourcePortNumberTC,
    ruijieBfdSessEchoSourceUdpPort        InetPortNumber,
    ruijieBfdSessAdminStatus              INTEGER,
    ruijieBfdSessState                    RuijieBfdSessStateTC,
    ruijieBfdSessRemoteHeardFlag          TruthValue,
    ruijieBfdSessDiag                     RuijieBfdDiagTC,
    ruijieBfdSessOperMode                 RuijieBfdSessOperModeTC,
    ruijieBfdSessDemandModeDesiredFlag    TruthValue,
    ruijieBfdSessControlPlaneIndepFlag    TruthValue,
    ruijieBfdSessMultipointFlag           TruthValue,
    ruijieBfdSessInterface                InterfaceIndexOrZero,
    ruijieBfdSessSrcAddrType              InetAddressType,
    ruijieBfdSessSrcAddr                  InetAddress,
    ruijieBfdSessDstAddrType              InetAddressType,
    ruijieBfdSessDstAddr                  InetAddress,
    ruijieBfdSessGTSM                     TruthValue,
    ruijieBfdSessGTSMTTL                  Unsigned32,
    ruijieBfdSessDesiredMinTxInterval     RuijieBfdIntervalTC,
    ruijieBfdSessReqMinRxInterval         RuijieBfdIntervalTC,
    ruijieBfdSessReqMinEchoRxInterval     RuijieBfdIntervalTC,
    ruijieBfdSessDetectMult               RuijieBfdMultiplierTC,
    ruijieBfdSessNegotiatedInterval       RuijieBfdIntervalTC,
    ruijieBfdSessNegotiatedEchoInterval   RuijieBfdIntervalTC,
    ruijieBfdSessNegotiatedDetectMult     RuijieBfdMultiplierTC,
    ruijieBfdSessAuthPresFlag             TruthValue,
    ruijieBfdSessAuthenticationType       RuijieBfdSessAuthenticationTypeTC,
    ruijieBfdSessAuthenticationKeyID      Integer32,
    ruijieBfdSessAuthenticationKey        RuijieBfdSessionAuthenticationKeyTC,
    ruijieBfdSessStorageType              StorageType,
    ruijieBfdSessRowStatus                RowStatus
}

ruijieBfdSessIndex OBJECT-TYPE
    SYNTAX     RuijieBfdSessIndexTC
    MAX-ACCESS not-accessible
    STATUS     current
    DESCRIPTION
        "This object contains an index used to represent a
         unique BFD session on this device."
    ::= { ruijieBfdSessEntry 1 }

ruijieBfdSessVersionNumber OBJECT-TYPE
    SYNTAX     Unsigned32 (0..7)
    MAX-ACCESS read-create
    STATUS     current
    DESCRIPTION
        "The version number of the BFD protocol that this session
         is running in. Write access is available for this object
         to provide ability to set desired version for this
         BFD session."
    REFERENCE
        "Katz, D. and D. Ward, Bidirectional Forwarding
          Detection (BFD), RFC 5880, June 2012."
    DEFVAL { 1 }
    ::= { ruijieBfdSessEntry 2 }

ruijieBfdSessType OBJECT-TYPE
    SYNTAX     RuijieBfdSessTypeTC
    MAX-ACCESS read-create
    STATUS     current
    DESCRIPTION
        "This object specifies the type of this BFD session."
    ::= { ruijieBfdSessEntry 3 }

ruijieBfdSessDiscriminator OBJECT-TYPE
    SYNTAX     Unsigned32 (1..4294967295)
    MAX-ACCESS read-only
    STATUS     current
    DESCRIPTION
        "This object specifies the local discriminator for this BFD
         session, used to uniquely identify it."
    ::= { ruijieBfdSessEntry 4 }

ruijieBfdSessRemoteDiscr OBJECT-TYPE
    SYNTAX     Unsigned32 (0 | 1..4294967295)
    MAX-ACCESS read-only
    STATUS     current
    DESCRIPTION
        "This object specifies the session discriminator chosen
         by the remote system for this BFD session.  The value may
         be zero(0) if the remote discriminator is not yet known
         or if the session is in the down or adminDown(1) state."
    REFERENCE
        "Section 6.8.6, from Katz, D. and D. Ward, Bidirectional 
         Forwarding Detection (BFD), RFC 5880, June 2012."
    ::= { ruijieBfdSessEntry 5 }

ruijieBfdSessDestinationUdpPort OBJECT-TYPE
    SYNTAX     RuijieBfdCtrlDestPortNumberTC
    MAX-ACCESS read-create
    STATUS     current
    DESCRIPTION
        "This object specifies the destination UDP port number
         used for this BFD session's control packets. The value
         may be zero(0) if the session is in adminDown(1) state."
    DEFVAL { 0 }
    ::= { ruijieBfdSessEntry 6 }

ruijieBfdSessSourceUdpPort OBJECT-TYPE
    SYNTAX     RuijieBfdCtrlSourcePortNumberTC
    MAX-ACCESS read-create
    STATUS     current
    DESCRIPTION
        "This object specifies the source UDP port number used
         for this BFD session's control packets. The value may be
         zero(0) if the session is in adminDown(1) state. Upon
         creation of a new BFD session via this MIB, the value of
         zero(0) specified would permit the implementation to
         chose its own source port number."
    DEFVAL { 0 }
    ::= { ruijieBfdSessEntry 7 }

ruijieBfdSessEchoSourceUdpPort OBJECT-TYPE
    SYNTAX     InetPortNumber
    MAX-ACCESS read-create
    STATUS     current
    DESCRIPTION
        "This object specifies the source UDP port number used for
         this BFD session's echo packets. The value may be zero(0)
         if the session is not running in the echo mode, or the
         session is in adminDown(1) state. Upon creation of a new
         BFD session via this MIB, the value of zero(0) would
         permit the implementation to chose its own source port
         number."
    DEFVAL { 0 }
    ::= { ruijieBfdSessEntry 8 }

ruijieBfdSessAdminStatus OBJECT-TYPE
    SYNTAX     INTEGER {
                        stop(1),
                        start(2)
               }
    MAX-ACCESS read-create
    STATUS     current
    DESCRIPTION
            "A transition from 'stop' to 'start' will start
             the BFD state machine for the session. The state
             machine will have an initial state of down.
             A transition from 'start' to 'stop' will cause
             the BFD sesssion to be brought down to
             adminDown(1). Care should be used in providing
             write access to this object without adequate
             authentication."
    DEFVAL { 2 }
    ::= { ruijieBfdSessEntry 9 }

ruijieBfdSessState OBJECT-TYPE
    SYNTAX     RuijieBfdSessStateTC
    MAX-ACCESS read-only
    STATUS     current
    DESCRIPTION
        "BFD session state."
    DEFVAL { 2 }
    ::= { ruijieBfdSessEntry 10 }

ruijieBfdSessRemoteHeardFlag OBJECT-TYPE
    SYNTAX     TruthValue
    MAX-ACCESS read-only
    STATUS     current
    DESCRIPTION
        "This object specifies status of BFD packet reception from
         the remote system. Specifically, it is set to true(1) if
         the local system is actively receiving BFD packets from the
         remote system, and is set to false(2) if the local system
         has not received BFD packets recently (within the detection
         time) or if the local system is attempting to tear down
         the BFD session."
    REFERENCE
        "Katz, D. and D. Ward, Bidirectional 
         Forwarding Detection (BFD), RFC 5880, June 2012."
    DEFVAL { false }
    ::= { ruijieBfdSessEntry 11 }

ruijieBfdSessDiag OBJECT-TYPE
    SYNTAX     RuijieBfdDiagTC
    MAX-ACCESS read-only
    STATUS     current
    DESCRIPTION
        "A diagnostic code specifying the local system's reason
         for the last transition of the session from up(4)
         to some other state."
    ::= { ruijieBfdSessEntry 12 }

ruijieBfdSessOperMode OBJECT-TYPE
    SYNTAX     RuijieBfdSessOperModeTC
    MAX-ACCESS read-create
    STATUS     current
    DESCRIPTION
        "This object specifies current operating mode that BFD
         session is operating in."
    ::= { ruijieBfdSessEntry 13 }

ruijieBfdSessDemandModeDesiredFlag OBJECT-TYPE
    SYNTAX     TruthValue
    MAX-ACCESS read-create
    STATUS     current
    DESCRIPTION
        "This object indicates that the local system's
         desire to use Demand mode. Specifically, it is set
         to true(1) if the local system wishes to use
         Demand mode or false(2) if not"
    DEFVAL { false }
    ::= { ruijieBfdSessEntry 14 }

ruijieBfdSessControlPlaneIndepFlag OBJECT-TYPE
    SYNTAX     TruthValue
    MAX-ACCESS read-create
    STATUS     current
    DESCRIPTION
        "This object indicates that the local system's
         ability to continue to function through a disruption of
         the control plane. Specifically, it is set
         to true(1) if the local system BFD implementation is
         independent of the control plane. Otherwise, the
         value is set to false(2)"
    DEFVAL { false }
    ::= { ruijieBfdSessEntry 15 }

ruijieBfdSessMultipointFlag OBJECT-TYPE
    SYNTAX     TruthValue
    MAX-ACCESS read-create
    STATUS     current
    DESCRIPTION
        "This object indicates the Multipoint (M) bit for this
         session. It is set to true(1) if Multipoint (M) bit is
         set to 1. Otherwise, the value is set to false(2)"
    DEFVAL { false }
    ::= { ruijieBfdSessEntry 16 }

ruijieBfdSessInterface OBJECT-TYPE
    SYNTAX     InterfaceIndexOrZero
    MAX-ACCESS read-create
    STATUS     current
    DESCRIPTION
        "This object contains an interface index used to indicate
         the interface which this BFD session is running on. This
         value can be zero if there is no interface associated
         with this BFD session."
    ::= { ruijieBfdSessEntry 17 }

ruijieBfdSessSrcAddrType OBJECT-TYPE
    SYNTAX     InetAddressType
    MAX-ACCESS read-create
    STATUS     current
    DESCRIPTION
        "This object specifies IP address type of the source IP
         address of this BFD session. Only values unknown(0),
         ipv4(1), ipv6(2), or ipv6z(4) have to be supported.
         The value of unknown(0) is allowed only when the session
         is singleHop(1) and the source IP address of this BFD
         session is drived from the outgoing interface, or when
         the BFD session is not associated with a specific
         interface. If any other unsupported values are attempted
         in a set operation, the agent MUST return an
         inconsistentValue error."
  ::= { ruijieBfdSessEntry 18 }

ruijieBfdSessSrcAddr OBJECT-TYPE
    SYNTAX     InetAddress
    MAX-ACCESS read-create
    STATUS     current
    DESCRIPTION
        "This object specifies the source IP address of this BFD
         session."
    ::= { ruijieBfdSessEntry 19 }

ruijieBfdSessDstAddrType OBJECT-TYPE
    SYNTAX     InetAddressType
    MAX-ACCESS read-create
    STATUS     current
    DESCRIPTION
        "This object specifies IP address type of the neighboring IP
         address which is being monitored with this BFD session.
         Only values unknown(0), ipv4(1), ipv6(2), or ipv6z(4)
         have to be supported. The value of unknown(0) is allowed
         only when the session is singleHop(1) and the outgoing
         interface is of type point-to-point, or when the BFD
         session is not associated with a specific interface. If any
         other unsupported values are attempted in a set operation,
         the agent MUST return an inconsistentValue error."
  ::= { ruijieBfdSessEntry 20 }

ruijieBfdSessDstAddr OBJECT-TYPE
    SYNTAX     InetAddress
    MAX-ACCESS read-create
    STATUS     current
    DESCRIPTION
        "This object specifies the neighboring IP address which is
         being monitored with this BFD session."
    ::= { ruijieBfdSessEntry 21 }

ruijieBfdSessGTSM OBJECT-TYPE
    SYNTAX  TruthValue
    MAX-ACCESS read-create
    STATUS current
    DESCRIPTION
       "Setting the value of this object to true(1) will enable GTSM
        protection of the BFD session.  GTSM MUST be enabled on a
        singleHop(1) session if no authentication is in use."
    REFERENCE
       "RFC5082, The Generalized TTL Security Mechanism (GTSM).
        RFC5881, Section 5"
    DEFVAL { false }
    ::= { ruijieBfdSessEntry 22 }

ruijieBfdSessGTSMTTL OBJECT-TYPE
    SYNTAX Unsigned32 (0..255)
    MAX-ACCESS read-create
    STATUS current
    DESCRIPTION
        "This object is valid only when ruijieBfdSessGTSM protection is
         enabled on the system. This object specifies the minimum
         allowed TTL for received BFD control packets. For
         singleHop(1) session, if GTSM protection is enabled,
         this object SHOULD be set to maximum TTL allowed for
         single hop. The value of zero(0) indicates that
         ruijieBfdSessGTSM is disabled."
    REFERENCE
       "RFC5082, The Generalized TTL Security Mechanism (GTSM).
        RFC5881, Section 5"
    DEFVAL { 0 }
    ::= { ruijieBfdSessEntry 23 }

ruijieBfdSessDesiredMinTxInterval OBJECT-TYPE
    SYNTAX     RuijieBfdIntervalTC
    MAX-ACCESS read-create
    STATUS     current
    DESCRIPTION
        "This object specifies the minimum interval, in
         microseconds, that the local system would like to use
         when transmitting BFD Control packets. The value of
         zero(0) is reserved, and should not be used."
    REFERENCE
        "Section 4.1 from Katz, D. and D. Ward, Bidirectional 
         Forwarding Detection (BFD), RFC 5880, June 2012."
    ::= { ruijieBfdSessEntry 24 }

ruijieBfdSessReqMinRxInterval OBJECT-TYPE
    SYNTAX     RuijieBfdIntervalTC
    MAX-ACCESS read-create
    STATUS     current
    DESCRIPTION
        "This object specifies the minimum interval, in
         microseconds, between received  BFD Control packets the
         local system is capable of supporting. The value of
         zero(0) can be specified when the transmitting system
         does not want the remote system to send any periodic BFD
         control packets."
    REFERENCE
        "Section 4.1 from Katz, D. and D. Ward, Bidirectional 
         Forwarding Detection (BFD), RFC 5880, June 2012."
    ::= { ruijieBfdSessEntry 25 }

ruijieBfdSessReqMinEchoRxInterval OBJECT-TYPE
    SYNTAX     RuijieBfdIntervalTC
    MAX-ACCESS read-create
    STATUS     current
    DESCRIPTION
        "This object specifies the minimum interval, in
         microseconds, between received BFD Echo packets that this
         system is capable of supporting. Value must be zero(0) if
         this is a multihop BFD session."
    ::= { ruijieBfdSessEntry 26 }

ruijieBfdSessDetectMult OBJECT-TYPE
    SYNTAX     RuijieBfdMultiplierTC
    MAX-ACCESS read-create
    STATUS     current
    DESCRIPTION
        "This object specifies the Detect time multiplier."
    ::= { ruijieBfdSessEntry 27 }

ruijieBfdSessNegotiatedInterval OBJECT-TYPE
    SYNTAX     RuijieBfdIntervalTC
    MAX-ACCESS read-only
    STATUS     current
    DESCRIPTION
        "This object specifies the negotiated interval, in
         microseconds, that the local system is transmitting
         BFD Control packets."
    ::= { ruijieBfdSessEntry 28 }

ruijieBfdSessNegotiatedEchoInterval OBJECT-TYPE
    SYNTAX     RuijieBfdIntervalTC
    MAX-ACCESS read-only
    STATUS     current
    DESCRIPTION
        "This object specifies the negotiated interval, in
         microseconds, that the local system is transmitting
         BFD echo packets. Value is expected to be zero if
         the sessions is not running in echo mode."
    ::= { ruijieBfdSessEntry 29 }

ruijieBfdSessNegotiatedDetectMult OBJECT-TYPE
    SYNTAX     RuijieBfdMultiplierTC
    MAX-ACCESS read-only
    STATUS     current
    DESCRIPTION
        "This object specifies the Detect time multiplier."
    ::= { ruijieBfdSessEntry 30 }

ruijieBfdSessAuthPresFlag OBJECT-TYPE
    SYNTAX     TruthValue
    MAX-ACCESS read-create
    STATUS     current
    DESCRIPTION
        "This object indicates that the local system's
         desire to use Authentication. Specifically, it is set
         to true(1) if the local system wishes the session
         to be authenticated or false(2) if not."
    REFERENCE
        "Sections 4.2 - 4.4 from Katz, D. and D. Ward, 
         Bidirectional Forwarding Detection (BFD), RFC 5880, 
         June 2012."
    DEFVAL { false }
    ::= { ruijieBfdSessEntry 31 }

ruijieBfdSessAuthenticationType OBJECT-TYPE
    SYNTAX     RuijieBfdSessAuthenticationTypeTC
    MAX-ACCESS read-create
    STATUS     current
    DESCRIPTION
        "The Authentication Type used for this BFD session.
         This field is valid only when the Authentication
         Present bit is set. Max-access to this object as well as
         other authentication related objects are set to
         read-create in order to support management of a single
         key ID at a time, key rotation is not handled. Key update
         in practice must be done by atomic update using a set
         containing all affected objects in the same varBindList
         or otherwise risk the session dropping. Value -1
         indicates that no authentication is in use for this
         session."
    REFERENCE
        "Sections 4.2 - 4.4 from Katz, D. and D. Ward, 
         Bidirectional Forwarding Detection (BFD), RFC 5880, 
         June 2012."
    DEFVAL { -1 }
    ::= { ruijieBfdSessEntry 32 }

ruijieBfdSessAuthenticationKeyID OBJECT-TYPE
    SYNTAX     Integer32 (-1 | 0..255)
    MAX-ACCESS read-create
    STATUS     current
    DESCRIPTION
        "The authentication key ID in use for this session.  This
         object permits multiple keys to be active simultaneously.
         When ruijieBfdSessAuthPresFlag is false(2), then the value
         of this object MUST be -1.  The value -1 indicates that
         no Authentication Key ID will be present in the optional
         BFD Authentication Section."
    REFERENCE
        "Sections 4.2 - 4.4 from Katz, D. and D. Ward, 
         Bidirectional Forwarding Detection (BFD), RFC 5880, 
         June 2012."
    DEFVAL { -1 }
    ::= { ruijieBfdSessEntry 33 }

ruijieBfdSessAuthenticationKey OBJECT-TYPE
    SYNTAX     RuijieBfdSessionAuthenticationKeyTC
    MAX-ACCESS read-create
    STATUS     current
    DESCRIPTION
        "The authentication key.  When the
         ruijieBfdSessAuthenticationType is simplePassword(1), the value
         of this object is the password present in the BFD packets.

         When the ruijieBfdSessAuthentication type is one of the keyed
         authentication types, this value is used in the
         computation of the key present in the BFD authentication
         packet."
    REFERENCE
        "Sections 4.2 - 4.4 from from Katz, D. and D. Ward, 
         Bidirectional Forwarding Detection (BFD), RFC 5880, 
         June 2012."
    ::= { ruijieBfdSessEntry 34 }

ruijieBfdSessStorageType OBJECT-TYPE
    SYNTAX     StorageType
    MAX-ACCESS read-create
    STATUS     current
    DESCRIPTION
        "This variable indicates the storage type for this
         object. Conceptual rows having the value
         'permanent' need not allow write-access to any
         columnar objects in the row."
    ::= { ruijieBfdSessEntry 35 }

ruijieBfdSessRowStatus OBJECT-TYPE
    SYNTAX     RowStatus
    MAX-ACCESS read-create
    STATUS     current
    DESCRIPTION
        "This variable is used to create, modify, and/or
         delete a row in this table. When a row in this
         table has a row in the active(1) state, no
         objects in this row can be modified except the
         ruijieBfdSessRowStatus and ruijieBfdSessStorageType."
    ::= { ruijieBfdSessEntry 36 }

-- BFD Session Performance Table

ruijieBfdSessPerfTable OBJECT-TYPE
    SYNTAX     SEQUENCE OF RuijieBfdSessPerfEntry
    MAX-ACCESS not-accessible
    STATUS     current
    DESCRIPTION
        "This table specifies BFD Session performance counters."
    ::= { ruijieBfdObjects 3 }

ruijieBfdSessPerfEntry OBJECT-TYPE
    SYNTAX     RuijieBfdSessPerfEntry
    MAX-ACCESS not-accessible
    STATUS     current
    DESCRIPTION
        "An entry in this table is created by a BFD-enabled node
         for every BFD Session. ruijieBfdSessPerfDiscTime is used to
         indicate potential discontinuity for all counter objects
         in this table."
    AUGMENTS    { ruijieBfdSessEntry }
    ::= { ruijieBfdSessPerfTable 1 }

RuijieBfdSessPerfEntry ::= SEQUENCE {
   ruijieBfdSessPerfCtrlPktIn           Counter32,
   ruijieBfdSessPerfCtrlPktOut          Counter32,
   ruijieBfdSessPerfCtrlPktDrop         Counter32,
   ruijieBfdSessPerfCtrlPktDropLastTime TimeStamp,
   ruijieBfdSessPerfEchoPktIn           Counter32,
   ruijieBfdSessPerfEchoPktOut          Counter32,
   ruijieBfdSessPerfEchoPktDrop         Counter32,
   ruijieBfdSessPerfEchoPktDropLastTime TimeStamp,
   ruijieBfdSessUpTime                  TimeStamp,
   ruijieBfdSessPerfLastSessDownTime    TimeStamp,
   ruijieBfdSessPerfLastCommLostDiag    RuijieBfdDiagTC,
   ruijieBfdSessPerfSessUpCount         Counter32,
   ruijieBfdSessPerfDiscTime            TimeStamp,

   -- High Capacity Counters
   ruijieBfdSessPerfCtrlPktInHC         Counter64,
   ruijieBfdSessPerfCtrlPktOutHC        Counter64,
   ruijieBfdSessPerfCtrlPktDropHC       Counter64,
   ruijieBfdSessPerfEchoPktInHC         Counter64,
   ruijieBfdSessPerfEchoPktOutHC        Counter64,
   ruijieBfdSessPerfEchoPktDropHC       Counter64
}

-- Ed Note: should we add per-diag code counts here,

ruijieBfdSessPerfCtrlPktIn OBJECT-TYPE
    SYNTAX     Counter32
    MAX-ACCESS read-only
    STATUS     current
    DESCRIPTION
        "The total number of BFD control messages received for this
         BFD session. This value MUST be equal to the least
         significant 32 bits of ruijieBfdSessPerfCtrlPktInHC."
    ::= { ruijieBfdSessPerfEntry 1 }

ruijieBfdSessPerfCtrlPktOut OBJECT-TYPE
    SYNTAX     Counter32
    MAX-ACCESS read-only
    STATUS     current
    DESCRIPTION
        "The total number of BFD control messages sent for this BFD
         session. 

         It MUST be equal to the least significant 32 bits of
         significant 32 bits of ruijieBfdSessPerfCtrlPktOutHC
         if supported, and MUST do so the rules spelled out in 
         RFC 2863."             

    ::= { ruijieBfdSessPerfEntry 2 }

ruijieBfdSessPerfCtrlPktDrop OBJECT-TYPE
    SYNTAX     Counter32
    MAX-ACCESS read-only
    STATUS     current
    DESCRIPTION
        "The total number of BFD control messages received for this
         session yet dropped for being invalid. 

         It MUST be equal to the least significant 32 bits of
         significant 32 bits of ruijieBfdSessPerfCtrlPktDropHC
         if supported, and MUST do so the rules spelled out in 
         RFC 2863."             
    ::= { ruijieBfdSessPerfEntry 3 }

ruijieBfdSessPerfCtrlPktDropLastTime OBJECT-TYPE
    SYNTAX     TimeStamp
    MAX-ACCESS read-only
    STATUS     current
    DESCRIPTION
        "The value of sysUpTime on the most recent occasion at
         which received BFD control message for this session was
         dropped. If no such up event exists, this object contains
         a zero value."
    ::= { ruijieBfdSessPerfEntry 4 }

ruijieBfdSessPerfEchoPktIn OBJECT-TYPE
    SYNTAX     Counter32
    MAX-ACCESS read-only
    STATUS     current
    DESCRIPTION
        "The total number of BFD echo messages received for this
         BFD session. 

         It MUST be equal to the least significant 32 bits of
         significant 32 bits of ruijieBfdSessPerfEchoPktInHC if 
         supported, and MUST do so the rules spelled out in 
         RFC 2863."             
    ::= { ruijieBfdSessPerfEntry 5 }

ruijieBfdSessPerfEchoPktOut OBJECT-TYPE
    SYNTAX     Counter32
    MAX-ACCESS read-only
    STATUS     current
    DESCRIPTION
        "The total number of BFD echo messages sent for this BFD
         session. 

         It MUST be equal to the least significant 32 bits of
         ruijieBfdSessPerfEchoPktOutHC if supported, and MUST do so
         the rules spelled out in RFC 2863."             
    ::= { ruijieBfdSessPerfEntry 6 }

ruijieBfdSessPerfEchoPktDrop OBJECT-TYPE
    SYNTAX     Counter32
    MAX-ACCESS read-only
    STATUS     current
    DESCRIPTION
        "The total number of BFD echo messages received for this
         session yet dropped for being invalid. 

         It MUST be equal to the least significant 32 bits of
         ruijieBfdSessPerfEchoPktDropHC if supported, and MUST do so
         the rules spelled out in RFC 2863."             
    ::= { ruijieBfdSessPerfEntry 7 }

ruijieBfdSessPerfEchoPktDropLastTime OBJECT-TYPE
    SYNTAX     TimeStamp
    MAX-ACCESS read-only
    STATUS     current
    DESCRIPTION
        "The value of sysUpTime on the most recent occasion at
         which received BFD echo message for this session was
         dropped. If no such up event exists, this object contains
         a zero value."
    ::= { ruijieBfdSessPerfEntry 8 }

ruijieBfdSessUpTime OBJECT-TYPE
    SYNTAX     TimeStamp
    MAX-ACCESS read-only
    STATUS     current
    DESCRIPTION
        "The value of sysUpTime on the most recent occasion at which
         the session came up. If no such up event exists this object
         contains a zero value."
    ::= { ruijieBfdSessPerfEntry 9 }

ruijieBfdSessPerfLastSessDownTime OBJECT-TYPE
    SYNTAX     TimeStamp
    MAX-ACCESS read-only
    STATUS     current
    DESCRIPTION
        "The value of sysUpTime on the most recent occasion at
         which the last time communication was lost with the
         neighbor. If no such down event exist this object
         contains a zero value."
    ::= { ruijieBfdSessPerfEntry 10 }

ruijieBfdSessPerfLastCommLostDiag OBJECT-TYPE
    SYNTAX     RuijieBfdDiagTC
    MAX-ACCESS read-only
    STATUS     current
    DESCRIPTION
        "The BFD diag code for the last time communication was lost
         with the neighbor. If no such down event exists this object
         contains a zero value."
    ::= { ruijieBfdSessPerfEntry 11 }

ruijieBfdSessPerfSessUpCount OBJECT-TYPE
    SYNTAX     Counter32
    MAX-ACCESS read-only
    STATUS     current
    DESCRIPTION
        "The number of times this session has gone into the Up
         state since the system last rebooted."
    ::= { ruijieBfdSessPerfEntry 12 }

ruijieBfdSessPerfDiscTime OBJECT-TYPE
    SYNTAX     TimeStamp
    MAX-ACCESS read-only
    STATUS     current
    DESCRIPTION
      "The value of sysUpTime on the most recent occasion at
       which any one or more of the session counters suffered
       a discontinuity.

       The relevant counters are the specific instances associated
       with this BFD session of any Counter32 object contained in
       the BfdSessPerfTable. If no such discontinuities have
       occurred since the last re-initialization of the local
       management subsystem, then this object contains a zero
       value."
    ::= { ruijieBfdSessPerfEntry 13 }

ruijieBfdSessPerfCtrlPktInHC OBJECT-TYPE
    SYNTAX     Counter64
    MAX-ACCESS read-only
    STATUS     current
    DESCRIPTION
        "This value represents the total number of BFD control
         messages received for this BFD session. 

         It MUST be equal to the least significant 32 bits of
         ruijieBfdSessPerfCtrlPktInHC if supported, and MUST do so
         the rules spelled out in RFC 2863."
    ::= { ruijieBfdSessPerfEntry 14 }

ruijieBfdSessPerfCtrlPktOutHC OBJECT-TYPE
    SYNTAX     Counter64
    MAX-ACCESS read-only
    STATUS     current
    DESCRIPTION
        "This value represents the total number of BFD control
         messages transmitted for this BFD session.

         It MUST be equal to the least significant 32 bits of
         ruijieBfdSessPerfCtrlPktOut if supported, and MUST do so
         the rules spelled out in RFC 2863."
    ::= { ruijieBfdSessPerfEntry 15 }

ruijieBfdSessPerfCtrlPktDropHC OBJECT-TYPE
    SYNTAX     Counter64
    MAX-ACCESS read-only
    STATUS     current
    DESCRIPTION
        "This value represents the total number of BFD control
         messages received for this BFD session yet dropped for
         being invalid.

         It MUST be equal to the least significant 32 bits of
         ruijieBfdSessPerfCtrlPktDrop if supported, and MUST do so
         the rules spelled out in RFC 2863."
    ::= { ruijieBfdSessPerfEntry 16 }

ruijieBfdSessPerfEchoPktInHC OBJECT-TYPE
    SYNTAX     Counter64
    MAX-ACCESS read-only
    STATUS     current
    DESCRIPTION
        "This value represents the total number of BFD echo
         messages received for this BFD session.

         It MUST be equal to the least significant 32 bits of
         ruijieBfdSessPerfEchoPktIn if supported, and MUST do so
         the rules spelled out in RFC 2863."
    ::= { ruijieBfdSessPerfEntry 17 }

ruijieBfdSessPerfEchoPktOutHC OBJECT-TYPE
    SYNTAX     Counter64
    MAX-ACCESS read-only
    STATUS     current
    DESCRIPTION
        "This value represents the total number of BFD echo
         messages transmitted for this BFD session.

         It MUST be equal to the least significant 32 bits of
         ruijieBfdSessPerfEchoPktOut if supported, and MUST do so
         the rules spelled out in RFC 2863."
    ::= { ruijieBfdSessPerfEntry 18 }

ruijieBfdSessPerfEchoPktDropHC OBJECT-TYPE
    SYNTAX     Counter64
    MAX-ACCESS read-only
    STATUS     current
    DESCRIPTION
        "This value represents the total number of BFD echo
         messages received for this BFD session yet dropped
         for being invalid.

         It MUST be equal to the least significant 32 bits of
         ruijieBfdSessPerfEchoPktDrop if supported, and MUST do so
         the rules spelled out in RFC 2863."
    ::= { ruijieBfdSessPerfEntry 19 }

-- BFD Session Discriminator Mapping Table

ruijieBfdSessDiscMapTable OBJECT-TYPE
    SYNTAX     SEQUENCE OF RuijieBfdSessDiscMapEntry
    MAX-ACCESS not-accessible
    STATUS     current
    DESCRIPTION
        "The BFD Session Discriminator Mapping Table maps a
         local discriminator value to associated BFD session's
         RuijieBfdSessIndexTC used in the ruijieBfdSessionTable."
    ::= { ruijieBfdObjects 4 }

ruijieBfdSessDiscMapEntry OBJECT-TYPE
    SYNTAX     RuijieBfdSessDiscMapEntry
    MAX-ACCESS not-accessible
    STATUS     current
    DESCRIPTION
        "The BFD Session Discriminator Map Entry describes
         BFD session that is mapped to this RuijieBfdSessIndexTC."
    INDEX { ruijieBfdSessDiscriminator }
    ::= { ruijieBfdSessDiscMapTable 1 }

RuijieBfdSessDiscMapEntry ::= SEQUENCE {
    ruijieBfdSessDiscMapIndex            RuijieBfdSessIndexTC,
    ruijieBfdSessDiscMapStorageType      StorageType,
    ruijieBfdSessDiscMapRowStatus        RowStatus
}

ruijieBfdSessDiscMapIndex OBJECT-TYPE
    SYNTAX     RuijieBfdSessIndexTC
    MAX-ACCESS read-only
    STATUS     current
    DESCRIPTION
        "This object specifies the RuijieBfdSessIndexTC referred to by
         the indices of this row. In essence, a mapping is
         provided between these indexes and the RuijieBfdSessTable."
    ::= { ruijieBfdSessDiscMapEntry 1 }

ruijieBfdSessDiscMapStorageType OBJECT-TYPE
    SYNTAX     StorageType
    MAX-ACCESS read-create
    STATUS     current
    DESCRIPTION
        "This variable indicates the storage type for this
         object. Conceptual rows having the value
         'permanent' need not allow write-access to any
         columnar objects in the row."
    ::= { ruijieBfdSessDiscMapEntry 2 }

ruijieBfdSessDiscMapRowStatus OBJECT-TYPE
    SYNTAX     RowStatus
    MAX-ACCESS read-create
    STATUS     current
    DESCRIPTION
        "This variable is used to create, modify, and/or
         delete a row in this table. When a row in this
         table has a row in the active(1) state, no
         objects in this row can be modified except the
         ruijieBfdSessDiscMapRowStatus and ruijieBfdSessDiscMapStorageType."
    ::= { ruijieBfdSessDiscMapEntry 3 }

-- BFD Session IP Mapping Table

ruijieBfdSessIpMapTable OBJECT-TYPE
    SYNTAX     SEQUENCE OF RuijieBfdSessIpMapEntry
    MAX-ACCESS not-accessible
    STATUS     current
    DESCRIPTION
        "The BFD Session IP Mapping Table maps given
         ruijieBfdSessInterface, ruijieBfdSessSrcAddrType, ruijieBfdSessSrcAddr,
         ruijieBfdSessDstAddrType and ruijieBfdSessDstAddr
         to an associated BFD session's RuijieBfdSessIndexTC used in
         the ruijieBfdSessionTable."
    ::= { ruijieBfdObjects 5 }

ruijieBfdSessIpMapEntry OBJECT-TYPE
    SYNTAX     RuijieBfdSessIpMapEntry
    MAX-ACCESS not-accessible
    STATUS     current
    DESCRIPTION
       "The BFD Session IP Map Entry describes
        BFD session that is mapped to this RuijieBfdSessIndexTC."
    INDEX {
        ruijieBfdSessInterface,
        ruijieBfdSessSrcAddrType,
        ruijieBfdSessSrcAddr,
        ruijieBfdSessDstAddrType,
        ruijieBfdSessDstAddr
    }
    ::= { ruijieBfdSessIpMapTable 1 }

RuijieBfdSessIpMapEntry ::= SEQUENCE {
    ruijieBfdSessIpMapIndex            RuijieBfdSessIndexTC,
    ruijieBfdSessIpMapStorageType      StorageType,
    ruijieBfdSessIpMapRowStatus        RowStatus
}

ruijieBfdSessIpMapIndex OBJECT-TYPE
    SYNTAX     RuijieBfdSessIndexTC
    MAX-ACCESS read-only
    STATUS     current
    DESCRIPTION
        "This object specifies the RuijieBfdSessIndexTC referred to by
         the indexes of this row. In essence, a mapping is
         provided between these indexes and the RuijieBfdSessTable."
    ::= { ruijieBfdSessIpMapEntry 1 }

ruijieBfdSessIpMapStorageType OBJECT-TYPE
    SYNTAX     StorageType
    MAX-ACCESS read-create
    STATUS     current
    DESCRIPTION
        "This variable indicates the storage type for this
         object. Conceptual rows having the value
         'permanent' need not allow write-access to any
         columnar objects in the row."
    ::= { ruijieBfdSessIpMapEntry 2 }

ruijieBfdSessIpMapRowStatus OBJECT-TYPE
    SYNTAX     RowStatus
    MAX-ACCESS read-create
    STATUS     current
    DESCRIPTION
        "This variable is used to create, modify, and/or
         delete a row in this table. When a row in this
         table has a row in the active(1) state, no
         objects in this row can be modified except the
         ruijieBfdSessIpMapRowStatus and ruijieBfdSessIpMapStorageType."
    ::= { ruijieBfdSessIpMapEntry 3 }

-- Notification Configuration

ruijieBfdSessUp NOTIFICATION-TYPE
    OBJECTS {
        ruijieBfdSessDiag, -- low range value
        ruijieBfdSessDiag  -- high range value
    }
    STATUS     current
    DESCRIPTION
        "This notification is generated when the
         ruijieBfdSessState object for one or more contiguous
         entries in ruijieBfdSessTable are about to enter the up(4)
         state from some other state. The included values of
         ruijieBfdSessDiag MUST both be set equal to this
         new state (i.e: up(4)).  The two instances of
         ruijieBfdSessDiag in this notification indicate the range
         of indexes that are affected.  Note that all the indexes
         of the two ends of the range can be derived from the
         instance identifiers of these two objects.  For the
         cases where a contiguous range of sessions
         have transitioned into the up(4) state at roughly
         the same time, the device SHOULD issue a single
         notification for each range of contiguous indexes in
         an effort to minimize the emission of a large number
         of notifications.  If a notification has to be
         issued for just a single ruijieBfdSessEntry, then
         the instance identifier (and values) of the two
         ruijieBfdSessDiag objects MUST be the identical."
    ::= { ruijieBfdNotifications 1 }

ruijieBfdSessDown NOTIFICATION-TYPE
    OBJECTS {
        ruijieBfdSessDiag, -- low range value
        ruijieBfdSessDiag  -- high range value
    }
    STATUS     current
    DESCRIPTION
        "This notification is generated when the
         ruijieBfdSessState object for one or more contiguous
         entries in ruijieBfdSessTable are about to enter the down(2)
         or adminDown(1) states from some other state. The included
         values of ruijieBfdSessDiag MUST both be set equal to this new
         state (i.e: down(2) or adminDown(1)).  The two instances
         of ruijieBfdSessDiag in this notification indicate the range
         of indexes that are affected.  Note that all the indexes
         of the two ends of the range can be derived from the
         instance identifiers of these two objects.  For
         cases where a contiguous range of sessions
         have transitioned into the down(2) or adminDown(1) states
         at roughly the same time, the device SHOULD issue a single
         notification for each range of contiguous indexes in
         an effort to minimize the emission of a large number
         of notifications.  If a notification has to be
         issued for just a single ruijieBfdSessEntry, then
         the instance identifier (and values) of the two
         ruijieBfdSessDiag objects MUST be the identical."
    ::= { ruijieBfdNotifications 2 }

-- Ed Note: We need to add notification for changes
-- when the two ends automatically negotiate to a new detection time
-- value or when detection multiplier changes.


-- Module compliance.

ruijieBfdGroups
    OBJECT IDENTIFIER ::= { ruijieBfdConformance 1 }

ruijieBfdCompliances
    OBJECT IDENTIFIER ::= { ruijieBfdConformance 2 }

-- Compliance requirement for fully compliant implementations.

ruijieBfdModuleFullCompliance MODULE-COMPLIANCE
    STATUS current
    DESCRIPTION
        "Compliance statement for agents that provide full
         support for the BFD-MIB module. Such devices can
         then be monitored and also be configured using
         this MIB module."
    MODULE -- This module.

    MANDATORY-GROUPS {
        ruijieBfdSessionGroup,
        ruijieBfdSessionReadOnlyGroup,
        ruijieBfdSessionPerfGroup,
        ruijieBfdNotificationGroup
    }

    GROUP        ruijieBfdSessionPerfHCGroup
    DESCRIPTION  "This group is mandatory for all systems that
                  are able to support the Counter64 date type."

    OBJECT       ruijieBfdSessSrcAddrType
    SYNTAX       InetAddressType --{ unknown(0), ipv4(1), ipv6(2), ipv6z(4) }
    DESCRIPTION  "Only unknown(0), ipv4(1), ipv6(2) and ipv6z(4)
                  support are required."

    OBJECT       ruijieBfdSessSrcAddr
    SYNTAX       InetAddress (SIZE (0|4|16|20))
    DESCRIPTION  "An implementation is only required to support
                  unknown(0), ipv4(1), ipv6(2) and ipv6z(4) sizes."

    OBJECT       ruijieBfdSessDstAddrType
    SYNTAX       InetAddressType --{ unknown(0), ipv4(1), ipv6(2), ipv6z(4) }
    DESCRIPTION  "Only unknown(0), ipv4(1), ipv6(2) and ipv6z(4)
                  support are required."

    OBJECT       ruijieBfdSessDstAddr
    SYNTAX       InetAddress (SIZE (0|4|16|20))
    DESCRIPTION  "An implementation is only required to support
                  unknown(0), ipv4(1), ipv6(2) and ipv6z(4) sizes."

    OBJECT       ruijieBfdSessRowStatus
    SYNTAX       RowStatus --{ active(1), notInService(2) }
    --WRITE-SYNTAX RowStatus { active(1), notInService(2), createAndGo(4), destroy(6) }
    DESCRIPTION  "Support for createAndWait and notReady is not
                  required."

    OBJECT       ruijieBfdSessDiscMapRowStatus
    SYNTAX       RowStatus --{ active(1), notInService(2) }
    --WRITE-SYNTAX RowStatus { active(1), notInService(2),
                             --createAndGo(4), destroy(6) }
    DESCRIPTION  "Support for createAndWait and notReady is not
                  required."


    OBJECT       ruijieBfdSessIpMapRowStatus
    SYNTAX       RowStatus --{ active(1), notInService(2) }
    --WRITE-SYNTAX RowStatus { active(1), notInService(2),
                             --createAndGo(4), destroy(6) }
    DESCRIPTION  "Support for createAndWait and notReady is not
                  required."

    ::= { ruijieBfdCompliances 1 }

ruijieBfdModuleReadOnlyCompliance MODULE-COMPLIANCE
    STATUS current
    DESCRIPTION
        "Compliance requirement for implementations that only
         provide read-only support for BFD-MIB. Such devices
         can then be monitored but cannot be configured using
         this MIB module."

    MODULE -- This module.

    MANDATORY-GROUPS {
        ruijieBfdSessionGroup,
        ruijieBfdSessionReadOnlyGroup,
        ruijieBfdSessionPerfGroup,
        ruijieBfdNotificationGroup
    }

    GROUP        ruijieBfdSessionPerfHCGroup
    DESCRIPTION  "This group is mandatory for all systems that
                  are able to support the Counter64 date type."

    OBJECT       ruijieBfdSessVersionNumber
    MIN-ACCESS   read-only
    DESCRIPTION  "Write access is not required."

    OBJECT       ruijieBfdSessType
    MIN-ACCESS   read-only
    DESCRIPTION  "Write access is not required."

    OBJECT       ruijieBfdSessDestinationUdpPort
    MIN-ACCESS   read-only
    DESCRIPTION  "Write access is not required."

    OBJECT       ruijieBfdSessSourceUdpPort
    MIN-ACCESS   read-only
    DESCRIPTION  "Write access is not required."

    OBJECT       ruijieBfdSessEchoSourceUdpPort
    MIN-ACCESS   read-only
    DESCRIPTION  "Write access is not required."

    OBJECT       ruijieBfdSessAdminStatus
    MIN-ACCESS   read-only
    DESCRIPTION  "Write access is not required."

    OBJECT       ruijieBfdSessOperMode
    MIN-ACCESS   read-only
    DESCRIPTION  "Write access is not required."

    OBJECT       ruijieBfdSessDemandModeDesiredFlag
    MIN-ACCESS   read-only
    DESCRIPTION  "Write access is not required."

    OBJECT       ruijieBfdSessControlPlaneIndepFlag
    MIN-ACCESS   read-only
    DESCRIPTION  "Write access is not required."

    OBJECT       ruijieBfdSessMultipointFlag
    MIN-ACCESS   read-only
    DESCRIPTION  "Write access is not required."

    OBJECT       ruijieBfdSessInterface
    MIN-ACCESS   read-only
    DESCRIPTION  "Write access is not required."

    OBJECT       ruijieBfdSessSrcAddrType
    SYNTAX       InetAddressType --{ unknown(0), ipv4(1), ipv6(2), ipv6z(4) }
    MIN-ACCESS   read-only
    DESCRIPTION  "Only unknown(0), ipv4(1), ipv6(2) and ipv6z(4)
                  support are required."

    OBJECT       ruijieBfdSessSrcAddr
    SYNTAX       InetAddress (SIZE (0|4|16|20))
    MIN-ACCESS   read-only
    DESCRIPTION  "An implementation is only required to support
                  unknown(0), ipv4(1), ipv6(2) and ipv6z(4) sizes."

    OBJECT       ruijieBfdSessDstAddrType
    SYNTAX       InetAddressType --{ unknown(0), ipv4(1), ipv6(2), ipv6z(4) }
    MIN-ACCESS   read-only
    DESCRIPTION  "Only unknown(0), ipv4(1), ipv6(2) and ipv6z(4)
                  support are required."

    OBJECT       ruijieBfdSessDstAddr
    SYNTAX       InetAddress (SIZE (0|4|16|20))
    MIN-ACCESS   read-only
    DESCRIPTION  "An implementation is only required to support
                  unknown(0), ipv4(1), ipv6(2) and ipv6z(4) sizes."

    OBJECT       ruijieBfdSessGTSM
    MIN-ACCESS   read-only
    DESCRIPTION  "Write access is not required."

    OBJECT       ruijieBfdSessGTSMTTL
    MIN-ACCESS   read-only
    DESCRIPTION  "Write access is not required."

    OBJECT       ruijieBfdSessDesiredMinTxInterval
    MIN-ACCESS   read-only
    DESCRIPTION  "Write access is not required."

    OBJECT       ruijieBfdSessReqMinRxInterval
    MIN-ACCESS   read-only
    DESCRIPTION  "Write access is not required."

    OBJECT       ruijieBfdSessReqMinEchoRxInterval
    MIN-ACCESS   read-only
    DESCRIPTION  "Write access is not required."

    OBJECT       ruijieBfdSessDetectMult
    MIN-ACCESS   read-only
    DESCRIPTION  "Write access is not required."

    OBJECT       ruijieBfdSessAuthPresFlag
    MIN-ACCESS   read-only
    DESCRIPTION  "Write access is not required."

    OBJECT       ruijieBfdSessAuthenticationType
    MIN-ACCESS   read-only
    DESCRIPTION  "Write access is not required."

    OBJECT       ruijieBfdSessAuthenticationKeyID
    MIN-ACCESS   read-only
    DESCRIPTION  "Write access is not required."

    OBJECT       ruijieBfdSessAuthenticationKey
    MIN-ACCESS   read-only
    DESCRIPTION  "Write access is not required."

    OBJECT       ruijieBfdSessStorageType
    MIN-ACCESS   read-only
    DESCRIPTION  "Write access is not required."

    OBJECT       ruijieBfdSessRowStatus
    SYNTAX       RowStatus --{ active(1) }
    MIN-ACCESS   read-only
    DESCRIPTION  "Write access is not required."

    OBJECT       ruijieBfdSessDiscMapStorageType
    MIN-ACCESS   read-only
    DESCRIPTION  "Write access is not required."

    OBJECT       ruijieBfdSessDiscMapRowStatus
    SYNTAX       RowStatus --{ active(1) }
    MIN-ACCESS   read-only
    DESCRIPTION  "Write access is not required."

    OBJECT       ruijieBfdSessIpMapStorageType
    MIN-ACCESS   read-only
    DESCRIPTION  "Write access is not required."

    OBJECT       ruijieBfdSessIpMapRowStatus
    SYNTAX       RowStatus --{ active(1) }
    MIN-ACCESS   read-only
    DESCRIPTION  "Write access is not required."

    ::= { ruijieBfdCompliances 2 }

-- Units of conformance.

ruijieBfdSessionGroup OBJECT-GROUP
    OBJECTS {
        ruijieBfdAdminStatus,
        ruijieBfdSessNotificationsEnable,
        ruijieBfdSessVersionNumber,
        ruijieBfdSessType,
        ruijieBfdSessDestinationUdpPort,
        ruijieBfdSessSourceUdpPort,
        ruijieBfdSessEchoSourceUdpPort,
        ruijieBfdSessAdminStatus,
        ruijieBfdSessOperMode,
        ruijieBfdSessDemandModeDesiredFlag,
        ruijieBfdSessControlPlaneIndepFlag,
        ruijieBfdSessMultipointFlag,
        ruijieBfdSessInterface,
        ruijieBfdSessSrcAddrType,
        ruijieBfdSessSrcAddr,
        ruijieBfdSessDstAddrType,
        ruijieBfdSessDstAddr,
        ruijieBfdSessGTSM,
        ruijieBfdSessGTSMTTL,
        ruijieBfdSessDesiredMinTxInterval,
        ruijieBfdSessReqMinRxInterval,
        ruijieBfdSessReqMinEchoRxInterval,
        ruijieBfdSessDetectMult,
        ruijieBfdSessAuthPresFlag,
        ruijieBfdSessAuthenticationType,
        ruijieBfdSessAuthenticationKeyID,
        ruijieBfdSessAuthenticationKey,
        ruijieBfdSessStorageType,
        ruijieBfdSessRowStatus,
        ruijieBfdSessDiscMapStorageType,
        ruijieBfdSessDiscMapRowStatus,
        ruijieBfdSessIpMapStorageType,
        ruijieBfdSessIpMapRowStatus
    }
    STATUS     current
    DESCRIPTION
        "Collection of objects needed for BFD sessions."
    ::= { ruijieBfdGroups 1 }

ruijieBfdSessionReadOnlyGroup OBJECT-GROUP
    OBJECTS {
        ruijieBfdSessDiscriminator,
        ruijieBfdSessRemoteDiscr,
        ruijieBfdSessState,
        ruijieBfdSessRemoteHeardFlag,
        ruijieBfdSessDiag,
        ruijieBfdSessNegotiatedInterval,
        ruijieBfdSessNegotiatedEchoInterval,
        ruijieBfdSessNegotiatedDetectMult,
        ruijieBfdSessDiscMapIndex,
        ruijieBfdSessIpMapIndex
    }
    STATUS     current
    DESCRIPTION
        "Collection of read-only objects needed for BFD sessions."
    ::= { ruijieBfdGroups 2 }

ruijieBfdSessionPerfGroup OBJECT-GROUP
    OBJECTS {
        ruijieBfdSessPerfCtrlPktIn,
        ruijieBfdSessPerfCtrlPktOut,
        ruijieBfdSessPerfCtrlPktDrop,
        ruijieBfdSessPerfCtrlPktDropLastTime,
        ruijieBfdSessPerfEchoPktIn,
        ruijieBfdSessPerfEchoPktOut,
        ruijieBfdSessPerfEchoPktDrop,
        ruijieBfdSessPerfEchoPktDropLastTime,
        ruijieBfdSessUpTime,
        ruijieBfdSessPerfLastSessDownTime,
        ruijieBfdSessPerfLastCommLostDiag,
        ruijieBfdSessPerfSessUpCount,
        ruijieBfdSessPerfDiscTime
    }
    STATUS     current
    DESCRIPTION
        "Collection of objects needed to monitor the
         performance of BFD sessions."
    ::= { ruijieBfdGroups 3 }

ruijieBfdSessionPerfHCGroup OBJECT-GROUP
    OBJECTS {
        ruijieBfdSessPerfCtrlPktInHC,
        ruijieBfdSessPerfCtrlPktOutHC,
        ruijieBfdSessPerfCtrlPktDropHC,
        ruijieBfdSessPerfEchoPktInHC,
        ruijieBfdSessPerfEchoPktOutHC,
        ruijieBfdSessPerfEchoPktDropHC
    }
    STATUS     current
    DESCRIPTION
        "Collection of objects needed to monitor the
         performance of BFD sessions for which the
         values of ruijieBfdSessPerfPktIn, ruijieBfdSessPerfPktOut
         wrap around too quickly."
    ::= { ruijieBfdGroups 4 }

ruijieBfdNotificationGroup NOTIFICATION-GROUP
    NOTIFICATIONS {
        ruijieBfdSessUp,
        ruijieBfdSessDown
    }
    STATUS     current
    DESCRIPTION
        "Set of notifications implemented in this
         module."
    ::= { ruijieBfdGroups 5 }

END
