-- *****************************************************************
-- RUIJIE-WLAN-WLOG-MIB.mib:  Ruijie WLAN WLOG MIB file
--
-- October 2012, jiangweifeng
-- 
-- Copyright (c) 2012 by Ruijie Networks Co.,Ltd.
-- All rights reserved.
-- *****************************************************************


RUIJIE-WLAN-WLOG-MIB DEFINITIONS ::= BEGIN

IMPORTS
    MODULE-IDENTITY, 
    OBJECT-TYPE,
    Integer32,
    IpAddress
        FROM SNMPv2-SMI
    MacAddress,
    DisplayString
        FROM SNMPv2-TC
    InetAddress,
    InetAddressType
        FROM INET-ADDRESS-MIB
    ruijieMgmt
        FROM RUIJIE-SMI;

ruijieWlanWlogMIB MODULE-IDENTITY
    LAST-UPDATED "201210100000Z"
    ORGANIZATION "Ruijie Networks Co.,Ltd."
    CONTACT-INFO
            " 
            Tel: 4008-111-000 
                
            E-mail: service@ruijie.com.cn"
    DESCRIPTION
            "This module defines wlan wlog mibs."
    REVISION  "201210100000Z"
    DESCRIPTION
            "Initial version of this mib."
    ::= { ruijieMgmt 118 }

-- ******** define the notify nodes ***************
ruijieWlanWlogNotificationsMIBObjects OBJECT IDENTIFIER      ::= { ruijieWlanWlogMIB 1 }
ruijieWlanWlogNtfObjects       OBJECT IDENTIFIER ::= { ruijieWlanWlogNotificationsMIBObjects 1 }
ruijieWlanWlogNotifications     OBJECT IDENTIFIER ::= { ruijieWlanWlogNotificationsMIBObjects 2 }

-- ****************************************
--
--               Notifications Objects
--
-- ****************************************
ruijieWlogNotifyApName OBJECT-TYPE
    SYNTAX      DisplayString
    MAX-ACCESS  accessible-for-notify
    STATUS      current
    DESCRIPTION
        "Represents the name of a WTP."
    ::= { ruijieWlanWlogNtfObjects 1 }

ruijieWlogNotifyApMac OBJECT-TYPE
    SYNTAX      MacAddress
    MAX-ACCESS  accessible-for-notify
    STATUS      current
    DESCRIPTION
        "Represents the unique identifier of a WTP."
    ::= { ruijieWlanWlogNtfObjects 2 }

ruijieWlogNotifyApIp OBJECT-TYPE
    SYNTAX      InetAddress
    MAX-ACCESS  accessible-for-notify
    STATUS      current
    DESCRIPTION
        "Represents the Ip address of a WTP."
    ::= { ruijieWlanWlogNtfObjects 3 }

ruijieWlogNotifyApCwDownId OBJECT-TYPE
    SYNTAX      INTEGER
    MAX-ACCESS  accessible-for-notify
    STATUS      current
    DESCRIPTION
        "Represents the identification for a WTP's capwap down incident."
    ::= { ruijieWlanWlogNtfObjects 4 }

ruijieWlogNotifyApCwDownReason OBJECT-TYPE
    SYNTAX      DisplayString
    MAX-ACCESS  accessible-for-notify
    STATUS      current
    DESCRIPTION
        "Represents the reason for a WTP's capwap down."
    ::= { ruijieWlanWlogNtfObjects 5 }

-- **** define AP ethernet interface statistics table ****
ruijieWlogNotifyApIntfStatTable OBJECT-TYPE
    SYNTAX      SEQUENCE OF RuijieWlogNotifyApIntfStatEntry
    MAX-ACCESS  accessible-for-notify
    STATUS      current
    DESCRIPTION
        "Represents the ethernet interface statistics table of a WTP."
    ::= { ruijieWlanWlogNtfObjects 6 }

ruijieWlogNotifyApIntfStatEntry OBJECT-TYPE
    SYNTAX      RuijieWlogNotifyApIntfStatEntry
    MAX-ACCESS  accessible-for-notify
    STATUS      current
    DESCRIPTION
        "Represents the WTP ethernet interface statistics table Entry."
    INDEX   { ruijieWlogNotifyApIntfName}
    ::= { ruijieWlogNotifyApIntfStatTable 1 }

RuijieWlogNotifyApIntfStatEntry ::=
    SEQUENCE {
        ruijieWlogNotifyApIntfName                    DisplayString,
        ruijieWlogNotifyApIntfInputRate               INTEGER,
        ruijieWlogNotifyApIntfOutputRate              INTEGER,
        ruijieWlogNotifyApIntfUnicastInputPkts        INTEGER,
        ruijieWlogNotifyApIntfUnicastOutputPkts       INTEGER,
        ruijieWlogNotifyApIntfMulticastInputPkts      INTEGER,
        ruijieWlogNotifyApIntfMulticastOutputPkts     INTEGER,
        ruijieWlogNotifyApIntfBroadcastInputPkts      INTEGER,
        ruijieWlogNotifyApIntfBroadcastOutputPkts     INTEGER,
        ruijieWlogNotifyApIntfErrorInputPkts          INTEGER,
        ruijieWlogNotifyApIntfErrorOutputPkts         INTEGER
     }

ruijieWlogNotifyApIntfName OBJECT-TYPE
    SYNTAX      DisplayString
    MAX-ACCESS  accessible-for-notify
    STATUS      current
    DESCRIPTION
        "Represents the name of a interface of a WTP."
    ::= { ruijieWlogNotifyApIntfStatEntry 1 }

ruijieWlogNotifyApIntfInputRate OBJECT-TYPE
    SYNTAX      INTEGER
    MAX-ACCESS  accessible-for-notify
    STATUS      current
    DESCRIPTION
        "AP's ethernet interface's input rate(Kbps) in 5 mins."
    ::= { ruijieWlogNotifyApIntfStatEntry 2 }

ruijieWlogNotifyApIntfOutputRate OBJECT-TYPE
    SYNTAX      INTEGER
    MAX-ACCESS  accessible-for-notify
    STATUS      current
    DESCRIPTION
        "AP's ethernet interface's output rate(Kbps) in 5 mins."
    ::= { ruijieWlogNotifyApIntfStatEntry 3 }

ruijieWlogNotifyApIntfUnicastInputPkts OBJECT-TYPE
    SYNTAX      INTEGER
    MAX-ACCESS  accessible-for-notify
    STATUS      current
    DESCRIPTION
        "AP's ethernet interface's unicast input packets."
    ::= { ruijieWlogNotifyApIntfStatEntry 4 }

ruijieWlogNotifyApIntfUnicastOutputPkts OBJECT-TYPE
    SYNTAX      INTEGER
    MAX-ACCESS  accessible-for-notify
    STATUS      current
    DESCRIPTION
        "AP's ethernet interface's unicast output packets."
    ::= { ruijieWlogNotifyApIntfStatEntry 5 }

ruijieWlogNotifyApIntfMulticastInputPkts OBJECT-TYPE
    SYNTAX      INTEGER
    MAX-ACCESS  accessible-for-notify
    STATUS      current
    DESCRIPTION
        "AP's ethernet interface's multicast input packets."
    ::= { ruijieWlogNotifyApIntfStatEntry 6 }

ruijieWlogNotifyApIntfMulticastOutputPkts OBJECT-TYPE
    SYNTAX      INTEGER
    MAX-ACCESS  accessible-for-notify
    STATUS      current
    DESCRIPTION
        "AP's ethernet interface's multicast output packets."
    ::= { ruijieWlogNotifyApIntfStatEntry 7 }

ruijieWlogNotifyApIntfBroadcastInputPkts OBJECT-TYPE
    SYNTAX      INTEGER
    MAX-ACCESS  accessible-for-notify
    STATUS      current
    DESCRIPTION
        "AP's ethernet interface's broadcast input packets."
    ::= { ruijieWlogNotifyApIntfStatEntry 8 }

ruijieWlogNotifyApIntfBroadcastOutputPkts OBJECT-TYPE
    SYNTAX      INTEGER
    MAX-ACCESS  accessible-for-notify
    STATUS      current
    DESCRIPTION
        "AP's ethernet interface's broadcast output packets."
    ::= { ruijieWlogNotifyApIntfStatEntry 9 }

ruijieWlogNotifyApIntfErrorInputPkts OBJECT-TYPE
    SYNTAX      INTEGER
    MAX-ACCESS  accessible-for-notify
    STATUS      current
    DESCRIPTION
        "AP's ethernet interface's error input packets."
    ::= { ruijieWlogNotifyApIntfStatEntry 10 }

ruijieWlogNotifyApIntfErrorOutputPkts OBJECT-TYPE
    SYNTAX      INTEGER
    MAX-ACCESS  accessible-for-notify
    STATUS      current
    DESCRIPTION
        "AP's ethernet interface's error output packets."
    ::= { ruijieWlogNotifyApIntfStatEntry 11 }

-- **** define AP's radio statistics table ****
ruijieWlogNotifyApRadioStatTable OBJECT-TYPE
    SYNTAX      SEQUENCE OF RuijieWlogNotifyApRadioStatEntry
    MAX-ACCESS  accessible-for-notify
    STATUS      current
    DESCRIPTION
        "Represents the radio statistics table of a WTP."
    ::= { ruijieWlanWlogNtfObjects 7 }

ruijieWlogNotifyApRadioStatEntry OBJECT-TYPE
    SYNTAX      RuijieWlogNotifyApRadioStatEntry
    MAX-ACCESS  accessible-for-notify
    STATUS      current
    DESCRIPTION
        "Represents the WTP radio statistics table Entry."
    INDEX   { ruijieWlogNotifyApRadioId}
    ::= { ruijieWlogNotifyApRadioStatTable 1 }

RuijieWlogNotifyApRadioStatEntry ::=
    SEQUENCE {
        ruijieWlogNotifyApRadioId             INTEGER,
        ruijieWlogNotifyApRadioWorkChnl       INTEGER,
        ruijieWlogNotifyApRadioPower          INTEGER,
        ruijieWlogNotifyApRadioRssi           INTEGER,
        ruijieWlogNotifyApRadioErrFrame       INTEGER,
        ruijieWlogNotifyApRadioRetrsmit       INTEGER,
        ruijieWlogNotifyApRadioTotalStaNum    INTEGER,
        ruijieWlogNotifyApRadioWebStaNum      INTEGER,
        ruijieWlogNotifyApRadioD1xStaNum      INTEGER
     }

ruijieWlogNotifyApRadioId OBJECT-TYPE
    SYNTAX      INTEGER
    MAX-ACCESS  accessible-for-notify
    STATUS      current
    DESCRIPTION
        "AP's radio id."
    ::= { ruijieWlogNotifyApRadioStatEntry 1 }

ruijieWlogNotifyApRadioWorkChnl OBJECT-TYPE
    SYNTAX      INTEGER
    MAX-ACCESS  accessible-for-notify
    STATUS      current
    DESCRIPTION
        "AP's radio work channel."
    ::= { ruijieWlogNotifyApRadioStatEntry 2 }

ruijieWlogNotifyApRadioPower OBJECT-TYPE
    SYNTAX      INTEGER
    MAX-ACCESS  accessible-for-notify
    STATUS      current
    DESCRIPTION
        "AP's radio work power."
    ::= { ruijieWlogNotifyApRadioStatEntry 3 }

ruijieWlogNotifyApRadioRssi OBJECT-TYPE
    SYNTAX      INTEGER
    MAX-ACCESS  accessible-for-notify
    STATUS      current
    DESCRIPTION
        "AP's radio 's RSSI(received signal strength indicator)."
    ::= { ruijieWlogNotifyApRadioStatEntry 4 }

ruijieWlogNotifyApRadioErrFrame OBJECT-TYPE
    SYNTAX      INTEGER
    MAX-ACCESS  accessible-for-notify
    STATUS      current
    DESCRIPTION
        "AP's radio's total error frame number."
    ::= { ruijieWlogNotifyApRadioStatEntry 5 }

ruijieWlogNotifyApRadioRetrsmit OBJECT-TYPE
    SYNTAX      INTEGER
    MAX-ACCESS  accessible-for-notify
    STATUS      current
    DESCRIPTION
        "AP's radio's total Retransmitted frame number."
    ::= { ruijieWlogNotifyApRadioStatEntry 6 }

ruijieWlogNotifyApRadioTotalStaNum OBJECT-TYPE
    SYNTAX      INTEGER
    MAX-ACCESS  accessible-for-notify
    STATUS      current
    DESCRIPTION
        "AP's radio's total online sta number."
    ::= { ruijieWlogNotifyApRadioStatEntry 7 }

ruijieWlogNotifyApRadioWebStaNum OBJECT-TYPE
    SYNTAX      INTEGER
    MAX-ACCESS  accessible-for-notify
    STATUS      current
    DESCRIPTION
        "AP's radio's web authenticated sta number."
    ::= { ruijieWlogNotifyApRadioStatEntry 8 }

ruijieWlogNotifyApRadioD1xStaNum OBJECT-TYPE
    SYNTAX      INTEGER
    MAX-ACCESS  accessible-for-notify
    STATUS      current
    DESCRIPTION
        "AP's radio's dot1x authenticated sta number."
    ::= { ruijieWlogNotifyApRadioStatEntry 9 }

-- **** define STA Operation notification objects ****
ruijieWlogNotifyStaMac OBJECT-TYPE
    SYNTAX      MacAddress
    MAX-ACCESS  accessible-for-notify
    STATUS      current
    DESCRIPTION
        "Represents the unique identifier of a STA."
    ::= { ruijieWlanWlogNtfObjects 8 }

ruijieWlogNotifyStaIp OBJECT-TYPE
    SYNTAX      IpAddress
    MAX-ACCESS  accessible-for-notify
    STATUS      current
    DESCRIPTION
        "Represents Ipv4 address of a STA."
    ::= { ruijieWlanWlogNtfObjects 9 }

ruijieWlogNotifyStaIpv6 OBJECT-TYPE
    SYNTAX      InetAddress
    MAX-ACCESS  accessible-for-notify
    STATUS      current
    DESCRIPTION
        "Represents Ipv6 address of a STA."
    ::= { ruijieWlanWlogNtfObjects 10 }

ruijieWlogNotifySsid OBJECT-TYPE
    SYNTAX      DisplayString
    MAX-ACCESS  accessible-for-notify
    STATUS      current
    DESCRIPTION
        "Represents the Wlan Ssid."
    ::= { ruijieWlanWlogNtfObjects 11 }

ruijieWlogNotifyStaRssi OBJECT-TYPE
    SYNTAX      INTEGER
    MAX-ACCESS  accessible-for-notify
    STATUS      current
    DESCRIPTION
        "Represents STA's RSSI(received signal strength indicator)."
    ::= { ruijieWlanWlogNtfObjects 12 }

ruijieWlogNotifyStaLinkrate OBJECT-TYPE
    SYNTAX      INTEGER
    MAX-ACCESS  accessible-for-notify
    STATUS      current
    DESCRIPTION
        "Represents STA's link rate(Kbps)."
    ::= { ruijieWlanWlogNtfObjects 13 }

ruijieWlogNotifyStaOperType OBJECT-TYPE
    SYNTAX      INTEGER
    MAX-ACCESS  accessible-for-notify
    STATUS      current
    DESCRIPTION
        "Represents the STA's normal operation, 
        1-associate,
        2-disassociate,
        3-roam in,
        4-roam out,
        5-ip update,
        6-ipv6 update."
    ::= { ruijieWlanWlogNtfObjects 14 }

ruijieWlogNotifyStaAbnormalOperType OBJECT-TYPE
    SYNTAX      INTEGER
    MAX-ACCESS  accessible-for-notify
    STATUS      current
    DESCRIPTION
        "Represents the STA's abnormal operation, 
        1-associate fail,
        2-offline,
        3-roam fail,
        4-dot1x authenticate fail,
        5-web authenticate fail."
    ::= { ruijieWlanWlogNtfObjects 15 }

ruijieWlogNotifyStaOperReason OBJECT-TYPE
    SYNTAX      DisplayString
    MAX-ACCESS  accessible-for-notify
    STATUS      current
    DESCRIPTION
        "Represents the reason of STA's abnormal operation"
    ::= { ruijieWlanWlogNtfObjects 16 }

-- ****************************************
--
--               Notify nodes
--
-- ****************************************
ruijieNotifyApCapwapDownReason NOTIFICATION-TYPE
    OBJECTS     {
                  ruijieWlogNotifyApName,
                  ruijieWlogNotifyApMac,
                  ruijieWlogNotifyApIp,
                  ruijieWlogNotifyApCwDownId,
                  ruijieWlogNotifyApCwDownReason
                }
    STATUS      current
    DESCRIPTION
        "This notification is sent by the AC when an AP's capwap down."
    ::= { ruijieWlanWlogNotifications 1 }

ruijieNotifyApCapwapDownIntf NOTIFICATION-TYPE
    OBJECTS     {
                  ruijieWlogNotifyApName,
                  ruijieWlogNotifyApMac,
                  ruijieWlogNotifyApIp,
                  ruijieWlogNotifyApCwDownId,
                  ruijieWlogNotifyApIntfName,
                  ruijieWlogNotifyApIntfInputRate,
                  ruijieWlogNotifyApIntfOutputRate,
                  ruijieWlogNotifyApIntfUnicastInputPkts,
                  ruijieWlogNotifyApIntfUnicastOutputPkts,
                  ruijieWlogNotifyApIntfMulticastInputPkts,
                  ruijieWlogNotifyApIntfMulticastOutputPkts,
                  ruijieWlogNotifyApIntfBroadcastInputPkts,
                  ruijieWlogNotifyApIntfBroadcastOutputPkts,
                  ruijieWlogNotifyApIntfErrorInputPkts,
                  ruijieWlogNotifyApIntfErrorOutputPkts
                }
    STATUS      current
    DESCRIPTION
        "This notification is sent by the AC when an AP's capwap down."
    ::= { ruijieWlanWlogNotifications 2 }

ruijieNotifyApCapwapDownRadio NOTIFICATION-TYPE
    OBJECTS     {
                  ruijieWlogNotifyApName,
                  ruijieWlogNotifyApMac,
                  ruijieWlogNotifyApIp,
                  ruijieWlogNotifyApCwDownId,
                  ruijieWlogNotifyApRadioId,
                  ruijieWlogNotifyApRadioWorkChnl,
                  ruijieWlogNotifyApRadioPower,
                  ruijieWlogNotifyApRadioRssi,
                  ruijieWlogNotifyApRadioErrFrame,
                  ruijieWlogNotifyApRadioRetrsmit,
                  ruijieWlogNotifyApRadioTotalStaNum,
                  ruijieWlogNotifyApRadioWebStaNum,
                  ruijieWlogNotifyApRadioD1xStaNum
                }
    STATUS      current
    DESCRIPTION
        "This notification is sent by the AC when an AP's capwap down."
    ::= { ruijieWlanWlogNotifications 3 }

ruijieNotifyStaOper NOTIFICATION-TYPE
    OBJECTS     {
                  ruijieWlogNotifyStaMac,
                  ruijieWlogNotifyStaIp,
                  ruijieWlogNotifyStaIpv6,
                  ruijieWlogNotifyStaRssi,
                  ruijieWlogNotifyStaLinkrate,
                  ruijieWlogNotifyApName,
                  ruijieWlogNotifySsid,
                  ruijieWlogNotifyStaOperType
                }
    STATUS      current
    DESCRIPTION
        "This notification is sent by the AC when an STA 
        associate/disassociate or roam in/out or ip address update."
    ::= { ruijieWlanWlogNotifications 4 }

ruijieNotifyStaAbnormalOper NOTIFICATION-TYPE
    OBJECTS     {
                  ruijieWlogNotifyStaMac,
                  ruijieWlogNotifyStaIp,
                  ruijieWlogNotifyStaIpv6,
                  ruijieWlogNotifyStaAbnormalOperType,
                  ruijieWlogNotifyStaOperReason
                }
    STATUS      current
    DESCRIPTION
        "This notification is sent by the AC when an STA 
        associate fail or abnormal offline or roam fail 
        or dot1x/web authenticate failed."
    ::= { ruijieWlanWlogNotifications 5 }

END
