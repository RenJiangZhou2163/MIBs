-- *****************************************************************
-- RUIJIE-DHCP-RELAY-MIB.mib:  Ruijie DHCP relay MIB file
--
-- Oct 2011, yangchanghua
--
-- Copyright (c) 2011 by Ruijie Networks Co.,Ltd.
-- All rights reserved.
-- *****************************************************************
--

RUIJIE-DHCP-RELAY-MIB DEFINITIONS ::= BEGIN

IMPORTS
        MODULE-IDENTITY,
        OBJECT-TYPE,
        NOTIFICATION-TYPE,
        Integer32,
        Counter32
                FROM SNMPv2-SMI
        TruthValue,
        DisplayString,
        RowStatus,
        MacAddress
                FROM SNMPv2-TC
        MODULE-COMPLIANCE,
        OBJECT-GROUP,
        NOTIFICATION-GROUP
                FROM SNMPv2-CONF
        ruijieMgmt
                FROM RUIJIE-SMI;
                
ruijieDhcpMIB  MODULE-IDENTITY
    LAST-UPDATED "201111280000Z"
    ORGANIZATION "Ruijie Networks Co.,Ltd."
    CONTACT-INFO
        				" 
                Tel: 4008-111-000 

                E-mail: service@ruijie.com.cn"
    DESCRIPTION
        "This module defines ruijie DHCP mibs."
    -- Revision History
    REVISION    "201111280000Z"
    DESCRIPTION
        "Initial version of this MIB module."
    ::= { ruijieMgmt 104 }
    
--
-- Declare top-level DHCP relay MIB objects
--
ruijieDhcpMIBObjects OBJECT-IDENTITY 
    STATUS      current
    DESCRIPTION
        "DHCP Relay MIB objects are defined in this branch."
    ::= { ruijieDhcpMIB 1 }
    
--
-- DHCP Relay
--
ruijieDhcpRelayMIBObjects OBJECT-IDENTITY 
    STATUS      current
    DESCRIPTION
        "DHCP Relay MIB identification objects are all defined
        in this branch."
    ::= { ruijieDhcpMIBObjects 1 }

--
-- DHCP Relay Status
--
ruijieDHCPRelayCycleStatus OBJECT-TYPE
    SYNTAX      INTEGER {
                             on(0), -- DHCP relay cycle mode status is on
                             off(1) -- DHCP relay cycle mode status is off
                        }
    MAX-ACCESS  read-write
    STATUS      current
    DESCRIPTION
        "Status of DHCP relay cycle mode,
         when the value is 0, cycle with the serveral DHCP servers addresses,
         when the value is 1, use one same DHCP server."
    ::= { ruijieDhcpRelayMIBObjects 1 }

ruijieDhcpRelayCounters OBJECT-IDENTITY
    STATUS      current
    DESCRIPTION
        "Group of objects that count various DHCP Relay events."
 ::= { ruijieDhcpRelayMIBObjects 2 }
 
--
-- DHCP Relay Counters
--
ruijieDHCPRRxBadPktNum OBJECT-TYPE
    SYNTAX      Integer32
    MAX-ACCESS  read-only
    STATUS      current
    DESCRIPTION
        "The total number of the bad packets received by 
            DHCP relay."
    ::= { ruijieDhcpRelayCounters 1 }
    
ruijieDHCPRRxServerPktNum OBJECT-TYPE
    SYNTAX      Integer32
    MAX-ACCESS  read-only
    STATUS      current
    DESCRIPTION
        "The total number of the packets received from
            DHCP servers by DHCP relay module."
    ::= { ruijieDhcpRelayCounters 2 }
    
ruijieDHCPRTxServerPktNum OBJECT-TYPE
    SYNTAX      Integer32
    MAX-ACCESS  read-only
    STATUS      current
    DESCRIPTION
        "The total number of the packets transmited to
            DHCP servers by DHCP relay module."
    ::= { ruijieDhcpRelayCounters 3 }

ruijieDHCPRRxClientPktNum OBJECT-TYPE
    SYNTAX      Integer32
    MAX-ACCESS  read-only
    STATUS      current
    DESCRIPTION
        "The total number of the packets received form DHCP
            clients by DHCP relay."
    ::= { ruijieDhcpRelayCounters 4 }
    
ruijieDHCPRTxClientPktNum OBJECT-TYPE
    SYNTAX      Integer32
    MAX-ACCESS  read-only
    STATUS      current
    DESCRIPTION
        "The total number of the packets transmited
            to DHCP clients by DHCP relay."
    ::= { ruijieDhcpRelayCounters 5 }

ruijieDHCPRRxClientUniPktNum OBJECT-TYPE
    SYNTAX      Integer32
    MAX-ACCESS  read-only
    STATUS      current
    DESCRIPTION
        "The total number of the unicast packets received form DHCP
            clients by DHCP relay."
    ::= { ruijieDhcpRelayCounters 6 }

ruijieDHCPRRxClientBroPktNum OBJECT-TYPE
    SYNTAX      Integer32
    MAX-ACCESS  read-only
    STATUS      current
    DESCRIPTION
        "The total number of the broadcast packets received form DHCP
            clients by DHCP relay."
    ::= { ruijieDhcpRelayCounters 7 }

ruijieDHCPRTxClientUniPktNum OBJECT-TYPE
    SYNTAX      Integer32
    MAX-ACCESS  read-only
    STATUS      current
    DESCRIPTION
        "The total number of the unicast packets transmited
            to DHCP clients by DHCP relay."
    ::= { ruijieDhcpRelayCounters 8 }
    
ruijieDHCPRTxClientBroPktNum OBJECT-TYPE
    SYNTAX      Integer32
    MAX-ACCESS  read-only
    STATUS      current
    DESCRIPTION
        "The total number of the broadcast packets transmited
            to DHCP clients by DHCP relay."
    ::= { ruijieDhcpRelayCounters 9 }
    
ruijieDHCPRelayDiscoverPktNum OBJECT-TYPE
    SYNTAX      Integer32
    MAX-ACCESS  read-only
    STATUS      current
    DESCRIPTION
        "The total number of the DHCP Discover packets handled
            by DHCP relay."
    ::= { ruijieDhcpRelayCounters 10 }
    
ruijieDHCPRelayRequestPktNum OBJECT-TYPE
    SYNTAX      Integer32
    MAX-ACCESS  read-only
    STATUS      current
    DESCRIPTION
        "The total number of the DHCP Request packets handled
            by DHCP relay."
    ::= { ruijieDhcpRelayCounters 11 }
    
ruijieDHCPRelayDeclinePktNum OBJECT-TYPE
    SYNTAX      Integer32
    MAX-ACCESS  read-only
    STATUS      current
    DESCRIPTION
        "The total number of the DHCP Decline packets handled
            by DHCP relay."
    ::= { ruijieDhcpRelayCounters 12 }
    
ruijieDHCPRelayReleasePktNum OBJECT-TYPE
    SYNTAX      Integer32
    MAX-ACCESS  read-only
    STATUS      current
    DESCRIPTION
        "The total number of the DHCP Release packets handled
            by DHCP relay."
    ::= { ruijieDhcpRelayCounters 13 }
    
ruijieDHCPRelayInformPktNum OBJECT-TYPE
    SYNTAX      Integer32
    MAX-ACCESS  read-only
    STATUS      current
    DESCRIPTION
        "The total number of the DHCP Inform packets handled
            by DHCP relay."
    ::= { ruijieDhcpRelayCounters 14 }
    
ruijieDHCPRelayOfferPktNum OBJECT-TYPE
    SYNTAX      Integer32
    MAX-ACCESS  read-only
    STATUS      current
    DESCRIPTION
        "The total number of the DHCP Offer packets handled
            by DHCP server."
    ::= { ruijieDhcpRelayCounters 15 }
    
ruijieDHCPRelayAckPktNum OBJECT-TYPE
    SYNTAX      Integer32
    MAX-ACCESS  read-only
    STATUS      current
    DESCRIPTION
        "The total number of the DHCP Ack packets handled
            by DHCP relay."
    ::= { ruijieDhcpRelayCounters 16 }
    
ruijieDHCPRelayNakPktNum OBJECT-TYPE
    SYNTAX      Integer32
    MAX-ACCESS  read-only
    STATUS      current
    DESCRIPTION
        "The total number of the DHCP Nak packets handled
            by DHCP relay."
    ::= { ruijieDhcpRelayCounters 17 }
    
--
-- Conformance
--
ruijieDhcpMIBConformance   OBJECT-IDENTITY 
    STATUS      current
    DESCRIPTION
        "DHCP relay conformance objects are all defined in this
        branch."
    ::= { ruijieDhcpMIB 2 }
    
ruijieDhcpMIBCompliances   OBJECT IDENTIFIER ::= { ruijieDhcpMIBConformance 1 }
ruijieDhcpMIBGroups        OBJECT IDENTIFIER ::= { ruijieDhcpMIBConformance 2 }

--
-- Compliance groups
--
ruijieDhcpRelayCompliance MODULE-COMPLIANCE
    STATUS      current
    DESCRIPTION
        "This group describes the requirements for conformance to the
        DHCP Relay MIB."
    MODULE  -- this module
    MANDATORY-GROUPS {
        ruijieDhcpRelayCountersObjects
    }
    ::= { ruijieDhcpMIBCompliances 1 } 
    
--
-- Object groups
--
ruijieDhcpRelayCountersObjects  OBJECT-GROUP
    OBJECTS {
        ruijieDHCPRelayCycleStatus,
        ruijieDHCPRRxBadPktNum,
        ruijieDHCPRRxServerPktNum,
        ruijieDHCPRTxServerPktNum,
        ruijieDHCPRRxClientPktNum,
        ruijieDHCPRTxClientPktNum,
        ruijieDHCPRRxClientUniPktNum,
        ruijieDHCPRRxClientBroPktNum,
        ruijieDHCPRTxClientUniPktNum,
        ruijieDHCPRTxClientBroPktNum,
        ruijieDHCPRelayDiscoverPktNum,
        ruijieDHCPRelayRequestPktNum,
        ruijieDHCPRelayDeclinePktNum,
        ruijieDHCPRelayReleasePktNum,
        ruijieDHCPRelayInformPktNum,
        ruijieDHCPRelayOfferPktNum,
		    ruijieDHCPRelayAckPktNum,
		    ruijieDHCPRelayNakPktNum }
    STATUS      current
    DESCRIPTION
        "The basic collection of objects providing management of DHCP
        Relay functionality."
    ::= { ruijieDhcpMIBGroups 1 }

END
