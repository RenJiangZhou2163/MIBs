-- *****************************************************************
-- RUIJIE-CAPWAP-APP-MIB.mib:  Ruijie CAPWAP APP MIB file
--
-- Jul 2010, Panshiyong
--
-- Copyright(c) 2010 by Ruijie Networks Co.,Ltd.
-- All rights reserved.
-- 
-- *****************************************************************
--

RUIJIE-CAPWAP-APP-MIB DEFINITIONS ::= BEGIN

IMPORTS
        MODULE-IDENTITY,
        OBJECT-TYPE,
        TimeTicks,
        Unsigned32,
        Integer32,
        IpAddress
                FROM SNMPv2-SMI
        DisplayString,
        TruthValue,
        TAddress,
        RowStatus
                FROM SNMPv2-TC
        MODULE-COMPLIANCE,
        OBJECT-GROUP
                FROM SNMPv2-CONF
        InetAddressType,
        InetAddress
                FROM INET-ADDRESS-MIB
        sysObjectID
                FROM RFC1213-MIB
        ruijieSystemSerialno
                FROM RUIJIE-SYSTEM-MIB
        ruijieDeviceMacAddress
                FROM RUIJIE-ENTITY-MIB
        ruijieMgmt
                FROM RUIJIE-SMI;

ruijieCapwapAppMIB MODULE-IDENTITY
        LAST-UPDATED "201006040000Z"
        ORGANIZATION "Ruijie Networks Co.,Ltd."
        CONTACT-INFO
                " 
                Tel: 4008-111-000 

                E-mail: service@ruijie.com.cn"
        DESCRIPTION
                "This module defines ruijie Capwap App mibs."
        REVISION      "201006040000Z"
        DESCRIPTION
                "Initial version of this MIB module."
        ::= { ruijieMgmt 87 }

ruijieCapwapAppMIBObjects   OBJECT IDENTIFIER ::= { ruijieCapwapAppMIB 1 }


--**********************************************************************
-- about heartbeat info 
--**********************************************************************
ruijieAppHeartbeatMIBObjects 
    OBJECT IDENTIFIER ::= { ruijieCapwapAppMIBObjects 1 }

ruijieAppHeartbeatOnOff OBJECT-TYPE
    SYNTAX INTEGER {
             off(0),
             on(1)
           }
    MAX-ACCESS read-write
    STATUS current
    DESCRIPTION
        "Heartbeat detect switch."
    ::= { ruijieAppHeartbeatMIBObjects 1 } 
     
ruijieAppHeartbeatPeriod OBJECT-TYPE
    SYNTAX INTEGER (60..3600)
    MAX-ACCESS read-write
    STATUS current
    DESCRIPTION
        "Heartbeat detect periode."
    ::= { ruijieAppHeartbeatMIBObjects 2 } 

ruijieAppHeartbeatIpAddr OBJECT-TYPE
    SYNTAX IpAddress
    MAX-ACCESS read-only
    STATUS current
    DESCRIPTION
        "IP address of the AP"
    ::= { ruijieAppHeartbeatMIBObjects 3 }
    
ruijieAppHeartbeatTimeStamp OBJECT-TYPE
    SYNTAX TimeTicks
    MAX-ACCESS read-only
    STATUS current
    DESCRIPTION
        "Time stamp of the AP"
    ::= { ruijieAppHeartbeatMIBObjects 4 }
    
    
-- heartbeat traps    
ruijieAppHeartbeatMIBTraps OBJECT IDENTIFIER ::= { ruijieAppHeartbeatMIBObjects 0 }

ruijieAppHeartbeatTrap NOTIFICATION-TYPE
    OBJECTS {
        ruijieAppHeartbeatIpAddr,
        ruijieAppHeartbeatTimeStamp
    }
    STATUS  current
    DESCRIPTION
            " This trap will be sent when a heartbeat periode pass."
    ::= { ruijieAppHeartbeatMIBTraps 1 } 


--**********************************************************************
-- about admin info 
--**********************************************************************
ruijieAppAdminInfoMIBObjects 
    OBJECT IDENTIFIER ::= { ruijieCapwapAppMIBObjects 2 }

ruijieAppAdminInfoTable OBJECT-TYPE
    SYNTAX SEQUENCE OF RuijieAppAdminInfoEntry
    MAX-ACCESS not-accessible
    STATUS current
    DESCRIPTION
        "The table about admin info."
    ::= { ruijieAppAdminInfoMIBObjects 1 }

ruijieAppAdminInfoEntry OBJECT-TYPE
    SYNTAX RuijieAppAdminInfoEntry
    MAX-ACCESS not-accessible
    STATUS current
    DESCRIPTION
        "The entry of ruijieAdminInfoTable."
    INDEX { ruijieAppAdminName }
    ::= { ruijieAppAdminInfoTable 1 }

RuijieAppAdminInfoEntry ::=
    SEQUENCE {
       ruijieAppAdminName      DisplayString,
       ruijieAppAdminPwd       DisplayString,
       ruijieAppAdminPriLevel  INTEGER,
       ruijieAppAdminStatus    RowStatus
    }

ruijieAppAdminName OBJECT-TYPE 
    SYNTAX DisplayString(SIZE(1..64))
    MAX-ACCESS read-only
    STATUS current
    DESCRIPTION
           "The name of the administrator."
    ::= { ruijieAppAdminInfoEntry 1 }
				
ruijieAppAdminPwd OBJECT-TYPE
    SYNTAX DisplayString(SIZE(1..255))
    MAX-ACCESS read-create
    STATUS current
    DESCRIPTION
           "The password of the administrator."
    ::= { ruijieAppAdminInfoEntry 2 }

ruijieAppAdminPriLevel OBJECT-TYPE
    SYNTAX INTEGER
    MAX-ACCESS read-create
    STATUS current
    DESCRIPTION
           "The privilege level of the administrator."
    ::= { ruijieAppAdminInfoEntry 3 }

ruijieAppAdminStatus OBJECT-TYPE
    SYNTAX RowStatus
    MAX-ACCESS read-create
    STATUS current
    DESCRIPTION
           "The rowstatus of the adminInfoEntry."
    ::= { ruijieAppAdminInfoEntry 4 }


ruijieAppAdminInfoName OBJECT-TYPE
    SYNTAX DisplayString(SIZE(1..64))
    MAX-ACCESS not-accessible
    STATUS current
    DESCRIPTION
        "The administrator name info."
    ::= { ruijieAppAdminInfoMIBObjects 2 }

ruijieAppAdminInfoIpAddr OBJECT-TYPE
    SYNTAX IpAddress
    MAX-ACCESS not-accessible
    STATUS current
    DESCRIPTION
        "The administrator ip address info."
    ::= { ruijieAppAdminInfoMIBObjects 3 }

ruijieAppAdminInfoConfigContext OBJECT-TYPE
    SYNTAX OCTET STRING(SIZE(1..512))
    MAX-ACCESS not-accessible
    STATUS current
    DESCRIPTION
        "The context of configuration."
    ::= { ruijieAppAdminInfoMIBObjects 4 }

ruijieAppAdminInfoLoginType OBJECT-TYPE
    SYNTAX DisplayString(SIZE(1..64))
    MAX-ACCESS not-accessible
    STATUS current
    DESCRIPTION
        "The administrator login type."
    ::= { ruijieAppAdminInfoMIBObjects 5 }

ruijieAppAdminTerminalInfo OBJECT-TYPE
    SYNTAX DisplayString(SIZE(1..64))
    MAX-ACCESS not-accessible
    STATUS current
    DESCRIPTION
        "The administrator terminal information:
         console  -  login from console
         aux id   -  login from auxiliary
         vty id   -  login from telnet or ssh
         web      -  login from http/web"
    ::= { ruijieAppAdminInfoMIBObjects 6 }

ruijieAppAdminLoginFailReason OBJECT-TYPE
    SYNTAX INTEGER 
    MAX-ACCESS not-accessible
    STATUS current
    DESCRIPTION
        "The administrator login fail reason:
         1  -  username or password is error "
    ::= { ruijieAppAdminInfoMIBObjects 7 }

ruijieAppAdminTargetLevel OBJECT-TYPE
    SYNTAX INTEGER (0..15)
    MAX-ACCESS not-accessible
    STATUS current
    DESCRIPTION
        "The administrator target level"
    ::= { ruijieAppAdminInfoMIBObjects 8 }

ruijieAppAdminInfoLoginProtocol OBJECT-TYPE
    SYNTAX DisplayString(SIZE(1..64))
    MAX-ACCESS not-accessible
    STATUS current
    DESCRIPTION
        "The administrator login protocol."
    ::= { ruijieAppAdminInfoMIBObjects 9 }
    
ruijieAppAdminInfoLoginIPv6 OBJECT-TYPE
    SYNTAX DisplayString(SIZE(1..64))
    MAX-ACCESS not-accessible
    STATUS current
    DESCRIPTION
        "The administrator login IPv6 address."
    ::= { ruijieAppAdminInfoMIBObjects 10 }

-- admin traps
ruijieAppAdminMIBTraps
    OBJECT IDENTIFIER ::= { ruijieAppAdminInfoMIBObjects 0 }

ruijieAppAdminLoginTrap NOTIFICATION-TYPE
    OBJECTS {
        ruijieAppAdminInfoName,
        ruijieAppAdminInfoIpAddr,
        ruijieAppAdminInfoLoginType,
        ruijieAppAdminInfoLoginProtocol,
        ruijieAppAdminInfoLoginIPv6
    }
    STATUS  current
    DESCRIPTION
            " This trap will be sent when the administrator rlogin the device."
    ::= { ruijieAppAdminMIBTraps 1 } 

ruijieAppAdminModifyConfigTrap NOTIFICATION-TYPE
    OBJECTS {
        ruijieAppAdminInfoName,
        ruijieAppAdminInfoIpAddr,
        ruijieAppAdminInfoConfigContext
    }
    STATUS  current
    DESCRIPTION
            " This trap will be sent when the administrator modify the configuration."
    ::= { ruijieAppAdminMIBTraps 2 } 

ruijieAppAdminLoginFailTrap NOTIFICATION-TYPE
    OBJECTS {
        ruijieAppAdminInfoName,
        ruijieAppAdminInfoIpAddr,
        ruijieAppAdminTerminalInfo,
        ruijieAppAdminLoginFailReason
    }
    STATUS  current
    DESCRIPTION
            " This trap will be sent when the administrator login the device failed."
    ::= { ruijieAppAdminMIBTraps 3 } 

ruijieAppAdminEnableFailTrap NOTIFICATION-TYPE
    OBJECTS {
        ruijieAppAdminInfoName,
        ruijieAppAdminInfoIpAddr,
        ruijieAppAdminTerminalInfo,
        ruijieAppAdminTargetLevel
    }
    STATUS  current
    DESCRIPTION
            " This trap will be sent when the administrator enter target cli level failed."
    ::= { ruijieAppAdminMIBTraps 4 } 

--**********************************************************************
-- about polltime info 
--**********************************************************************
ruijieAppPollTimeMIBObjects 
    OBJECT IDENTIFIER ::= { ruijieCapwapAppMIBObjects 3 }

ruijieAppPollTimeOfLast OBJECT-TYPE
    SYNTAX TimeTicks
    MAX-ACCESS read-only
    STATUS current
    DESCRIPTION
           "The last time of administrator 
            poll the devices."
		::= { ruijieAppPollTimeMIBObjects 1 }


--**********************************************************************
-- about config info 
--**********************************************************************
ruijieAppConfigMIBObjects 
    OBJECT IDENTIFIER ::= { ruijieCapwapAppMIBObjects 4 }
    
ruijieAppRcvToDefConfig OBJECT-TYPE
    SYNTAX INTEGER{
         normal(0),
         reset(1)
    }
    MAX-ACCESS read-write
    STATUS current
    DESCRIPTION
        "0 - normal, 
         1 - recove the device to default config. then reload the device"
    ::= { ruijieAppConfigMIBObjects 1 }

ruijieAppConfigFileName OBJECT-TYPE
    SYNTAX DisplayString(SIZE (1..32))
    MAX-ACCESS read-only
    STATUS current
    DESCRIPTION
        "Name of configuration file."
    ::= { ruijieAppConfigMIBObjects 2 }

ruijieAppConfigParseErrReason OBJECT-TYPE
    SYNTAX DisplayString(SIZE (1..255))
    MAX-ACCESS read-only
    STATUS current
    DESCRIPTION
        "The reason of configuration file parse error."
    ::= { ruijieAppConfigMIBObjects 3 }

-- modify config trap
ruijieAppConfigMIBTraps
    OBJECT IDENTIFIER ::= { ruijieAppConfigMIBObjects 0 }
    
ruijieAppConfigModifyFileTrap NOTIFICATION-TYPE
    STATUS  current
    DESCRIPTION
            "The notification of discovering someone 
             modify the configuration file." 
    ::= { ruijieAppConfigMIBTraps 1 } 
    
ruijieAppConfigParseErrTrap NOTIFICATION-TYPE
    OBJECTS {
        ruijieAppConfigFileName,
        ruijieAppConfigParseErrReason
    }
    STATUS  current
    DESCRIPTION
        "The notification of discovering parser 
         configuration file error." 
    ::= { ruijieAppConfigMIBTraps 2 } 


--**********************************************************************
-- about syslog info 
--**********************************************************************
ruijieAppSyslogMIBObjects 
    OBJECT IDENTIFIER ::= { ruijieCapwapAppMIBObjects 5 }

ruijieAppSyslogSvcEnable OBJECT-TYPE
    SYNTAX TruthValue
    MAX-ACCESS read-write
    STATUS current
    DESCRIPTION
        "Whether to open syslog service or not:
         2 - no
         1 - yes.
        "
    ::= { ruijieAppSyslogMIBObjects 1 }

ruijieAppSyslogReportEventLevel OBJECT-TYPE
    SYNTAX INTEGER
    MAX-ACCESS read-write
    STATUS current
    DESCRIPTION
        "Report event level"
    ::= { ruijieAppSyslogMIBObjects 2 }


ruijieAppSyslogSvrCfgTable OBJECT-TYPE
    SYNTAX SEQUENCE OF RuijieAppSyslogSvrCfgEntry
    MAX-ACCESS not-accessible
    STATUS current
    DESCRIPTION
        "The table discribe the system log configuration of the AP."
    ::= { ruijieAppSyslogMIBObjects 3 }

ruijieAppSyslogSvrCfgEntry OBJECT-TYPE
    SYNTAX RuijieAppSyslogSvrCfgEntry
    MAX-ACCESS not-accessible
    STATUS current
    DESCRIPTION
        "The entry of apSyslogSvrCfgTable."
    INDEX { 
          ruijieAppSyslogSvrNetType,
          ruijieAppSyslogSvrNetAddr
      }
    ::= { ruijieAppSyslogSvrCfgTable 1 }

RuijieAppSyslogSvrCfgEntry ::=
    SEQUENCE {
        ruijieAppSyslogSvrNetType    InetAddressType,
        ruijieAppSyslogSvrNetAddr    InetAddress,
        ruijieAppSyslogSvrNetPort    Unsigned32,
        ruijieAppSyslogVrfName       DisplayString,
        ruijieAppSyslogStatus        RowStatus
	  } 

ruijieAppSyslogSvrNetType  OBJECT-TYPE
    SYNTAX InetAddressType
    MAX-ACCESS read-only           
    STATUS current               
    DESCRIPTION               
        "Address type of syslog server."               
    ::= { ruijieAppSyslogSvrCfgEntry 1 }   
    
ruijieAppSyslogSvrNetAddr OBJECT-TYPE
    SYNTAX InetAddress               
    MAX-ACCESS read-only             
    STATUS current               
    DESCRIPTION               
        "Address of syslog server."               
    ::= { ruijieAppSyslogSvrCfgEntry 2 } 

ruijieAppSyslogSvrNetPort OBJECT-TYPE
    SYNTAX Unsigned32               
    MAX-ACCESS read-create             
    STATUS current               
    DESCRIPTION               
        "NetPort of syslog server."               
    ::= { ruijieAppSyslogSvrCfgEntry 3 }

ruijieAppSyslogVrfName OBJECT-TYPE
    SYNTAX DisplayString               
    MAX-ACCESS read-create             
    STATUS current               
    DESCRIPTION               
        "Vrf name of syslog server."               
    ::= { ruijieAppSyslogSvrCfgEntry 4 } 

ruijieAppSyslogStatus OBJECT-TYPE               
    SYNTAX RowStatus               
    MAX-ACCESS read-create              
    STATUS current               
    DESCRIPTION               
        "RowStatus of syslog server."               
    ::= { ruijieAppSyslogSvrCfgEntry 5 } 

--
-- about syslog Taddress info 
--
ruijieSyslogServerAddrInfoTable OBJECT-TYPE
    SYNTAX SEQUENCE OF RuijieSyslogServerAddrInfoEntry
    MAX-ACCESS not-accessible
    STATUS current
    DESCRIPTION
        "The table discribe the syslog server informations."
    ::= { ruijieAppSyslogMIBObjects 4 }

ruijieSyslogServerAddrInfoEntry OBJECT-TYPE
    SYNTAX RuijieSyslogServerAddrInfoEntry
    MAX-ACCESS not-accessible
    STATUS current
    DESCRIPTION
        "The entry of ruijieSyslogServerAddrInfoTable."
    INDEX { 
        ruijieSyslogServerIndex
    }
    ::= { ruijieSyslogServerAddrInfoTable 1 }

RuijieSyslogServerAddrInfoEntry ::=
    SEQUENCE {
        ruijieSyslogServerIndex      Integer32,
        ruijieSyslogServerAddr       TAddress,
        ruijieSyslogServerVrfName    DisplayString,
        ruijieSyslogServerStatus     RowStatus
	  } 

ruijieSyslogServerIndex OBJECT-TYPE
    SYNTAX Integer32
    MAX-ACCESS read-only          
    STATUS current        
    DESCRIPTION               
        "Index of syslog server information table."               
    ::= { ruijieSyslogServerAddrInfoEntry 1 }

ruijieSyslogServerAddr OBJECT-TYPE
    SYNTAX TAddress
    MAX-ACCESS read-create          
    STATUS current        
    DESCRIPTION               
        "Taddess of syslog server."               
    ::= { ruijieSyslogServerAddrInfoEntry 2 }

ruijieSyslogServerVrfName OBJECT-TYPE
    SYNTAX DisplayString               
    MAX-ACCESS read-create             
    STATUS current               
    DESCRIPTION               
        "Vrf name of syslog server."               
    ::= { ruijieSyslogServerAddrInfoEntry 3 } 

ruijieSyslogServerStatus OBJECT-TYPE               
    SYNTAX RowStatus               
    MAX-ACCESS read-create              
    STATUS current
    DESCRIPTION               
        "RowStatus of syslog server."               
    ::= { ruijieSyslogServerAddrInfoEntry 4 } 


--**********************************************************************
-- about Trap Action info 
--**********************************************************************
ruijieAppTrapActionMIBObjects 
    OBJECT IDENTIFIER ::= { ruijieCapwapAppMIBObjects 6 }

ruijieAppTrapActionEnable OBJECT-TYPE
    SYNTAX INTEGER {
        disableSendTrap(0),  -- disable send trap
        enableSendTrap(1)    -- enable  send trap
    }
    MAX-ACCESS read-write
    STATUS current
    DESCRIPTION
        "This value decide enable or not to send trap 
         while some notification happen."
    ::= { ruijieAppTrapActionMIBObjects 1 }

ruijieAppTrapActionTable OBJECT-TYPE
    SYNTAX SEQUENCE OF RuijieAppTrapActionEntry
    MAX-ACCESS not-accessible
    STATUS current
    DESCRIPTION
        "This table of the trap's action."
    ::= { ruijieAppTrapActionMIBObjects 2 }

ruijieAppTrapActionEntry OBJECT-TYPE
    SYNTAX RuijieAppTrapActionEntry
    MAX-ACCESS not-accessible
    STATUS current
    DESCRIPTION
        "List of of the trap's action."
    INDEX { ruijieAppTrapType }
    ::= { ruijieAppTrapActionTable 1 }
    
RuijieAppTrapActionEntry ::=
    SEQUENCE {
        ruijieAppTrapType   INTEGER,
        ruijieAppTrapAction INTEGER,
        ruijieAppTrapDescr  DisplayString
    }

ruijieAppTrapType OBJECT-TYPE
    SYNTAX INTEGER { 
        gencoldstart(1),
        genwarmstart(2),
        genlinkdown(3),
        genlinkup(4),
        genauthenfail(5),
        genegpnbloss(6),
        spenewroot(7),
        spetopchange(8),
        spehardchange(9),
        speportsecuviolation(10),
        spestormviolation(11),
        spemacnotification(12),
        spevrrpnewmaster(13),
        spevrrpauthfailure(14),
        spepowerstatetrans(15),
        spefanstatetrans(16),
        speospf(17),
        speospfvifstatechange(18),
        speospfnbrstatechange(19),
        speospfvifnbrstatechange(20),
        speospfifconfigerror(21),
        speospfvifconfigerror(22),
        speospfifauthfailure(23),
        speospfvifauthfailure(24),
        speospfifrxbadpacket(25),
        speospfvifrxbadpacket(26),
        speospftxretransmit(27),
        speospfviftxretransmit(28),
        speospforiginatelsa(29),
        speospfmaxagelsa(30),
        speospflsdboverflow(31),
        speospflsdbapproachingoverflow(32),
        speospfifstatechange(33),
        spebgpestablished(34),
        spebgpbackwardtransition(35),
        speisisdatabaseoverload(36),
        speisismanualaddressdrop(37),
        speisiscorruptedlspdetected(38),
        speisisattempttoexceedmaxseq(39),
        speisisidlenmismatch(40),
        speisismaxareaaddrmismatch(41),
        speisisownlsppurge(42),
        speisisseqnumberskip(43),
        speisisauthtypefailure(44),
        speisisauthfailure(45),
        speisisversionskew(46),
        speisisareamismatch(47),
        speisisrejectedadj(48),
        speisislsptoolargetopropagate(49),
        speisisoriglspbufsizemismatch(50),
        speisisprotocolsupportedmismatch(51),
        speisisadjchange(52),
        spepim(53),
        speigmp(54),
        spedvmrp(55),
        speentitychange(56),
        specluster(57),
        spedetectipviolation(58),
        spelinestate(59),
        spesysguard(60),
        spernfpmsgtrap(61),
        sperrmclientsfailedtrap(62),
        sperrmloadfailedtrap(63),
        sperrmnoisefailedtrap(64),
        sperrminterferencefailedtrap(65),
        sperrmperformancefailedtrap(66),
        sperrmclientspasstrap(67),
        sperrmloadpasstrap(68),
        sperrmnoisepasstrap(69),
        sperrminterferencepasstrap(70),
        sperrmperformancepasstrap(71),
        sperrmchannelchangetrap(72),
        sperrmtxpowerchangetrap(73),
        sperrmleaderachangetrap(74),
        sperrmleaderbchangetrap(75),
        sperrmdfsfreecountatrap(76),
        sperrmdfsfreecountbtrap(77),
        sperrmneighborapintertrap(78),
        sperrmstationintertrap(79),
        sperrmotherdiveceintertrap(80),
        rmonalarmfallingtrap(81),
        rmonalarmrisingtrap(82),
        smpframerelaytrap(83),
        priventitytrans(84),
        privtemperaturetrans(85),
        speipv6ifstatechange(86),
        psmachashconflicttrap(87),
        privwebauthuserleave(88),
        radiusauthserverdowntrap(89),
        radiusacctserverdowntrap(90),
        configurationerrortrap(91),
        cpuusagetoohightrap(92),
        cpuusagetoohighrecovtrap(93),
        memusagetoohightrap(94),
        memusagetoohighrecovtrap(95),
        systmcoldstarttrap(96),
        ipaddrchangetrap(97),
        apmtworkmodechgtrap(98),
        apswupdatefailtrap(99),
        ssidkeyconflicttrap(100),
        fatapheartbeattrap(101),
        acconfigurationerrortrap(102),
        accpuusagetoohightrap(103),
        accpuusagetoohighrecovtrap(104),
        acmemusagetoohightrap(105),
        acmemusagetoohighrecovtrap(106),
        acofflinetrap(107),
        aconlinetrap(108),
        acapmtworkmodechgtrap(109),
        acapswupdatefailtrap(110),
        acssidkeyconflicttrap(111),
        acfatapheartbeattrap(112),
        staauthfailtrap(113),
        staassofailtrap(114),
        acstaauthfailtrap(115),
        acstaassofailtrap(116),
        invalidcertinvadetrap(117),
        repaccacktrap(118),
        tamperattacktrap(119),
        lowersafeattacktrap(120),
        addrredirectiontrap(121),
        acinvalidcertinvadetrap(122),
        acrepaccacktrap(123),
        actamperattacktrap(124),
        aclowersafeattacktrap(125),
        acaddrredirectiontrap(126),
        widsieee80211connect(127),
        widsieee80211disconnect(128),
        widsieee80211reauthentication(129),
        widsieee80211authenticationfailure(130),
        widsieee80211connectfailure(131),
        apcointerfdetectedtrap(132),
        apcointerfcleartrap(133),
        apnerborinterfdetectedtrap(134),
        apneiborinterfcleartrap(135),
        stainterfdetectedtrap(136),
        stainterfcleartrap(137),
        otherdeviceinterfdetectedtrap(138),
        otherdevinterfcleartrap(139),
        radiodowntrap(140),
        radiodownrecovtrap(141),
        apstafulltrap(142),
        apstafullrecovertrap(143),
        apmtrdochanlchgtrap(144),
        acapcointerfdetectedtrap(145),
        acapcointerfcleartrap(146),
        acapnerborinterfdetectedtrap(147),
        acapneiborinterfcleartrap(148),
        acstainterfdetectedtrap(149),
        acstainterfcleartrap(150),
        acotherdeviceinterfdetectedtrap(151),
        acotherdevinterfcleartrap(152),
        acradiodowntrap(153),
        acradiodownrecovtrap(154),
        acapstafulltrap(155),
        acapstafullrecovertrap(156),
        acapmtrdochanlchgtrap(157),
        acspeciousdevicedetecttrap(158),
        acrxpackage(159),
        accpuusage(160),
        capwapbasechanup(161),
        capwapbasechandown(162),
        capwapbasedecrypterrorreport(163),
        capwapbasejoinfail(164),
        capwapbaseimageupgradefail(165),
        capwapbaseconifgmsgerror(166),
        capwapbaseradiooperstatu(167),
        capwapbaseauthenfail(168),
        apmgmtaptimestamp(169),
        apmgmtstaoper(170),
        apmgmtmbchange(171),
        apmgmtapswupdtfail(172),
        widswarninginfo(173),
        privcmccportalunavailable(174),
        privipaddrchange(175),
        dhcppoolexhaust(176),
        dhcppoolnoexhaust(177),
        speheartbeatperiodtrap(178),
        tftpupgradefailed(179),
        syscpuhigh(180),
        syscpuhighrecov(181),
        systemperaturehigh(182),
        systemperaturehighrecov(183),
        sysmemoryhigh(184),
        sysmemoryhighrecov(185),
        speconfigmodifytrap(186),
        speconfigparseerrtrap(187),
        apmgmtstaactoverthrehold(188),
        apmgmtstadisactoverthredhold(189),
        apmgmtstaroamtotaloverthredhlod(190),
        apmgmtstaroamoerminoverthredhold(191),
        apmgmtapwritebuffero(192),
        apmgmtacheartbeat(193),
        apmgmtacpowerstatus(194),
        radiusauthserverrecovertrap(195),
        radiusacctserverrecovertrap(196),
        privcmccportalavailable(197),
        sysapcpuhigh(198),
        sysapcpuhighrecov(199),
        sysapmemoryhigh(200),
        sysapmemoryhighrecov(201),
        syssystemreset(202)
    } 
    MAX-ACCESS read-only
    STATUS current
    DESCRIPTION
        "Trap type identifier, every kind of trap which the system support
         will has one entry in this table."
    ::= { ruijieAppTrapActionEntry 1 }

ruijieAppTrapAction OBJECT-TYPE
    SYNTAX INTEGER {
        off(0),     -- do nothing
        on(1)       -- send trap
    }
    MAX-ACCESS read-write
    STATUS current
    DESCRIPTION
        "This value decide how to deal with when this type trap has happened."
    ::= { ruijieAppTrapActionEntry 2 }

ruijieAppTrapDescr OBJECT-TYPE
    SYNTAX DisplayString
    MAX-ACCESS read-write
    STATUS current
    DESCRIPTION
        "The description of the trap."
    ::= { ruijieAppTrapActionEntry 3 }    

--**********************************************************************
-- about ZCM Zero-Config Management info 
--**********************************************************************
ruijieZCMMIBObjects 
    OBJECT IDENTIFIER ::= { ruijieCapwapAppMIBObjects 7 }

-- zcm mib
ruijieAssignedIPAddress OBJECT-TYPE
    SYNTAX IpAddress
    MAX-ACCESS not-accessible
    STATUS current
    DESCRIPTION
        "The device ip address information."
    ::= { ruijieZCMMIBObjects 1 }

ruijieNeedConfiguration OBJECT-TYPE
    SYNTAX INTEGER {
             no(0),  -- system does not need configuration
             yes(1)  -- system need configuration
           }
    MAX-ACCESS not-accessible
    STATUS current
    DESCRIPTION
        "The device does need configuration."
    ::= { ruijieZCMMIBObjects 2 }

-- zcm trap
ruijieZCMMIBTraps
    OBJECT IDENTIFIER ::= { ruijieZCMMIBObjects 0 }

ruijieZCMNotifyTrap NOTIFICATION-TYPE
    OBJECTS {
        ruijieSystemSerialno,
        ruijieDeviceMacAddress,
        ruijieAssignedIPAddress,
        ruijieNeedConfiguration,
        sysObjectID
    }
    STATUS  current
    DESCRIPTION
            "The notification sent when the device startup." 
    ::= { ruijieZCMMIBTraps 1 } 

--**********************************************************************
-- about conformance info 
--**********************************************************************
ruijieCapwapAppMIBConformance OBJECT IDENTIFIER ::= { ruijieCapwapAppMIB 2 }
ruijieCapwapAppMIBCompliances OBJECT IDENTIFIER ::= { ruijieCapwapAppMIBConformance 1 }
ruijieCapwapAppMIBGroups      OBJECT IDENTIFIER ::= { ruijieCapwapAppMIBConformance 2 }

-- compliance statements
ruijieCapwapAppMIBCompliance MODULE-COMPLIANCE
    STATUS  current
    DESCRIPTION
        "The compliance statement for entities which implement
         the Ruijie Capwap App MIB"
    MODULE  
    MANDATORY-GROUPS { 
        ruijieCapwapAppMIBGroup
    }
    ::= { ruijieCapwapAppMIBCompliances 1 }
                
-- units of conformance

ruijieCapwapAppMIBGroup OBJECT-GROUP
        OBJECTS {
           ruijieAppHeartbeatOnOff,
           ruijieAppHeartbeatPeriod,
           ruijieAppHeartbeatIpAddr,
           ruijieAppHeartbeatTimeStamp,	
           ruijieAppAdminName,
           ruijieAppAdminPwd,
           ruijieAppAdminPriLevel,
           ruijieAppAdminStatus,
           ruijieAppPollTimeOfLast,
           ruijieAppRcvToDefConfig,
           ruijieAppConfigFileName,
           ruijieAppConfigParseErrReason,
           ruijieAppSyslogSvcEnable,
           ruijieAppSyslogReportEventLevel,
           ruijieAppSyslogSvrNetType,
           ruijieAppSyslogSvrNetAddr,
           ruijieAppSyslogSvrNetPort,
           ruijieAppSyslogVrfName,
           ruijieAppSyslogStatus,
           ruijieSyslogServerAddr,
           ruijieSyslogServerVrfName,
           ruijieSyslogServerStatus
        }
        STATUS  current
        DESCRIPTION
                "A collection of objects providing Capwap App configure."
        ::= { ruijieCapwapAppMIBGroups 1 }
        
END
