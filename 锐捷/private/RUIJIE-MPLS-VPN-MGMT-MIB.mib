-- *****************************************************************
-- RUIJIE-MPLS-VPN-MGMT-MIB.mib:  Ruijie MPLS VPN MGMT MIB file
--
-- Jan 2013, Daizhibin
-- Mar 2021, wangmeng add ruijieMplsVPNMgmtL2vpn、ruijieMplsVPNMgmtL2vpnAc
--           ruijieMplsVPNMgmtVrfTable.ruijieMplsVPNMgmtVrfVpnRunState
--
-- Copyright (c) 2013 by Ruijie Networks Co.,Ltd.
-- All rights reserved.
-- 
-- *****************************************************************
--

RUIJIE-MPLS-VPN-MGMT-MIB DEFINITIONS ::= BEGIN
IMPORTS
        MODULE-IDENTITY,
        OBJECT-TYPE,
        IpAddress,
        Unsigned32,
        Gauge32,
        Counter32
                FROM SNMPv2-SMI
        DisplayString,
        RowStatus
                FROM SNMPv2-TC
        TimeStamp, StorageType
                FROM SNMPv2-TC          -- [RFC2579]
        InetAddressPrefixLength,
        InetAddressType,
        InetAddress,
        InetPortNumber
             FROM INET-ADDRESS-MIB      --  [RFC3291]                
        MODULE-COMPLIANCE,
        OBJECT-GROUP
            FROM SNMPv2-CONF       
        Dscp
          FROM DIFFSERV-DSCP-TC      -- [RFC3289]
        VPNIdOrZero
        FROM VPN-TC-STD-MIB                                  -- [RFC4265]
        mplsL3VpnVrfName
            FROM MPLS-L3VPN-STD-MIB
        ruijieMgmt
                FROM RUIJIE-SMI;

ruijieMplsVPNMgmtMIB MODULE-IDENTITY
        LAST-UPDATED "201301280000Z"
        ORGANIZATION "Ruijie Networks Co.,Ltd."
        CONTACT-INFO
                " 
                Tel: 4008-111-000 

                E-mail: service@ruijie.com.cn"
        DESCRIPTION
                "This module defines ruijie mpls VPN management mibs."
        REVISION      "201301280000Z"
        DESCRIPTION
                "Initial version of this MIB module."
        ::= { ruijieMgmt 122 }

ruijieMplsVPNMgmtMIBObjects     OBJECT IDENTIFIER ::= { ruijieMplsVPNMgmtMIB 1 }
ruijieMplsVPNMgmtMIBConformance OBJECT IDENTIFIER ::= { ruijieMplsVPNMgmtMIB 2 }
--****************************************************************

ruijieMplsVPNMgmtVrf            OBJECT IDENTIFIER ::= { ruijieMplsVPNMgmtMIBObjects 1 }
ruijieMplsVPNMgmtRoute          OBJECT IDENTIFIER ::= { ruijieMplsVPNMgmtMIBObjects 2 }
ruijieMplsVPNMgmtQos            OBJECT IDENTIFIER ::= { ruijieMplsVPNMgmtMIBObjects 3 }
ruijieMplsVPNMgmtL2vpn          OBJECT IDENTIFIER ::= { ruijieMplsVPNMgmtMIBObjects 4 }
ruijieMplsVPNMgmtL2vpnAc        OBJECT IDENTIFIER ::= { ruijieMplsVPNMgmtMIBObjects 5 }

--****************************************************************
-- MPLS VPN Management Vrf Configure Objects
--****************************************************************


ruijieMplsVPNMgmtVrfTable OBJECT-TYPE
    SYNTAX SEQUENCE OF RuijieMplsVPNMgmtVrfEntry
    MAX-ACCESS not-accessible
    STATUS current
    DESCRIPTION
        "This table specified ruijie mpls l3vpn vrf information."
    ::={ ruijieMplsVPNMgmtVrf 1 }

ruijieMplsVPNMgmtVrfEntry OBJECT-TYPE
    SYNTAX  RuijieMplsVPNMgmtVrfEntry
    MAX-ACCESS not-accessible
    STATUS current
    DESCRIPTION
        "Each entry in this table is meant to correspond to an entry in the Vrf table."
    INDEX { mplsL3VpnVrfName }
    ::= { ruijieMplsVPNMgmtVrfTable 1 }

RuijieMplsVPNMgmtVrfEntry ::=
    SEQUENCE {
        ruijieMplsVPNMgmtVrfName            DisplayString,
        ruijieMplsVPNMgmtVrfIntfFault       Unsigned32,
        ruijieMplsVPNMgmtVrfVpnId           VPNIdOrZero,
        ruijieMplsVPNMgmtVrfVpnIdType       INTEGER,
		ruijieMplsVPNMgmtVrfVpnRunState     INTEGER
    }

ruijieMplsVPNMgmtVrfName OBJECT-TYPE
    SYNTAX DisplayString
    MAX-ACCESS read-only
    STATUS current
    DESCRIPTION
        "The human-readable name of this VPN."
    ::= { ruijieMplsVPNMgmtVrfEntry 1 }

ruijieMplsVPNMgmtVrfIntfFault OBJECT-TYPE
    SYNTAX Unsigned32
    MAX-ACCESS read-only
    STATUS current
    DESCRIPTION
        "Indicates the number of fault in the interface binding this vrf."
    ::= { ruijieMplsVPNMgmtVrfEntry 2 }

ruijieMplsVPNMgmtVrfVpnId OBJECT-TYPE
    SYNTAX VPNIdOrZero
    MAX-ACCESS read-only
    STATUS current
    DESCRIPTION
        "The VPN ID as specified in [RFC2685].  If a VPN ID
        has not been specified for this VRF, then this
        variable SHOULD be set to a zero-length OCTET
        STRING."
    ::= { ruijieMplsVPNMgmtVrfEntry 3 }

ruijieMplsVPNMgmtVrfVpnIdType OBJECT-TYPE
    SYNTAX INTEGER {
        l3vpn(1),
        l2vpn(2),
        other(3)
    }
    MAX-ACCESS read-only
    STATUS current
    DESCRIPTION
        "The VPN ID Type"
    ::= { ruijieMplsVPNMgmtVrfEntry 4 }

ruijieMplsVPNMgmtVrfVpnRunState OBJECT-TYPE
    SYNTAX INTEGER {
        ACTIVE(1),
        INACTIVE(2)
    }
    MAX-ACCESS read-only
    STATUS current
    DESCRIPTION
        "The VPN Running State"
    ::= { ruijieMplsVPNMgmtVrfEntry 5 }

--****************************************************************
-- MPLS VPN Management Vrf route Objects
--****************************************************************

ruijieMplsVPNMgmtVrfRteTable OBJECT-TYPE
    SYNTAX SEQUENCE OF RuijieMplsVPNMgmtVrfRteEntry
    MAX-ACCESS not-accessible
    STATUS current
    DESCRIPTION
        "This table specified MPLS L3VPN VRF table routing information."
    REFERENCE 
        "[RFC4382]"
    ::= { ruijieMplsVPNMgmtRoute 1 }


ruijieMplsVPNMgmtVrfRteEntry OBJECT-TYPE
    SYNTAX RuijieMplsVPNMgmtVrfRteEntry
    MAX-ACCESS not-accessible
    STATUS current
    DESCRIPTION
        "Each entry in this table contained the routing infomation in one's vrf."
    INDEX { mplsL3VpnVrfName, ruijieMplsVPNMgmtRteDestType, ruijieMplsVPNMgmtRteDest, ruijieMplsVPNMgmtRtePfxLen, ruijieMplsVPNMgmtRtePolicy,
        ruijieMplsVPNMgmtRteNHopType, ruijieMplsVPNMgmtRteNextHop }
    ::= { ruijieMplsVPNMgmtVrfRteTable 1 }

RuijieMplsVPNMgmtVrfRteEntry ::= 
    SEQUENCE {
        ruijieMplsVPNMgmtRteDestType     InetAddressType,
        ruijieMplsVPNMgmtRteDest         InetAddress,
        ruijieMplsVPNMgmtRtePfxLen       InetAddressPrefixLength,
        ruijieMplsVPNMgmtRtePolicy       OBJECT IDENTIFIER,
        ruijieMplsVPNMgmtRteNHopType     InetAddressType,
        ruijieMplsVPNMgmtRteNextHop      InetAddress,
        ruijieMplsVPNMgmtRteDscp         Dscp,
        ruijieMplsVPNMgmtRteStorageType  StorageType
    }

ruijieMplsVPNMgmtRteDestType OBJECT-TYPE
    SYNTAX     InetAddressType
    MAX-ACCESS read-only
    STATUS current
    DESCRIPTION
        "The type of the ruijieMplsVPNMgmtRteDest address, as
        defined in the InetAddress MIB.
        Only those address types that may appear in an actual
        routing table are allowed as values of this object."
    REFERENCE
        "[RFC4001]"
    ::= { ruijieMplsVPNMgmtVrfRteEntry 1 }

ruijieMplsVPNMgmtRteDest  OBJECT-TYPE
    SYNTAX     InetAddress
    MAX-ACCESS read-only
    STATUS     current
    DESCRIPTION
        "The destination IP address of this route.
        The type of this address is determined by the value of
        the ruijieMplsVPNMgmtRteDestType object."
    ::= { ruijieMplsVPNMgmtVrfRteEntry 2 }

ruijieMplsVPNMgmtRtePfxLen OBJECT-TYPE
    SYNTAX     InetAddressPrefixLength (0..128)
    MAX-ACCESS read-only
    STATUS     current
    DESCRIPTION
        "Indicates the number of leading one bits that form the
        mask to be logical-ANDed with the destination address
        before being compared to the value in the
        ruijieMplsVPNMgmtRteDest field."
    ::= { ruijieMplsVPNMgmtVrfRteEntry 3 }


ruijieMplsVPNMgmtRtePolicy OBJECT-TYPE
    SYNTAX     OBJECT IDENTIFIER
    MAX-ACCESS read-only
    STATUS     current
    DESCRIPTION
        "This object is an opaque object without any defined
        semantics.  Its purpose is to serve as an additional
        index that may delineate between multiple entries to
        the same destination.  The value { 0 0 } shall be used
        as the default value for this object."
    ::= { ruijieMplsVPNMgmtVrfRteEntry 4 }


ruijieMplsVPNMgmtRteNHopType OBJECT-TYPE
    SYNTAX     InetAddressType
    MAX-ACCESS read-only
    STATUS     current
    DESCRIPTION
        "The type of the ruijieMplsVPNMgmtRteNextHop address,
        as defined in the InetAddress MIB.
        Value should be set to unknown(0) for non-remote
        routes.
        Only those address types that may appear in an actual
        routing table are allowed as values of this object."
    REFERENCE "RFC4001"
    ::= { ruijieMplsVPNMgmtVrfRteEntry 5 }

ruijieMplsVPNMgmtRteNextHop OBJECT-TYPE
    SYNTAX     InetAddress
    MAX-ACCESS read-only
    STATUS     current
    DESCRIPTION
        "On remote routes, the address of the next system en
        route.  For non-remote routes, a zero-length string.
        The type of this address is determined by the value of
        the ruijieMplsVPNMgmtRteNHopType object."
    ::= { ruijieMplsVPNMgmtVrfRteEntry 6 }

ruijieMplsVPNMgmtRteDscp OBJECT-TYPE
    SYNTAX  Dscp
    MAX-ACCESS read-only
    STATUS current
    DESCRIPTION
        "The Differentiated Services Code-Point of this vrf route."
    ::= { ruijieMplsVPNMgmtVrfRteEntry 7 }

ruijieMplsVPNMgmtRteStorageType OBJECT-TYPE
    SYNTAX StorageType
    MAX-ACCESS read-only
    STATUS current
    DESCRIPTION
        "The storage type of this vrf route entry."
    ::= { ruijieMplsVPNMgmtVrfRteEntry 8 }


ruijieMplsVPNMgmtQosLSP     OBJECT IDENTIFIER ::= { ruijieMplsVPNMgmtQos 1 }
ruijieMplsVPNMgmtQosFault   OBJECT IDENTIFIER ::= { ruijieMplsVPNMgmtQos 2 }
    

ruijieMplsVPNMgmtLSPNum  OBJECT-TYPE
    SYNTAX Unsigned32
    MAX-ACCESS read-only
    STATUS current
    DESCRIPTION
        "Total number of the working LSPs."
    ::= { ruijieMplsVPNMgmtQosLSP 1 }

ruijieMplsVPNMgmtBackupLSPNum OBJECT-TYPE
    SYNTAX Unsigned32
    MAX-ACCESS read-only
    STATUS current
    DESCRIPTION
        "Total number of the backup LSPs."
    ::= { ruijieMplsVPNMgmtQosLSP 2 }

ruijieMplsVPNMgmtLDPLSPNum OBJECT-TYPE
    SYNTAX Unsigned32
    MAX-ACCESS read-only
    STATUS current
    DESCRIPTION
        "Total number of the LDP LSPs."
    ::= { ruijieMplsVPNMgmtQosLSP 3 }

ruijieMplsVPNMgmtBGPLSPNum OBJECT-TYPE
    SYNTAX Unsigned32
    MAX-ACCESS read-only
    STATUS current
    DESCRIPTION
        "Total number of the BGP LSPs."
    ::= { ruijieMplsVPNMgmtQosLSP 4 }

ruijieMplsVPNMgmtStaticLSPNum OBJECT-TYPE
    SYNTAX Unsigned32
    MAX-ACCESS read-only
    STATUS current
    DESCRIPTION
        "Total number of the static LSPs."
    ::= { ruijieMplsVPNMgmtQosLSP 5 }

ruijieMplsVPNMgmtCRLDPLSPNum OBJECT-TYPE
    SYNTAX Unsigned32
    MAX-ACCESS read-only
    STATUS current
    DESCRIPTION
        "Total number of the CR-LDP LSPs."
    ::= { ruijieMplsVPNMgmtQosLSP 6 }

ruijieMplsVPNMgmtRsvpLSPNum OBJECT-TYPE
    SYNTAX Unsigned32
    MAX-ACCESS read-only
    STATUS current
    DESCRIPTION
        "Total number of the RSVP LSPs."
    ::= { ruijieMplsVPNMgmtQosLSP 7 }

ruijieMplsVPNMgmtBFDLSPNum OBJECT-TYPE
    SYNTAX Unsigned32
    MAX-ACCESS read-only
    STATUS current
    DESCRIPTION
        "Total number of the LSP which detecting by BFD."
    ::= { ruijieMplsVPNMgmtQosLSP  8 }

ruijieMplsVPNMgmtOAMLSPNum OBJECT-TYPE
    SYNTAX Unsigned32
    MAX-ACCESS read-only
    STATUS current
    DESCRIPTION
        "Total number of the LSP which detecting by OAM."
    ::= { ruijieMplsVPNMgmtQosLSP 9 }

ruijieMplsVPNMgmtIngressLSPNum OBJECT-TYPE
    SYNTAX Unsigned32
    MAX-ACCESS read-only
    STATUS current
    DESCRIPTION 
        "Total number of the Ingress LSPs."
    ::= { ruijieMplsVPNMgmtQosLSP 10 }

ruijieMplsVPNMgmtTransitLSPNum OBJECT-TYPE
    SYNTAX Unsigned32
    MAX-ACCESS read-only
    STATUS current
    DESCRIPTION
        "Total number of the transit LSPs."
    ::= { ruijieMplsVPNMgmtQosLSP 11 }
     
ruijieMplsVPNMgmtEgressLSPNum OBJECT-TYPE
    SYNTAX Unsigned32
    MAX-ACCESS read-only
    STATUS current
    DESCRIPTION
        "Total number of the Egress LSPs."
    ::= { ruijieMplsVPNMgmtQosLSP 12 }

ruijieMplsLSPFaultBFD OBJECT-TYPE
    SYNTAX Unsigned32
    MAX-ACCESS read-only
    STATUS current
    DESCRIPTION
        "The count of the fault which is detected by BFD."
    ::= { ruijieMplsVPNMgmtQosFault 1 }

ruijieMplsLSPFaultOAM OBJECT-TYPE
    SYNTAX Unsigned32
    MAX-ACCESS read-only
    STATUS current
    DESCRIPTION
        "The count of the fault which is detected by OAM."
    ::= { ruijieMplsVPNMgmtQosFault 2 }

ruijieMplsVrfFault OBJECT-TYPE
    SYNTAX Unsigned32
    MAX-ACCESS read-only
    STATUS current
    DESCRIPTION
        "The count of the L3VPN VRF fault."
    ::= { ruijieMplsVPNMgmtQosFault 3 }


ruijieMplsPWFault OBJECT-TYPE
    SYNTAX Unsigned32
    MAX-ACCESS read-only
    STATUS current
    DESCRIPTION
        "The count of the L2VPN PW fault."
    ::= { ruijieMplsVPNMgmtQosFault 4 }


--****************************************************************
-- MPLS VPN Management L2VPN Configure Objects
--****************************************************************

ruijieMplsVPNMgmtL2vpnTable OBJECT-TYPE
    SYNTAX SEQUENCE OF RuijieMplsVPNMgmtL2vpnEntry
    MAX-ACCESS not-accessible
    STATUS current
    DESCRIPTION
        "This table specified ruijie mpls l2vpn information."
    ::={ ruijieMplsVPNMgmtL2vpn 1 }

ruijieMplsVPNMgmtL2vpnEntry OBJECT-TYPE
    SYNTAX  RuijieMplsVPNMgmtL2vpnEntry
    MAX-ACCESS not-accessible
    STATUS current
    DESCRIPTION
        "Each entry in this table is meant to correspond to an entry in the l2vpn table."
    INDEX { ruijieMplsVPNMgmtL2vpnRmUID }
    ::= { ruijieMplsVPNMgmtL2vpnTable 1 }

RuijieMplsVPNMgmtL2vpnEntry ::=
    SEQUENCE {
	    ruijieMplsVPNMgmtL2vpnRmUID         Unsigned32,
        ruijieMplsVPNMgmtL2vpnNativeName    DisplayString,
        ruijieMplsVPNMgmtL2vpnServiceType   INTEGER,
		ruijieMplsVPNMgmtL2vpnOwner         DisplayString,
        ruijieMplsVPNMgmtL2vpnRunState      INTEGER,
        ruijieMplsVPNMgmtL2vpnCIR           Unsigned32,
        ruijieMplsVPNMgmtL2vpnPIR           Unsigned32		
    }

ruijieMplsVPNMgmtL2vpnRmUID OBJECT-TYPE
    SYNTAX OCTET STRING (SIZE (0..64))
    MAX-ACCESS read-only
    STATUS current
    DESCRIPTION
        "Indicates the rmUID of this l2vpn."
    ::= { ruijieMplsVPNMgmtL2vpnEntry 1 }

ruijieMplsVPNMgmtL2vpnNativeName OBJECT-TYPE
    SYNTAX OCTET STRING (SIZE (0..255))
    MAX-ACCESS read-only
    STATUS current
    DESCRIPTION
        "The human-readable name of this l2vpn."
    ::= { ruijieMplsVPNMgmtL2vpnEntry 2 }

ruijieMplsVPNMgmtL2vpnServiceType OBJECT-TYPE
    SYNTAX INTEGER {
        PWE3(1),
        VPLS(2)
    }
    MAX-ACCESS read-only
    STATUS current
    DESCRIPTION
        "The ServiceType of this l2vpn."
    ::= { ruijieMplsVPNMgmtL2vpnEntry 3 }

ruijieMplsVPNMgmtL2vpnOwner OBJECT-TYPE
    SYNTAX OCTET STRING (SIZE (0..64))
    MAX-ACCESS read-only
    STATUS current
    DESCRIPTION
        "The owner name of this l2vpn."
    ::= { ruijieMplsVPNMgmtL2vpnEntry 4 }

ruijieMplsVPNMgmtL2vpnRunState OBJECT-TYPE
    SYNTAX INTEGER {
        UP(1),
        DOWN(2)
    }
    MAX-ACCESS read-only
    STATUS current
    DESCRIPTION
        "The Run State of this l2vpn."
    ::= { ruijieMplsVPNMgmtL2vpnEntry 5 }

ruijieMplsVPNMgmtL2vpnCIR OBJECT-TYPE
    SYNTAX OCTET STRING (SIZE (0..20))
    MAX-ACCESS read-only
    STATUS current
    DESCRIPTION
        "Indicates the CIR of this l2vpn, unit: kbit/s."
    ::= { ruijieMplsVPNMgmtL2vpnEntry 6 }

ruijieMplsVPNMgmtL2vpnPIR OBJECT-TYPE
    SYNTAX OCTET STRING (SIZE (0..20))
    MAX-ACCESS read-only
    STATUS current
    DESCRIPTION
        "Indicates the PIR of this l2vpn, unit: kbit/s."
    ::= { ruijieMplsVPNMgmtL2vpnEntry 7 }


--****************************************************************
-- MPLS VPN Management L2VPN AC Configure Objects
--****************************************************************

ruijieMplsVPNMgmtL2vpnAcTable OBJECT-TYPE
    SYNTAX SEQUENCE OF RuijieMplsVPNMgmtL2vpnAcEntry
    MAX-ACCESS not-accessible
    STATUS current
    DESCRIPTION
        "This table specified ruijie mpls l2vpn attach circuit information."
    ::={ ruijieMplsVPNMgmtL2vpnAc 1 }

ruijieMplsVPNMgmtL2vpnAcEntry OBJECT-TYPE
    SYNTAX  RuijieMplsVPNMgmtL2vpnAcEntry
    MAX-ACCESS not-accessible
    STATUS current
    DESCRIPTION
        "Each entry in this table is meant to correspond to an entry in the l2vpn attach circuit table."
    INDEX { ruijieMplsVPNMgmtL2vpnAcRmUID, ruijieMplsVPNMgmtL2vpnAcNermUID, ruijieMplsVPNMgmtL2vpnAcPortrmUID }
    ::= { ruijieMplsVPNMgmtL2vpnAcTable 1 }

RuijieMplsVPNMgmtL2vpnAcEntry ::=
    SEQUENCE {
	    ruijieMplsVPNMgmtL2vpnAcRmUID         Unsigned32,
		ruijieMplsVPNMgmtL2vpnAcNermUID       Unsigned32,
		ruijieMplsVPNMgmtL2vpnAcPortrmUID     Unsigned32,
		ruijieMplsVPNMgmtL2vpnAcCvid          Unsigned32,
		ruijieMplsVPNMgmtL2vpnAcSvid          Unsigned32,
        ruijieMplsVPNMgmtL2vpnAcIngCIR        Unsigned32,
        ruijieMplsVPNMgmtL2vpnAcIngPIR        Unsigned32,
        ruijieMplsVPNMgmtL2vpnAcEgCIR         Unsigned32,
        ruijieMplsVPNMgmtL2vpnAcEgPIR         Unsigned32		
    }

ruijieMplsVPNMgmtL2vpnAcRmUID OBJECT-TYPE
    SYNTAX OCTET STRING (SIZE (0..64))
    MAX-ACCESS read-only
    STATUS current
    DESCRIPTION
        "Indicates the rmUID of this l2vpn."
    ::= { ruijieMplsVPNMgmtL2vpnAcEntry 1 }

ruijieMplsVPNMgmtL2vpnAcNermUID OBJECT-TYPE
    SYNTAX OCTET STRING (SIZE (0..64))
    MAX-ACCESS read-only
    STATUS current
    DESCRIPTION
        "Indicates the attach circuit rmUID of this l2vpn."
    ::= { ruijieMplsVPNMgmtL2vpnAcEntry 2 }
	
ruijieMplsVPNMgmtL2vpnAcPortrmUID OBJECT-TYPE
    SYNTAX OCTET STRING (SIZE (0..64))
    MAX-ACCESS read-only
    STATUS current
    DESCRIPTION
        "Indicates the port of attach circuit rmUID of this l2vpn."
    ::= { ruijieMplsVPNMgmtL2vpnAcEntry 3 }

ruijieMplsVPNMgmtL2vpnAcCvid OBJECT-TYPE
    SYNTAX OCTET STRING (SIZE (0..50))
    MAX-ACCESS read-only
    STATUS current
    DESCRIPTION
        "Indicates the custom vid of attach circuit of this l2vpn."
    ::= { ruijieMplsVPNMgmtL2vpnAcEntry 4 }

ruijieMplsVPNMgmtL2vpnAcSvid OBJECT-TYPE
    SYNTAX OCTET STRING (SIZE (0..50))
    MAX-ACCESS read-only
    STATUS current
    DESCRIPTION
        "Indicates the service vid of attach circuit of this l2vpn."
    ::= { ruijieMplsVPNMgmtL2vpnAcEntry 5 }

ruijieMplsVPNMgmtL2vpnAcIngCIR OBJECT-TYPE
    SYNTAX OCTET STRING (SIZE (0..20))
    MAX-ACCESS read-only
    STATUS current
    DESCRIPTION
        "Indicates the ingress CIR of attach circuit of this l2vpn, unit: kbit/s."
    ::= { ruijieMplsVPNMgmtL2vpnAcEntry 6 }

ruijieMplsVPNMgmtL2vpnAcIngPIR OBJECT-TYPE
    SYNTAX OCTET STRING (SIZE (0..20))
    MAX-ACCESS read-only
    STATUS current
    DESCRIPTION
        "Indicates the ingress PIR of attach circuit of this l2vpn, unit: kbit/s."
    ::= { ruijieMplsVPNMgmtL2vpnAcEntry 7 }

ruijieMplsVPNMgmtL2vpnAcEgCIR OBJECT-TYPE
    SYNTAX OCTET STRING (SIZE (0..20))
    MAX-ACCESS read-only
    STATUS current
    DESCRIPTION
        "Indicates the egress CIR of attach circuit of this l2vpn, unit: kbit/s."
    ::= { ruijieMplsVPNMgmtL2vpnAcEntry 8 }

ruijieMplsVPNMgmtL2vpnAcEgPIR OBJECT-TYPE
    SYNTAX OCTET STRING (SIZE (0..20))
    MAX-ACCESS read-only
    STATUS current
    DESCRIPTION
        "Indicates the egress PIR of attach circuit of this l2vpn, unit: kbit/s."
    ::= { ruijieMplsVPNMgmtL2vpnAcEntry 9 }
	
END
