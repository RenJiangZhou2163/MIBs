-- *****************************************************************
-- RUIJIE-WIRELESS-SMI.mib: Ruijie Wireless SMI File
-- 
-- July 2007, Wuzg
-- 
-- Copyright (c) 2007 by Ruijie Networks Co.,Ltd.
-- All rights reserved.
-- 
-- *****************************************************************
--

RUIJIE-WIRELESS-SMI DEFINITIONS ::= BEGIN

IMPORTS
        MODULE-IDENTITY,
        OBJECT-IDENTITY
                FROM SNMPv2-SMI
        products
                FROM RUIJIE-SMI;
                
wireless        OBJECT IDENTIFIER ::= { products 3 }

wirelessMib MODULE-IDENTITY
        LAST-UPDATED "200707040000Z"
        ORGANIZATION "Ruijie Networks Co.,Ltd."
        CONTACT-INFO
                " 
                Tel: 4008-111-000 

                E-mail: service@ruijie.com.cn"
        DESCRIPTION
                "The Structure of Management Information for the
                 Ruijie enterprise."
        REVISION      "200707040000Z"
        DESCRIPTION
                "Initial version of this MIB module."
        ::= { wireless 1 }        

ruijieWirelessProducts OBJECT-IDENTITY
        STATUS  current
        DESCRIPTION
                "ruijieWirelessProducts is the root OBJECT IDENTIFIER from
                which sysObjectID values are assigned for wireless product.
                Actual values are defined in RUIJIE-PRODUCTS-MIB."
        ::= { wirelessMib 1 }

ruijieWirelessMgmt OBJECT-IDENTITY
        STATUS  current
        DESCRIPTION
                "ruijieWirelessMgmt is the main subtree for those functional mib."
        ::= { wirelessMib 2 }
        
END
