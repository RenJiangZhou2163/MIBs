-- ====================================================================
-- Copyright (c) 2011 by Ruijie Networks Co.,Ltd. All rights reserved.
--
-- Description: The MIB is designed to get 3G wireless safenet solution statistic information.
-- Reference: rujie Enterprise MIB
-- =====================================================================

RUIJIE-AG-MIB DEFINITIONS ::= BEGIN

    IMPORTS
        DisplayString,TEXTUAL-CONVENTION,TimeStamp
            FROM SNMPv2-TC
        IpAddress, Integer32, Counter32, Counter64, OBJECT-TYPE,
        MODULE-IDENTITY, Gauge32, NOTIFICATION-TYPE, Unsigned32
            FROM SNMPv2-SMI
        MODULE-COMPLIANCE, OBJECT-GROUP, NOTIFICATION-GROUP
            FROM SNMPv2-CONF
        ruijieMgmt
            FROM RUIJIE-SMI;
            
    ruijieAG MODULE-IDENTITY
        LAST-UPDATED "201102220000Z"            
        ORGANIZATION
            "Ruijie Networks Co.,Ltd."
        CONTACT-INFO
            "Tel: 4008-111-000 
             E-mail: service@ruijie.com.cn"  
        DESCRIPTION
            "The MIB is designed to get statistic information of
             3G wireless safenet. With this MIB, we can get information of a certain
             3G user or all users."
        REVISION      "201102220000Z"
        DESCRIPTION
                "Initial version of this MIB module."
        ::= { ruijieMgmt 95 }


-- ========================================================================
-- Node definitions
-- ========================================================================
--Begin the node of ruijieAGObjects.

    ruijieAGObjects OBJECT IDENTIFIER ::= { ruijieAG 1 }

-- ===============================================
-- Begin the table of ruijieApConfigTable_table.
-- ===============================================
    
    ruijieApConfigNumber OBJECT-TYPE
        SYNTAX ApConfigNumber
        ACCESS read-only
        STATUS current
        DESCRIPTION
            "The AP Number currently configured."
        ::= { ruijieApConfigTableEntry 1 }
        
    ruijieApConfigIndex OBJECT-TYPE
        SYNTAX ruijieApConfigIndex
        ACCESS read-only
        STATUS current
        DESCRIPTION
            "The AP Index currently configured."
        ::= { ruijieApConfigTableEntry 2 }
    
    ruijieApConfigMaxPtNumber OBJECT-TYPE
        SYNTAX ruijieApConfigMaxPtNumber
        ACCESS read-only
        STATUS current
        DESCRIPTION
            "The Max AP Number that could be configured."
        ::= { ruijieApConfigTableEntry 3 }
        
    ruijieApConfigCurrentPtNumber OBJECT-TYPE
        SYNTAX ruijieApConfigCurrentPtNumber
        ACCESS read-only
        STATUS current
        DESCRIPTION
            "The AP Port Number under configuration."
        ::= { ruijieApConfigTableEntry 4 }
    
    ruijieApConfigPortMember OBJECT-TYPE
        SYNTAX ruijieApConfigPortMember
        ACCESS read-only
        STATUS current
        DESCRIPTION
            "The AP Member Port under configuration."
        ::= { ruijieApConfigTableEntry 5}
        
    ruijieApConfigAction OBJECT-TYPE
        SYNTAX ruijieApConfigAction
        ACCESS read-write
        STATUS current
        DESCRIPTION
            "The AP Configuration Action."
        ::= { ruijieApConfigTableEntry 6 }
        
    ruijieApConfigBalance OBJECT-TYPE
        SYNTAX ruijieApConfigBalance
        ACCESS read-only
        STATUS current
        DESCRIPTION
            "The AP Balance Type."
        ::= { ruijieApConfigTableEntry 7 }
        
    ruijieApConfigStatus OBJECT-TYPE
        SYNTAX ruijieApConfigStatus
        ACCESS read-only
        STATUS current
        DESCRIPTION
            "The AP Configuration Status."
        ::= { ruijieApConfigTableEntry 8 }
        
    ruijieApConfigTableEntry ::=
        SEQUENCE {
            ruijieApConfigNumber
                Integer,
            ruijieApConfigIndex
                Integer,
            ruijieApConfigMaxPtNumber
                Integer,
            ruijieApConfigCurrentPtNumber
                DisplayString,
            ruijieApConfigPortMember
                DisplayString,
            ruijieApConfigAction
								Integer,
					  ruijieApConfigBalance
					      Integer,
					  ruijieApConfigStatus
					      Integer
        }
        
-- ===============================================
-- Begin the table of ruijieApPortMemberTable_table.
-- ===============================================

    ruijieApPortMemberPortIndex OBJECT-TYPE
        SYNTAX ruijieApPortMemberPortIndex
        ACCESS read-only
        STATUS current
        DESCRIPTION
            "The AP Member Port Index."
        ::= { ruijieApPortMemberTableEntry 1 }
        
    ruijieApPortMemberApNumber OBJECT-TYPE
        SYNTAX ruijieApPortMemberApNumber
        ACCESS read-only
        STATUS current
        DESCRIPTION
            "The member port number that AP aggregates."
        ::= { ruijieApPortMemberTableEntry 2 }
    
    ruijieApPortMemberAction OBJECT-TYPE
        SYNTAX ruijieApPortMemberAction
        ACCESS read-only
        STATUS current
        DESCRIPTION
            "The AP Member Port Action."
        ::= { ruijieApPortMemberTableEntry 3 }
        
    ruijieApPortMemberTableEntry ::=
        SEQUENCE {
            ruijieApPortMemberPortIndex
                Integer,
            ruijieApPortMemberApNumber
                Integer,
            ruijieApPortMemberAction
                Integer,
        }
        
END
