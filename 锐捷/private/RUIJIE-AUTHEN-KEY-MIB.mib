-- *****************************************************************
-- RUIJIE-AUTHEN-KEY-MIB.mib:  Ruijie Authentication Key MIB file
--
-- March 2002, Wuzg
--
-- Copyright (c) 2002 by Ruijie Networks Co.,Ltd.
-- All rights reserved.
-- 
-- *****************************************************************
--

RUIJIE-AUTHEN-KEY-MIB DEFINITIONS ::= BEGIN

IMPORTS
        MODULE-IDENTITY,
        OBJECT-TYPE,
        Integer32,
        Unsigned32
                FROM SNMPv2-SMI
        DisplayString,
        RowStatus,
        DateAndTime,
        TEXTUAL-CONVENTION
                FROM SNMPv2-TC
        MODULE-COMPLIANCE,
        OBJECT-GROUP
                FROM SNMPv2-CONF
        ConfigStatus
                FROM RUIJIE-TC        
        ruijieMgmt
                FROM RUIJIE-SMI;

ruijieAuthenKeyMIB MODULE-IDENTITY
        LAST-UPDATED "200203200000Z"
        ORGANIZATION "Ruijie Networks Co.,Ltd."
        CONTACT-INFO
                " 
                Tel: 4008-111-000 

                E-mail: service@ruijie.com.cn"
        DESCRIPTION
                "This module defines authentication key managment mibs."
        REVISION      "200203200000Z"
        DESCRIPTION
                "Initial version of this MIB module."
        ::= { ruijieMgmt 24}



ruijieAuthenKeyMIBObjects OBJECT IDENTIFIER ::= { ruijieAuthenKeyMIB 1 }


RuijieKeyTimeMode ::= TEXTUAL-CONVENTION        
   STATUS current                          
   DESCRIPTION                             
            "Time managment mode of key." 
   SYNTAX INTEGER {                        
            infinite(1), -- Key will be valid all along when the key start to become effective
            duration(2), -- Key will be valid for designate duration when the key start to 
                         -- become effective.  
            end-time(3)  -- Key will be valid when the key start to become effective till
                         -- designate end time reach.                           
  }                        
  
--    Key management is a method of controlling authentication keys used by some protocol. Not 
-- all protocols can use key management. To manage authentication keys, define a  key chain, 
-- identify the keys that belong to the key chain, and specify how long each key is valid. Each
-- key has its own key identifier (specified with the key chain and key number),
-- which is stored locally. 
--     The combination of the key identifier and the interface associated with the message
-- uniquely identifies the authentication algorithm and Message Digest 5 (MD5) authentication
-- key in use.
--     You can configure multiple keys with life times. Only one authentication packet is sent,
-- regardless of how many valid keys exist. The software examines the key numbers in order from
-- lowest to highest, and uses the first valid key it encounters. The lifetimes allow for 
-- overlap during key changes. Note that the router must know these lifetimes.

ruijieAuthenKeyChainTable OBJECT-TYPE
        SYNTAX SEQUENCE OF RuijieAuthenKeyChainEntry
        MAX-ACCESS not-accessible
        STATUS current
        DESCRIPTION
               "A table of key chain entries."
        ::= { ruijieAuthenKeyMIBObjects 1 }
    
ruijieAuthenKeyChainEntry OBJECT-TYPE
        SYNTAX RuijieAuthenKeyChainEntry
        MAX-ACCESS not-accessible
        STATUS current
        DESCRIPTION
                "Entry contains key chain."  
        INDEX { ruijieAuthenKeyChainName }
        ::= { ruijieAuthenKeyChainTable 1 }
        
RuijieAuthenKeyChainEntry ::= 
        SEQUENCE {
                ruijieAuthenKeyChainName DisplayString,
                ruijieAuthenKeyChainEntryStatus ConfigStatus
        } 
           
ruijieAuthenKeyChainName OBJECT-TYPE
        SYNTAX DisplayString(SIZE (1..32))
        MAX-ACCESS read-only
        STATUS current
        DESCRIPTION
            "Key chain name of this entry.This value is unique for every entry
            When this string be used as an index,Value of a sub-identifier equal 
            ASCII value of corresponding character(first sub-identifier corresponds
            first character of string). The number of sub-identifiers of this string
            must be 32,If length of string is less than 32 the sub-identifier(0x0) 
            will be filled in tail."
        ::= { ruijieAuthenKeyChainEntry  1 }
                
ruijieAuthenKeyChainEntryStatus OBJECT-TYPE
        SYNTAX ConfigStatus
        MAX-ACCESS read-create
        STATUS current
        DESCRIPTION
            "Status of this entry, set its value to invalid will delete this entry.
            set its value to valid has no effect."
        ::= { ruijieAuthenKeyChainEntry 2 }


ruijieAuthenKeyTable OBJECT-TYPE
        SYNTAX SEQUENCE OF RuijieAuthenKeyEntry
        MAX-ACCESS not-accessible
        STATUS current
        DESCRIPTION
               "A table of authentication key entries."
        ::= { ruijieAuthenKeyMIBObjects 2 }
    
ruijieAuthenKeyEntry OBJECT-TYPE
        SYNTAX RuijieAuthenKeyEntry
        MAX-ACCESS not-accessible
        STATUS current
        DESCRIPTION
                "Entry contains authentication key parameters.
                                
                We must set all specifies valid values for the 
                non-defaulted configuration objects, certainly, it should
                also modify  the default values for the other configuration 
                objects if the defaults are not appropriate.
                                       
                Once the appropriate instance of all the configuration
                objects have been created or set,the row status should be set
                to active to initiate the request."  
        INDEX { ruijieKeyChainName,ruijieAuthenKeyNumber }
        ::= { ruijieAuthenKeyTable 1 }
        
RuijieAuthenKeyEntry ::= 
        SEQUENCE {
                ruijieKeyChainName DisplayString,
                ruijieAuthenKeyNumber Integer32,
                ruijieKeyString DisplayString,
                ruijieAuthenKeyReceiveRuijieTime DateAndTime,
                ruijieAuthenKeyReceiveTimeMode RuijieKeyTimeMode,
                ruijieAuthenKeyReceiveEndTime DateAndTime,
                ruijieAuthenKeyReceiveDuration Unsigned32,
                ruijieAuthenKeySendRuijieTime DateAndTime,
                ruijieAuthenKeySendTimeMode RuijieKeyTimeMode,
                ruijieAuthenKeySendEndTime DateAndTime,
                ruijieAuthenKeySendDuration Unsigned32,
                ruijieAuthenReceiveKeyState       INTEGER,
                ruijieAuthenSendKeyState       INTEGER,
                ruijieAuthenKeyEntryStauts RowStatus 
        }

ruijieKeyChainName OBJECT-TYPE
        SYNTAX DisplayString(SIZE (1..32))
        MAX-ACCESS read-only
        STATUS current
        DESCRIPTION
            "Key chain name of this key belong to which indentified in ruijieAuthenKeyChainEntry.
            When this string be used as an index,Value of a sub-identifier equal 
            ASCII value of corresponding character(first sub-identifier corresponds
            first character of string). The number of sub-identifiers of this string
            must be 32,If length of string is less than 32 the sub-identifier(0x0) 
            will be filled in tail."
        ::= { ruijieAuthenKeyEntry  1 }

ruijieAuthenKeyNumber OBJECT-TYPE
        SYNTAX Integer32(0..2147483647)
        MAX-ACCESS read-only
        STATUS current
        DESCRIPTION
               "The number identify a unique key in the key chain."
        ::= { ruijieAuthenKeyEntry 2 }

ruijieKeyString OBJECT-TYPE
        SYNTAX DisplayString(SIZE (1..80))
        MAX-ACCESS read-only
        STATUS current
        DESCRIPTION
            "Key String of the key. The string can contain from 1 to
             80 uppercase and lowercase alphanumeric characters,
             but the first character cannot be a number."
        ::= { ruijieAuthenKeyEntry  3 }
           
ruijieAuthenKeyReceiveRuijieTime OBJECT-TYPE
        SYNTAX DateAndTime
        MAX-ACCESS read-create
        STATUS current
        DESCRIPTION
            "The start time which the key can be received."
        ::= { ruijieAuthenKeyEntry 4 }
        
ruijieAuthenKeyReceiveTimeMode OBJECT-TYPE
        SYNTAX RuijieKeyTimeMode
        MAX-ACCESS read-create
        STATUS current
        DESCRIPTION
            "The time mode of key receive."
        ::= { ruijieAuthenKeyEntry 5 }

ruijieAuthenKeyReceiveEndTime OBJECT-TYPE
        SYNTAX DateAndTime
        MAX-ACCESS read-create
        STATUS current
        DESCRIPTION
            "The end time which the key can be received."
        ::= { ruijieAuthenKeyEntry 6 }

ruijieAuthenKeyReceiveDuration OBJECT-TYPE
        SYNTAX Unsigned32
        MAX-ACCESS read-create
        STATUS current
        DESCRIPTION
            "The duration time which the key is valid, in units of second."
        ::= { ruijieAuthenKeyEntry 7 }
        
ruijieAuthenKeySendRuijieTime OBJECT-TYPE
        SYNTAX DateAndTime
        MAX-ACCESS read-create
        STATUS current
        DESCRIPTION
            "The start time which the key can be send."
        ::= { ruijieAuthenKeyEntry 8 }
        
ruijieAuthenKeySendTimeMode OBJECT-TYPE
        SYNTAX RuijieKeyTimeMode
        MAX-ACCESS read-create
        STATUS current
        DESCRIPTION
            "The time mode of key send."
        ::= { ruijieAuthenKeyEntry 9 }

ruijieAuthenKeySendEndTime OBJECT-TYPE
        SYNTAX DateAndTime
        MAX-ACCESS read-create
        STATUS current
        DESCRIPTION
            "The end time which the key can be send."
        ::= { ruijieAuthenKeyEntry 10 }

ruijieAuthenKeySendDuration OBJECT-TYPE
        SYNTAX Unsigned32
        MAX-ACCESS read-create
        STATUS current
        DESCRIPTION
            "The duration time which the key is valid,in units of second."
        ::= { ruijieAuthenKeyEntry 11 }        

ruijieAuthenReceiveKeyState OBJECT-TYPE
        SYNTAX INTEGER{
                  valid(1),
                  invalid(2)
               }
        MAX-ACCESS read-only
        STATUS current
        DESCRIPTION
            "The key is valid or invalid currently for receiving."
        ::= { ruijieAuthenKeyEntry 12 }        
        
ruijieAuthenSendKeyState OBJECT-TYPE
        SYNTAX INTEGER{
                  valid(1),
                  invalid(2)
               }
        MAX-ACCESS read-only
        STATUS current
        DESCRIPTION
            "The key is valid or invalid currently for sending."
        ::= { ruijieAuthenKeyEntry 13 }        
                  
ruijieAuthenKeyEntryStauts OBJECT-TYPE
        SYNTAX RowStatus
        MAX-ACCESS read-create
        STATUS current
        DESCRIPTION
            "entry status for this list."
        ::= { ruijieAuthenKeyEntry 14 }
 
-- conformance information

ruijieAuthenKeyChainMIBConformance OBJECT IDENTIFIER ::= { ruijieAuthenKeyMIB 2 }
ruijieAuthenKeyChainMIBCompliances OBJECT IDENTIFIER ::= { ruijieAuthenKeyChainMIBConformance 1 }
ruijieAuthenKeyChainMIBGroups      OBJECT IDENTIFIER ::= { ruijieAuthenKeyChainMIBConformance 2 }


-- compliance statements

ruijieAuthenKeyChainMIBCompliance MODULE-COMPLIANCE
        STATUS  current
        DESCRIPTION
                "The compliance statement for entities which implement
                the Ruijie Acl MIB"
        MODULE  -- this module
                MANDATORY-GROUPS { ruijieAuthenKeyChainMIBGroup }
        ::= { ruijieAuthenKeyChainMIBCompliances 1 }
        
        
-- units of conformance

ruijieAuthenKeyChainMIBGroup OBJECT-GROUP
        OBJECTS {
                ruijieAuthenKeyChainName,
                ruijieAuthenKeyChainEntryStatus,        
                ruijieKeyChainName,
                ruijieAuthenKeyNumber, 
                ruijieKeyString, 
                ruijieAuthenKeyReceiveRuijieTime ,
                ruijieAuthenKeyReceiveTimeMode, 
                ruijieAuthenKeyReceiveEndTime ,
                ruijieAuthenKeyReceiveDuration, 
                ruijieAuthenKeySendRuijieTime ,
                ruijieAuthenKeySendTimeMode ,
                ruijieAuthenKeySendEndTime ,
                ruijieAuthenKeySendDuration, 
                ruijieAuthenReceiveKeyState,
                ruijieAuthenSendKeyState,
                ruijieAuthenKeyEntryStauts 
        }
        STATUS  current
        DESCRIPTION
                "A collection of objects providing acl (echo) ability to a
                Ruijie agent."
        ::= { ruijieAuthenKeyChainMIBGroups 1 }        
        
END
