-- *****************************************************************
-- RUIJIE-CUSTOM-INTERFACE-MIB.mib: Ruijie CUSTOM INTERFACE MIB file
--
-- Aug 2020, huangdi
-- 
-- Copyright (c) 2003 by Ruijie Networks Co.,Ltd.
-- All rights reserved.
-- *****************************************************************

RUIJIE-CUSTOM-INTERFACE-MIB DEFINITIONS ::= BEGIN

IMPORTS
        MODULE-IDENTITY, 
        OBJECT-TYPE, 
        Integer32, 
        Counter32,
        NOTIFICATION-TYPE
                    FROM SNMPv2-SMI
        MacAddress, 
        DisplayString
                FROM SNMPv2-TC
        MODULE-COMPLIANCE, 
        OBJECT-GROUP
                    FROM SNMPv2-CONF
        IfIndex
                FROM RUIJIE-TC
        nisac
                FROM NISAC-SMI;

device MODULE-IDENTITY
	      LAST-UPDATED "200304010000Z"
    	  ORGANIZATION "Ruijie Networks Co.,Ltd."
        CONTACT-INFO
                " 
                Tel: 4008-111-000

                E-mail: service@ruijie.com.cn"
	      DESCRIPTION
		            "The MIB module for managing the Physical Topology Discovery
	 	    Protocol."
    	  REVISION  "200304010000Z"
	      DESCRIPTION
		            ""
        ::= { nisac 1 }

network MODULE-IDENTITY
	      LAST-UPDATED "200304010000Z"
    	  ORGANIZATION "Ruijie Networks Co.,Ltd."
        CONTACT-INFO
                " 
                Tel: 4008-111-000

                E-mail: service@ruijie.com.cn"
	      DESCRIPTION
		            "The MIB module for managing the Physical Topology Discovery
	 	    Protocol."
    	  REVISION  "200304010000Z"
	      DESCRIPTION
		            ""
        ::= { nisac 2 }

devStatetraps            OBJECT IDENTIFIER ::= { device 5 }
--
-- ***********************************************************
--
-- DEV STATE TRAP VALUE
--
-- ***********************************************************
--

--
-- The Physical Topology Discovery Protocol Configuration Group
--
linkAbnormalTrapValue OBJECT-TYPE
    SYNTAX      OCTET STRING(SIZE(0..255))
    MAX-ACCESS  not-accessible
    STATUS      current
    DESCRIPTION
        "The Trap Value."
    ::= { devStatetraps 1 }
    
ifOverflowTrapValue OBJECT-TYPE
    SYNTAX      OCTET STRING(SIZE(0..255))
    MAX-ACCESS  not-accessible
    STATUS      current
    DESCRIPTION
        "The Trap Value."
    ::= { devStatetraps 2 }

innerOverflowTrapValue OBJECT-TYPE
    SYNTAX      OCTET STRING(SIZE(0..255))
    MAX-ACCESS  not-accessible
    STATUS      current
    DESCRIPTION
        "The Trap Value."
    ::= { devStatetraps 3 }

lossOverflowTrapValue OBJECT-TYPE
    SYNTAX      OCTET STRING(SIZE(0..255))
    MAX-ACCESS  not-accessible
    STATUS      current
    DESCRIPTION
        "The Trap Value."
    ::= { devStatetraps 5 }

ifPhysicalStatusChangeTrapValue OBJECT-TYPE
    SYNTAX      OCTET STRING(SIZE(0..255))
    MAX-ACCESS  not-accessible
    STATUS      current
    DESCRIPTION
        "The Trap Value."
    ::= { devStatetraps 6 }

ifAdminStatusChangeTrapValue OBJECT-TYPE
    SYNTAX      OCTET STRING(SIZE(0..255))
    MAX-ACCESS  not-accessible
    STATUS      current
    DESCRIPTION
        "The Trap Value."
    ::= { devStatetraps 7 }

unknownPacketRatioHighTrapValue OBJECT-TYPE
    SYNTAX      OCTET STRING(SIZE(0..255))
    MAX-ACCESS  not-accessible
    STATUS      current
    DESCRIPTION
        "The Trap Value."
    ::= { devStatetraps 9 }

crcErrorPacketRatioHighTrapValue OBJECT-TYPE
    SYNTAX      OCTET STRING(SIZE(0..255))
    MAX-ACCESS  not-accessible
    STATUS      current
    DESCRIPTION
        "The Trap Value."
    ::= { devStatetraps 10 }

trafficChangeTrapValue OBJECT-TYPE
    SYNTAX      OCTET STRING(SIZE(0..255))
    MAX-ACCESS  not-accessible
    STATUS      current
    DESCRIPTION
        "The Trap Value."
    ::= { devStatetraps 13 }

ifTafficRateHighTrapValue OBJECT-TYPE
    SYNTAX      OCTET STRING(SIZE(0..255))
    MAX-ACCESS  not-accessible
    STATUS      current
    DESCRIPTION
        "The Trap Value."
    ::= { devStatetraps 16 }
    
opticalPowerDeviateRangeTrapValue OBJECT-TYPE
    SYNTAX      OCTET STRING(SIZE(0..255))
    MAX-ACCESS  not-accessible
    STATUS      current
    DESCRIPTION
        "The Trap Value."
    ::= { devStatetraps 18 }

totalInputAndOutputTrafficInconsistentTrapValue OBJECT-TYPE
    SYNTAX      OCTET STRING(SIZE(0..255))
    MAX-ACCESS  not-accessible
    STATUS      current
    DESCRIPTION
        "The Trap Value."
    ::= { devStatetraps 19 }
--
-- ***********************************************************
--
-- DEV STATE TRAPS
--
-- ***********************************************************
--
linkAbnormal NOTIFICATION-TYPE
    OBJECTS {
        linkAbnormalTrapValue
    }
    STATUS current
    DESCRIPTION
        "The Port access signal is abnormal."
::= { devStatetraps 1 }

ifOverflow NOTIFICATION-TYPE
    OBJECTS {
        ifOverflowTrapValue
    }
    STATUS current
    DESCRIPTION
        "The Port forwarding traffic overflow."
::= { devStatetraps 2 }

innerOverflow NOTIFICATION-TYPE
    OBJECTS {
        innerOverflowTrapValue
    }
    STATUS current
    DESCRIPTION
        "The Cross-board traffic loss."
::= { devStatetraps 3 }

lossOverflow NOTIFICATION-TYPE
    OBJECTS {
        lossOverflowTrapValue
    }
    STATUS current
    DESCRIPTION
        "The ratio of flow input to output loss exceeds the threshold."
::= { devStatetraps 5 }

ifPhysicalStatusChange NOTIFICATION-TYPE
    OBJECTS {
        ifPhysicalStatusChangeTrapValue
    }
    STATUS current
    DESCRIPTION
        "The Port physical status changes."
::= { devStatetraps 6 }

ifAdminStatusChange NOTIFICATION-TYPE
    OBJECTS {
        ifAdminStatusChangeTrapValue
    }
    STATUS current
    DESCRIPTION
        "The Port enable state change."
::= { devStatetraps 7 }

unknownPacketRatioHigh NOTIFICATION-TYPE
    OBJECTS {
        unknownPacketRatioHighTrapValue
    }
    STATUS current
    DESCRIPTION
        "The proportion of unrecognized packets exceeds the threshold."
::= { devStatetraps 9 }

crcErrorPacketRatioHigh NOTIFICATION-TYPE
    OBJECTS {
        crcErrorPacketRatioHighTrapValue
    }
    STATUS current
    DESCRIPTION
        "The CRC error packet ratio exceeds the threshold."
::= { devStatetraps 10 }

trafficChange NOTIFICATION-TYPE
    OBJECTS {
        trafficChangeTrapValue
    }
    STATUS current
    DESCRIPTION
        "The degree of traffic change exceeds the threshold."
::= { devStatetraps 13 }

ifTafficRateHigh NOTIFICATION-TYPE
    OBJECTS {
        ifTafficRateHighTrapValue
    }
    STATUS current
    DESCRIPTION
        "The Port traffic rate exceeds the threshold."
::= { devStatetraps 16 }

opticalPowerDeviateRange NOTIFICATION-TYPE
    OBJECTS {
        opticalPowerDeviateRangeTrapValue
    }
    STATUS current
    DESCRIPTION
        "The Port optical power deviates from the receiving range exceeding the threshold."
::= { devStatetraps 18 }

totalInputAndOutputTrafficInconsistent NOTIFICATION-TYPE
    OBJECTS {
        totalInputAndOutputTrafficInconsistentTrapValue
    }
    STATUS current
    DESCRIPTION
        "The total input and output flow deviation exceeds the threshold."
::= { devStatetraps 19 }

ifTable OBJECT-TYPE
    SYNTAX      SEQUENCE OF IfEntry
    MAX-ACCESS  not-accessible
    STATUS      current
    DESCRIPTION
            "This table contains one or more rows per port information
            associated with the local system known to this agent."
    ::= { network 2 }

ifEntry OBJECT-TYPE
    SYNTAX      IfEntry 
    MAX-ACCESS  not-accessible
    STATUS      current
    DESCRIPTION
            "Information about a particular port component.

            Entries may be created and deleted in this table by the
            agent."
    INDEX   { ruijiePortIndex }
    ::= { ifTable 1 }

IfEntry ::= SEQUENCE {
      ruijiePortIndex IfIndex,
      ifRxPower DisplayString,
      ifTxPower DisplayString,
      ifProtocol DisplayString
}

ruijiePortIndex OBJECT-TYPE
        SYNTAX IfIndex
        MAX-ACCESS not-accessible
        STATUS current
        DESCRIPTION
            "Port index of the port."
        ::= { ifEntry 1 }

ifRxPower OBJECT-TYPE
        SYNTAX DisplayString (SIZE(1..32))
        MAX-ACCESS read-only
        STATUS current
        DESCRIPTION
            "Port optical power status."
        ::= { ifEntry 2 }

ifTxPower OBJECT-TYPE
        SYNTAX DisplayString (SIZE(1..32))
        MAX-ACCESS read-only
        STATUS current
        DESCRIPTION
            "Port optical power status."
        ::= { ifEntry 3 }

ifProtocol OBJECT-TYPE
        SYNTAX DisplayString (SIZE(1..32))
        MAX-ACCESS read-only
        STATUS current
        DESCRIPTION
            "Link layer protocol."
        ::= { ifEntry 4 }

END
