-- *****************************************************************
-- RUIJIE-WLAN-HOTBACKUP-MIB.mib:  Ruijie WLAN HOT-BACKUP MIB file
--
-- July 2012, jiangweifeng
-- 
-- Copyright (c) 2012 by Ruijie Networks Co.,Ltd.
-- All rights reserved.
-- *****************************************************************


RUIJIE-WLAN-HOTBACKUP-MIB DEFINITIONS ::= BEGIN

IMPORTS
    MODULE-IDENTITY, 
    OBJECT-TYPE,
    Integer32,
    IpAddress
        FROM SNMPv2-SMI
    ruijieMgmt
        FROM RUIJIE-SMI
    InetAddress,
    InetAddressType
        FROM INET-ADDRESS-MIB;

ruijieWlanHotbackupMIB MODULE-IDENTITY
    LAST-UPDATED "201207310000Z"
    ORGANIZATION "Ruijie Networks Co.,Ltd."
    CONTACT-INFO
            " 
            Tel: 4008-111-000 
                
            E-mail: service@ruijie.com.cn"
    DESCRIPTION
            "This MIB is intended to get the wlan hot-backup 
            information on AC. AC may establish hot-backup relationship 
            with several ACs(called peers)."
    REVISION  "201207310000Z"
    DESCRIPTION
            "Initial version of this mib."
    ::= { ruijieMgmt 115 }

ruijieWlanHotbackupMIBObjects OBJECT IDENTIFIER 
    ::= { ruijieWlanHotbackupMIB 1 }

ruijieWlanHotbackupNotificationsMIBObjects OBJECT IDENTIFIER
    ::= { ruijieWlanHotbackupMIB 2 }

ruijieWlanHotbackupNtfObjects OBJECT IDENTIFIER
    ::= { ruijieWlanHotbackupNotificationsMIBObjects 1 }

ruijieWlanHotbackupNotifications OBJECT IDENTIFIER
    ::= { ruijieWlanHotbackupNotificationsMIBObjects 2 }

--*******************************************************************
--ruijieWlanHotbackupPeerTable:  list of wlan hot-backup peer
--*******************************************************************
ruijieWlanHotbackupPeerTable  OBJECT-TYPE
     SYNTAX      SEQUENCE OF RuijieWlanHotbackupPeerEntry
     MAX-ACCESS  not-accessible
     STATUS      current
     DESCRIPTION
                 "A table listing the peers establishing hot-backup 
                 relationship with this AC."
     ::= { ruijieWlanHotbackupMIBObjects 1 }

ruijieWlanHotbackupPeerEntry OBJECT-TYPE
     SYNTAX      RuijieWlanHotbackupPeerEntry
     MAX-ACCESS  not-accessible
     STATUS      current
     DESCRIPTION
                 "Wlan hot-backup peer entry."
     INDEX       { ruijieWlanHotbackupIpAddress }
     ::= { ruijieWlanHotbackupPeerTable  1 }

RuijieWlanHotbackupPeerEntry ::= SEQUENCE {
         ruijieWlanHotbackupIpAddress        IpAddress,
         ruijieWlanHotbackupIsEnabled        INTEGER,
         ruijieWlanHotbackupState            INTEGER
         }

ruijieWlanHotbackupIpAddress OBJECT-TYPE
     SYNTAX      IpAddress
     MAX-ACCESS  not-accessible
     STATUS      current
     DESCRIPTION
                 "Wlan hot-backup peer's IP address."
     ::= { ruijieWlanHotbackupPeerEntry 1 }

ruijieWlanHotbackupIsEnabled OBJECT-TYPE
     SYNTAX      INTEGER {
                     disable(0),
                     enable(1)
                 }
     MAX-ACCESS  read-only
     STATUS      current
     DESCRIPTION
                 "Wlan hot-backup enable state with this peer."
     ::= { ruijieWlanHotbackupPeerEntry 2 }

ruijieWlanHotbackupState OBJECT-TYPE
     SYNTAX      INTEGER {
                     hb-disable(1),
                     probe(2),
                     hdsk(3),
                     tcp-connect(4),
                     sulking(5),
                     channel-up(6)
                 }
     MAX-ACCESS  read-only
     STATUS      current
     DESCRIPTION
                 "Wlan hot-backup state with this peer."
     ::= { ruijieWlanHotbackupPeerEntry 3 }

--*******************************************************************
--ruijieWlanHotbackupContextTable:  list of wlan hot-backup context
--*******************************************************************
ruijieWlanHotbackupContextTable OBJECT-TYPE
    SYNTAX      SEQUENCE OF RuijieWlanHotbackupContextEntry
    MAX-ACCESS  not-accessible
    STATUS      current
    DESCRIPTION
        "The table descrips information about AC context info."
    ::= { ruijieWlanHotbackupMIBObjects 2 }

ruijieWlanHotbackupContextEntry OBJECT-TYPE
    SYNTAX      RuijieWlanHotbackupContextEntry
    MAX-ACCESS  not-accessible
    STATUS      current
    DESCRIPTION
        "Each entry contains information about AC context info."
    INDEX { ruijieWlanHotbackupCtxIpAddress, ruijieWlanHotbackupContextId }
    ::= { ruijieWlanHotbackupContextTable 1 }

RuijieWlanHotbackupContextEntry ::=
    SEQUENCE {
		ruijieWlanHotbackupCtxIpAddress IpAddress,
        ruijieWlanHotbackupContextId  INTEGER,
        ruijieWlanHotbackupContextState INTEGER
    }

ruijieWlanHotbackupCtxIpAddress OBJECT-TYPE
     SYNTAX      IpAddress
     MAX-ACCESS  read-only
     STATUS      current
     DESCRIPTION
                 "Wlan hot-backup peer's IP address."
     ::= { ruijieWlanHotbackupContextEntry 1 }
	
ruijieWlanHotbackupContextId OBJECT-TYPE
    SYNTAX      INTEGER
    MAX-ACCESS  read-only
    STATUS      current
    DESCRIPTION
        "Each entry contains context id."
    ::= { ruijieWlanHotbackupContextEntry 2 }

ruijieWlanHotbackupContextState OBJECT-TYPE
    SYNTAX      INTEGER {
                    disable(0),
                    unknown(1),
                    single-active(2),
                    single-standby(3),
                    pair-active(4),
                    pair-standby(5)
                }
    MAX-ACCESS  read-only
    STATUS      current
    DESCRIPTION
         "Each entry contains context state."
    ::= { ruijieWlanHotbackupContextEntry 3 }

-- ****************************************
--
--               Notify nodes
--
-- ****************************************
ruijieNotifyPeerIpType OBJECT-TYPE
    SYNTAX      InetAddressType
    MAX-ACCESS  accessible-for-notify
    STATUS      current
    DESCRIPTION
        "Represents the peer ip type."
    ::= { ruijieWlanHotbackupNtfObjects 1 }
    
ruijieNotifyPeerIp OBJECT-TYPE
    SYNTAX      InetAddress
    MAX-ACCESS  accessible-for-notify
    STATUS      current
    DESCRIPTION
        "Represents the peer ip."
    ::= { ruijieWlanHotbackupNtfObjects 2 }

ruijieNotifyCtxId OBJECT-TYPE
    SYNTAX      INTEGER(0..65535)
    MAX-ACCESS  accessible-for-notify
    STATUS      current
    DESCRIPTION
        "Represents the context id."
    ::= { ruijieWlanHotbackupNtfObjects 3 }
    
ruijieNotifyOldState OBJECT-TYPE
    SYNTAX      INTEGER {
                    disable(0),
                    unknown(1),
                    single-active(2),
                    single-standby(3),
                    pair-active(4),
                    pair-standby(5)
                }
    MAX-ACCESS  accessible-for-notify
    STATUS      current
    DESCRIPTION
        "Represents the old state."
    ::= { ruijieWlanHotbackupNtfObjects 4 }
    
ruijieNotifyNewState OBJECT-TYPE
    SYNTAX      INTEGER {
                    disable(0),
                    unknown(1),
                    single-active(2),
                    single-standby(3),
                    pair-active(4),
                    pair-standby(5)
                }
    MAX-ACCESS  accessible-for-notify
    STATUS      current
    DESCRIPTION
        "Represents the new state."
    ::= { ruijieWlanHotbackupNtfObjects 5 }
    
ruijieNotifyWlanHBChange NOTIFICATION-TYPE
    OBJECTS     {
                  ruijieNotifyPeerIpType,
                  ruijieNotifyPeerIp,
                  ruijieNotifyCtxId,
                  ruijieNotifyOldState,
                  ruijieNotifyNewState
                }
    STATUS      current
    DESCRIPTION
        "This notification is sent by the AC hotbackup change state."
    ::= { ruijieWlanHotbackupNotifications 1 }
    
END
