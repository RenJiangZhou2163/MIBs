-- *****************************************************************
-- RUIJIE-TRAP-FORMAT-MIB.mib:  Ruijie TRAP FORMAT MIB file
--
-- May 2011, Panshiyong
--
-- Copyright(c) 2011 by Ruijie Networks Co.,Ltd.
-- All rights reserved.
-- 
-- *****************************************************************
--

RUIJIE-TRAP-FORMAT-MIB DEFINITIONS ::= BEGIN

IMPORTS
        MODULE-IDENTITY,
        OBJECT-TYPE,
        TimeTicks,
        Unsigned32,
        IpAddress
                FROM SNMPv2-SMI
        Counter
                FROM RFC1155-SMI
        DisplayString
                FROM SNMPv2-TC
        MODULE-COMPLIANCE,
        OBJECT-GROUP
                FROM SNMPv2-CONF
        ruijieMgmt
                FROM RUIJIE-SMI;

ruijieTrapFormatMIB MODULE-IDENTITY
        LAST-UPDATED "201105110000Z"
        ORGANIZATION "Ruijie Networks Co.,Ltd."
        CONTACT-INFO
                " 
                Tel: 4008-111-000 

                E-mail: service@ruijie.com.cn"
        DESCRIPTION
                "This module defines ruijie trap-format mibs."
        REVISION      "201105110000Z"
        DESCRIPTION
                "Initial version of this MIB module."
        ::= { ruijieMgmt 97 }


ruijieTrapFormatMIBObjects OBJECT IDENTIFIER ::= { ruijieTrapFormatMIB 1 }


--**********************************************************************
-- ruijie Trap Format MIB info 
--**********************************************************************
ruijieTrapFormatTrapSerialNo OBJECT-TYPE
    SYNTAX DisplayString(SIZE (1..32))
    MAX-ACCESS read-only
    STATUS current
    DESCRIPTION
        "Serial NO. of trap informations."
    ::= { ruijieTrapFormatMIBObjects 1 }

ruijieTrapFormatTrapLevel OBJECT-TYPE
    SYNTAX DisplayString(SIZE (1..32))
    MAX-ACCESS read-only
    STATUS current
    DESCRIPTION
        "Original level of trap informations:
         1 - critical,
         2 - major,
         3 - minor,
         4 - normal,
         5 - uncertain.
        "
    ::= { ruijieTrapFormatMIBObjects 2 }

ruijieTrapFormatTrapType OBJECT-TYPE
    SYNTAX DisplayString(SIZE (1..32))
    MAX-ACCESS read-only
    STATUS current
    DESCRIPTION
        "Original type of trap informations:
         1 - Communication Trap,
         2 - Environment Trap,
         3 - Device Trap,
         4 - Process Error Trap,
         5 - Quality of Service Trap.
        "
    ::= { ruijieTrapFormatMIBObjects 3 }

ruijieTrapFormatTrapReasonNo OBJECT-TYPE
    SYNTAX INTEGER
    MAX-ACCESS read-only
    STATUS current
    DESCRIPTION
        "Reason NO. of trap informations."
    ::= { ruijieTrapFormatMIBObjects 4 }

ruijieTrapFormatTrapReasons OBJECT-TYPE
    SYNTAX DisplayString(SIZE (1..64))
    MAX-ACCESS read-only
    STATUS current
    DESCRIPTION
        "Reasons of trap informations."
    ::= { ruijieTrapFormatMIBObjects 5 }

ruijieTrapFormatTrapStatus OBJECT-TYPE
    SYNTAX INTEGER
    MAX-ACCESS read-only
    STATUS current
    DESCRIPTION
        "Status of trap informations:
         1 - active,
         0 - eliminate.
        "
    ::= { ruijieTrapFormatMIBObjects 6 }

ruijieTrapFormatTrapTitle OBJECT-TYPE
    SYNTAX DisplayString(SIZE (1..64))
    MAX-ACCESS read-only
    STATUS current
    DESCRIPTION
        "Title of trap informations."
    ::= { ruijieTrapFormatMIBObjects 7 }

ruijieTrapFormatTrapContent OBJECT-TYPE
    SYNTAX DisplayString(SIZE (1..64))
    MAX-ACCESS read-only
    STATUS current
    DESCRIPTION
        "Content of trap informations."
    ::= { ruijieTrapFormatMIBObjects 8 }

ruijieTrapFormatTrapTime OBJECT-TYPE
    SYNTAX Counter
    MAX-ACCESS read-only
    STATUS current
    DESCRIPTION
        "The time (in seconds) since the trap alarm occurred 
         of the system was last re-initialized."
    ::= { ruijieTrapFormatMIBObjects 9 }
	
ruijieTrapFormatTrapSlotInfo OBJECT-TYPE
    SYNTAX DisplayString
    MAX-ACCESS read-only
    STATUS current
    DESCRIPTION
        "The slot info(1/2 or 2) of slot that send trap."
    ::= { ruijieTrapFormatMIBObjects 10 }
	
ruijieTrapFormatTrapVendorId OBJECT-TYPE
    SYNTAX INTEGER
    MAX-ACCESS read-only
    STATUS current
    DESCRIPTION
        "The vendor id of the send trap."
    ::= { ruijieTrapFormatMIBObjects 11 }
    
ruijieTrapFormatTrapSerialNum OBJECT-TYPE
    SYNTAX DisplayString(SIZE (1..64))
    MAX-ACCESS read-only
    STATUS current
    DESCRIPTION
        "The serial number of the send trap."
    ::= { ruijieTrapFormatMIBObjects 12 }   

ruijieTrapFormatTrapDateTime OBJECT-TYPE
    SYNTAX DisplayString(SIZE (1..64))
    MAX-ACCESS read-only
    STATUS current
    DESCRIPTION
        "The date time when the trap occurred ."
    ::= { ruijieTrapFormatMIBObjects 13 }       
    
--**********************************************************************
-- about conformance info 
--**********************************************************************
ruijieTrapFormatMIBConformance OBJECT IDENTIFIER ::= { ruijieTrapFormatMIB 2 }
ruijieTrapFormatMIBCompliances OBJECT IDENTIFIER ::= { ruijieTrapFormatMIBConformance 1 }
ruijieTrapFormatMIBGroups      OBJECT IDENTIFIER ::= { ruijieTrapFormatMIBConformance 2 }

-- compliance statements
ruijieTrapFormatMIBCompliance MODULE-COMPLIANCE
    STATUS  current
    DESCRIPTION
        "The compliance statement for entities which implement
         the Ruijie Trap Format MIB"
    MODULE  
    MANDATORY-GROUPS { 
        ruijieTrapFormatMIBGroup
    }
    ::= { ruijieTrapFormatMIBCompliances 1 }
                
-- units of conformance
ruijieTrapFormatMIBGroup OBJECT-GROUP
        OBJECTS {
            ruijieTrapFormatTrapSerialNo,
            ruijieTrapFormatTrapLevel,
            ruijieTrapFormatTrapType,
            ruijieTrapFormatTrapReasonNo,
            ruijieTrapFormatTrapReasons,
            ruijieTrapFormatTrapStatus,
            ruijieTrapFormatTrapTitle,
            ruijieTrapFormatTrapContent,
            ruijieTrapFormatTrapTime,
			ruijieTrapFormatTrapSlotInfo,
            ruijieTrapFormatTrapVendorId,
            ruijieTrapFormatTrapSerialNum,
            ruijieTrapFormatTrapDateTime
        }
        STATUS  current
        DESCRIPTION
                "A collection of objects providing Capwap App configure."
        ::= { ruijieTrapFormatMIBGroups 1 }
        
END
