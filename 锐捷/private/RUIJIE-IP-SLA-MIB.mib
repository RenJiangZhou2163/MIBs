-- *****************************************************************
-- RUIJIE-IP-RNS-MIB.mib:  Ruijie interface MIB file
--
-- March 2014, tangyoucan
--
-- Copyright (c) 2014 by Ruijie Networks Co.,Ltd.
-- All rights reserved.
-- 
-- *****************************************************************
--

RUIJIE-IP-SLA-MIB DEFINITIONS ::= BEGIN

IMPORTS
        MODULE-IDENTITY,
        OBJECT-TYPE,
        NOTIFICATION-TYPE,
        Integer32,
        OBJECT-TYPE,
        Counter32,
        Counter64,
        Unsigned32,
        IpAddress
                FROM SNMPv2-SMI   
        RowStatus, 
        DateAndTime
                FROM SNMPv2-TC
        MODULE-COMPLIANCE,
        OBJECT-GROUP
                FROM SNMPv2-CONF
        ConfigStatus,
        IfIndex
                FROM RUIJIE-TC
        EnabledStatus 
                FROM P-BRIDGE-MIB
        ifIndex
                FROM RFC1213-MIB
        Gauge,
        TimeTicks
                FROM RFC1155-SMI
        ruijieMgmt
                FROM RUIJIE-SMI
        ruijieRouterQoSMIB
                FROM RUIJIE-ROUTER-QOS-MIB 
        pingCtlOwnerIndex, pingCtlTestName
        FROM DISMAN-PING-MIB 
        IANAifType
                FROM IANAifType-MIB
        InterfaceIndex
                FROM IF-MIB
       SnmpAdminString
                FROM SNMP-FRAMEWORK-MIB          -- RFC3411
       InetAddressType, InetAddress
                FROM INET-ADDRESS-MIB;           -- RFC4001

                
ruijieIpSlaMIB MODULE-IDENTITY
        LAST-UPDATED "201409120000Z"
        ORGANIZATION "Ruijie Networks Co.,Ltd."
        CONTACT-INFO
                " 
                Tel: 4008-111-000 

                E-mail: service@ruijie.com.cn"
        DESCRIPTION
                "This module defines ruijie ip rns mibs."
        REVISION      "201409120000Z"
        DESCRIPTION
                "Initial version of this MIB module."
        ::= { ruijieRouterQoSMIB 5}

ruijieIpSlaMIBObjects OBJECT IDENTIFIER ::= { ruijieIpSlaMIB 1 }
   -- Results Table
        ruijieIpSlaResultsTable OBJECT-TYPE
        SYNTAX      SEQUENCE OF RuijieIpSlaResultsEntry
        MAX-ACCESS  not-accessible
        STATUS      current
        DESCRIPTION
            "The results of these operations are stored in the ruijieIpSlaResultsTable."
        ::= { ruijieIpSlaMIBObjects 1 }

        ruijieIpSlaResultsEntry OBJECT-TYPE
        SYNTAX      RuijieIpSlaResultsEntry
        MAX-ACCESS  not-accessible
        STATUS      current
        DESCRIPTION
            "Defines an entry in the ruijieIpSlaResultsTable.  The
            ruijieIpSlaResultsTable has the same indexing as the
            ruijieIpSlaCtlTable so that a ruijieIpSlaResultsEntry
            corresponds to the ruijieIpSlaCtlEntry that caused it to
            be created."
        INDEX {
                 pingCtlOwnerIndex,
                 pingCtlTestName
              }
        ::= { ruijieIpSlaResultsTable 1 }

        RuijieIpSlaResultsEntry ::=
        SEQUENCE { 
           ruijieIpSlaResultsOperStatus          INTEGER,
           ruijieIpSlaResultsIpTargetAddressType InetAddressType,
           ruijieIpSlaResultsIpTargetAddress     InetAddress,
           ruijieIpSlaResultsMaxRtt              Unsigned32,
           ruijieIpSlaResultsMinRtt              Unsigned32,
           ruijieIpSlaResultsAverageRtt          Unsigned32,
           ruijieIpSlaResultsDelayJitter         Unsigned32,
           ruijieIpSlaResultsPktsLossRate        Unsigned32,
           ruijieIpSlaResultsNetworkAF           Unsigned32,
           ruijieIpSlaResultsProbeResponses      Gauge32,
           ruijieIpSlaResultsSentProbes          Gauge32,
           ruijieIpSlaResultsRttSumOfSquares     Unsigned32,
           ruijieIpSlaResultsLastGoodProbe       DateAndTime
        }
 
        ruijieIpSlaResultsOperStatus OBJECT-TYPE
        SYNTAX      INTEGER {
                             enabled(1),   -- test is in progress
                             disabled(2),  -- test has stopped
                             completed(3)  -- test is completed
                           }
        MAX-ACCESS  read-only
        STATUS      current
        DESCRIPTION
            "Reflects the operational state of a ruijieIpSlaCtlEntry:
              enabled(1)    - Test is active.
              disabled(2)   - Test has stopped.
              completed(3)  - Test is completed."
        ::= { ruijieIpSlaResultsEntry 1 }

        ruijieIpSlaResultsIpTargetAddressType OBJECT-TYPE
        SYNTAX      InetAddressType
        MAX-ACCESS  read-only
        STATUS      current
        DESCRIPTION
            "This object indicates the type of address stored in the 
            corresponding ruijieIpSlaResultsIpTargetAddress object."
        DEFVAL { unknown }
        ::= { ruijieIpSlaResultsEntry 2 }

        ruijieIpSlaResultsIpTargetAddress OBJECT-TYPE
        SYNTAX      InetAddress
        MAX-ACCESS  read-only
        STATUS      current
        DESCRIPTION
            "This object reports the IP address associated with a 
            ruijieIpSlaCtlTargetAddress value when the destination
            address is specified as a DNS name.  The value of this 
            object should be a zero-length octet string when a DNS 
            name is not specified or when a specified DNS name fails
            to resolve.

            The address type (InetAddressType) that relates to
            this object is specified by the corresponding value
            of ruijieIpSlaResultsIpTargetAddressType."
        DEFVAL { ''H }
        ::= { ruijieIpSlaResultsEntry 3 }

        ruijieIpSlaResultsMaxRtt OBJECT-TYPE
        SYNTAX      Unsigned32
        UNITS       "milliseconds"
        MAX-ACCESS  read-only
        STATUS      current
        DESCRIPTION
            "The maximum packet round-trip-time (RTT) that received. A value
            of 0 for this object implies that no RTT has been received."
        ::= { ruijieIpSlaResultsEntry 4 }

        ruijieIpSlaResultsMinRtt OBJECT-TYPE
        SYNTAX      Unsigned32
        UNITS       "milliseconds"
        MAX-ACCESS  read-only
        STATUS      current
        DESCRIPTION
            "The minimum packet round-trip-time (RTT) that received. A value
            of 0 for this object implies that no RTT has been received."
        ::= { ruijieIpSlaResultsEntry 5 }

        ruijieIpSlaResultsAverageRtt OBJECT-TYPE
        SYNTAX      Unsigned32
        UNITS       "milliseconds"
        MAX-ACCESS  read-only
        STATUS      current
        DESCRIPTION
            "The current average packet round-trip-time (RTT)."
        ::= { ruijieIpSlaResultsEntry 6 }

        ruijieIpSlaResultsDelayJitter OBJECT-TYPE
        SYNTAX      Unsigned32
        UNITS       "milliseconds"
        MAX-ACCESS  read-only
        STATUS      current
        DESCRIPTION
            "This object contains the sum of the squares for all ping
            responses received.  Its purpose is to enable standard
            deviation calculation. The estimate value of the delay jitter."
        ::= { ruijieIpSlaResultsEntry 7 } 
       
        ruijieIpSlaResultsPktsLossRate OBJECT-TYPE
        SYNTAX      Unsigned32     
        MAX-ACCESS  read-only
        STATUS      current
        DESCRIPTION
            "The packets loss rate of the link."
        ::= { ruijieIpSlaResultsEntry 8 }

        ruijieIpSlaResultsNetworkAF  OBJECT-TYPE
        SYNTAX       Unsigned32 
        MAX-ACCESS   read-only
        STATUS       current
        DESCRIPTION
            "The network availability factor." 
        ::= { ruijieIpSlaResultsEntry 9 }
     ruijieIpSlaResultsProbeResponses OBJECT-TYPE
       SYNTAX      Gauge32
       UNITS       "responses"
       MAX-ACCESS  read-only
       STATUS      current
       DESCRIPTION
           "Number of responses received for the corresponding
           pingCtlEntry and pingResultsEntry.  The value of this object
           MUST be reported as 0 when no probe responses have been
           received."
       ::= { ruijieIpSlaResultsEntry 10 }

     ruijieIpSlaResultsSentProbes OBJECT-TYPE
       SYNTAX      Gauge32
       UNITS       "probes"
       MAX-ACCESS  read-only
       STATUS      current
       DESCRIPTION
           "The value of this object reflects the number of probes sent
           for the corresponding pingCtlEntry and pingResultsEntry.
           The value of this object MUST be reported as 0 when no probes
           have been sent."
       ::= { ruijieIpSlaResultsEntry 11 }

     ruijieIpSlaResultsRttSumOfSquares OBJECT-TYPE
       SYNTAX      Unsigned32
       UNITS       "milliseconds"
       MAX-ACCESS  read-only
       STATUS      current
       DESCRIPTION
           "This object contains the sum of the squares for all ping
           responses received.  Its purpose is to enable standard
           deviation calculation.  The value of this object MUST
           be reported as 0 when no ping responses have been
           received."
       ::= { ruijieIpSlaResultsEntry 12 }
    ruijieIpSlaResultsLastGoodProbe OBJECT-TYPE
       SYNTAX      DateAndTime
       MAX-ACCESS  read-only
       STATUS      current
       DESCRIPTION
           "Date and time when the last response was received for
           a probe."
       ::= { ruijieIpSlaResultsEntry 13 }
   END
