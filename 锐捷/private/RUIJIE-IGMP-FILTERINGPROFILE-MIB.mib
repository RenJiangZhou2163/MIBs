-- *****************************************************************
-- RUIJIE-IGMP-FILTERINGPROFILE-MIB.mib:  Ruijie IGMP profiles MIB file
--
-- Dec 2003, Billy
--
-- Copyright (c) 2003 by Ruijie Networks Co.,Ltd.
-- All rights reserved.
-- 
-- *****************************************************************
--
RUIJIE-IGMP-FILTERINGPROFILE-MIB DEFINITIONS ::= BEGIN

IMPORTS
        MODULE-IDENTITY,
        OBJECT-TYPE,
        Unsigned32,
        IpAddress
                FROM SNMPv2-SMI
        RowStatus
                FROM SNMPv2-TC              
        MODULE-COMPLIANCE,
        OBJECT-GROUP
                FROM SNMPv2-CONF
        ruijieMgmt
                FROM RUIJIE-SMI;

ruijieIgmpFilteringProfileMIB MODULE-IDENTITY
        LAST-UPDATED "200312090000Z"
        ORGANIZATION "Ruijie Networks Co.,Ltd."
        CONTACT-INFO
                " 
                Tel: 4008-111-000 

                E-mail: service@ruijie.com.cn"
        DESCRIPTION
                "This module defines ruijie IGMP filtering profile mibs."
        REVISION      "200312090000Z"
        DESCRIPTION
                "Initial version of this MIB module."
        ::= { ruijieMgmt 37}

ruijieIgmpFilteringProfileMIBObjects OBJECT IDENTIFIER ::= { ruijieIgmpFilteringProfileMIB 1 }

ruijieIgmpFilteringMaxProfiles OBJECT-TYPE
        SYNTAX     Unsigned32
        MAX-ACCESS read-only
        STATUS     current
        DESCRIPTION
            "Indicates the maximum number of profiles supported by
            this device.  A value of zero indicates no limitation on
            the number of profiles."
        ::= { ruijieIgmpFilteringProfileMIBObjects 1 }
        
ruijieIgmpFilteringProfileActionTable OBJECT-TYPE
        SYNTAX SEQUENCE OF RuijieIgmpFilteringProfileActionEntry
        MAX-ACCESS not-accessible
        STATUS current
        DESCRIPTION
            "profile action table."
        ::= { ruijieIgmpFilteringProfileMIBObjects 2}
    
ruijieIgmpFilteringProfileActionEntry OBJECT-TYPE
        SYNTAX RuijieIgmpFilteringProfileActionEntry
        MAX-ACCESS not-accessible
        STATUS current
        DESCRIPTION
            "list of profile table"
        INDEX { ruijieIgmpFilteringProfileIndex }         
        ::= { ruijieIgmpFilteringProfileActionTable 1}
        
RuijieIgmpFilteringProfileActionEntry ::= 
        SEQUENCE {
        ruijieIgmpFilteringProfileIndex Unsigned32,
        ruijieIgmpFilteringProfileAction INTEGER,
        ruijieIgmpFilteringProfileStatus INTEGER
        }

ruijieIgmpFilteringProfileIndex OBJECT-TYPE
        SYNTAX Unsigned32
        MAX-ACCESS read-only
        STATUS current
        DESCRIPTION     
            ""
        ::= { ruijieIgmpFilteringProfileActionEntry 1}  
        
ruijieIgmpFilteringProfileAction OBJECT-TYPE
        SYNTAX INTEGER {
            permit(1),
	    deny(2)
	}
        MAX-ACCESS read-write
        STATUS current
        DESCRIPTION     
            "This object defines the action of this profile.
	     
	     If the object is set to deny(2):
             then all IGMP reports associated to IP multicast
             groups included in the profile identified by
             ruijieIgmpFilteringProfileIndex will be dropped.

             If the object is set to permit(1):
             then all IGMP reports associated to IP multicast
             groups not included in the profile identified by
             ruijieIgmpFilteringProfileIndex will be dropped."                        
        ::= { ruijieIgmpFilteringProfileActionEntry 2}     
        
ruijieIgmpFilteringProfileStatus OBJECT-TYPE
        SYNTAX INTEGER{
        	valid(1),
        	invalid(2)
        }
        MAX-ACCESS read-write
        STATUS current
        DESCRIPTION     
            "set this object to invalid(2) will remove current item"
        ::= { ruijieIgmpFilteringProfileActionEntry 3}          

ruijieIgmpFilteringProfileRangeTable OBJECT-TYPE
        SYNTAX SEQUENCE OF RuijieIgmpFilteringProfileRangeEntry
        MAX-ACCESS not-accessible
        STATUS current
        DESCRIPTION
            "IGMP filtering profile range table"
        ::= { ruijieIgmpFilteringProfileMIBObjects 3}        
    
ruijieIgmpFilteringProfileRangeEntry OBJECT-TYPE
        SYNTAX RuijieIgmpFilteringProfileRangeEntry
        MAX-ACCESS not-accessible
        STATUS current
        DESCRIPTION
            "list of profile table"
        INDEX { ruijieIgmpFilteringProfileRangeIndex,
        	ruijieIgmpFilteringProfieRangeRuijieAddress }         
        ::= { ruijieIgmpFilteringProfileRangeTable 1}
        
RuijieIgmpFilteringProfileRangeEntry ::= 
        SEQUENCE {
        ruijieIgmpFilteringProfileRangeIndex Unsigned32,
        ruijieIgmpFilteringProfieRangeRuijieAddress IpAddress,
        ruijieIgmpFilteringProfieRangeEndAddress IpAddress,  
        ruijieIgmpFilteringProfileRangeStatus RowStatus      
        }

ruijieIgmpFilteringProfileRangeIndex OBJECT-TYPE
        SYNTAX Unsigned32
        MAX-ACCESS read-only
        STATUS current
        DESCRIPTION     
            ""
        ::= { ruijieIgmpFilteringProfileRangeEntry 1}               

ruijieIgmpFilteringProfieRangeRuijieAddress OBJECT-TYPE
        SYNTAX IpAddress
        MAX-ACCESS read-create
        STATUS current
        DESCRIPTION
            "This object describes the ruijie of the IP multicast 
             group address of a contiguous range which will be
             subjected to filtering operation."
        ::= { ruijieIgmpFilteringProfileRangeEntry 2 }      
        
ruijieIgmpFilteringProfieRangeEndAddress OBJECT-TYPE
        SYNTAX IpAddress
        MAX-ACCESS read-create
        STATUS current
        DESCRIPTION
            "This object indicates the type of Internet
	     address used to determine the end address 
	     of IP multicast group for a profile."
        ::= { ruijieIgmpFilteringProfileRangeEntry 3 }     
        
ruijieIgmpFilteringProfileRangeStatus OBJECT-TYPE
        SYNTAX RowStatus
        MAX-ACCESS read-create
        STATUS current
        DESCRIPTION
            "the item status"
        ::= { ruijieIgmpFilteringProfileRangeEntry 4 }            
        
ruijieIgmpFilteringProfileMIBConformance OBJECT IDENTIFIER ::= { ruijieIgmpFilteringProfileMIB 2 }
ruijieIgmpFilteringProfileMIBCompliances OBJECT IDENTIFIER ::= { ruijieIgmpFilteringProfileMIBConformance 1 }
ruijieIgmpFilteringProfileMIBGroups      OBJECT IDENTIFIER ::= { ruijieIgmpFilteringProfileMIBConformance 2 }


-- compliance statements

ruijieIgmpFilteringProfileMIBCompliance MODULE-COMPLIANCE
        STATUS  current
        DESCRIPTION
                "The compliance statement for entities which implement
                the Ruijie Igmp filtering profile MIB"
        MODULE  -- this module
                MANDATORY-GROUPS { ruijieIgmpFilteringProfileMIBGroup
                 }
        ::= { ruijieIgmpFilteringProfileMIBCompliances 1 }
                
-- units of conformance

ruijieIgmpFilteringProfileMIBGroup OBJECT-GROUP
        OBJECTS {
        	ruijieIgmpFilteringMaxProfiles,
        	ruijieIgmpFilteringProfileIndex,
        	ruijieIgmpFilteringProfileAction,
        	ruijieIgmpFilteringProfileStatus,
        	ruijieIgmpFilteringProfileRangeIndex,
          ruijieIgmpFilteringProfieRangeRuijieAddress,
          ruijieIgmpFilteringProfieRangeEndAddress,
          ruijieIgmpFilteringProfileRangeStatus
        }
        STATUS  current
        DESCRIPTION
                "A collection of objects providing Igmp filtering profile configure ."
        ::= { ruijieIgmpFilteringProfileMIBGroups 1 }
        
END
