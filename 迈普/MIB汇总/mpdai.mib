DEFINITIONS ::= BEGIN

mpSwDynamicARPIPSpection  OBJECT IDENTIFIER ::= {mpSwitchTech 9}

logLevel  OBJECT-TYPE
    SYNTAX  INTEGER(0..11)
    ACCESS  read-write
    STATUS  5
    DESCRIPTION
            "Dynamic ARP Inspection log level"
    ::= {mpSwDynamicARPIPSpection 1}

logBuf  OBJECT-TYPE
    SYNTAX  INTEGER(0..1024)
    ACCESS  read-write
    STATUS  5
    DESCRIPTION
            "Dynamic ARP Inspection log buffer"
    ::= {mpSwDynamicARPIPSpection 2}

logInterval  OBJECT-TYPE
    SYNTAX  INTEGER
    ACCESS  read-write
    STATUS  5
    DESCRIPTION
            "Dynamic ARP Inspection log interval"
    ::= {mpSwDynamicARPIPSpection 3}

logDropCount  OBJECT-TYPE
    SYNTAX  INTEGER
    ACCESS  read-only
    STATUS  5
    DESCRIPTION
            "drop log statistics in an interval"
    ::= {mpSwDynamicARPIPSpection 4}

logDropCountTotal  OBJECT-TYPE
    SYNTAX  INTEGER
    ACCESS  read-only
    STATUS  5
    DESCRIPTION
            "drop log statistics total"
    ::= {mpSwDynamicARPIPSpection 5}

logCount  OBJECT-TYPE
    SYNTAX  INTEGER
    ACCESS  read-only
    STATUS  5
    DESCRIPTION
            "log statistics"
    ::= {mpSwDynamicARPIPSpection 6}

logCountTotal  OBJECT-TYPE
    SYNTAX  INTEGER
    ACCESS  read-only
    STATUS  5
    DESCRIPTION
            "log statistics total"
    ::= {mpSwDynamicARPIPSpection 7}

logToken  OBJECT-TYPE
    SYNTAX  INTEGER
    ACCESS  read-only
    STATUS  5
    DESCRIPTION
            "log token"
    ::= {mpSwDynamicARPIPSpection 8}

daiPortTable  OBJECT-TYPE
    SYNTAX  SEQUENCE OF daiPortEntry
    ACCESS  not-accessible
    STATUS  5
    DESCRIPTION
            "The table of port information."
    ::= {mpSwDynamicARPIPSpection 20}

daiPortEntry  OBJECT-TYPE
    SYNTAX  daiPortEntry
    ACCESS  not-accessible
    STATUS  5
    DESCRIPTION
            "The table of port information."
    INDEX   {daiPortId}
    ::= {daiPortTable 1}

daiPortId  OBJECT-TYPE
    SYNTAX  INTEGER
    ACCESS  read-only
    STATUS  5
    DESCRIPTION
            "The index of the port information"
    ::= {daiPortEntry 1}

daiPortEnable  OBJECT-TYPE
    SYNTAX  INTEGER {
            enable(1),
            disable(2)
            }
    ACCESS  read-write
    STATUS  5
    DESCRIPTION
            "The status of the dynamic arp inspection"
    ::= {daiPortEntry 2}

daiPortRateLimit  OBJECT-TYPE
    SYNTAX  INTEGER(1..2048)
    ACCESS  read-write
    STATUS  5
    DESCRIPTION
            "Rate limit of the port"
    ::= {daiPortEntry 3}

daiPortName  OBJECT-TYPE
    SYNTAX  DisplayString(SIZE(1..42))
    ACCESS  read-only
    STATUS  5
    DESCRIPTION
            "port name"
    ::= {daiPortEntry 4}

daiPortRowStatus  OBJECT-TYPE
    SYNTAX  RowStatus
    ACCESS  read-only
    STATUS  5
    DESCRIPTION
            ""
    ::= {daiPortEntry 11}
END
