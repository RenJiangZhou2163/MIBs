------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPPORTARL DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;


maipu               	OBJECT IDENTIFIER ::= { enterprises 5651 }
mpMgmt2             	OBJECT IDENTIFIER ::= { maipu 6 }
mpSwitchTech        	OBJECT IDENTIFIER ::= { mpMgmt2 3 }
mpSwPort            	OBJECT IDENTIFIER ::= { mpSwitchTech 1 }



mpPortArl           	MODULE-IDENTITY
                    		LAST-UPDATED 	"1012271526Z"
                    		ORGANIZATION 	"Maipu (Sichuan) Communication Technology Co. LTD."
                    		CONTACT-INFO
                    			""
                    		DESCRIPTION
                      			""
                    		::= { mpSwPort  14 }



mprSwIvlArlTable    	OBJECT-TYPE
                    		SYNTAX  SEQUENCE OF  MprSwIvlArlEntry
                    		MAX-ACCESS  not-accessible
                    		STATUS  
                    		DESCRIPTION
                    			"Ivl ARL information table"
                    		::= { mpPortArl 1 }

mprSwIvlArlEntry    	OBJECT-TYPE
                    		SYNTAX  MprSwIvlArlEntry
                    		MAX-ACCESS  not-accessible
                    		STATUS  
                    		DESCRIPTION
                    			"Ivl ARL information table"
                    		INDEX  { mprSwIvlArlEntry, mprSwIvlArlVlan }
                    		::= { mprSwIvlArlTable 1 }

MprSwIvlArlEntry    	::= SEQUENCE {
                    			mprSwIvlArlMac         PhysAddress,
                    			mprSwIvlArlVlan        INTEGER,
                    			mprSwIvlArlPortSlot    INTEGER,
                    			mprSwIvlArlPortIndex   INTEGER,
                    			mprSwIvlArlAge         INTEGER
                    	             }


mprSwIvlArlMac      	OBJECT-TYPE
                    		SYNTAX  PhysAddress
                    		MAX-ACCESS  read-only
                    		STATUS  
                    		DESCRIPTION
                    			"Ivl ARL table index 1"
                    		::= { mprSwIvlArlEntry 1 }

mprSwIvlArlVlan     	OBJECT-TYPE
                    		SYNTAX  INTEGER(1..4094)
                    		MAX-ACCESS  read-only
                    		STATUS  
                    		DESCRIPTION
                    			"Ivl ARL table index 2"
                    		::= { mprSwIvlArlEntry 2 }

mprSwIvlArlPortSlot 	OBJECT-TYPE
                    		SYNTAX  INTEGER
                    		MAX-ACCESS  read-only
                    		STATUS  
                    		DESCRIPTION
                    			"Related port's slot number"
                    		::= { mprSwIvlArlEntry 3 }

mprSwIvlArlPortIndex	OBJECT-TYPE
                    		SYNTAX  INTEGER
                    		MAX-ACCESS  read-only
                    		STATUS  
                    		DESCRIPTION
                    			"Related port's number"
                    		::= { mprSwIvlArlEntry 4 }

mprSwIvlArlAge      	OBJECT-TYPE
                    		SYNTAX  INTEGER
                    		MAX-ACCESS  read-only
                    		STATUS  
                    		DESCRIPTION
                    			"existed time"
                    		::= { mprSwIvlArlEntry 5 }



END
------------------------------------------------------------------------------
-- ============================================================================
-- $Log: mpPortArl.mib,v $
-- Revision 1.1  2010/12/28 00:57:21  yanxq
-- add mprSwIvlArlTable #ROUTER-16526
--
--
--
-- ============================================================================
