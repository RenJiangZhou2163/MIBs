------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPQOSMIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;



mpQosMib            	MODULE-IDENTITY
                    		LAST-UPDATED 	"0511151511Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { mpMgmt  21 }



wfqListTable        	OBJECT-TYPE
                    		SYNTAX  SEQUENCE OF  WfqListEntry
                    		MAX-ACCESS  not-accessible
                    		STATUS  current
                    		DESCRIPTION
                    			"加权公平排队列表."
                    		::= { mpQosMib 1 }

wfqListEntry        	OBJECT-TYPE
                    		SYNTAX  WfqListEntry
                    		MAX-ACCESS  not-accessible
                    		STATUS  current
                    		DESCRIPTION
                    			"加权公平排队列表."
                    		INDEX  { wfqIndex }
                    		::= { wfqListTable 1 }

WfqListEntry        	::= SEQUENCE {
                    			wfqIndex               INTEGER,
                    			wfqListNum             INTEGER,
                    			wfqCtrlType            INTEGER,
                    			wfqQueueLimit          INTEGER,
                    			wfqQueueNumber         INTEGER,
                    			wfqWeightNumber        INTEGER,
                    			wfqWeightType          INTEGER,
                    			wfqSrcIp               IpAddress,
                    			wfqSrcPort             INTEGER,
                    			wfqDstIp               IpAddress,
                    			wfqDstPort             INTEGER,
                    			wfqStatus              RowStatus
                    	             }


wfqIndex            	OBJECT-TYPE
                    		SYNTAX  INTEGER
                    		MAX-ACCESS  read-only
                    		STATUS  current
                    		DESCRIPTION
                    			"加权公平排队列表索引"
                    		::= { wfqListEntry 1 }

wfqListNum          	OBJECT-TYPE
                    		SYNTAX  INTEGER(1..16)
                    		MAX-ACCESS  read-create
                    		STATUS  current
                    		DESCRIPTION
                    			"加权公平排队列表号"
                    		::= { wfqListEntry 2 }

wfqCtrlType         	OBJECT-TYPE
                    		SYNTAX  INTEGER {
                    			         limitAndNumber(1),
                    			          weight(2)
                    			        }
                    		MAX-ACCESS  read-create
                    		STATUS  current
                    		DESCRIPTION
                    			"加权公平排队列表定义方式."
                    		::= { wfqListEntry 3 }

wfqQueueLimit       	OBJECT-TYPE
                    		SYNTAX  INTEGER (64..96)
                    		MAX-ACCESS  read-create
                    		STATUS  current
                    		DESCRIPTION
                    			"加权公平排队队列限制."
							DEFVAL { 64 }
                    		::= { wfqListEntry 4 }

wfqQueueNumber      	OBJECT-TYPE
                    		SYNTAX  INTEGER (16..2048)
                    		MAX-ACCESS  read-create
                    		STATUS  current
                    		DESCRIPTION
                    			"加权公平排队队列数量值."
							DEFVAL { 256 }
                    		::= { wfqListEntry 5 }

wfqWeightNumber     	OBJECT-TYPE
                    		SYNTAX  INTEGER (1..100)
                    		MAX-ACCESS  read-create
                    		STATUS  current
                    		DESCRIPTION
                    			"加权公平排队权重值."
                    		::= { wfqListEntry 6 }

wfqWeightType       	OBJECT-TYPE
                    		SYNTAX  INTEGER {
                    			         tcp(1),
                    			          udp(2),
                    			          icmp(3),
                    			          igmp(4)
                    			        }
                    		MAX-ACCESS  read-create
                    		STATUS  current
                    		DESCRIPTION
                    			"加权公平排队规则."
                    		::= { wfqListEntry 7 }

wfqSrcIp            	OBJECT-TYPE
                    		SYNTAX  IpAddress
                    		MAX-ACCESS  read-create
                    		STATUS  current
                    		DESCRIPTION
                    			"加权公平排队规则tcp/udp方式的源地址,若为空表示any."
                    		::= { wfqListEntry 8 }

wfqSrcPort          	OBJECT-TYPE
                    		SYNTAX  INTEGER (0..65535)
                    		MAX-ACCESS  read-create
                    		STATUS  current
                    		DESCRIPTION
                    			"加权公平排队规则tcp/udp方式的源端口号,若为空表示any."
                    		::= { wfqListEntry 9 }

wfqDstIp            	OBJECT-TYPE
                    		SYNTAX  IpAddress
                    		MAX-ACCESS  read-create
                    		STATUS  current
                    		DESCRIPTION
                    			"加权公平排队排队规则tcp/udp方式的目的地址,若为空表示any."
                    		::= { wfqListEntry 10 }

wfqDstPort          	OBJECT-TYPE
                    		SYNTAX  INTEGER (0..65535)
                    		MAX-ACCESS  read-create
                    		STATUS  current
                    		DESCRIPTION
                    			"加权公平排队规则tcp/udp方式的目的端口号,若为空表示any."
                    		::= { wfqListEntry 11 }

wfqStatus           	OBJECT-TYPE
                    		SYNTAX  RowStatus
                    		MAX-ACCESS  read-create
                    		STATUS  current
                    		DESCRIPTION
                    			"加权公平排队列表行状态,用于增加,删除或修改一行的内容."
                    		::= { wfqListEntry 12 }

pqListTable         	OBJECT-TYPE
                    		SYNTAX  SEQUENCE OF  PqListEntry
                    		MAX-ACCESS  not-accessible
                    		STATUS  current
                    		DESCRIPTION
                    			"优先级列表."
                    		::= { mpQosMib 2 }

pqListEntry         	OBJECT-TYPE
                    		SYNTAX  PqListEntry
                    		MAX-ACCESS  not-accessible
                    		STATUS  current
                    		DESCRIPTION
                    			"优先级列表."
                    		INDEX  { pqIndex }
                    		::= { pqListTable 1 }

PqListEntry         	::= SEQUENCE {
                    			pqIndex                INTEGER,
                    			pqListNum              INTEGER,
                    			pqCtrlType             INTEGER,
                    			pqDefault              INTEGER,
                    			pqIfIndex              INTEGER,
                    			pqProtocol             INTEGER,
                    			pqPriority             INTEGER,
                    			pqProtType             INTEGER,
                    			pqProtValue            INTEGER,
                    			pqQueueHigh            INTEGER,
                    			pqQueueMedium          INTEGER,
                    			pqQueueNormal          INTEGER,
                    			pqQueueLow             INTEGER,
                    			pqStatus               RowStatus
                    	             }


pqIndex             	OBJECT-TYPE
                    		SYNTAX  INTEGER
                    		MAX-ACCESS  read-only
                    		STATUS  current
                    		DESCRIPTION
                    			"优先级列表的索引."
                    		::= { pqListEntry 1 }

pqListNum           	OBJECT-TYPE
                    		SYNTAX  INTEGER(1..16)
                    		MAX-ACCESS  read-create
                    		STATUS  current
                    		DESCRIPTION
                    			"优先级列表号."
                    		::= { pqListEntry 2 }

pqCtrlType          	OBJECT-TYPE
                    		SYNTAX  INTEGER {
                    			         defaultAndLimit(1),
                    			          interface(2),
                    			          protocol(3)
                    			        }
                    		MAX-ACCESS  read-create
                    		STATUS  current
                    		DESCRIPTION
                    			"优先级列表定义方式."
                    		::= { pqListEntry 3 }

pqDefault           	OBJECT-TYPE
                    		SYNTAX  INTEGER {
                    			         high(1),
                    			          medium(2),
                    			          normal(3),
                    			          low(4)
                    			        }
                    		MAX-ACCESS  read-create
                    		STATUS  current
                    		DESCRIPTION
                    			"优先级排队缺省级别."
							DEFVAL { normal }
                    		::= { pqListEntry 4 }

pqIfIndex           	OBJECT-TYPE
                    		SYNTAX  INTEGER
                    		MAX-ACCESS  read-create
                    		STATUS  current
                    		DESCRIPTION
                    			"优先级若是分配给通过接口的数据包,此处取值为该接口的接口索引."
                    		::= { pqListEntry 5 }

pqProtocol          	OBJECT-TYPE
                    		SYNTAX  INTEGER {
                    			         ip(1)
                    			        }
                    		MAX-ACCESS  read-create
                    		STATUS  current
                    		DESCRIPTION
                    			"优先级若是分配给协议,此处取值为协议类型."
                    		::= { pqListEntry 6 }

pqPriority          	OBJECT-TYPE
                    		SYNTAX  INTEGER {
                    			         high(1),
                    			          medium(2),
                    			          normal(3),
                    			          low(4)
                    			        }
                    		MAX-ACCESS  read-create
                    		STATUS  current
                    		DESCRIPTION
                    			"进入接口或协议的优先级级别."
							DEFVAL { normal }
                    		::= { pqListEntry 7 }

pqProtType          	OBJECT-TYPE
                    		SYNTAX  INTEGER {
                    			         fragments(1),
                    			          gt(2),
                    			          list(3),
                    			          lt(4),
                    			          tcp(5),
                    			          udp(6)
                    			        }
                    		MAX-ACCESS  read-create
                    		STATUS  current
                    		DESCRIPTION
                    			"优先级对应协议的附加选项."
                    		::= { pqListEntry 8 }

pqProtValue         	OBJECT-TYPE
                    		SYNTAX  INTEGER
                    		MAX-ACCESS  read-create
                    		STATUS  current
                    		DESCRIPTION
                    			"优先级对应协议附加选项取值.若是gt/lt/tcp/udp 那么范围是(0..65535),若是list那么范围是(1..2000)."
                    		::= { pqListEntry 9 }

pqQueueHigh         	OBJECT-TYPE
                    		SYNTAX  INTEGER(0..32767)
                    		MAX-ACCESS  read-create
                    		STATUS  current
                    		DESCRIPTION
                    			"cisco高优先级队列的队列深度."
							DEFVAL { 20 }
                    		::= { pqListEntry 10 }

pqQueueMedium       	OBJECT-TYPE
                    		SYNTAX  INTEGER(0..32767)
                    		MAX-ACCESS  read-create
                    		STATUS  current
                    		DESCRIPTION
                    			"cisco中优先级队列的队列深度."
							DEFVAL { 40 }
                    		::= { pqListEntry 11 }

pqQueueNormal       	OBJECT-TYPE
                    		SYNTAX  INTEGER(0..32767)
                    		MAX-ACCESS  read-create
                    		STATUS  current
                    		DESCRIPTION
                    			"cisco较低优先级队列的队列深度."
							DEFVAL { 60 }
                    		::= { pqListEntry 12 }

pqQueueLow          	OBJECT-TYPE
                    		SYNTAX  INTEGER(0..32767)
                    		MAX-ACCESS  read-create
                    		STATUS  current
                    		DESCRIPTION
                    			"cisco低优先级队列的队列深度."
							DEFVAL { 80 }
                    		::= { pqListEntry 13 }

pqStatus            	OBJECT-TYPE
                    		SYNTAX  RowStatus
                    		MAX-ACCESS  read-create
                    		STATUS  current
                    		DESCRIPTION
                    			"优先级列表的行状态,用于增加,删除或修改一行的内容."
                    		::= { pqListEntry 14 }


------------------------------------------------------------------------------
classMap            	OBJECT IDENTIFIER ::= { mpQosMib 3 }

classMapTable       	OBJECT-TYPE
                    		SYNTAX  SEQUENCE OF  ClassMapEntry
                    		MAX-ACCESS  not-accessible
                    		STATUS  current
                    		DESCRIPTION
                    			"分类列表."
                    		::= { classMap 1 }

classMapEntry       	OBJECT-TYPE
                    		SYNTAX  ClassMapEntry
                    		MAX-ACCESS  not-accessible
                    		STATUS  current
                    		DESCRIPTION
                    			"分类列表."
                    		INDEX  { classMapClassName }
                    		::= { classMapTable 1 }

ClassMapEntry       	::= SEQUENCE {
                    			classMapClassName      DisplayString,
                    			classMapMatchType      INTEGER,
                    			classMapRowStatus      RowStatus
                    	             }


classMapClassName   	OBJECT-TYPE
                    		SYNTAX  DisplayString(SIZE(0..32))
                    		MAX-ACCESS  read-create
                    		STATUS  current
                    		DESCRIPTION
                    			"分类列表条目的名称."
                    		::= { classMapEntry 1 }

classMapMatchType   	OBJECT-TYPE
                    		SYNTAX  INTEGER {
                    			         match-all(0),
                    			          match-any(1)
                    			        }
                    		MAX-ACCESS  read-create
                    		STATUS  current
                    		DESCRIPTION
                    			"匹配类型."
                    		::= { classMapEntry 2 }

classMapRowStatus   	OBJECT-TYPE
                    		SYNTAX  RowStatus
                    		MAX-ACCESS  read-create
                    		STATUS  current
                    		DESCRIPTION
                    			"分类列表的行状态."
                    		::= { classMapEntry 3 }

classMapAclTable    	OBJECT-TYPE
                    		SYNTAX  SEQUENCE OF   ClassMapAclEntry
                    		MAX-ACCESS  not-accessible
                    		STATUS  current
                    		DESCRIPTION
                    			"ACL分类列表."
                    		::= { classMap 10 }

classMapAclEntry    	OBJECT-TYPE
                    		SYNTAX  ClassMapAclEntry
                    		MAX-ACCESS  not-accessible
                    		STATUS  current
                    		DESCRIPTION
                    			"ACL分类列表."
                    		INDEX  { classMapAclClassName, classMapAclListName }
                    		::= { classMapAclTable 1 }

ClassMapAclEntry    	::= SEQUENCE {
                    			classMapAclClassName   DisplayString,
                    			classMapAclListName    DisplayString,
                    			classMapAclRowStatus   RowStatus
                    	             }


classMapAclClassName	OBJECT-TYPE
                    		SYNTAX  DisplayString(SIZE(0..32))
                    		MAX-ACCESS  read-create
                    		STATUS  current
                    		DESCRIPTION
                    			"ACL分类列表名称."
                    		::= { classMapAclEntry 1 }

classMapAclListName 	OBJECT-TYPE
                    		SYNTAX  DisplayString(SIZE(0..32))
                    		MAX-ACCESS  read-create
                    		STATUS  current
                    		DESCRIPTION
                    			"访问列表名称."
                    		::= { classMapAclEntry 2 }

classMapAclRowStatus	OBJECT-TYPE
                    		SYNTAX  RowStatus
                    		MAX-ACCESS  read-create
                    		STATUS  current
                    		DESCRIPTION
                    			"ACL分类列表的行状态."
                    		::= { classMapAclEntry 3 }

classMapInputIfTable	OBJECT-TYPE
                    		SYNTAX  SEQUENCE OF   ClassMapInputIfEntry
                    		MAX-ACCESS  not-accessible
                    		STATUS  current
                    		DESCRIPTION
                    			"输入接口分类列表."
                    		::= { classMap 20 }

classMapInputIfEntry	OBJECT-TYPE
                    		SYNTAX  ClassMapInputIfEntry
                    		MAX-ACCESS  not-accessible
                    		STATUS  current
                    		DESCRIPTION
                    			"输入接口分类列表."
                    		INDEX  { classMapInputIfClassName, classMapInputIfName }
                    		::= { classMapInputIfTable 1 }

ClassMapInputIfEntry	::= SEQUENCE {
                    			classMapInputIfClassName   DisplayString,
                    			classMapInputIfName    DisplayString,
                    			classMapInputIfRowStatus   RowStatus
                    	             }


classMapInputIfClassName	OBJECT-TYPE
                    		SYNTAX  DisplayString(SIZE(0..32))
                    		MAX-ACCESS  read-create
                    		STATUS  current
                    		DESCRIPTION
                    			"输入接口分类列表的名称."
                    		::= { classMapInputIfEntry 1 }

classMapInputIfName 	OBJECT-TYPE
                    		SYNTAX  DisplayString(SIZE(0..48))
                    		MAX-ACCESS  read-create
                    		STATUS  current
                    		DESCRIPTION
                    			"输入接口的名称."
                    		::= { classMapInputIfEntry 2 }

classMapInputIfRowStatus	OBJECT-TYPE
                    		SYNTAX  RowStatus
                    		MAX-ACCESS  read-create
                    		STATUS  current
                    		DESCRIPTION
                    			"输入接口分类列表的行状态."
                    		::= { classMapInputIfEntry 3 }

classMapIpPrecedenceTable	OBJECT-TYPE
                    		SYNTAX  SEQUENCE OF   ClassMapIpPrecedenceEntry
                    		MAX-ACCESS  not-accessible
                    		STATUS  current
                    		DESCRIPTION
                    			"IP优先级分类列表."
                    		::= { classMap 30 }

classMapIpPrecedenceEntry	OBJECT-TYPE
                    		SYNTAX  ClassMapIpPrecedenceEntry
                    		MAX-ACCESS  not-accessible
                    		STATUS  current
                    		DESCRIPTION
                    			"IP优先级分类列表."
                    		INDEX  { classMapIpPrecedenceClassName, classMapIpPrecedenceValue }
                    		::= { classMapIpPrecedenceTable 1 }

ClassMapIpPrecedenceEntry	::= SEQUENCE {
                    			classMapIpPrecedenceClassName   DisplayString,
                    			classMapIpPrecedenceValue   INTEGER,
                    			classMapIpPrecedenceRowStatus   RowStatus
                    	             }


classMapIpPrecedenceClassName	OBJECT-TYPE
                    		SYNTAX  DisplayString(SIZE(0..32))
                    		MAX-ACCESS  read-create
                    		STATUS  current
                    		DESCRIPTION
                    			"IP优先级分类列表的名称."
                    		::= { classMapIpPrecedenceEntry 1 }

classMapIpPrecedenceValue	OBJECT-TYPE
                    		SYNTAX  INTEGER(0..7)
                    		MAX-ACCESS  read-create
                    		STATUS  current
                    		DESCRIPTION
                    			"IP优先级的值."
                    		::= { classMapIpPrecedenceEntry 2 }

classMapIpPrecedenceRowStatus	OBJECT-TYPE
                    		SYNTAX  RowStatus
                    		MAX-ACCESS  read-create
                    		STATUS  current
                    		DESCRIPTION
                    			"IP优先级分类列表的行状态."
                    		::= { classMapIpPrecedenceEntry 3 }

classMapIpDscpTable 	OBJECT-TYPE
                    		SYNTAX  SEQUENCE OF   ClassMapIpDscpEntry
                    		MAX-ACCESS  not-accessible
                    		STATUS  current
                    		DESCRIPTION
                    			"IP DSCP分类列表."
                    		::= { classMap 40 }

classMapIpDscpEntry 	OBJECT-TYPE
                    		SYNTAX  ClassMapIpDscpEntry
                    		MAX-ACCESS  not-accessible
                    		STATUS  current
                    		DESCRIPTION
                    			"IP DSCP分类列表."
                    		INDEX  { classMapIpDscpClassName, classMapIpDscpValue }
                    		::= { classMapIpDscpTable 1 }

ClassMapIpDscpEntry 	::= SEQUENCE {
                    			classMapIpDscpClassName   DisplayString,
                    			classMapIpDscpValue    INTEGER,
                    			classMapIpDscpRowStatus   RowStatus
                    	             }


classMapIpDscpClassName	OBJECT-TYPE
                    		SYNTAX  DisplayString(SIZE(0..32))
                    		MAX-ACCESS  read-create
                    		STATUS  current
                    		DESCRIPTION
                    			"IP DSCP分类列表的名称."
                    		::= { classMapIpDscpEntry 1 }

classMapIpDscpValue 	OBJECT-TYPE
                    		SYNTAX  INTEGER(0..63)
                    		MAX-ACCESS  read-create
                    		STATUS  current
                    		DESCRIPTION
                    			"IP DSCP的值."
                    		::= { classMapIpDscpEntry 2 }

classMapIpDscpRowStatus	OBJECT-TYPE
                    		SYNTAX  RowStatus
                    		MAX-ACCESS  read-create
                    		STATUS  current
                    		DESCRIPTION
                    			"IP DSCP分类列表的行状态."
                    		::= { classMapIpDscpEntry 3 }

classMapMplsExpTable	OBJECT-TYPE
                    		SYNTAX  SEQUENCE OF   ClassMapMplsExpEntry
                    		MAX-ACCESS  not-accessible
                    		STATUS  current
                    		DESCRIPTION
                    			"MPLS EXP分类列表."
                    		::= { classMap 50 }

classMapMplsExpEntry	OBJECT-TYPE
                    		SYNTAX  ClassMapMplsExpEntry
                    		MAX-ACCESS  not-accessible
                    		STATUS  current
                    		DESCRIPTION
                    			"MPLS EXP分类列表."
                    		INDEX  { classMapMplsExpClassName, classMapMplsExpValue }
                    		::= { classMapMplsExpTable 1 }

ClassMapMplsExpEntry	::= SEQUENCE {
                    			classMapMplsExpClassName   DisplayString,
                    			classMapMplsExpValue   INTEGER,
                    			classMapMplsExpRowStatus   RowStatus
                    	             }


classMapMplsExpClassName	OBJECT-TYPE
                    		SYNTAX  DisplayString(SIZE(0..32))
                    		MAX-ACCESS  read-create
                    		STATUS  current
                    		DESCRIPTION
                    			"MPLS EXP分类列表的名称."
                    		::= { classMapMplsExpEntry 1 }

classMapMplsExpValue	OBJECT-TYPE
                    		SYNTAX  INTEGER(0..7)
                    		MAX-ACCESS  read-create
                    		STATUS  current
                    		DESCRIPTION
                    			"MPLS EXP的值."
                    		::= { classMapMplsExpEntry 2 }

classMapMplsExpRowStatus	OBJECT-TYPE
                    		SYNTAX  RowStatus
                    		MAX-ACCESS  read-create
                    		STATUS  current
                    		DESCRIPTION
                    			"MPLS EXP分类列表的行状态."
                    		::= { classMapMplsExpEntry 3 }

classMapProtocolTable	OBJECT-TYPE
                    		SYNTAX  SEQUENCE OF   ClassMapProtocolEntry
                    		MAX-ACCESS  not-accessible
                    		STATUS  current
                    		DESCRIPTION
                    			"协议分类列表."
                    		::= { classMap 60 }

classMapProtocolEntry	OBJECT-TYPE
                    		SYNTAX  ClassMapProtocolEntry
                    		MAX-ACCESS  not-accessible
                    		STATUS  current
                    		DESCRIPTION
                    			"协议分类列表."
                    		INDEX  { classMapProtocolClassName, classMapProtocolName }
                    		::= { classMapProtocolTable 1 }

ClassMapProtocolEntry	::= SEQUENCE {
                    			classMapProtocolClassName   DisplayString,
                    			classMapProtocolName   DisplayString,
                    			classMapProtocolRowStatus   RowStatus
                    	             }


classMapProtocolClassName	OBJECT-TYPE
                    		SYNTAX  DisplayString(SIZE(0..32))
                    		MAX-ACCESS  read-create
                    		STATUS  current
                    		DESCRIPTION
                    			"协议分类列表的名称."
                    		::= { classMapProtocolEntry 1 }

classMapProtocolName	OBJECT-TYPE
                    		SYNTAX  DisplayString(SIZE(0..32))
                    		MAX-ACCESS  read-create
                    		STATUS  current
                    		DESCRIPTION
                    			"协议的名称."
                    		::= { classMapProtocolEntry 2 }

classMapProtocolRowStatus	OBJECT-TYPE
                    		SYNTAX  RowStatus
                    		MAX-ACCESS  read-create
                    		STATUS  current
                    		DESCRIPTION
                    			"协议分类列表的行状态."
                    		::= { classMapProtocolEntry 3 }

classMapNestTable   	OBJECT-TYPE
                    		SYNTAX  SEQUENCE OF   ClassMapNestEntry
                    		MAX-ACCESS  not-accessible
                    		STATUS  current
                    		DESCRIPTION
                    			"嵌套分类列表."
                    		::= { classMap 70 }

classMapNestEntry   	OBJECT-TYPE
                    		SYNTAX  ClassMapNestEntry
                    		MAX-ACCESS  not-accessible
                    		STATUS  current
                    		DESCRIPTION
                    			"嵌套分类列表."
                    		INDEX  { classMapNestClassName, classMapNestName }
                    		::= { classMapNestTable 1 }

ClassMapNestEntry   	::= SEQUENCE {
                    			classMapNestClassName   DisplayString,
                    			classMapNestName       DisplayString,
                    			classMapNestRowStatus   RowStatus
                    	             }


classMapNestClassName	OBJECT-TYPE
                    		SYNTAX  DisplayString(SIZE(0..32))
                    		MAX-ACCESS  read-create
                    		STATUS  current
                    		DESCRIPTION
                    			"嵌套分类列表的名称."
                    		::= { classMapNestEntry 1 }

classMapNestName    	OBJECT-TYPE
                    		SYNTAX  DisplayString(SIZE(0..32))
                    		MAX-ACCESS  read-create
                    		STATUS  current
                    		DESCRIPTION
                    			"所嵌入的分类列表的名称."
                    		::= { classMapNestEntry 2 }

classMapNestRowStatus	OBJECT-TYPE
                    		SYNTAX  RowStatus
                    		MAX-ACCESS  read-create
                    		STATUS  current
                    		DESCRIPTION
                    			"嵌套分类列表的行状态."
                    		::= { classMapNestEntry 3 }


------------------------------------------------------------------------------
policyMap           	OBJECT IDENTIFIER ::= { mpQosMib 4 }

policyMapTable      	OBJECT-TYPE
                    		SYNTAX  SEQUENCE OF   PolicyMapEntry
                    		MAX-ACCESS  not-accessible
                    		STATUS  current
                    		DESCRIPTION
                    			"策略列表."
                    		::= { policyMap 10 }

policyMapEntry      	OBJECT-TYPE
                    		SYNTAX  PolicyMapEntry
                    		MAX-ACCESS  not-accessible
                    		STATUS  current
                    		DESCRIPTION
                    			"策略列表."
                    		INDEX  { policyMapName }
                    		::= { policyMapTable 1 }

PolicyMapEntry      	::= SEQUENCE {
                    			policyMapName          DisplayString,
                    			policyMapRowStatus     RowStatus
                    	             }


policyMapName       	OBJECT-TYPE
                    		SYNTAX  DisplayString(SIZE(0..32))
                    		MAX-ACCESS  read-create
                    		STATUS  current
                    		DESCRIPTION
                    			"策略名."
                    		::= { policyMapEntry 1 }

policyMapRowStatus  	OBJECT-TYPE
                    		SYNTAX  RowStatus
                    		MAX-ACCESS  read-create
                    		STATUS  current
                    		DESCRIPTION
                    			"策略列表的行状态,用于增加,删除或修改一行的内容."
                    		::= { policyMapEntry 2 }

policyClassTable    	OBJECT-TYPE
                    		SYNTAX  SEQUENCE OF  PolicyClassEntry
                    		MAX-ACCESS  not-accessible
                    		STATUS  current
                    		DESCRIPTION
                    			"策略分类列表."
                    		::= { policyMap 20 }

policyClassEntry    	OBJECT-TYPE
                    		SYNTAX  PolicyClassEntry
                    		MAX-ACCESS  not-accessible
                    		STATUS  current
                    		DESCRIPTION
                    			"策略分类列表."
                    		INDEX  { policyClassPolicyName, policyClassClassName }
                    		::= { policyClassTable 1 }

PolicyClassEntry    	::= SEQUENCE {
                    			policyClassPolicyName   DisplayString,
                    			policyClassClassName   DisplayString,
                    			policyClassBandWidthKbps   INTEGER,
                    			policyClassBandWidthTotal   INTEGER,
                    			policyClassBandWidthPercent   INTEGER,
                    			policyClassPriorityBps   INTEGER,
                    			policyClassPriorityPercent   INTEGER,
                    			policyClassWredEnable   INTEGER,
                    			policyClassWredWeight   INTEGER,
                    			policyClassWredMinThreshold0   INTEGER,
                    			policyClassWredMaxThreshold0   INTEGER,
                    			policyClassWredMinThreshold1   INTEGER,
                    			policyClassWredMaxThreshold1   INTEGER,
                    			policyClassWredMinThreshold2   INTEGER,
                    			policyClassWredMaxThreshold2   INTEGER,
                    			policyClassWredMinThreshold3   INTEGER,
                    			policyClassWredMaxThreshold3   INTEGER,
                    			policyClassWredMinThreshold4   INTEGER,
                    			policyClassWredMaxThreshold4   INTEGER,
                    			policyClassWredMinThreshold5   INTEGER,
                    			policyClassWredMaxThreshold5   INTEGER,
                    			policyClassWredMinThreshold6   INTEGER,
                    			policyClassWredMaxThreshold6   INTEGER,
                    			policyClassWredMinThreshold7   INTEGER,
                    			policyClassWredMaxThreshold7   INTEGER,
                    			policyClassSetIpPrecedence   INTEGER,
                    			policyClassSetIpDscp   INTEGER,
                    			policyClassSetMplsImp   INTEGER,
                    			policyClassSetMplsTop   INTEGER,
                    			policyClassNestName    DisplayString,
                    			policyClassRowStatus   RowStatus
                    	             }


policyClassPolicyName	OBJECT-TYPE
                    		SYNTAX  DisplayString(SIZE(0..32))
                    		MAX-ACCESS  read-create
                    		STATUS  current
                    		DESCRIPTION
                    			"策略名."
                    		::= { policyClassEntry 1 }

policyClassClassName	OBJECT-TYPE
                    		SYNTAX  DisplayString(SIZE(0..32))
                    		MAX-ACCESS  read-create
                    		STATUS  current
                    		DESCRIPTION
                    			"策略对应分类名."
                    		::= { policyClassEntry 2 }

policyClassBandWidthKbps	OBJECT-TYPE
                    		SYNTAX  INTEGER(0..100000)
                    		MAX-ACCESS  read-create
                    		STATUS  current
                    		DESCRIPTION
                    			"带宽速率,以Kbit/s为单位.0表示该项未设置."
                    		::= { policyClassEntry 3 }

policyClassBandWidthTotal	OBJECT-TYPE
                    		SYNTAX  INTEGER(0..100000)
                    		MAX-ACCESS  read-create
                    		STATUS  current
                    		DESCRIPTION
                    			"接口总带宽,以Kbit/s为单位.0表示该项未设置."
                    		::= { policyClassEntry 4 }

policyClassBandWidthPercent	OBJECT-TYPE
                    		SYNTAX  INTEGER(0..100)
                    		MAX-ACCESS  read-create
                    		STATUS  current
                    		DESCRIPTION
                    			"带宽占用率.0表示该项未设置."
                    		::= { policyClassEntry 5 }

policyClassPriorityBps	OBJECT-TYPE
                    		SYNTAX  INTEGER(0..10000000)
                    		MAX-ACCESS  read-create
                    		STATUS  current
                    		DESCRIPTION
                    			"优先级速率,以Byte/s为单位.0表示该项未设置."
                    		::= { policyClassEntry 6 }

policyClassPriorityPercent	OBJECT-TYPE
                    		SYNTAX  INTEGER(0..100)
                    		MAX-ACCESS  read-create
                    		STATUS  current
                    		DESCRIPTION
                    			"优先级占有率.0表示该项未设置."
                    		::= { policyClassEntry 7 }

policyClassWredEnable	OBJECT-TYPE
                    		SYNTAX  INTEGER(0..1) {
                    			         disable(0),
                    			          enable(1)
                    			        }
                    		MAX-ACCESS  read-create
                    		STATUS  current
                    		DESCRIPTION
                    			"是否启动加权随机早检测."
                    		::= { policyClassEntry 8 }

policyClassWredWeight	OBJECT-TYPE
                    		SYNTAX  INTEGER(0..12)
                    		MAX-ACCESS  read-create
                    		STATUS  current
                    		DESCRIPTION
                    			"策略加权随机早检测权重.0表示该项未设置."
                    		::= { policyClassEntry 9 }

policyClassWredMinThreshold0	OBJECT-TYPE
                    		SYNTAX  INTEGER(0..32767)
                    		MAX-ACCESS  read-create
                    		STATUS  current
                    		DESCRIPTION
                    			"Precedence 0所对应的策略加权随机早检测最小字节数.0表示未设置."
                    		::= { policyClassEntry 10 }

policyClassWredMaxThreshold0	OBJECT-TYPE
                    		SYNTAX  INTEGER(0..32767)
                    		MAX-ACCESS  read-create
                    		STATUS  current
                    		DESCRIPTION
                    			"Precedence 0所对应的策略加权随机早检测最大字节数.0表示未设置."
                    		::= { policyClassEntry 11 }

policyClassWredMinThreshold1	OBJECT-TYPE
                    		SYNTAX  INTEGER(0..32767)
                    		MAX-ACCESS  read-create
                    		STATUS  current
                    		DESCRIPTION
                    			"Precedence 1所对应的策略加权随机早检测最小字节数.0表示未设置."
                    		::= { policyClassEntry 12 }

policyClassWredMaxThreshold1	OBJECT-TYPE
                    		SYNTAX  INTEGER(0..32767)
                    		MAX-ACCESS  read-create
                    		STATUS  current
                    		DESCRIPTION
                    			"Precedence 1所对应的策略加权随机早检测最大字节数.0表示未设置."
                    		::= { policyClassEntry 13 }

policyClassWredMinThreshold2	OBJECT-TYPE
                    		SYNTAX  INTEGER(0..32767)
                    		MAX-ACCESS  read-create
                    		STATUS  current
                    		DESCRIPTION
                    			"Precedence 2所对应的策略加权随机早检测最小字节数.0表示未设置."
                    		::= { policyClassEntry 14 }

policyClassWredMaxThreshold2	OBJECT-TYPE
                    		SYNTAX  INTEGER(0..32767)
                    		MAX-ACCESS  read-create
                    		STATUS  current
                    		DESCRIPTION
                    			"Precedence 2所对应的策略加权随机早检测最大字节数.0表示未设置."
                    		::= { policyClassEntry 15 }

policyClassWredMinThreshold3	OBJECT-TYPE
                    		SYNTAX  INTEGER(0..32767)
                    		MAX-ACCESS  read-create
                    		STATUS  current
                    		DESCRIPTION
                    			"Precedence 3所对应的策略加权随机早检测最小字节数.0表示未设置."
                    		::= { policyClassEntry 16 }

policyClassWredMaxThreshold3	OBJECT-TYPE
                    		SYNTAX  INTEGER(0..32767)
                    		MAX-ACCESS  read-create
                    		STATUS  current
                    		DESCRIPTION
                    			"Precedence 3所对应的策略加权随机早检测最大字节数.0表示未设置."
                    		::= { policyClassEntry 17 }

policyClassWredMinThreshold4	OBJECT-TYPE
                    		SYNTAX  INTEGER(0..32767)
                    		MAX-ACCESS  read-create
                    		STATUS  current
                    		DESCRIPTION
                    			"Precedence 4所对应的策略加权随机早检测最小字节数.0表示未设置."
                    		::= { policyClassEntry 18 }

policyClassWredMaxThreshold4	OBJECT-TYPE
                    		SYNTAX  INTEGER(0..32767)
                    		MAX-ACCESS  read-create
                    		STATUS  current
                    		DESCRIPTION
                    			"Precedence 4所对应的策略加权随机早检测最大字节数.0表示未设置."
                    		::= { policyClassEntry 19 }

policyClassWredMinThreshold5	OBJECT-TYPE
                    		SYNTAX  INTEGER(0..32767)
                    		MAX-ACCESS  read-create
                    		STATUS  current
                    		DESCRIPTION
                    			"Precedence 5所对应的策略加权随机早检测最小字节数.0表示未设置."
                    		::= { policyClassEntry 20 }

policyClassWredMaxThreshold5	OBJECT-TYPE
                    		SYNTAX  INTEGER(0..32767)
                    		MAX-ACCESS  read-create
                    		STATUS  current
                    		DESCRIPTION
                    			"Precedence 5所对应的策略加权随机早检测最大字节数.0表示未设置."
                    		::= { policyClassEntry 21 }

policyClassWredMinThreshold6	OBJECT-TYPE
                    		SYNTAX  INTEGER(0..32767)
                    		MAX-ACCESS  read-create
                    		STATUS  current
                    		DESCRIPTION
                    			"Precedence 6所对应的策略加权随机早检测最小字节数.0表示未设置."
                    		::= { policyClassEntry 22 }

policyClassWredMaxThreshold6	OBJECT-TYPE
                    		SYNTAX  INTEGER(0..32767)
                    		MAX-ACCESS  read-create
                    		STATUS  current
                    		DESCRIPTION
                    			"Precedence 6所对应的策略加权随机早检测最大字节数.0表示未设置."
                    		::= { policyClassEntry 23 }

policyClassWredMinThreshold7	OBJECT-TYPE
                    		SYNTAX  INTEGER(0..32767)
                    		MAX-ACCESS  read-create
                    		STATUS  current
                    		DESCRIPTION
                    			"Precedence 7所对应的策略加权随机早检测最小字节数.0表示未设置."
                    		::= { policyClassEntry 24 }

policyClassWredMaxThreshold7	OBJECT-TYPE
                    		SYNTAX  INTEGER(0..32767)
                    		MAX-ACCESS  read-create
                    		STATUS  current
                    		DESCRIPTION
                    			"Precedence 7所对应的策略加权随机早检测最大字节数.0表示未设置."
                    		::= { policyClassEntry 25 }

policyClassSetIpPrecedence	OBJECT-TYPE
                    		SYNTAX  INTEGER(-1..7)
                    		MAX-ACCESS  read-create
                    		STATUS  current
                    		DESCRIPTION
                    			"设置IP Precedence的值.-1表示该项未设置."
                    		::= { policyClassEntry 26 }

policyClassSetIpDscp	OBJECT-TYPE
                    		SYNTAX  INTEGER(-1..63)
                    		MAX-ACCESS  read-create
                    		STATUS  current
                    		DESCRIPTION
                    			"设置IP DSCP的值.-1表示该项未设置."
                    		::= { policyClassEntry 27 }

policyClassSetMplsImp	OBJECT-TYPE
                    		SYNTAX  INTEGER(-1..7)
                    		MAX-ACCESS  read-create
                    		STATUS  current
                    		DESCRIPTION
                    			"设置MPLS experimental imposition的值.-1表示该项未设置."
                    		::= { policyClassEntry 28 }

policyClassSetMplsTop	OBJECT-TYPE
                    		SYNTAX  INTEGER(-1..7)
                    		MAX-ACCESS  read-create
                    		STATUS  current
                    		DESCRIPTION
                    			"设置MPLS experimental topmost的值.-1表示该项未设置."
                    		::= { policyClassEntry 29 }

policyClassNestName 	OBJECT-TYPE
                    		SYNTAX  DisplayString(SIZE(0..32))
                    		MAX-ACCESS  read-create
                    		STATUS  current
                    		DESCRIPTION
                    			"所嵌入的策略名."
                    		::= { policyClassEntry 30 }

policyClassRowStatus	OBJECT-TYPE
                    		SYNTAX  RowStatus
                    		MAX-ACCESS  read-create
                    		STATUS  current
                    		DESCRIPTION
                    			"策略列表的行状态,用于增加,删除或修改一行的内容."
                    		::= { policyClassEntry 31 }


------------------------------------------------------------------------------
priorityList        	OBJECT IDENTIFIER ::= { mpQosMib 5 }

priorityListTable   	OBJECT-TYPE
                    		SYNTAX  SEQUENCE OF  PriorityListEntry
                    		MAX-ACCESS  not-accessible
                    		STATUS  current
                    		DESCRIPTION
                    			"优先级队列."
                    		::= { priorityList 1 }

priorityListEntry   	OBJECT-TYPE
                    		SYNTAX  PriorityListEntry
                    		MAX-ACCESS  not-accessible
                    		STATUS  current
                    		DESCRIPTION
                    			"优先级队列."
                    		INDEX  { priorityListNo }
                    		::= { priorityListTable 1 }

PriorityListEntry   	::= SEQUENCE {
                    			priorityListNo         INTEGER,
                    			priorityListDefQType   INTEGER,
                    			priorityListQHigh      INTEGER,
                    			priorityListQMedium    INTEGER,
                    			priorityListQNormal    INTEGER,
                    			priorityListQLow       INTEGER,
                    			priorityListWredGrpName   DisplayString,
                    			priorityListDropType   INTEGER,
                    			priorityListStatus     RowStatus
                    	             }


priorityListNo      	OBJECT-TYPE
                    		SYNTAX  INTEGER (1..16)
                    		MAX-ACCESS  read-create
                    		STATUS  current
                    		DESCRIPTION
                    			"优先级队列号."
                    		::= { priorityListEntry 1 }

priorityListDefQType	OBJECT-TYPE
                    		SYNTAX  INTEGER {
                    			         high(1),
                    			          medium(2),
                    			          normal(3),
                    			          low(4)
                    			        }
                    		MAX-ACCESS  read-create
                    		STATUS  current
                    		DESCRIPTION
                    			"优先级队列确省队列类型."
                    		::= { priorityListEntry 2 }

priorityListQHigh   	OBJECT-TYPE
                    		SYNTAX  INTEGER (0..15000)
                    		MAX-ACCESS  read-create
                    		STATUS  current
                    		DESCRIPTION
                    			"高优先级队列字节数."
                    		::= { priorityListEntry 3 }

priorityListQMedium 	OBJECT-TYPE
                    		SYNTAX  INTEGER (0..32767)
                    		MAX-ACCESS  read-create
                    		STATUS  current
                    		DESCRIPTION
                    			"中优先级队列字节数."
                    		::= { priorityListEntry 4 }

priorityListQNormal 	OBJECT-TYPE
                    		SYNTAX  INTEGER (0..45000)
                    		MAX-ACCESS  read-create
                    		STATUS  current
                    		DESCRIPTION
                    			"一般优先级队列字节数."
                    		::= { priorityListEntry 5 }

priorityListQLow    	OBJECT-TYPE
                    		SYNTAX  INTEGER (0..65535)
                    		MAX-ACCESS  read-create
                    		STATUS  current
                    		DESCRIPTION
                    			"低优先级队列字节数."
                    		::= { priorityListEntry 6 }

priorityListWredGrpName	OBJECT-TYPE
                    		SYNTAX  DisplayString
                    		MAX-ACCESS  read-create
                    		STATUS  current
                    		DESCRIPTION
                    			"优先级队列对应加权优先级组名称."
                    		::= { priorityListEntry 7 }

priorityListDropType	OBJECT-TYPE
                    		SYNTAX  INTEGER {
                    			         random-detect(1),
                    			          tailed-dropped(2)
                    			        }
                    		MAX-ACCESS  read-create
                    		STATUS  current
                    		DESCRIPTION
                    			"优先级队列丢弃类型."
                    		::= { priorityListEntry 8 }

priorityListStatus  	OBJECT-TYPE
                    		SYNTAX  RowStatus
                    		MAX-ACCESS  read-create
                    		STATUS  current
                    		DESCRIPTION
                    			"优先级队列的行状态,用于增加,删除或修改一行的内容."
                    		::= { priorityListEntry 9 }

priorityListRuleTable	OBJECT-TYPE
                    		SYNTAX  SEQUENCE OF  PriorityListRuleEntry
                    		MAX-ACCESS  not-accessible
                    		STATUS  current
                    		DESCRIPTION
                    			"优先级队列规则."
                    		::= { priorityList 2 }

priorityListRuleEntry	OBJECT-TYPE
                    		SYNTAX  PriorityListRuleEntry
                    		MAX-ACCESS  not-accessible
                    		STATUS  current
                    		DESCRIPTION
                    			"优先级队列规则."
                    		INDEX  { priorityListNoIndex,  priorityListRuleIndex }
                    		::= { priorityListRuleTable 1 }

PriorityListRuleEntry	::= SEQUENCE {
                    			priorityListNoIndex    INTEGER,
                    			priorityListRuleIndex   INTEGER,
                    			priorityListRuleType   INTEGER,
                    			priorityListRulePriType   INTEGER,
                    			priorityListforIntIfIndex   INTEGER,
                    			priorityListProtocolType   INTEGER,
                    			priorityListClassFlag   INTEGER,
                    			priorityListGtSize     INTEGER,
                    			priorityListLtSize     INTEGER,
                    			priorityListAccListNo   INTEGER,
                    			priorityListTCPPort    INTEGER,
                    			priorityListUDPPort    INTEGER,
                    			priorityListRuleStatus   RowStatus
                    	             }


priorityListNoIndex 	OBJECT-TYPE
                    		SYNTAX  INTEGER (1..16)
                    		MAX-ACCESS  read-only
                    		STATUS  current
                    		DESCRIPTION
                    			"优先级队列号."
                    		::= { priorityListRuleEntry 1 }

priorityListRuleIndex	OBJECT-TYPE
                    		SYNTAX  INTEGER
                    		MAX-ACCESS  read-create
                    		STATUS  current
                    		DESCRIPTION
                    			"优先级队列规则索引."
                    		::= { priorityListRuleEntry 2 }

priorityListRuleType	OBJECT-TYPE
                    		SYNTAX  INTEGER {
                    			         interface(1),
                    			          protocol(2)
                    			        }
                    		MAX-ACCESS  read-create
                    		STATUS  current
                    		DESCRIPTION
                    			"优先级队列规则类型."
                    		::= { priorityListRuleEntry 3 }

priorityListRulePriType	OBJECT-TYPE
                    		SYNTAX  INTEGER {
                    			         high(1),
                    			          medium(2),
                    			          normal(3),
                    			          low(4)
                    			        }
                    		MAX-ACCESS  read-create
                    		STATUS  current
                    		DESCRIPTION
                    			"优先级队列规则优先级类型."
                    		::= { priorityListRuleEntry 4 }

priorityListforIntIfIndex	OBJECT-TYPE
                    		SYNTAX  INTEGER
                    		MAX-ACCESS  read-create
                    		STATUS  current
                    		DESCRIPTION
                    			"优先级队列规则对应接口的接口索引."
                    		::= { priorityListRuleEntry 5 }

priorityListProtocolType	OBJECT-TYPE
                    		SYNTAX  INTEGER {
                    			         ip(1),
                    			          arp(2),
                    			          llx(3)
                    			        }
                    		MAX-ACCESS  read-create
                    		STATUS  current
                    		DESCRIPTION
                    			"优先级队列规则协议类型.为IP则可配置ClassFlag"
                    		::= { priorityListRuleEntry 6 }

priorityListClassFlag	OBJECT-TYPE
                    		SYNTAX  INTEGER {
                    			         fragments(1),
                    			          gt(2),
                    			          list(3),
                    			          lt(4),
                    			          tcp(5),
                    			          udp(6)
                    			        }
                    		MAX-ACCESS  read-create
                    		STATUS  current
                    		DESCRIPTION
                    			"优先级队列规则分类标记."
                    		::= { priorityListRuleEntry 7 }

priorityListGtSize  	OBJECT-TYPE
                    		SYNTAX  INTEGER (0..65535)
                    		MAX-ACCESS  read-create
                    		STATUS  current
                    		DESCRIPTION
                    			"优先级队列规则：报文大于此字节数放入指定队列."
                    		::= { priorityListRuleEntry 8 }

priorityListLtSize  	OBJECT-TYPE
                    		SYNTAX  INTEGER (0..65535)
                    		MAX-ACCESS  read-create
                    		STATUS  current
                    		DESCRIPTION
                    			"优先级队列规则：报文小于此字节数放入指定队列."
                    		::= { priorityListRuleEntry 9 }

priorityListAccListNo	OBJECT-TYPE
                    		SYNTAX  INTEGER (1..2000)
                    		MAX-ACCESS  read-create
                    		STATUS  current
                    		DESCRIPTION
                    			"优先级队列规则对应访问控制列表号."
                    		::= { priorityListRuleEntry 10 }

priorityListTCPPort 	OBJECT-TYPE
                    		SYNTAX  INTEGER (0..65535)
                    		MAX-ACCESS  read-create
                    		STATUS  current
                    		DESCRIPTION
                    			"优先级队列规则TCP端口号."
                    		::= { priorityListRuleEntry 11 }

priorityListUDPPort 	OBJECT-TYPE
                    		SYNTAX  INTEGER (0..65535)
                    		MAX-ACCESS  read-create
                    		STATUS  current
                    		DESCRIPTION
                    			"优先级队列规则UDP端口号."
                    		::= { priorityListRuleEntry 12 }

priorityListRuleStatus	OBJECT-TYPE
                    		SYNTAX  RowStatus
                    		MAX-ACCESS  read-create
                    		STATUS  current
                    		DESCRIPTION
                    			"优先级队列规则列表的行状态,用于增加,删除或修改一行的内容."
                    		::= { priorityListRuleEntry 13 }


------------------------------------------------------------------------------
customList          	OBJECT IDENTIFIER ::= { mpQosMib 6 }

customListTable     	OBJECT-TYPE
                    		SYNTAX  SEQUENCE OF  CustomListEntry
                    		MAX-ACCESS  not-accessible
                    		STATUS  current
                    		DESCRIPTION
                    			"自定义队列."
                    		::= { customList 1 }

customListEntry     	OBJECT-TYPE
                    		SYNTAX  CustomListEntry
                    		MAX-ACCESS  not-accessible
                    		STATUS  current
                    		DESCRIPTION
                    			"自定义队列."
                    		INDEX  { customListNo }
                    		::= { customListTable 1 }

CustomListEntry     	::= SEQUENCE {
                    			customListNo           INTEGER,
                    			customListDefNo        INTEGER,
                    			customListWredName     DisplayString,
                    			customListDropType     INTEGER,
                    			customListStatus       RowStatus
                    	             }


customListNo        	OBJECT-TYPE
                    		SYNTAX  INTEGER (1..16)
                    		MAX-ACCESS  read-create
                    		STATUS  current
                    		DESCRIPTION
                    			"自定义队列号."
                    		::= { customListEntry 1 }

customListDefNo     	OBJECT-TYPE
                    		SYNTAX  INTEGER (0..16)
                    		MAX-ACCESS  read-create
                    		STATUS  current
                    		DESCRIPTION
                    			"自定义队列缺省规则号."
                    		::= { customListEntry 2 }

customListWredName  	OBJECT-TYPE
                    		SYNTAX  DisplayString
                    		MAX-ACCESS  read-create
                    		STATUS  current
                    		DESCRIPTION
                    			"自定义队列的加权优先级队列名."
                    		::= { customListEntry 3 }

customListDropType  	OBJECT-TYPE
                    		SYNTAX  INTEGER {
                    			         random-detect(1),
                    			          tailed-dropped(2)
                    			        }
                    		MAX-ACCESS  read-create
                    		STATUS  current
                    		DESCRIPTION
                    			"自定义队列丢弃方式."
                    		::= { customListEntry 4 }

customListStatus    	OBJECT-TYPE
                    		SYNTAX  RowStatus
                    		MAX-ACCESS  read-create
                    		STATUS  current
                    		DESCRIPTION
                    			"自定义队列的行状态,用于增加,删除或修改一行的内容."
                    		::= { customListEntry 5 }

customListRuleTable 	OBJECT-TYPE
                    		SYNTAX  SEQUENCE OF  CustomListRuleEntry
                    		MAX-ACCESS  not-accessible
                    		STATUS  current
                    		DESCRIPTION
                    			"自定义队列规则."
                    		::= { customList 2 }

customListRuleEntry 	OBJECT-TYPE
                    		SYNTAX  CustomListRuleEntry
                    		MAX-ACCESS  not-accessible
                    		STATUS  current
                    		DESCRIPTION
                    			"自定义队列规则."
                    		INDEX  { customListNoIndex,  customListIndex }
                    		::= { customListRuleTable 1 }

CustomListRuleEntry 	::= SEQUENCE {
                    			customListNoIndex      INTEGER,
                    			customListIndex        INTEGER,
                    			customListICMP         INTEGER,
                    			customListIGMP         INTEGER,
                    			customListQNo          INTEGER,
                    			customListFragPktQNo   INTEGER,
                    			customListPktEtSize    INTEGER,
                    			customListPktGtSize    INTEGER,
                    			customListPktLtSize    INTEGER,
                    			customListIpSrcAddr    IpAddress,
                    			customListIpSrcAddrMask   IpAddress,
                    			customListIpDestAddr   IpAddress,
                    			customListIpDestAddrMask   IpAddress,
                    			customListAccListNo    INTEGER,
                    			customListQByteCount   INTEGER,
                    			customListQLimit       INTEGER,
                    			customListTCPSrcAddr   IpAddress,
                    			customListTCPSrcAddrMask   IpAddress,
                    			customListTCPSrcPort   INTEGER,
                    			customListTCPDestAddr   IpAddress,
                    			customListTCPDestAddrMask   IpAddress,
                    			customListTCPDestPort   INTEGER,
                    			customListUDPSrcAddr   IpAddress,
                    			customListUDPSrcAddrMask   IpAddress,
                    			customListUDPSrcPort   INTEGER,
                    			customListUDPDestAddr   IpAddress,
                    			customListUDPDestAddrMask   IpAddress,
                    			customListUDPDestPort   INTEGER,
                    			customIntListIfIndex   INTEGER,
                    			customListRuleStatus   RowStatus
                    	             }


customListNoIndex   	OBJECT-TYPE
                    		SYNTAX  INTEGER (1..16)
                    		MAX-ACCESS  read-only
                    		STATUS  current
                    		DESCRIPTION
                    			"自定义队列规则对应队列号."
                    		::= { customListRuleEntry 1 }

customListIndex     	OBJECT-TYPE
                    		SYNTAX  INTEGER
                    		MAX-ACCESS  read-create
                    		STATUS  current
                    		DESCRIPTION
                    			"自定义队列规则，队列规则号."
                    		::= { customListRuleEntry 2 }

customListICMP      	OBJECT-TYPE
                    		SYNTAX  INTEGER {
                    			         enable(1),
                    			          disable(2)
                    			        }
                    		MAX-ACCESS  read-create
                    		STATUS  current
                    		DESCRIPTION
                    			"自定义队列接收ICMP."
                    		::= { customListRuleEntry 3 }

customListIGMP      	OBJECT-TYPE
                    		SYNTAX  INTEGER {
                    			         enable(1),
                    			          disable(2)
                    			        }
                    		MAX-ACCESS  read-create
                    		STATUS  current
                    		DESCRIPTION
                    			"自定义队列接收IGMP."
                    		::= { customListRuleEntry 4 }

customListQNo       	OBJECT-TYPE
                    		SYNTAX  INTEGER (0..16)
                    		MAX-ACCESS  read-create
                    		STATUS  current
                    		DESCRIPTION
                    			"自定义队列规则使用队列号."
                    		::= { customListRuleEntry 5 }

customListFragPktQNo	OBJECT-TYPE
                    		SYNTAX  INTEGER (0..16)
                    		MAX-ACCESS  read-create
                    		STATUS  current
                    		DESCRIPTION
                    			"自定义队列规则分片报文队列号."
                    		::= { customListRuleEntry 6 }

customListPktEtSize 	OBJECT-TYPE
                    		SYNTAX  INTEGER (1..1500)
                    		MAX-ACCESS  read-create
                    		STATUS  current
                    		DESCRIPTION
                    			"自定义队列规则."
                    		::= { customListRuleEntry 7 }

customListPktGtSize 	OBJECT-TYPE
                    		SYNTAX  INTEGER (1..1500)
                    		MAX-ACCESS  read-create
                    		STATUS  current
                    		DESCRIPTION
                    			"自定义队列规则."
                    		::= { customListRuleEntry 8 }

customListPktLtSize 	OBJECT-TYPE
                    		SYNTAX  INTEGER (1..1500)
                    		MAX-ACCESS  read-create
                    		STATUS  current
                    		DESCRIPTION
                    			"自定义队列规则."
                    		::= { customListRuleEntry 9 }

customListIpSrcAddr 	OBJECT-TYPE
                    		SYNTAX  IpAddress
                    		MAX-ACCESS  read-create
                    		STATUS  current
                    		DESCRIPTION
                    			"自定义队列规则IP报文源地址."
                    		::= { customListRuleEntry 10 }

customListIpSrcAddrMask	OBJECT-TYPE
                    		SYNTAX  IpAddress
                    		MAX-ACCESS  read-create
                    		STATUS  current
                    		DESCRIPTION
                    			"自定义队列规则IP报文源地址掩码."
                    		::= { customListRuleEntry 11 }

customListIpDestAddr	OBJECT-TYPE
                    		SYNTAX  IpAddress
                    		MAX-ACCESS  read-create
                    		STATUS  current
                    		DESCRIPTION
                    			"自定义队列规则IP报文目的地址."
                    		::= { customListRuleEntry 12 }

customListIpDestAddrMask	OBJECT-TYPE
                    		SYNTAX  IpAddress
                    		MAX-ACCESS  read-create
                    		STATUS  current
                    		DESCRIPTION
                    			"自定义队列规则IP报文目的地址掩码."
                    		::= { customListRuleEntry 13 }

customListAccListNo 	OBJECT-TYPE
                    		SYNTAX  INTEGER (1..2000)
                    		MAX-ACCESS  read-create
                    		STATUS  current
                    		DESCRIPTION
                    			"自定义队列规则访问控制列表号."
                    		::= { customListRuleEntry 14 }

customListQByteCount	OBJECT-TYPE
                    		SYNTAX  INTEGER (1..65535)
                    		MAX-ACCESS  read-create
                    		STATUS  current
                    		DESCRIPTION
                    			"自定义队列规则字节数."
                    		::= { customListRuleEntry 15 }

customListQLimit    	OBJECT-TYPE
                    		SYNTAX  INTEGER (0..65535)
                    		MAX-ACCESS  read-create
                    		STATUS  current
                    		DESCRIPTION
                    			"自定义队列规则."
                    		::= { customListRuleEntry 16 }

customListTCPSrcAddr	OBJECT-TYPE
                    		SYNTAX  IpAddress
                    		MAX-ACCESS  read-create
                    		STATUS  current
                    		DESCRIPTION
                    			"自定义队列规则TCP报文源地址."
                    		::= { customListRuleEntry 17 }

customListTCPSrcAddrMask	OBJECT-TYPE
                    		SYNTAX  IpAddress
                    		MAX-ACCESS  read-create
                    		STATUS  current
                    		DESCRIPTION
                    			"自定义队列规则TCP报文源地址掩码."
                    		::= { customListRuleEntry 18 }

customListTCPSrcPort	OBJECT-TYPE
                    		SYNTAX  INTEGER (0..65535)
                    		MAX-ACCESS  read-create
                    		STATUS  current
                    		DESCRIPTION
                    			"自定义队列规则TCP报文源端口号."
                    		::= { customListRuleEntry 19 }

customListTCPDestAddr	OBJECT-TYPE
                    		SYNTAX  IpAddress
                    		MAX-ACCESS  read-create
                    		STATUS  current
                    		DESCRIPTION
                    			"自定义队列规则TCP报文目的地址."
                    		::= { customListRuleEntry 20 }

customListTCPDestAddrMask	OBJECT-TYPE
                    		SYNTAX  IpAddress
                    		MAX-ACCESS  read-create
                    		STATUS  current
                    		DESCRIPTION
                    			"自定义队列规则TCP报文目的地址掩码."
                    		::= { customListRuleEntry 21 }

customListTCPDestPort	OBJECT-TYPE
                    		SYNTAX  INTEGER (0..65535)
                    		MAX-ACCESS  read-create
                    		STATUS  current
                    		DESCRIPTION
                    			"自定义队列规则TCP报文目的端口号."
                    		::= { customListRuleEntry 22 }

customListUDPSrcAddr	OBJECT-TYPE
                    		SYNTAX  IpAddress
                    		MAX-ACCESS  read-create
                    		STATUS  current
                    		DESCRIPTION
                    			"自定义队列规则UDP报文源地址."
                    		::= { customListRuleEntry 23 }

customListUDPSrcAddrMask	OBJECT-TYPE
                    		SYNTAX  IpAddress
                    		MAX-ACCESS  read-create
                    		STATUS  current
                    		DESCRIPTION
                    			"自定义队列规则UDP报文源地址掩码."
                    		::= { customListRuleEntry 24 }

customListUDPSrcPort	OBJECT-TYPE
                    		SYNTAX  INTEGER (0..65535)
                    		MAX-ACCESS  read-create
                    		STATUS  current
                    		DESCRIPTION
                    			"自定义队列规则UDP报文源端口号."
                    		::= { customListRuleEntry 25 }

customListUDPDestAddr	OBJECT-TYPE
                    		SYNTAX  IpAddress
                    		MAX-ACCESS  read-create
                    		STATUS  current
                    		DESCRIPTION
                    			"自定义队列规则UDP报文目的地址."
                    		::= { customListRuleEntry 26 }

customListUDPDestAddrMask	OBJECT-TYPE
                    		SYNTAX  IpAddress
                    		MAX-ACCESS  read-create
                    		STATUS  current
                    		DESCRIPTION
                    			"自定义队列规则UDP报文目的地址掩码."
                    		::= { customListRuleEntry 27 }

customListUDPDestPort	OBJECT-TYPE
                    		SYNTAX  INTEGER (0..65535)
                    		MAX-ACCESS  read-create
                    		STATUS  current
                    		DESCRIPTION
                    			"自定义队列规则UDP报文目的端口号."
                    		::= { customListRuleEntry 28 }

customIntListIfIndex	OBJECT-TYPE
                    		SYNTAX  INTEGER
                    		MAX-ACCESS  read-create
                    		STATUS  current
                    		DESCRIPTION
                    			"自定义队列规则接口索引."
                    		::= { customListRuleEntry 29 }

customListRuleStatus	OBJECT-TYPE
                    		SYNTAX  RowStatus
                    		MAX-ACCESS  read-create
                    		STATUS  current
                    		DESCRIPTION
                    			"自定义队列规则行状态."
                    		::= { customListRuleEntry 30 }


------------------------------------------------------------------------------
wredGroup           	OBJECT IDENTIFIER ::= { mpQosMib 7 }

wredGrpTable        	OBJECT-TYPE
                    		SYNTAX  SEQUENCE OF  WredGrpEntry
                    		MAX-ACCESS  not-accessible
                    		STATUS  current
                    		DESCRIPTION
                    			"全局加权随机早检测列表."
                    		::= { wredGroup 1 }

wredGrpEntry        	OBJECT-TYPE
                    		SYNTAX  WredGrpEntry
                    		MAX-ACCESS  not-accessible
                    		STATUS  current
                    		DESCRIPTION
                    			"全局加权随机早检测列表."
                    		INDEX  { wredGrpName }
                    		::= { wredGrpTable 1 }

WredGrpEntry        	::= SEQUENCE {
                    			wredGrpName            DisplayString,
                    			wredGrpExpWeight       INTEGER,
                    			wredGrpStatus          RowStatus
                    	             }


wredGrpName         	OBJECT-TYPE
                    		SYNTAX  DisplayString
                    		MAX-ACCESS  read-create
                    		STATUS  current
                    		DESCRIPTION
                    			"全局加权随机早检测队列名."
                    		::= { wredGrpEntry 1 }

wredGrpExpWeight    	OBJECT-TYPE
                    		SYNTAX  INTEGER
                    		MAX-ACCESS  read-create
                    		STATUS  current
                    		DESCRIPTION
                    			"全局加权随机早检测队列加权因子."
                    		::= { wredGrpEntry 2 }

wredGrpStatus       	OBJECT-TYPE
                    		SYNTAX  RowStatus
                    		MAX-ACCESS  read-create
                    		STATUS  current
                    		DESCRIPTION
                    			"全局加权随机早检测行状态."
                    		::= { wredGrpEntry 3 }

wredGrpPreTable     	OBJECT-TYPE
                    		SYNTAX  SEQUENCE OF  WredGrpPreEntry
                    		MAX-ACCESS  not-accessible
                    		STATUS  current
                    		DESCRIPTION
                    			"全局加权随机早检测优先级列表."
                    		::= { wredGroup 2 }

wredGrpPreEntry     	OBJECT-TYPE
                    		SYNTAX  WredGrpPreEntry
                    		MAX-ACCESS  not-accessible
                    		STATUS  current
                    		DESCRIPTION
                    			"全局加权随机早检测优先级列表."
                    		INDEX  { wredGrpPreName,  wredGrpPreNo }
                    		::= { wredGrpPreTable 1 }

WredGrpPreEntry     	::= SEQUENCE {
                    			wredGrpPreName         DisplayString,
                    			wredGrpPreNo           INTEGER,
                    			wredGrpPreMinBytes     INTEGER,
                    			wredGrpPreMaxBytes     INTEGER,
                    			wredGrpPreDenominator   INTEGER,
                    			wredGrpPreRandomDropsBytes   INTEGER,
                    			wredGrpPreTailDropsBytes   INTEGER,
                    			wredGrpPreStatus       RowStatus
                    	             }


wredGrpPreName      	OBJECT-TYPE
                    		SYNTAX  DisplayString
                    		MAX-ACCESS  read-only
                    		STATUS  current
                    		DESCRIPTION
                    			"全局加权随机早检测优先级队列名."
                    		::= { wredGrpPreEntry 1 }

wredGrpPreNo        	OBJECT-TYPE
                    		SYNTAX  INTEGER (1..8)
                    		MAX-ACCESS  read-create
                    		STATUS  current
                    		DESCRIPTION
                    			"全局加权随机早检测优先级队列号.本应是0～7."
                    		::= { wredGrpPreEntry 2 }

wredGrpPreMinBytes  	OBJECT-TYPE
                    		SYNTAX  INTEGER (0..65535)
                    		MAX-ACCESS  read-create
                    		STATUS  current
                    		DESCRIPTION
                    			"全局加权随机早检测优先级队列最小字节数限制."
                    		::= { wredGrpPreEntry 3 }

wredGrpPreMaxBytes  	OBJECT-TYPE
                    		SYNTAX  INTEGER (0..65535)
                    		MAX-ACCESS  read-create
                    		STATUS  current
                    		DESCRIPTION
                    			"全局加权随机早检测优先级队列最大字节数限制."
                    		::= { wredGrpPreEntry 4 }

wredGrpPreDenominator	OBJECT-TYPE
                    		SYNTAX  INTEGER (1..100)
                    		MAX-ACCESS  read-create
                    		STATUS  current
                    		DESCRIPTION
                    			"全局加权随机早检测优先级队列标记概率分母."
                    		::= { wredGrpPreEntry 5 }

wredGrpPreRandomDropsBytes	OBJECT-TYPE
                    		SYNTAX  INTEGER
                    		MAX-ACCESS  read-only
                    		STATUS  current
                    		DESCRIPTION
                    			"全局加权随机早检测优先级队列随机丢弃字节数."
                    		::= { wredGrpPreEntry 6 }

wredGrpPreTailDropsBytes	OBJECT-TYPE
                    		SYNTAX  INTEGER
                    		MAX-ACCESS  read-only
                    		STATUS  current
                    		DESCRIPTION
                    			"全局加权随机早检测优先级队列尾部丢弃字节数."
                    		::= { wredGrpPreEntry 7 }

wredGrpPreStatus    	OBJECT-TYPE
                    		SYNTAX  RowStatus
                    		MAX-ACCESS  read-create
                    		STATUS  current
                    		DESCRIPTION
                    			"全局加权随机早检测优先级队列行状态."
                    		::= { wredGrpPreEntry 8 }

ifWredTable         	OBJECT-TYPE
                    		SYNTAX  SEQUENCE OF  IfWredEntry
                    		MAX-ACCESS  not-accessible
                    		STATUS  current
                    		DESCRIPTION
                    			"接口上的全局加权随机早检测队列."
                    		::= { wredGroup 3 }

ifWredEntry         	OBJECT-TYPE
                    		SYNTAX  IfWredEntry
                    		MAX-ACCESS  not-accessible
                    		STATUS  current
                    		DESCRIPTION
                    			"接口上的全局加权随机早检测队列."
                    		INDEX  { ifWredIfIndex }
                    		::= { ifWredTable 1 }

IfWredEntry         	::= SEQUENCE {
                    			ifWredIfIndex          INTEGER,
                    			ifWredExpWeight        INTEGER,
                    			ifWredStatus           RowStatus
                    	             }


ifWredIfIndex       	OBJECT-TYPE
                    		SYNTAX  INTEGER
                    		MAX-ACCESS  read-create
                    		STATUS  current
                    		DESCRIPTION
                    			"接口上的加权随机早检测队列接口索引."
                    		::= { ifWredEntry 1 }

ifWredExpWeight     	OBJECT-TYPE
                    		SYNTAX  INTEGER (1..16)
                    		MAX-ACCESS  read-create
                    		STATUS  current
                    		DESCRIPTION
                    			"接口上的加权随机早检测加权因子."
                    		::= { ifWredEntry 2 }

ifWredStatus        	OBJECT-TYPE
                    		SYNTAX  RowStatus
                    		MAX-ACCESS  read-create
                    		STATUS  current
                    		DESCRIPTION
                    			"接口上的加权随机早检测列表行状态."
                    		::= { ifWredEntry 3 }

ifWredRuleTable     	OBJECT-TYPE
                    		SYNTAX  SEQUENCE OF  IfWredRuleEntry
                    		MAX-ACCESS  not-accessible
                    		STATUS  current
                    		DESCRIPTION
                    			"接口上的全局加权随机早检测队列规则."
                    		::= { wredGroup 4 }

ifWredRuleEntry     	OBJECT-TYPE
                    		SYNTAX  IfWredRuleEntry
                    		MAX-ACCESS  not-accessible
                    		STATUS  current
                    		DESCRIPTION
                    			"接口上的全局加权随机早检测队列规则."
                    		INDEX  { ifWredRuleIfIndex,  ifWredPreNo }
                    		::= { ifWredRuleTable 1 }

IfWredRuleEntry     	::= SEQUENCE {
                    			ifWredRuleIfIndex      INTEGER,
                    			ifWredPreNo            INTEGER,
                    			ifWredPreMinBytes      INTEGER,
                    			ifWredPreMaxBytes      INTEGER,
                    			ifWredPreDenominator   INTEGER,
                    			ifWredRuleStatus       RowStatus
                    	             }


ifWredRuleIfIndex   	OBJECT-TYPE
                    		SYNTAX  INTEGER
                    		MAX-ACCESS  read-create
                    		STATUS  current
                    		DESCRIPTION
                    			"接口上的加权随机早检测队列接口索引."
                    		::= { ifWredRuleEntry 1 }

ifWredPreNo         	OBJECT-TYPE
                    		SYNTAX  INTEGER (1..9)
                    		MAX-ACCESS  read-create
                    		STATUS  current
                    		DESCRIPTION
                    			"接口上的加权随机早检测队列号，9表示RSVP.本应是0～8."
                    		::= { ifWredRuleEntry 2 }

ifWredPreMinBytes   	OBJECT-TYPE
                    		SYNTAX  INTEGER (1000..65535)
                    		MAX-ACCESS  read-create
                    		STATUS  current
                    		DESCRIPTION
                    			"接口上的加权随机早检测队列报文最小字节数."
                    		::= { ifWredRuleEntry 3 }

ifWredPreMaxBytes   	OBJECT-TYPE
                    		SYNTAX  INTEGER (2000..65535)
                    		MAX-ACCESS  read-create
                    		STATUS  current
                    		DESCRIPTION
                    			"接口上的加权随机早检测队列报文最大字节数."
                    		::= { ifWredRuleEntry 4 }

ifWredPreDenominator	OBJECT-TYPE
                    		SYNTAX  INTEGER (1..100)
                    		MAX-ACCESS  read-create
                    		STATUS  current
                    		DESCRIPTION
                    			"接口上的加权随机早检测队列标记概率分母."
                    		::= { ifWredRuleEntry 5 }

ifWredRuleStatus    	OBJECT-TYPE
                    		SYNTAX  RowStatus
                    		MAX-ACCESS  read-create
                    		STATUS  current
                    		DESCRIPTION
                    			"接口上的加权随机早检测列表行状态."
                    		::= { ifWredRuleEntry 6 }


------------------------------------------------------------------------------
ifQos               	OBJECT IDENTIFIER ::= { mpQosMib 8 }

ifQosTable          	OBJECT-TYPE
                    		SYNTAX  SEQUENCE OF  IfQosEntry
                    		MAX-ACCESS  not-accessible
                    		STATUS  current
                    		DESCRIPTION
                    			"接口QOS策略表."
                    		::= { ifQos 1 }

ifQosEntry          	OBJECT-TYPE
                    		SYNTAX  IfQosEntry
                    		MAX-ACCESS  not-accessible
                    		STATUS  current
                    		DESCRIPTION
                    			"接口QOS策略表."
                    		INDEX  { ifQosIfIndex }
                    		::= { ifQosTable 1 }

IfQosEntry          	::= SEQUENCE {
                    			ifQosIfIndex           INTEGER,
                    			ifQosOutputPolicyName   DisplayString,
                    			ifQosInputPolicyName   DisplayString,
                    			ifQosListType          INTEGER,
                    			ifQosListNo            INTEGER,
                    			ifQosTrafficShapeRate  INTEGER,
                    			ifQosTrafficShapeBurst INTEGER,
                    			ifQosStatus            RowStatus
                    	             }


ifQosIfIndex        	OBJECT-TYPE
                    		SYNTAX  INTEGER
                    		MAX-ACCESS  read-create
                    		STATUS  current
                    		DESCRIPTION
                    			"接口QOS策略接口索引."
                    		::= { ifQosEntry 1 }

ifQosOutputPolicyName	OBJECT-TYPE
                    		SYNTAX  DisplayString
                    		MAX-ACCESS  read-create
                    		STATUS  current
                    		DESCRIPTION
                    			"接口QOS策略，输出策略名."
                    		::= { ifQosEntry 2 }

ifQosInputPolicyName	OBJECT-TYPE
                    		SYNTAX  DisplayString
                    		MAX-ACCESS  read-create
                    		STATUS  current
                    		DESCRIPTION
                    			"接口QOS策略，输入策略名."
                    		::= { ifQosEntry 3 }

ifQosListType       	OBJECT-TYPE
                    		SYNTAX  INTEGER {
                    			         pq(1),
                    			          cq(2),
                    			          wred(3),
                    			          cbwfq(4),
                    			          fair-queue(5),
                    			          fifo(6)
                    			        }
                    		MAX-ACCESS  read-create
                    		STATUS  current
                    		DESCRIPTION
                    			"接口QOS队列类型."
                    		::= { ifQosEntry 4 }

ifQosListNo         	OBJECT-TYPE
                    		SYNTAX  INTEGER
                    		MAX-ACCESS  read-create
                    		STATUS  current
                    		DESCRIPTION
                    			"接口QOS队列号."
                    		::= { ifQosEntry 5 }

ifQosTrafficShapeRate OBJECT-TYPE
                    		SYNTAX  INTEGER
                    		MAX-ACCESS  read-create
                    		STATUS  current
                    		DESCRIPTION
                    			"接口流量整形速率."
                    		::= { ifQosEntry 6 }

ifQosTrafficShapeBurst OBJECT-TYPE
                    		SYNTAX  INTEGER
                    		MAX-ACCESS  read-create
                    		STATUS  current
                    		DESCRIPTION
                    			"接口流量整形突发量."
                    		::= { ifQosEntry 7 }

ifQosStatus         	OBJECT-TYPE
                    		SYNTAX  RowStatus
                    		MAX-ACCESS  read-create
                    		STATUS  current
                    		DESCRIPTION
                    			"接口QOS策略表行状态."
                    		::= { ifQosEntry 8 }

ifQosIfTable        	OBJECT-TYPE
                    		SYNTAX  SEQUENCE OF  IfQosIfEntry
                    		MAX-ACCESS  not-accessible
                    		STATUS  current
                    		DESCRIPTION
                    			"接口QOS统计表."
                    		::= { ifQos 2 }

ifQosIfEntry        	OBJECT-TYPE
                    		SYNTAX  IfQosIfEntry
                    		MAX-ACCESS  not-accessible
                    		STATUS  current
                    		DESCRIPTION
                    			"接口QOS统计表."
                    		INDEX  { ifQosIfQIndex }
                    		::= { ifQosIfTable 1 }

IfQosIfEntry        	::= SEQUENCE {
                    			ifQosIfQIfIndex        INTEGER,
                    			ifQosIfQType           INTEGER,
                    			ifQosIfQNum            INTEGER,
                    			ifQosTotalBytes        INTEGER,
                    			ifQosCurTotalBytes     INTEGER,
                    			ifQosTotalInputPkts    Counter,
                    			ifQosTotalInputBytes   Counter,
                    			ifQosTotalOutputPkts   Counter,
                    			ifQosTotalOutputBytes   Counter,
                    			ifQosTotalDropPkts     Counter,
                    			ifQosTotalDropBytes    Counter,
                    			ifQosActiveQCnt        INTEGER,
                    			ifQosCBWFQActQCnt      INTEGER,
                    			ifQosRSVPReq           INTEGER
                    	             }


ifQosIfQIfIndex     	OBJECT-TYPE
                    		SYNTAX  INTEGER
                    		MAX-ACCESS  read-only
                    		STATUS  current
                    		DESCRIPTION
                    			"接口QOS统计接口索引."
                    		::= { ifQosIfEntry 1 }

ifQosIfQType        	OBJECT-TYPE
                    		SYNTAX  INTEGER {
                    			         pq(1),
                    			          cq(2),
                    			          wred(3),
                    			          cbwfq(4),
                    			          fair-queue(5)
                    			        }
                    		MAX-ACCESS  read-only
                    		STATUS  current
                    		DESCRIPTION
                    			"接口QOS统计的队列类型."
                    		::= { ifQosIfEntry 2 }

ifQosIfQNum         	OBJECT-TYPE
                    		SYNTAX  INTEGER
                    		MAX-ACCESS  read-only
                    		STATUS  current
                    		DESCRIPTION
                    			"接口QOS统计队列数目."
                    		::= { ifQosIfEntry 3 }

ifQosTotalBytes     	OBJECT-TYPE
                    		SYNTAX  INTEGER
                    		MAX-ACCESS  read-only
                    		STATUS  current
                    		DESCRIPTION
                    			"接口QOS统计接口缓冲区大小."
                    		::= { ifQosIfEntry 4 }

ifQosCurTotalBytes  	OBJECT-TYPE
                    		SYNTAX  INTEGER
                    		MAX-ACCESS  read-only
                    		STATUS  current
                    		DESCRIPTION
                    			"接口QOS统计当前接口队列里共有多少字节."
                    		::= { ifQosIfEntry 5 }

ifQosTotalInputPkts 	OBJECT-TYPE
                    		SYNTAX  Counter
                    		MAX-ACCESS  read-only
                    		STATUS  current
                    		DESCRIPTION
                    			"接口QOS统计一个接口的总的输入包数目（可清空）."
                    		::= { ifQosIfEntry 6 }

ifQosTotalInputBytes	OBJECT-TYPE
                    		SYNTAX  Counter
                    		MAX-ACCESS  read-only
                    		STATUS  current
                    		DESCRIPTION
                    			"接口QOS统计一个接口的总的输入字节数目（可清空）."
                    		::= { ifQosIfEntry 7 }

ifQosTotalOutputPkts	OBJECT-TYPE
                    		SYNTAX  Counter
                    		MAX-ACCESS  read-only
                    		STATUS  current
                    		DESCRIPTION
                    			"接口QOS统计一个接口的总的输出包数目（可清空）."
                    		::= { ifQosIfEntry 8 }

ifQosTotalOutputBytes	OBJECT-TYPE
                    		SYNTAX  Counter
                    		MAX-ACCESS  read-only
                    		STATUS  current
                    		DESCRIPTION
                    			"接口QOS统计一个接口的总的输出字节数目（可清空）."
                    		::= { ifQosIfEntry 9 }

ifQosTotalDropPkts  	OBJECT-TYPE
                    		SYNTAX  Counter
                    		MAX-ACCESS  read-only
                    		STATUS  current
                    		DESCRIPTION
                    			"接口QOS统计一个接口的总的丢弃包数目（可清空）."
                    		::= { ifQosIfEntry 10 }

ifQosTotalDropBytes 	OBJECT-TYPE
                    		SYNTAX  Counter
                    		MAX-ACCESS  read-only
                    		STATUS  current
                    		DESCRIPTION
                    			"接口QOS统计一个接口的总的丢弃字节数目（可清空）."
                    		::= { ifQosIfEntry 11 }

ifQosActiveQCnt     	OBJECT-TYPE
                    		SYNTAX  INTEGER
                    		MAX-ACCESS  read-only
                    		STATUS  current
                    		DESCRIPTION
                    			"接口QOS统计当前活动队列数目."
                    		::= { ifQosIfEntry 12 }

ifQosCBWFQActQCnt   	OBJECT-TYPE
                    		SYNTAX  INTEGER
                    		MAX-ACCESS  read-only
                    		STATUS  current
                    		DESCRIPTION
                    			"接口QOS统计当前CBWFQ活动队列数目."
                    		::= { ifQosIfEntry 13 }

ifQosRSVPReq        	OBJECT-TYPE
                    		SYNTAX  INTEGER {
                    			         yes(1),
                    			          no(2)
                    			        }
                    		MAX-ACCESS  read-only
                    		STATUS  current
                    		DESCRIPTION
                    			"接口QOS统计是否有RSVP请求."
                    		::= { ifQosIfEntry 14 }

ifQosQTable         	OBJECT-TYPE
                    		SYNTAX  SEQUENCE OF  IfQosQEntry
                    		MAX-ACCESS  not-accessible
                    		STATUS  current
                    		DESCRIPTION
                    			"接口QOS队列统计表."
                    		::= { ifQos 3 }

ifQosQEntry         	OBJECT-TYPE
                    		SYNTAX  IfQosQEntry
                    		MAX-ACCESS  not-accessible
                    		STATUS  current
                    		DESCRIPTION
                    			"接口QOS队列统计表."
                    		INDEX  { ifQosQIndex,  ifQosQId }
                    		::= { ifQosQTable 1 }

IfQosQEntry         	::= SEQUENCE {
                    			ifQosQIfIndex          INTEGER,
                    			ifQosQId               INTEGER,
                    			ifQosQLimit            INTEGER,
                    			ifQosQSndPkts          Counter,
                    			ifQosQSndBytes         Counter,
                    			ifQosQDropPkts         Counter,
                    			ifQosQDropBytes        Counter,
                    			ifQosQCurBytes         INTEGER,
                    			ifQosQMaxSndBytes      Counter
                    	             }


ifQosQIfIndex       	OBJECT-TYPE
                    		SYNTAX  INTEGER
                    		MAX-ACCESS  read-only
                    		STATUS  current
                    		DESCRIPTION
                    			"接口QOS队列统计接口索引."
                    		::= { ifQosQEntry 1 }

ifQosQId            	OBJECT-TYPE
                    		SYNTAX  INTEGER
                    		MAX-ACCESS  read-only
                    		STATUS  current
                    		DESCRIPTION
                    			"接口QOS队列统计队列号."
                    		::= { ifQosQEntry 2 }

ifQosQLimit         	OBJECT-TYPE
                    		SYNTAX  INTEGER
                    		MAX-ACCESS  read-only
                    		STATUS  current
                    		DESCRIPTION
                    			"接口QOS队列统计队列字节数限制."
                    		::= { ifQosQEntry 3 }

ifQosQSndPkts       	OBJECT-TYPE
                    		SYNTAX  Counter
                    		MAX-ACCESS  read-only
                    		STATUS  current
                    		DESCRIPTION
                    			"接口QOS队列统计队列的发送字包数."
                    		::= { ifQosQEntry 4 }

ifQosQSndBytes      	OBJECT-TYPE
                    		SYNTAX  Counter
                    		MAX-ACCESS  read-only
                    		STATUS  current
                    		DESCRIPTION
                    			"接口QOS队列统计队列的发送字节数."
                    		::= { ifQosQEntry 5 }

ifQosQDropPkts      	OBJECT-TYPE
                    		SYNTAX  Counter
                    		MAX-ACCESS  read-only
                    		STATUS  current
                    		DESCRIPTION
                    			"接口QOS队列统计队列的丢弃包数."
                    		::= { ifQosQEntry 6 }

ifQosQDropBytes     	OBJECT-TYPE
                    		SYNTAX  Counter
                    		MAX-ACCESS  read-only
                    		STATUS  current
                    		DESCRIPTION
                    			"接口QOS队列统计队列的丢弃字节数."
                    		::= { ifQosQEntry 7 }

ifQosQCurBytes      	OBJECT-TYPE
                    		SYNTAX  INTEGER
                    		MAX-ACCESS  read-only
                    		STATUS  current
                    		DESCRIPTION
                    			"接口QOS队列统计队列当前的字节数."
                    		::= { ifQosQEntry 8 }

ifQosQMaxSndBytes   	OBJECT-TYPE
                    		SYNTAX  Counter
                    		MAX-ACCESS  read-only
                    		STATUS  current
                    		DESCRIPTION
                    			"接口QOS队列统计队列当前送往cq和wred的最大字节数."
                    		::= { ifQosQEntry 9 }


------------------------------------------------------------------------------
cbwfqConf           	OBJECT IDENTIFIER ::= { mpQosMib 9 }

cbwfqConfMaxClassNum	OBJECT-TYPE
                    		SYNTAX  INTEGER
                    		MAX-ACCESS  read-only
                    		STATUS  current
                    		DESCRIPTION
                    			"CBWFQ最大分类数."
                    		::= { cbwfqConf 1 }

cbwfqConfMaxPolicyNum	OBJECT-TYPE
                    		SYNTAX  INTEGER
                    		MAX-ACCESS  read-only
                    		STATUS  current
                    		DESCRIPTION
                    			"CBWFQ最大策略数."
                    		::= { cbwfqConf 2 }


------------------------------------------------------------------------------
qosCar              	OBJECT IDENTIFIER ::= { mpQosMib 10 }

qosCarTable         	OBJECT-TYPE
                    		SYNTAX  SEQUENCE OF  QosCarEntry
                    		MAX-ACCESS  not-accessible
                    		STATUS  current
                    		DESCRIPTION
                    			"承诺接入速率控制策略表."
                    		::= { qosCar 3 }

qosCarEntry         	OBJECT-TYPE
                    		SYNTAX  QosCarEntry
                    		MAX-ACCESS  not-accessible
                    		STATUS  current
                    		DESCRIPTION
                    			"承诺接入速率控制策略表."
                    		INDEX  { qosCarIndex,  qosCarIfIndex }
                    		::= { qosCarTable 1 }

QosCarEntry         	::= SEQUENCE {
                    			qosCarIndex            INTEGER,
                    			qosCarIfIndex          INTEGER,
                    			qosCarMaxBw            INTEGER,
                    			qosCarNormalBw         INTEGER,
                    			qosCarExceedBw         INTEGER,
                    			qosCarConformAct       INTEGER,
                    			qosCarExceedAct        INTEGER,
                    			qosCarConformActNo     INTEGER,
                    			qosCarExceedActNo      INTEGER,
                    			qosCarStatus           RowStatus,
                    			qosCarConformPkts      Counter,
                    			qosCarConformBytes     Counter,
                    			qosCarExceedPkts       Counter,
                    			qosCarExceedBytes      Counter,
                    			qosCarDirection        INTEGER,
                    			qosCarAclGrp           INTEGER
                    	             }


qosCarIndex         	OBJECT-TYPE
                    		SYNTAX  INTEGER
                    		MAX-ACCESS  read-only
                    		STATUS  current
                    		DESCRIPTION
                    			"承诺接入速率控制策略索引."
                    		::= { qosCarEntry 1 }

qosCarIfIndex       	OBJECT-TYPE
                    		SYNTAX  INTEGER
                    		MAX-ACCESS  read-create
                    		STATUS  current
                    		DESCRIPTION
                    			"承诺接入速率控制策略接口索引."
                    		::= { qosCarEntry 2 }

qosCarMaxBw         	OBJECT-TYPE
                    		SYNTAX  INTEGER
                    		MAX-ACCESS  read-create
                    		STATUS  current
                    		DESCRIPTION
                    			"承诺接入速率控制策略承诺信息速率."
                    		::= { qosCarEntry 3 }

qosCarNormalBw      	OBJECT-TYPE
                    		SYNTAX  INTEGER
                    		MAX-ACCESS  read-create
                    		STATUS  current
                    		DESCRIPTION
                    			"承诺接入速率控制策略一级令牌桶深度."
                    		::= { qosCarEntry 4 }

qosCarExceedBw      	OBJECT-TYPE
                    		SYNTAX  INTEGER
                    		MAX-ACCESS  read-create
                    		STATUS  current
                    		DESCRIPTION
                    			"承诺接入速率控制策略二级令牌桶深度."
                    		::= { qosCarEntry 5 }

qosCarConformAct    	OBJECT-TYPE
                    		SYNTAX  INTEGER {
                    			         continue(1),
                    			          drop(2),
                    			          transmit(3),
                    			          set-dscp-continue(4),
                    			          set-dscp-transmit(5),
                    			          set-prec-continue(6),
                    			          set-prec-transmit(7)
                    			        }
                    		MAX-ACCESS  read-create
                    		STATUS  current
                    		DESCRIPTION
                    			"承诺接入速率控制策略顺从行为."
                    		::= { qosCarEntry 6 }

qosCarExceedAct     	OBJECT-TYPE
                    		SYNTAX  INTEGER {
                    			         continue(1),
                    			          drop(2),
                    			          transmit(3),
                    			          set-dscp-continue(4),
                    			          set-dscp-transmit(5),
                    			          set-prec-continue(6),
                    			          set-prec-transmit(7)
                    			        }
                    		MAX-ACCESS  read-create
                    		STATUS  current
                    		DESCRIPTION
                    			"承诺接入速率控制策略扩展行为."
                    		::= { qosCarEntry 7 }

qosCarConformActNo  	OBJECT-TYPE
                    		SYNTAX  INTEGER
                    		MAX-ACCESS  read-create
                    		STATUS  current
                    		DESCRIPTION
                    			"承诺接入速率控制策略顺从行为里的优先级或DSCP值."
                    		::= { qosCarEntry 8 }

qosCarExceedActNo   	OBJECT-TYPE
                    		SYNTAX  INTEGER
                    		MAX-ACCESS  read-create
                    		STATUS  current
                    		DESCRIPTION
                    			"承诺接入速率控制策略扩展行为里的优先级或DSCP值."
                    		::= { qosCarEntry 9 }

qosCarStatus        	OBJECT-TYPE
                    		SYNTAX  RowStatus
                    		MAX-ACCESS  read-create
                    		STATUS  current
                    		DESCRIPTION
                    			"承诺接入速率控制策略行状态."
                    		::= { qosCarEntry 10 }

qosCarConformPkts   	OBJECT-TYPE
                    		SYNTAX  Counter
                    		MAX-ACCESS  read-only
                    		STATUS  current
                    		DESCRIPTION
                    			"承诺接入速率控制策略顺从包数目."
                    		::= { qosCarEntry 11 }

qosCarConformBytes  	OBJECT-TYPE
                    		SYNTAX  Counter
                    		MAX-ACCESS  read-only
                    		STATUS  current
                    		DESCRIPTION
                    			"承诺接入速率控制策略顺从包字节数."
                    		::= { qosCarEntry 12 }

qosCarExceedPkts    	OBJECT-TYPE
                    		SYNTAX  Counter
                    		MAX-ACCESS  read-only
                    		STATUS  current
                    		DESCRIPTION
                    			"承诺接入速率控制策略扩展包数目."
                    		::= { qosCarEntry 13 }

qosCarExceedBytes   	OBJECT-TYPE
                    		SYNTAX  Counter
                    		MAX-ACCESS  read-only
                    		STATUS  current
                    		DESCRIPTION
                    			"承诺接入速率控制策略扩展包字节数."
                    		::= { qosCarEntry 14 }

qosCarDirection     	OBJECT-TYPE
                    		SYNTAX  INTEGER {
                    			         in(1),
                    			          out(2)
                    			        }
                    		MAX-ACCESS  read-create
                    		STATUS  current
                    		DESCRIPTION
                    			"承诺接入速率控制策略应用方向."
                    		::= { qosCarEntry 15 }

qosCarAclGrp        	OBJECT-TYPE
                    		SYNTAX  INTEGER (1..2000)
                    		MAX-ACCESS  read-create
                    		STATUS  current
                    		DESCRIPTION
                    			"承诺接入速率控制策略访问控制列表号."
                    		::= { qosCarEntry 16 }


------------------------------------------------------------------------------
policyStatis        	OBJECT IDENTIFIER ::= { mpQosMib 20 }

policyStatisTable   	OBJECT-TYPE
                    		SYNTAX  SEQUENCE OF   PolicyStatisEntry
                    		MAX-ACCESS  not-accessible
                    		STATUS  current
                    		DESCRIPTION
                    			""
                    		::= { policyStatis 10 }

policyStatisEntry   	OBJECT-TYPE
                    		SYNTAX  PolicyStatisEntry
                    		MAX-ACCESS  not-accessible
                    		STATUS  current
                    		DESCRIPTION
                    			""
                    		INDEX  { policyStatisIfIndex, policyStatisDirection, policyStatisClassName, policyStatisSubClassName }
                    		::= { policyStatisTable 1 }

PolicyStatisEntry   	::= SEQUENCE {
                    			policyStatisIfIndex    Unsigned32,
                    			policyStatisDirection   INTEGER,
                    			policyStatisClassName   DisplayString,
                    			policyStatisSubClassName   DisplayString,
                    			policyStatisRemark     DisplayString,
                    			policyStatisPackets    Counter64,
                    			policyStatisBytes      Counter64,
                    			policyStatisRowStatus   RowStatus
                    	             }


policyStatisIfIndex 	OBJECT-TYPE
                    		SYNTAX  Unsigned32
                    		MAX-ACCESS  read-only
                    		STATUS  current
                    		DESCRIPTION
                    			"Interface index for policy classfication statistics."
                    		::= { policyStatisEntry 1 }

policyStatisDirection	OBJECT-TYPE
                    		SYNTAX  INTEGER {
                    			         input(1),
                    			          output(2)
                    			        }
                    		MAX-ACCESS  read-only
                    		STATUS  current
                    		DESCRIPTION
                    			"Direction for policy classfication statistics."
                    		::= { policyStatisEntry 2 }

policyStatisClassName	OBJECT-TYPE
                    		SYNTAX  DisplayString(SIZE(0..31))
                    		MAX-ACCESS  read-only
                    		STATUS  current
                    		DESCRIPTION
                    			"Class Name for policy classfication statistics."
                    		::= { policyStatisEntry 3 }

policyStatisSubClassName	OBJECT-TYPE
                    		SYNTAX  DisplayString(SIZE(0..31))
                    		MAX-ACCESS  read-only
                    		STATUS  current
                    		DESCRIPTION
                    			"SubClass Name for policy classfication statistics."
                    		::= { policyStatisEntry 4 }

policyStatisRemark  	OBJECT-TYPE
                    		SYNTAX  DisplayString(SIZE(0..127))
                    		MAX-ACCESS  read-only
                    		STATUS  current
                    		DESCRIPTION
                    			"Remark for policy classfication statistics."
                    		::= { policyStatisEntry 5 }

policyStatisPackets 	OBJECT-TYPE
                    		SYNTAX  Counter64
                    		MAX-ACCESS  read-only
                    		STATUS  current
                    		DESCRIPTION
                    			"Packets counter for policy classfication statistics."
                    		::= { policyStatisEntry 6 }

policyStatisBytes   	OBJECT-TYPE
                    		SYNTAX  Counter64
                    		MAX-ACCESS  read-only
                    		STATUS  current
                    		DESCRIPTION
                    			"Bytes counter for policy classfication statistics."
                    		::= { policyStatisEntry 7 }

policyStatisRowStatus	OBJECT-TYPE
                    		SYNTAX  RowStatus
                    		MAX-ACCESS  read-create
                    		STATUS  current
                    		DESCRIPTION
                    			"Row Status for policy classfication statistics."
                    		::= { policyStatisEntry 8 }



END
------------------------------------------------------------------------------
-- ============================================================================
-- $Log: mpQos.mib,v $
-- Revision 1.1  2010/06/21 11:18:46  liyh
-- first commit
--
--
--
-- ============================================================================
