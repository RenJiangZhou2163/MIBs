DEFINITIONS ::= BEGIN

mprSwRuleTable  OBJECT-TYPE
    SYNTAX  SEQUENCE OF mprSwRuleEntry
    ACCESS  not-accessible
    STATUS  5
    DESCRIPTION
            "Switch port security rules table"
    ::= {mpSwPort 3}

mprSwRuleEntry  OBJECT-TYPE
    SYNTAX  mprSwRuleEntry
    ACCESS  not-accessible
    STATUS  5
    DESCRIPTION
            "Switch port security rules table entry"
    INDEX   {mprSwRuleMac, mprSwRulePortSlot, mprSwRulePortIndex}
    ::= {mprSwRuleTable 1}
    
mprSwRulePortSlot  OBJECT-TYPE
    SYNTAX  INTEGER
    ACCESS  read-only
    STATUS  5
    DESCRIPTION
            "table index, rule's related port's slot number"
    ::= {mprSwRuleEntry 1}

mprSwRulePortIndex  OBJECT-TYPE
    SYNTAX  INTEGER
    ACCESS  read-only
    STATUS  5
    DESCRIPTION
            "table index, rule's related port's number"
    ::= {mprSwRuleEntry 2}
    
mprSwRuleMac  OBJECT-TYPE
    SYNTAX  MacAddress
    ACCESS  read-only
    STATUS  5
    DESCRIPTION
            "table index, rule's related MAC"
    ::= {mprSwRuleEntry 3}

mprSwRuleCmd  OBJECT-TYPE
    SYNTAX  INTEGER {
            permit(1),
            deny(2)
            }
    ACCESS  read-write
    STATUS  5
    DESCRIPTION
            "rule command"
    ::= {mprSwRuleEntry 4}

mprSwRuleType  OBJECT-TYPE
    SYNTAX  INTEGER {
            MAC(1),
            MAC+IP(2),
            MAC+VLAN(3)
            }
    ACCESS  read-write
    STATUS  5
    DESCRIPTION
            "rule type"
    ::= {mprSwRuleEntry 5}

mprSwRuleIP  OBJECT-TYPE
    SYNTAX  IpAddress
    ACCESS  read-write
    STATUS  5
    DESCRIPTION
            "related IP"
    ::= {mprSwRuleEntry 6}   
     
mprSwRuleVid  OBJECT-TYPE
    SYNTAX  INTEGER(1~4094)
    ACCESS  read-write
    STATUS  5
    DESCRIPTION
            "related vlan id"
    ::= {mprSwRuleEntry 7}
    
mprSwRuleRowStatus  OBJECT-TYPE
    SYNTAX  RowStatus
    ACCESS  read-create
    STATUS  5
    DESCRIPTION
            "row config status"
    ::= {mprSwRuleEntry 8}
END
