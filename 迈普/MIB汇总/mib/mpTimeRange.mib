------------------------------------------------------------------------------
--
--  File         : mpTimeRange.mib
--  Description  : 
--  Version      :  
--  Date         : June 6, 2006
-- 	Copyright    : 2006 by maipu (sichuan) communication technology co.,ltd.
--					All rights reserved.
--
-- $Id:
-- 
------------------------------------------------------------------------------

------------------------------------------------------------------------------
MPTIMERANGEMIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;



mpTimeRangeMib      	MODULE-IDENTITY
                    		LAST-UPDATED 	"0606061029Z"
                    		ORGANIZATION 	"四川迈普数据通信股份有限公司,
                    		             	 Maipu (Sichuan) Communication Technology Co. LTD."
                    		CONTACT-INFO
                    			"编 写 人:  huyaqing
                    			 联系地址：四川省 成都市 高新区 九兴大道16号
                    			 邮    编：    610041
                    			 电    话：
                    			 传    真：
                    			 电子邮件： huyq@mis.maipu.com"
                    		DESCRIPTION
                      			""
                    		::= { mpMgmt  400 }

------------------------------------------------------------------------------
-- Textual Conventions
------------------------------------------------------------------------------
EnabledStatus ::= TEXTUAL-CONVENTION
    STATUS      current
    DESCRIPTION
        "A simple status value for the object."
    SYNTAX      INTEGER {
	enabled(1), disabled(2) }

------------------------------------------------------------------------------


timeRangeEnable     	OBJECT-TYPE
                    		SYNTAX  EnabledStatus
                    		MAX-ACCESS  read-write
                    		STATUS  current
                    		DESCRIPTION
                    			"是否使能time range功能，缺省为enable。"
                    		::= { mpTimeRangeMib 1 }

timeRangeFrequency  	OBJECT-TYPE
                    		SYNTAX  INTEGER(1..60)
                    		MAX-ACCESS  read-write
                    		STATUS  current
                    		DESCRIPTION
                    			"Time range刷新频率，以分钟为单位，缺省为1分钟。"
                    		::= { mpTimeRangeMib 2 }

timeRangeMaxOffset  	OBJECT-TYPE
                    		SYNTAX  INTEGER(1..300)
                    		MAX-ACCESS  read-write
                    		STATUS  current
                    		DESCRIPTION
                    			"Time range最大时间偏差，单位为秒，缺省为100秒。"
                    		::= { mpTimeRangeMib 3 }

timeRangeTable      	OBJECT-TYPE
                    		SYNTAX  SEQUENCE OF   TimeRangeEntry
                    		MAX-ACCESS  not-accessible
                    		STATUS  current
                    		DESCRIPTION
                    			"Time range预览表。"
                    		::= { mpTimeRangeMib 6 }

timeRangeEntry      	OBJECT-TYPE
                    		SYNTAX  TimeRangeEntry
                    		MAX-ACCESS  not-accessible
                    		STATUS  current
                    		DESCRIPTION
                    			"Time range预览表。"
                    		INDEX  { timeRangeName }
                    		::= { timeRangeTable 1 }

TimeRangeEntry      	::= SEQUENCE {
                    			timeRangeName          DisplayString,
                    			timeRangeState         INTEGER,
                    			timeRangeRowStatus     RowStatus
                    	             }


timeRangeName       	OBJECT-TYPE
                    		SYNTAX  DisplayString(SIZE(1..31))
                    		MAX-ACCESS  read-create
                    		STATUS  current
                    		DESCRIPTION
                    			"Time range的名称。"
                    		::= { timeRangeEntry 1 }

timeRangeState      	OBJECT-TYPE
                    		SYNTAX  INTEGER {
                    			         active(1),
                    			          inactive(2),
                    			          disabled(3)
                    			        }
                    		MAX-ACCESS  read-only
                    		STATUS  current
                    		DESCRIPTION
                    			"Time range的状态。"
                    		::= { timeRangeEntry 2 }

timeRangeRowStatus  	OBJECT-TYPE
                    		SYNTAX  RowStatus
                    		MAX-ACCESS  read-create
                    		STATUS  current
                    		DESCRIPTION
                    			"行状态。"
                    		::= { timeRangeEntry 3 }

timeRangeRuleTable  	OBJECT-TYPE
                    		SYNTAX  SEQUENCE OF   TimeRangeRuleEntry
                    		MAX-ACCESS  not-accessible
                    		STATUS  current
                    		DESCRIPTION
                    			"Time range规则表。"
                    		::= { mpTimeRangeMib 8 }

timeRangeRuleEntry  	OBJECT-TYPE
                    		SYNTAX  TimeRangeRuleEntry
                    		MAX-ACCESS  not-accessible
                    		STATUS  current
                    		DESCRIPTION
                    			"Time range规则表。"
                    		INDEX  { timeRangeRuleName, timeRangeRuleIndex }
                    		::= { timeRangeRuleTable 1 }

TimeRangeRuleEntry  	::= SEQUENCE {
                    			timeRangeRuleName      DisplayString,
                    			timeRangeRuleIndex     INTEGER,
                    			timeRangeRuleType      INTEGER,
                    			timeRangeRuleStartWeekDay   INTEGER,
                    			timeRangeRuleEndWeekDay   INTEGER,
                    			timeRangeRuleStartTimeHour   INTEGER,
                    			timeRangeRuleStartTimeMinute   INTEGER,
                    			timeRangeRuleEndTimeHour   INTEGER,
                    			timeRangeRuleEndTimeMinute   INTEGER,
                    			timeRangeRuleStartDateDay   INTEGER,
                    			timeRangeRuleStartDateMonth   INTEGER,
                    			timeRangeRuleStartDateYear   INTEGER,
                    			timeRangeRuleEndDateDay   INTEGER,
                    			timeRangeRuleEndDateMonth   INTEGER,
                    			timeRangeRuleEndDateYear   INTEGER,
                    			timeRangeRuleState     INTEGER,
                    			timeRangeRuleRowStatus   RowStatus
                    	             }


timeRangeRuleName   	OBJECT-TYPE
                    		SYNTAX  DisplayString(SIZE(1..31))
                    		MAX-ACCESS  read-create
                    		STATUS  current
                    		DESCRIPTION
                    			"Time range的名称。"
                    		::= { timeRangeRuleEntry 1 }

timeRangeRuleIndex  	OBJECT-TYPE
                    		SYNTAX  INTEGER(1..2147483647)
                    		MAX-ACCESS  read-create
                    		STATUS  current
                    		DESCRIPTION
                    			"Time range规则的编号。"
                    		::= { timeRangeRuleEntry 2 }

timeRangeRuleType   	OBJECT-TYPE
                    		SYNTAX  INTEGER {
                    			         periodic(1),
                    			          absolute(2)
                    			        }
                    		MAX-ACCESS  read-write
                    		STATUS  current
                    		DESCRIPTION
                    			"Time range规则的类型"
                    		::= { timeRangeRuleEntry 3 }

timeRangeRuleStartWeekDay	OBJECT-TYPE
                    		SYNTAX  INTEGER(0..127)
                    		MAX-ACCESS  read-write
                    		STATUS  current
                    		DESCRIPTION
                    			"标识起始时间位于一周中的星期几，每一bit代表一周中的一天。例如：0x01－monday，0x02－tuesday，0x03－monday and tuesday，0x1f－weekdays，0x60－weekend，0x7f－daily。仅当规则类型为periodic时该字段有意义。"
                    		::= { timeRangeRuleEntry 4 }

timeRangeRuleEndWeekDay	OBJECT-TYPE
                    		SYNTAX  INTEGER(0..127)
                    		MAX-ACCESS  read-write
                    		STATUS  current
                    		DESCRIPTION
                    			"标识结束时间位于一周中的星期几，每一bit代表一周中的一天。例如：0x01－monday，0x02－tuesday，0x03－monday and tuesday，0x1f－weekdays，0x60－weekend，0x7f－daily。仅当规则类型为periodic时该字段有意义。如果timeRangeRuleEndWeekDay与timeRangeRuleStartWeekDay不相同，那么这两个字段都只能占用1bit。"
                    		::= { timeRangeRuleEntry 5 }

timeRangeRuleStartTimeHour	OBJECT-TYPE
                    		SYNTAX  INTEGER(0..24)
                    		MAX-ACCESS  read-write
                    		STATUS  current
                    		DESCRIPTION
                    			"起始时间之小时。缺省值为0。"
                    		::= { timeRangeRuleEntry 6 }

timeRangeRuleStartTimeMinute	OBJECT-TYPE
                    		SYNTAX  INTEGER(0..60)
                    		MAX-ACCESS  read-write
                    		STATUS  current
                    		DESCRIPTION
                    			"起始时间之分钟。缺省值为0。"
                    		::= { timeRangeRuleEntry 7 }

timeRangeRuleEndTimeHour	OBJECT-TYPE
                    		SYNTAX  INTEGER(0..24)
                    		MAX-ACCESS  read-write
                    		STATUS  current
                    		DESCRIPTION
                    			"结束时间之小时。缺省值为24。"
                    		::= { timeRangeRuleEntry 8 }

timeRangeRuleEndTimeMinute	OBJECT-TYPE
                    		SYNTAX  INTEGER(0..60)
                    		MAX-ACCESS  read-write
                    		STATUS  current
                    		DESCRIPTION
                    			"结束时间之分钟。缺省值为0。"
                    		::= { timeRangeRuleEntry 9 }

timeRangeRuleStartDateDay	OBJECT-TYPE
                    		SYNTAX  INTEGER(0..31)
                    		MAX-ACCESS  read-write
                    		STATUS  current
                    		DESCRIPTION
                    			"起始日期之日。缺省值为0，表示未指定日。仅当规则类型为absolue时该字段有意义。"
                    		::= { timeRangeRuleEntry 10 }

timeRangeRuleStartDateMonth	OBJECT-TYPE
                    		SYNTAX  INTEGER(0..12)
                    		MAX-ACCESS  read-write
                    		STATUS  current
                    		DESCRIPTION
                    			"起始日期之月。缺省值为0，表示未指定月。仅当规则类型为absolue时该字段有意义。"
                    		::= { timeRangeRuleEntry 11 }

timeRangeRuleStartDateYear	OBJECT-TYPE
                    		SYNTAX  INTEGER(0..2100)
                    		MAX-ACCESS  read-write
                    		STATUS  current
                    		DESCRIPTION
                    			"起始日期之年。缺省值为0，表示未指定年。仅当规则类型为absolue时该字段有意义。"
                    		::= { timeRangeRuleEntry 12 }

timeRangeRuleEndDateDay	OBJECT-TYPE
                    		SYNTAX  INTEGER(0..31)
                    		MAX-ACCESS  read-write
                    		STATUS  current
                    		DESCRIPTION
                    			"结束日期之日。缺省值为0，表示未指定日。仅当规则类型为absolue时该字段有意义。"
                    		::= { timeRangeRuleEntry 13 }

timeRangeRuleEndDateMonth	OBJECT-TYPE
                    		SYNTAX  INTEGER(0..12)
                    		MAX-ACCESS  read-write
                    		STATUS  current
                    		DESCRIPTION
                    			"结束日期之月。缺省值为0，表示未指定月。仅当规则类型为absolue时该字段有意义。"
                    		::= { timeRangeRuleEntry 14 }

timeRangeRuleEndDateYear	OBJECT-TYPE
                    		SYNTAX  INTEGER(0..2100)
                    		MAX-ACCESS  read-write
                    		STATUS  current
                    		DESCRIPTION
                    			"结束日期之年。缺省值为0，表示未指定年。仅当规则类型为absolue时该字段有意义。"
                    		::= { timeRangeRuleEntry 15 }

timeRangeRuleState  	OBJECT-TYPE
                    		SYNTAX  INTEGER {
                    			         active(1),
                    			          inactive(2),
                    			          disabled(3)
                    			        }
                    		MAX-ACCESS  read-only
                    		STATUS  current
                    		DESCRIPTION
                    			"Time range规则的状态。"
                    		::= { timeRangeRuleEntry 16 }

timeRangeRuleRowStatus	OBJECT-TYPE
                    		SYNTAX  RowStatus
                    		MAX-ACCESS  read-create
                    		STATUS  current
                    		DESCRIPTION
                    			"行状态。"
                    		::= { timeRangeRuleEntry 17 }



END
------------------------------------------------------------------------------
-- ============================================================================
-- $Log: mpTimeRange.mib,v $
-- Revision 1.1  2010/06/21 11:18:46  liyh
-- first commit
--
-- Revision 1.2  2006/06/08 03:35:09  huyq
-- [ROUTER-7109]time-range增加对SNMP的支持
--
--
--
-- ============================================================================
