------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPRTMPLS DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;


maipu               	OBJECT IDENTIFIER ::= { enterprises 5651 }
mpMgmt2             	OBJECT IDENTIFIER ::= { maipu 6 }
mpRouterTech        	OBJECT IDENTIFIER ::= { mpMgmt2 2 }



mpRtMPLS            	MODULE-IDENTITY
                    		LAST-UPDATED 	"1103041003Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { mpRouterTech  1 }




------------------------------------------------------------------------------
mpRtMPLSBase        	OBJECT IDENTIFIER ::= { mpRtMPLS 1 }

mplsFWDEnable       	OBJECT-TYPE
                    		SYNTAX  Integer32 {
                    			         enable(1),
                    			          disable(2)
                    			        }
                    		MAX-ACCESS  read-write
                    		STATUS  current
                    		DESCRIPTION
                    			"enable or disable mpls forward.
                    			 1 enable
                    			 2 disable"
                    		::= { mpRtMPLSBase 1 }

mplsIfConfigTable   	OBJECT-TYPE
                    		SYNTAX  SEQUENCE OF   MplsIfConfigEntry
                    		MAX-ACCESS  not-accessible
                    		STATUS  current
                    		DESCRIPTION
                    			""
                    		::= { mpRtMPLSBase 2 }

mplsIfConfigEntry   	OBJECT-TYPE
                    		SYNTAX  MplsIfConfigEntry
                    		MAX-ACCESS  not-accessible
                    		STATUS  current
                    		DESCRIPTION
                    			""
                    		INDEX  { ifConfigTableIfIndex }
                    		::= { mplsIfConfigTable 1 }

MplsIfConfigEntry   	::= SEQUENCE {
                    			ifConfigTableIfIndex   Integer32,
                    			ifConfigTableEnable    Integer32,
                    			ifConfigTableRowStatus   RowStatus
                    	             }


ifConfigTableIfIndex	OBJECT-TYPE
                    		SYNTAX  Integer32
                    		MAX-ACCESS  read-only
                    		STATUS  current
                    		DESCRIPTION
                    			"interface index"
                    		::= { mplsIfConfigEntry 1 }

ifConfigTableEnable 	OBJECT-TYPE
                    		SYNTAX  Integer32 {
                    			         enable(1),
                    			          disable(2)
                    			        }
                    		MAX-ACCESS  read-create
                    		STATUS  current
                    		DESCRIPTION
                    			"enable or disable mpls on interface.
                    			 1 enable
                    			 2 disable"
                    		::= { mplsIfConfigEntry 2 }

ifConfigTableRowStatus	OBJECT-TYPE
                    		SYNTAX  RowStatus
                    		MAX-ACCESS  read-create
                    		STATUS  current
                    		DESCRIPTION
                    			""
                    		::= { mplsIfConfigEntry 3 }


------------------------------------------------------------------------------
mpRtMPLSL2VPN       	OBJECT IDENTIFIER ::= { mpRtMPLS 2 }

mplsL2VpnInfoTable  	OBJECT-TYPE
                    		SYNTAX  SEQUENCE OF   MplsL2VpnInfoEntry
                    		MAX-ACCESS  not-accessible
                    		STATUS  current
                    		DESCRIPTION
                    			""
                    		::= { mpRtMPLSL2VPN 1 }

mplsL2VpnInfoEntry  	OBJECT-TYPE
                    		SYNTAX  MplsL2VpnInfoEntry
                    		MAX-ACCESS  not-accessible
                    		STATUS  current
                    		DESCRIPTION
                    			""
                    		INDEX  { l2VpnInfoTableVpnId, l2VpnInfoTableVpnType, l2VpnInfoTableAcIfIndex }
                    		::= { mplsL2VpnInfoTable 1 }

MplsL2VpnInfoEntry  	::= SEQUENCE {
                    			l2VpnInfoTableVpnId    Unsigned32,
                    			l2VpnInfoTableVpnType   INTEGER,
                    			l2VpnInfoTableAcIfIndex   INTEGER,
                    			l2VpnInfoTableAcIfName   DisplayString,
                    			l2VpnInfoTableAcType   INTEGER
                    	             }


l2VpnInfoTableVpnId 	OBJECT-TYPE
                    		SYNTAX  Unsigned32
                    		MAX-ACCESS  read-only
                    		STATUS  current
                    		DESCRIPTION
                    			"在PE上手工配置的VPN标识。对于Martini来说是VC-ID，对于VPLS来说是VPN-ID。"
                    		::= { mplsL2VpnInfoEntry 1 }

l2VpnInfoTableVpnType	OBJECT-TYPE
                    		SYNTAX  INTEGER {
                    			         L2 VPWS Martini(1),
                    			          L2 VPWS Kompella(2),
                    			          L2 VPLS Martini(3),
                    			          L2 VPLS Kompella(4),
                    			          L2 VPLS Martini SVC(5)
                    			        }
                    		MAX-ACCESS  read-only
                    		STATUS  current
                    		DESCRIPTION
                    			"L2 VPN的类型，约定：
                    			 1：L2 VPWS Martini；
                    			 2：L2 VPWS Kompella；
                    			 3：L2 VPLS Martini；
                    			 4：L2 VPLS Kompella；
                    			 5：L2 VPLS Martini SVC；"
                    		::= { mplsL2VpnInfoEntry 2 }

l2VpnInfoTableAcIfIndex	OBJECT-TYPE
                    		SYNTAX  INTEGER
                    		MAX-ACCESS  read-only
                    		STATUS  current
                    		DESCRIPTION
                    			"AC接口索引号。"
                    		::= { mplsL2VpnInfoEntry 3 }

l2VpnInfoTableAcIfName	OBJECT-TYPE
                    		SYNTAX  DisplayString
                    		MAX-ACCESS  read-only
                    		STATUS  current
                    		DESCRIPTION
                    			"AC接口名称。"
                    		::= { mplsL2VpnInfoEntry 4 }

l2VpnInfoTableAcType	OBJECT-TYPE
                    		SYNTAX  INTEGER {
                    			         PPP(1),
                    			          FR(Port to Port)(2),
                    			          ATM(AAL5)(3),
                    			          HDLC(4),
                    			          ETH(5),
                    			          VLAN(6)
                    			        }
                    		MAX-ACCESS  read-only
                    		STATUS  current
                    		DESCRIPTION
                    			"二层协议的类型，约定：
                    			 1：PPP；
                    			 2：FR(Port to Port)；
                    			 3：ATM(AAL5)；
                    			 4：HDLC；
                    			 5：ETH；
                    			 6：VLAN；"
                    		::= { mplsL2VpnInfoEntry 5 }

mplsL2VpnPWTable    	OBJECT-TYPE
                    		SYNTAX  SEQUENCE OF   MplsL2VpnPWEntry
                    		MAX-ACCESS  not-accessible
                    		STATUS  current
                    		DESCRIPTION
                    			""
                    		::= { mpRtMPLSL2VPN 2 }

mplsL2VpnPWEntry    	OBJECT-TYPE
                    		SYNTAX  MplsL2VpnPWEntry
                    		MAX-ACCESS  not-accessible
                    		STATUS  current
                    		DESCRIPTION
                    			""
                    		INDEX  { l2VpnPWTableVpnId, l2VpnPWTableVpnType, l2VpnPWTablePeerAddress }
                    		::= { mplsL2VpnPWTable 1 }

MplsL2VpnPWEntry    	::= SEQUENCE {
                    			l2VpnPWTableVpnId      Unsigned32,
                    			l2VpnPWTableVpnType    INTEGER,
                    			l2VpnPWTablePeerAddress   IpAddress,
                    			l2VpnPWTableIfIndex    INTEGER,
                    			l2VpnPWTableOutboundOperStatus   INTEGER,
                    			l2VpnPWTableInboundOperStatus   INTEGER,
                    			l2VpnPWTableFlowInKBytes   Counter64,
                    			l2VpnPWTableFlowOutBytes   Counter64,
                    			l2VpnPWTableFlowInPackets   Counter64,
                    			l2VpnPWTableFlowOutPackets   Counter64
                    	             }


l2VpnPWTableVpnId   	OBJECT-TYPE
                    		SYNTAX  Unsigned32
                    		MAX-ACCESS  read-only
                    		STATUS  current
                    		DESCRIPTION
                    			"在PE上手工配置的VPN标识。对于Martini来说是VC-ID，对于VPLS来说是VPN-ID。"
                    		::= { mplsL2VpnPWEntry 1 }

l2VpnPWTableVpnType 	OBJECT-TYPE
                    		SYNTAX  INTEGER {
                    			         L2 VPWS Martini(1),
                    			          L2 VPWS Kompella(2),
                    			          L2 VPLS Martini(3),
                    			          L2 VPLS Kompella(4),
                    			          L2 VPLS Martini SVC(5)
                    			        }
                    		MAX-ACCESS  read-only
                    		STATUS  current
                    		DESCRIPTION
                    			"L2 VPN的类型，约定：
                    			 1：L2 VPWS Martini；
                    			 2：L2 VPWS Kompella；
                    			 3：L2 VPLS Martini；
                    			 4：L2 VPLS Kompella；
                    			 5：L2 VPLS Martini SVC；"
                    		::= { mplsL2VpnPWEntry 2 }

l2VpnPWTablePeerAddress	OBJECT-TYPE
                    		SYNTAX  IpAddress
                    		MAX-ACCESS  read-only
                    		STATUS  current
                    		DESCRIPTION
                    			"对端PE的IP地址。"
                    		::= { mplsL2VpnPWEntry 3 }

l2VpnPWTableIfIndex 	OBJECT-TYPE
                    		SYNTAX  INTEGER
                    		MAX-ACCESS  read-only
                    		STATUS  current
                    		DESCRIPTION
                    			"本端PE面向PW的接口。"
                    		::= { mplsL2VpnPWEntry 4 }

l2VpnPWTableOutboundOperStatus	OBJECT-TYPE
                    		SYNTAX  INTEGER {
                    			         UP(1),
                    			          DOWN(2)
                    			        }
                    		MAX-ACCESS  read-only
                    		STATUS  current
                    		DESCRIPTION
                    			"正向的PW的状态，约定"1"为UP，"2"为DOWN。"
                    		::= { mplsL2VpnPWEntry 5 }

l2VpnPWTableInboundOperStatus	OBJECT-TYPE
                    		SYNTAX  INTEGER {
                    			         UP(1),
                    			          DOWN(2)
                    			        }
                    		MAX-ACCESS  read-only
                    		STATUS  current
                    		DESCRIPTION
                    			"反向的PW的状态，约定"1"为UP，"2"为DOWN。"
                    		::= { mplsL2VpnPWEntry 6 }

l2VpnPWTableFlowInKBytes	OBJECT-TYPE
                    		SYNTAX  Counter64
                    		MAX-ACCESS  read-only
                    		STATUS  current
                    		DESCRIPTION
                    			"流入字节数。"
                    		::= { mplsL2VpnPWEntry 7 }

l2VpnPWTableFlowOutBytes	OBJECT-TYPE
                    		SYNTAX  Counter64
                    		MAX-ACCESS  read-only
                    		STATUS  current
                    		DESCRIPTION
                    			"流出字节数。"
                    		::= { mplsL2VpnPWEntry 8 }

l2VpnPWTableFlowInPackets	OBJECT-TYPE
                    		SYNTAX  Counter64
                    		MAX-ACCESS  read-only
                    		STATUS  current
                    		DESCRIPTION
                    			"流入报文数。"
                    		::= { mplsL2VpnPWEntry 9 }

l2VpnPWTableFlowOutPackets	OBJECT-TYPE
                    		SYNTAX  Counter64
                    		MAX-ACCESS  read-only
                    		STATUS  current
                    		DESCRIPTION
                    			"流出报文数。"
                    		::= { mplsL2VpnPWEntry 10 }


------------------------------------------------------------------------------
mpRtMPLSL3VPN       	OBJECT IDENTIFIER ::= { mpRtMPLS 3 }

mplsL3VpnVrfFlowInfoTable	OBJECT-TYPE
                    		SYNTAX  SEQUENCE OF   MplsL3VpnVrfFlowInfoEntry
                    		MAX-ACCESS  not-accessible
                    		STATUS  current
                    		DESCRIPTION
                    			"Flow statistics of VPN Routing/Forwarding instance"
                    		::= { mpRtMPLSL3VPN 1 }

mplsL3VpnVrfFlowInfoEntry	OBJECT-TYPE
                    		SYNTAX  MplsL3VpnVrfFlowInfoEntry
                    		MAX-ACCESS  not-accessible
                    		STATUS  current
                    		DESCRIPTION
                    			"Flow statistics of VPN Routing/Forwarding instance"
                    		INDEX  { l3VpnVrfFlowInfoTableVrfName, l3VpnVrfFlowInfoTablePeerAddress }
                    		::= { mplsL3VpnVrfFlowInfoTable 1 }

MplsL3VpnVrfFlowInfoEntry	::= SEQUENCE {
                    			l3VpnVrfFlowInfoTableVrfName   DisplayString,
                    			l3VpnVrfFlowInfoTablePeerAddress   IpAddress,
                    			l3VpnVrfFlowInfoTableFlowInBytes   Counter64,
                    			l3VpnVrfFlowInfoTableFlowInPackets   Counter64,
                    			l3VpnVrfFlowInfoTableFlowOutBytes   Counter64,
                    			l3VpnVrfFlowInfoTableFlowOutPackets   Counter64
                    	             }


l3VpnVrfFlowInfoTableVrfName	OBJECT-TYPE
                    		SYNTAX  DisplayString
                    		MAX-ACCESS  read-only
                    		STATUS  current
                    		DESCRIPTION
                    			"name of VPN Routing/Forwarding instance"
                    		::= { mplsL3VpnVrfFlowInfoEntry 1 }

l3VpnVrfFlowInfoTablePeerAddress	OBJECT-TYPE
                    		SYNTAX  IpAddress
                    		MAX-ACCESS  read-only
                    		STATUS  current
                    		DESCRIPTION
                    			"IP address of remote PE.(this is reserved for the statistics of out-flow to specific destination PE,it should be set to 0.0.0.0 when it is not used)"
                    		::= { mplsL3VpnVrfFlowInfoEntry 2 }

l3VpnVrfFlowInfoTableFlowInBytes	OBJECT-TYPE
                    		SYNTAX  Counter64
                    		MAX-ACCESS  read-only
                    		STATUS  current
                    		DESCRIPTION
                    			"The total number of bytes that the specific VRF received  from MPLS network"
                    		::= { mplsL3VpnVrfFlowInfoEntry 3 }

l3VpnVrfFlowInfoTableFlowInPackets	OBJECT-TYPE
                    		SYNTAX  Counter64
                    		MAX-ACCESS  read-only
                    		STATUS  current
                    		DESCRIPTION
                    			"The total number of packets that the specific VRF received  from MPLS network"
                    		::= { mplsL3VpnVrfFlowInfoEntry 4 }

l3VpnVrfFlowInfoTableFlowOutBytes	OBJECT-TYPE
                    		SYNTAX  Counter64
                    		MAX-ACCESS  read-only
                    		STATUS  current
                    		DESCRIPTION
                    			"The total number of bytes transmitted out of the specific VRF to MPLS network"
                    		::= { mplsL3VpnVrfFlowInfoEntry 5 }

l3VpnVrfFlowInfoTableFlowOutPackets	OBJECT-TYPE
                    		SYNTAX  Counter64
                    		MAX-ACCESS  read-only
                    		STATUS  current
                    		DESCRIPTION
                    			"The total number of packets transmitted out of the specific VRF to MPLS network"
                    		::= { mplsL3VpnVrfFlowInfoEntry 6 }


------------------------------------------------------------------------------
mpRtMPLSTE          	OBJECT IDENTIFIER ::= { mpRtMPLS 4 }


------------------------------------------------------------------------------
mpRtMPLSOAM         	OBJECT IDENTIFIER ::= { mpRtMPLS 5 }

mplsOAMNextNewEntityId	OBJECT-TYPE
                    		SYNTAX  Unsigned32
                    		MAX-ACCESS  read-only
                    		STATUS  current
                    		DESCRIPTION
                    			"The ID of MPLS OAM entity.The entity ID should be taken before start MPLS OAM detection,and the entity ID is the unique index of following tables.This is used to avoid the appearance of same index when visited by multi-user."
                    		::= { mpRtMPLSOAM 1 }

mplsL2VpnOAMTable   	OBJECT-TYPE
                    		SYNTAX  SEQUENCE OF   MplsL2VpnOAMEntry
                    		MAX-ACCESS  not-accessible
                    		STATUS  current
                    		DESCRIPTION
                    			""
                    		::= { mpRtMPLSOAM 2 }

mplsL2VpnOAMEntry   	OBJECT-TYPE
                    		SYNTAX  MplsL2VpnOAMEntry
                    		MAX-ACCESS  not-accessible
                    		STATUS  current
                    		DESCRIPTION
                    			""
                    		INDEX  { l2VpnOAMTableEntityId }
                    		::= { mplsL2VpnOAMTable 1 }

MplsL2VpnOAMEntry   	::= SEQUENCE {
                    			l2VpnOAMTableEntityId   Unsigned32,
                    			l2VpnOAMTableVpnId     INTEGER,
                    			l2VpnOAMTableVpnType   INTEGER,
                    			l2VpnOAMTablePeerAddress   IpAddress,
                    			l2VpnOAMTableDelay     INTEGER,
                    			l2VpnOAMTableLose      INTEGER,
                    			l2VpnOAMTableStatus    INTEGER
                    	             }


l2VpnOAMTableEntityId	OBJECT-TYPE
                    		SYNTAX  Unsigned32
                    		MAX-ACCESS  read-write
                    		STATUS  current
                    		DESCRIPTION
                    			"Index"
                    		::= { mplsL2VpnOAMEntry 1 }

l2VpnOAMTableVpnId  	OBJECT-TYPE
                    		SYNTAX  INTEGER
                    		MAX-ACCESS  read-write
                    		STATUS  current
                    		DESCRIPTION
                    			"VPN ID"
                    		::= { mplsL2VpnOAMEntry 2 }

l2VpnOAMTableVpnType	OBJECT-TYPE
                    		SYNTAX  INTEGER {
                    			         L2VPWSMartini(1),
                    			          L2VPWSKompella(2),
                    			          L2VPLSMartini(3),
                    			          L2VPLSKompella(4),
                    			          L2VPLSMartiniSVC(5)
                    			        }
                    		MAX-ACCESS  read-write
                    		STATUS  current
                    		DESCRIPTION
                    			"The type of L2VPN."
                    		::= { mplsL2VpnOAMEntry 3 }

l2VpnOAMTablePeerAddress	OBJECT-TYPE
                    		SYNTAX  IpAddress
                    		MAX-ACCESS  read-write
                    		STATUS  current
                    		DESCRIPTION
                    			"IP address of remote PE."
                    		::= { mplsL2VpnOAMEntry 4 }

l2VpnOAMTableDelay  	OBJECT-TYPE
                    		SYNTAX  INTEGER
                    		MAX-ACCESS  read-only
                    		STATUS  current
                    		DESCRIPTION
                    			"Time delay:negative indicates the failue of detecting,and positive indicates the value of time delay."
                    		::= { mplsL2VpnOAMEntry 5 }

l2VpnOAMTableLose   	OBJECT-TYPE
                    		SYNTAX  INTEGER
                    		MAX-ACCESS  read-only
                    		STATUS  current
                    		DESCRIPTION
                    			"The total number of loss packet:negative indicates the failue of detecting,and positive indicates the number of loss packet."
                    		::= { mplsL2VpnOAMEntry 6 }

l2VpnOAMTableStatus 	OBJECT-TYPE
                    		SYNTAX  INTEGER
                    		MAX-ACCESS  read-only
                    		STATUS  current
                    		DESCRIPTION
                    			"The cause of the detecting failue,meaningful only when failue is occured."
                    		::= { mplsL2VpnOAMEntry 7 }

mplsL3VpnOAMTable   	OBJECT-TYPE
                    		SYNTAX  SEQUENCE OF   MplsL3VpnOAMEntry
                    		MAX-ACCESS  not-accessible
                    		STATUS  current
                    		DESCRIPTION
                    			""
                    		::= { mpRtMPLSOAM 3 }

mplsL3VpnOAMEntry   	OBJECT-TYPE
                    		SYNTAX  MplsL3VpnOAMEntry
                    		MAX-ACCESS  not-accessible
                    		STATUS  current
                    		DESCRIPTION
                    			""
                    		INDEX  { l3VpnOAMTableEntityId }
                    		::= { mplsL3VpnOAMTable 1 }

MplsL3VpnOAMEntry   	::= SEQUENCE {
                    			l3VpnOAMTableEntityId   Unsigned32,
                    			l3VpnOAMTableVrfName   DisplayString,
                    			l3VpnOAMTablePeerDetectAddress   IpAddress,
                    			l3VpnOAMTablePeerDetectAddressMask   IpAddress,
                    			l3VpnOAMTableCount     INTEGER,
                    			l3VpnOAMTableSize      INTEGER,
                    			l3VpnOAMTableInterval   INTEGER,
                    			l3VpnOAMTableTimeout   INTEGER,
                    			l3VpnOAMTableTtl       INTEGER,
                    			l3VpnOAMTableExp       INTEGER,
                    			l3VpnOAMTableSentCount   INTEGER,
                    			l3VpnOAMTableSuccessCount   INTEGER,
                    			l3VpnOAMTableDelay     INTEGER,
                    			l3VpnOAMTableStatus    INTEGER,
                    			l3VpnOAMTableRowStatus   RowStatus
                    	             }


l3VpnOAMTableEntityId	OBJECT-TYPE
                    		SYNTAX  Unsigned32
                    		MAX-ACCESS  read-write
                    		STATUS  current
                    		DESCRIPTION
                    			"Index"
                    		::= { mplsL3VpnOAMEntry 1 }

l3VpnOAMTableVrfName	OBJECT-TYPE
                    		SYNTAX  DisplayString
                    		MAX-ACCESS  read-write
                    		STATUS  current
                    		DESCRIPTION
                    			"Name of VRF"
                    		::= { mplsL3VpnOAMEntry 2 }

l3VpnOAMTablePeerDetectAddress	OBJECT-TYPE
                    		SYNTAX  IpAddress
                    		MAX-ACCESS  read-write
                    		STATUS  current
                    		DESCRIPTION
                    			"IP address of targeted PE."
                    		::= { mplsL3VpnOAMEntry 3 }

l3VpnOAMTablePeerDetectAddressMask	OBJECT-TYPE
                    		SYNTAX  IpAddress
                    		MAX-ACCESS  read-write
                    		STATUS  current
                    		DESCRIPTION
                    			"IP address mask of targeted PE."
                    		::= { mplsL3VpnOAMEntry 4 }

l3VpnOAMTableCount  	OBJECT-TYPE
                    		SYNTAX  INTEGER(1..2147483647)
                    		MAX-ACCESS  read-write
                    		STATUS  current
                    		DESCRIPTION
                    			"The specified count of MPLS echo request packets which will be sent at once.(default:5)"
                    		::= { mplsL3VpnOAMEntry 5 }

l3VpnOAMTableSize   	OBJECT-TYPE
                    		SYNTAX  INTEGER(120..18024)
                    		MAX-ACCESS  read-write
                    		STATUS  current
                    		DESCRIPTION
                    			"The specified size of MPLS echo request packet.(unit:byte,default:120)"
                    		::= { mplsL3VpnOAMEntry 6 }

l3VpnOAMTableInterval	OBJECT-TYPE
                    		SYNTAX  INTEGER(0..1000)
                    		MAX-ACCESS  read-write
                    		STATUS  current
                    		DESCRIPTION
                    			"The specified interval of sending MPLS echo request.(unit:ms,default:0)"
                    		::= { mplsL3VpnOAMEntry 7 }

l3VpnOAMTableTimeout	OBJECT-TYPE
                    		SYNTAX  INTEGER(1..3600)
                    		MAX-ACCESS  read-write
                    		STATUS  current
                    		DESCRIPTION
                    			"MPLS echo reply timeout in seconds.(default:2)"
                    		::= { mplsL3VpnOAMEntry 8 }

l3VpnOAMTableTtl    	OBJECT-TYPE
                    		SYNTAX  INTEGER(1..255)
                    		MAX-ACCESS  read-write
                    		STATUS  current
                    		DESCRIPTION
                    			"The specified TTL of MPLS echo request.(default:255)"
                    		::= { mplsL3VpnOAMEntry 9 }

l3VpnOAMTableExp    	OBJECT-TYPE
                    		SYNTAX  INTEGER(0..7)
                    		MAX-ACCESS  read-write
                    		STATUS  current
                    		DESCRIPTION
                    			"The specified MPLS experimental field value in the MPLS header for an MPLS echo reply.(default:0)"
                    		::= { mplsL3VpnOAMEntry 10 }

l3VpnOAMTableSentCount	OBJECT-TYPE
                    		SYNTAX  INTEGER
                    		MAX-ACCESS  read-only
                    		STATUS  current
                    		DESCRIPTION
                    			"The total number of MPLS echo request packets which have been sent."
                    		::= { mplsL3VpnOAMEntry 11 }

l3VpnOAMTableSuccessCount	OBJECT-TYPE
                    		SYNTAX  INTEGER
                    		MAX-ACCESS  read-only
                    		STATUS  current
                    		DESCRIPTION
                    			"The total number of MPLS echo request packets which have been response by echo reply successfully."
                    		::= { mplsL3VpnOAMEntry 12 }

l3VpnOAMTableDelay  	OBJECT-TYPE
                    		SYNTAX  INTEGER
                    		MAX-ACCESS  read-only
                    		STATUS  current
                    		DESCRIPTION
                    			"The average time delay.(unit:ms)"
                    		::= { mplsL3VpnOAMEntry 13 }

l3VpnOAMTableStatus 	OBJECT-TYPE
                    		SYNTAX  INTEGER {
                    			         detecting(1),
                    			          detectSuccess(2),
                    			          detectFailure(3)
                    			        }
                    		MAX-ACCESS  read-only
                    		STATUS  current
                    		DESCRIPTION
                    			"Status of each MPLS ping entity:
                    			 1:detecting;
                    			 2:detectSuccess;(The definition of success:one of the MPLS echo request packets has been response by echo reply successfully)
                    			 3:detectFailure;(The definition of failure:all of the MPLS echo request packets are failed)"
                    		::= { mplsL3VpnOAMEntry 14 }

l3VpnOAMTableRowStatus 	OBJECT-TYPE
                    		SYNTAX  RowStatus
                    		MAX-ACCESS  read-create
                    		STATUS  current
                    		DESCRIPTION
                    			 "Status of this row."
                    		::= { mplsL3VpnOAMEntry 15 }

mplsL3VpnTraceCtlTable	OBJECT-TYPE
                    		SYNTAX  SEQUENCE OF   MplsL3VpnTraceCtlEntry
                    		MAX-ACCESS  not-accessible
                    		STATUS  current
                    		DESCRIPTION
                    			"The control table of MPLS L3VPN traceroute,for the use of setting arguments of MPLS traceroute."
                    		::= { mpRtMPLSOAM 4 }

mplsL3VpnTraceCtlEntry	OBJECT-TYPE
                    		SYNTAX  MplsL3VpnTraceCtlEntry
                    		MAX-ACCESS  not-accessible
                    		STATUS  current
                    		DESCRIPTION
                    			"The control table of MPLS L3VPN traceroute,for the use of setting arguments of MPLS traceroute."
                    		INDEX  { l3VpnTraceCtlEntityId }
                    		::= { mplsL3VpnTraceCtlTable 1 }

MplsL3VpnTraceCtlEntry	::= SEQUENCE {
                    			l3VpnTraceCtlEntityId   Unsigned32,
                    			l3VpnTraceCtlVrfName   DisplayString,
                    			l3VpnTraceCtlDestinationPeAddress   IpAddress,
                    			l3VpnTraceCtlDestinationPeAddressMaskLen   INTEGER,
                    			l3VpnTraceCtlTimeOut   INTEGER,
                    			l3VpnTraceCtlMaxTtl    INTEGER,
                    			l3VpnTraceCtlExp       INTEGER,
                    			l3VpnTraceCtlErrorCode   INTEGER,
                    			l3VpnTraceCtlRowStatus   RowStatus
                    	             }


l3VpnTraceCtlEntityId	OBJECT-TYPE
                    		SYNTAX  Unsigned32
                    		MAX-ACCESS  read-only
                    		STATUS  current
                    		DESCRIPTION
                    			"The entity ID of MPLS traceroute,which is the index of table.The entity ID should be taken before start MPLS traceroute."
                    		::= { mplsL3VpnTraceCtlEntry 1 }

l3VpnTraceCtlVrfName	OBJECT-TYPE
                    		SYNTAX  DisplayString(SIZE(1..255))
                    		MAX-ACCESS  read-write
                    		STATUS  current
                    		DESCRIPTION
                    			"VRF name."
                    		::= { mplsL3VpnTraceCtlEntry 2 }

l3VpnTraceCtlDestinationPeAddress	OBJECT-TYPE
                    		SYNTAX  IpAddress
                    		MAX-ACCESS  read-write
                    		STATUS  current
                    		DESCRIPTION
                    			"IP address of destination PE."
                    		::= { mplsL3VpnTraceCtlEntry 3 }

l3VpnTraceCtlDestinationPeAddressMaskLen	OBJECT-TYPE
                    		SYNTAX  INTEGER(1..32)
                    		MAX-ACCESS  read-write
                    		STATUS  current
                    		DESCRIPTION
                    			"The IP address mask length of destination PE."
                    		::= { mplsL3VpnTraceCtlEntry 4 }

l3VpnTraceCtlTimeOut	OBJECT-TYPE
                    		SYNTAX  INTEGER(1..3600)
                    		MAX-ACCESS  read-write
                    		STATUS  current
                    		DESCRIPTION
                    			"MPLS traceroute echo reply timeout in seconds.(default:2)"
                    		::= { mplsL3VpnTraceCtlEntry 5 }

l3VpnTraceCtlMaxTtl 	OBJECT-TYPE
                    		SYNTAX  INTEGER(1..255)
                    		MAX-ACCESS  read-write
                    		STATUS  current
                    		DESCRIPTION
                    			"The specified maximum hop count.(default:30)"
                    		::= { mplsL3VpnTraceCtlEntry 6 }

l3VpnTraceCtlExp    	OBJECT-TYPE
                    		SYNTAX  INTEGER(0..7)
                    		MAX-ACCESS  read-write
                    		STATUS  current
                    		DESCRIPTION
                    			"The specified MPLS experimental field value in the MPLS header for an MPLS echo reply.(default:0)"
                    		::= { mplsL3VpnTraceCtlEntry 7 }

l3VpnTraceCtlErrorCode  OBJECT-TYPE
                    		SYNTAX  INTEGER {
                    			          wrong entity ID(1),
                    			          entity ID is up to max(2),
                    			          entity ID is used(3),
                    			          memory short(4),
                    			          wrong vrf name(5),
                    			          wrong mask length(6),
                    			          wrong timeout value(7),
                    			          wrong ttl value(8),
                    			          wrong exp value(9),
                    			          parameters missed(10)
                    			        }
                    		MAX-ACCESS  read-only
                    		STATUS  current
                    		DESCRIPTION
                    			"error code of LSP traceroute:
                    			 1: wrong entity ID;
                    			 2: entity ID is up to max;
                    			 3: entity ID is used;
                    			 4: memory short;
                    			 5: wrong vrf name;
                    			 6: wrong mask length;
                    			 7: wrong timeout value;
                    			 8: wrong ttl value;
                    			 9: wrong exp value;
                    			 10: parameters missed;"
                    		::= { mplsL3VpnTraceCtlEntry 8 }

l3VpnTraceCtlRowStatus	OBJECT-TYPE
                    		SYNTAX  RowStatus
                    		MAX-ACCESS  read-write
                    		STATUS  current
                    		DESCRIPTION
                    			"MPLS traceroute row status."
                    		::= { mplsL3VpnTraceCtlEntry 9 }

mplsl3VpnTraceResultsTable	OBJECT-TYPE
                    		SYNTAX  SEQUENCE OF   Mplsl3VpnTraceResultsEntry
                    		MAX-ACCESS  not-accessible
                    		STATUS  current
                    		DESCRIPTION
                    			"The results table of MPLS L3VPN traceroute,for the use of returning results of MPLS traceroute."
                    		::= { mpRtMPLSOAM 5 }

mplsl3VpnTraceResultsEntry	OBJECT-TYPE
                    		SYNTAX  Mplsl3VpnTraceResultsEntry
                    		MAX-ACCESS  not-accessible
                    		STATUS  current
                    		DESCRIPTION
                    			"The results table of MPLS L3VPN traceroute,for the use of returning results of MPLS traceroute."
                    		INDEX  { l3VpnTraceResultsEntityId, l3VpnTraceResultsTtlIndex }
                    		::= { mplsl3VpnTraceResultsTable 1 }

Mplsl3VpnTraceResultsEntry	::= SEQUENCE {
                    			l3VpnTraceResultsEntityId   Unsigned32,
                    			l3VpnTraceResultsTtlIndex   INTEGER,
                    			l3VpnTraceResultsResultCode   INTEGER,
                    			l3VpnTraceResultsHopAddress   IpAddress,
                    			l3VpnTraceResultsHopMtu   INTEGER,
                    			l3VpnTraceResultsHopLableCount   INTEGER,
                    			l3VpnTraceResultsHopLableValue1   INTEGER,
                    			l3VpnTraceResultsHopLableExp1   INTEGER,
                    			l3VpnTraceResultsHopLableValue2   INTEGER,
                    			l3VpnTraceResultsHopLableExp2   INTEGER,
                    			l3VpnTraceResultsHopLableValue3   INTEGER,
                    			l3VpnTraceResultsHopLableExp3   INTEGER,
                    			l3VpnTraceResultsHopLableValue4   INTEGER,
                    			l3VpnTraceResultsHopLableExp4   INTEGER,
                    			l3VpnTraceResultsHopLableValue5   INTEGER,
                    			l3VpnTraceResultsHopLableExp5   INTEGER,
                    			l3VpnTraceResultsHopRtt   INTEGER,
                    			l3VpnTraceResultsStatus   INTEGER
                    	             }


l3VpnTraceResultsEntityId	OBJECT-TYPE
                    		SYNTAX  Unsigned32
                    		MAX-ACCESS  read-only
                    		STATUS  current
                    		DESCRIPTION
                    			"The entity ID of MPLS traceroute,corresponding to the entity ID in mplsL3VpnTraceCtlTable."
                    		::= { mplsl3VpnTraceResultsEntry 1 }

l3VpnTraceResultsTtlIndex	OBJECT-TYPE
                    		SYNTAX  INTEGER(0..255)
                    		MAX-ACCESS  read-only
                    		STATUS  current
                    		DESCRIPTION
                    			"The TTL in outermost lable of each echo request which has been sent,it is one of the indices.(The TTL of the initial PE is 0)"
                    		::= { mplsl3VpnTraceResultsEntry 2 }

l3VpnTraceResultsResultCode	OBJECT-TYPE
                    		SYNTAX  INTEGER {
                    			          skipDisplay(-1),
                    			          success(0),
                    			          requestNotTransmitted(1),
                    			          timeout(2),
                    			          unreachable(3),
                    			          downstreamRouterButNotDestination(4),
                    			          malformedRequest(5),
                    			          malformedReply(6)
                    			        }
                    		MAX-ACCESS  read-only
                    		STATUS  current
                    		DESCRIPTION
                    			"The result code of one MPLS traceroute process:
                    			 skip display(1)
                    			 success(2)
                    			 request not transmitted(3)
                    			 timeout(4)
                    			 unreachable(5)
                    			 downstream router but not destination(6)
                    			 malformed request(7)
                    			 malformed reply(8)"
                    		::= { mplsl3VpnTraceResultsEntry 3 }

l3VpnTraceResultsHopAddress	OBJECT-TYPE
                    		SYNTAX  IpAddress
                    		MAX-ACCESS  read-only
                    		STATUS  current
                    		DESCRIPTION
                    			"IP address of one hop on the path(0.0.0.0 indicate that the IP address should not be shown)"
                    		::= { mplsl3VpnTraceResultsEntry 4 }

l3VpnTraceResultsHopMtu	OBJECT-TYPE
                    		SYNTAX  INTEGER
                    		MAX-ACCESS  read-only
                    		STATUS  current
                    		DESCRIPTION
                    			"The interface MTU of one hop on the path.(unit:byte,-1 indicate that the interface MTU should not be shown)"
                    		::= { mplsl3VpnTraceResultsEntry 5 }

l3VpnTraceResultsHopLableCount	OBJECT-TYPE
                    		SYNTAX  INTEGER(0..5)
                    		MAX-ACCESS  read-only
                    		STATUS  current
                    		DESCRIPTION
                    			"The total count of lables in lablestack which a certain hop will use.(0 indicate that the label count and the following lable value&exp should not be shown)"
                    		::= { mplsl3VpnTraceResultsEntry 6 }

l3VpnTraceResultsHopLableValue1	OBJECT-TYPE
                    		SYNTAX  INTEGER(0..1048575)
                    		MAX-ACCESS  read-only
                    		STATUS  current
                    		DESCRIPTION
                    			"The lable value of first lable.(outermost)"
                    		::= { mplsl3VpnTraceResultsEntry 7 }

l3VpnTraceResultsHopLableExp1	OBJECT-TYPE
                    		SYNTAX  INTEGER(0..7)
                    		MAX-ACCESS  read-only
                    		STATUS  current
                    		DESCRIPTION
                    			"The lable exp of first lable."
                    		::= { mplsl3VpnTraceResultsEntry 8 }

l3VpnTraceResultsHopLableValue2	OBJECT-TYPE
                    		SYNTAX  INTEGER(0..1048575)
                    		MAX-ACCESS  read-only
                    		STATUS  current
                    		DESCRIPTION
                    			"The lable value of second lable."
                    		::= { mplsl3VpnTraceResultsEntry 9 }

l3VpnTraceResultsHopLableExp2	OBJECT-TYPE
                    		SYNTAX  INTEGER(0..7)
                    		MAX-ACCESS  read-only
                    		STATUS  current
                    		DESCRIPTION
                    			"The lable exp of second lable."
                    		::= { mplsl3VpnTraceResultsEntry 10 }

l3VpnTraceResultsHopLableValue3	OBJECT-TYPE
                    		SYNTAX  INTEGER(0..1048575)
                    		MAX-ACCESS  read-only
                    		STATUS  current
                    		DESCRIPTION
                    			"The lable value of third lable."
                    		::= { mplsl3VpnTraceResultsEntry 11 }

l3VpnTraceResultsHopLableExp3	OBJECT-TYPE
                    		SYNTAX  INTEGER(0..7)
                    		MAX-ACCESS  read-only
                    		STATUS  current
                    		DESCRIPTION
                    			"The lable exp of third lable."
                    		::= { mplsl3VpnTraceResultsEntry 12 }

l3VpnTraceResultsHopLableValue4	OBJECT-TYPE
                    		SYNTAX  INTEGER(0..1048575)
                    		MAX-ACCESS  read-only
                    		STATUS  current
                    		DESCRIPTION
                    			"The lable value of fourth lable."
                    		::= { mplsl3VpnTraceResultsEntry 13 }

l3VpnTraceResultsHopLableExp4	OBJECT-TYPE
                    		SYNTAX  INTEGER(0..7)
                    		MAX-ACCESS  read-only
                    		STATUS  current
                    		DESCRIPTION
                    			"The lable exp of fourth lable."
                    		::= { mplsl3VpnTraceResultsEntry 14 }

l3VpnTraceResultsHopLableValue5	OBJECT-TYPE
                    		SYNTAX  INTEGER(0..1048575)
                    		MAX-ACCESS  read-only
                    		STATUS  current
                    		DESCRIPTION
                    			"The lable value of fifth lable.(innermost)"
                    		::= { mplsl3VpnTraceResultsEntry 15 }

l3VpnTraceResultsHopLableExp5	OBJECT-TYPE
                    		SYNTAX  INTEGER(0..7)
                    		MAX-ACCESS  read-only
                    		STATUS  current
                    		DESCRIPTION
                    			"The lable exp of fifth lable."
                    		::= { mplsl3VpnTraceResultsEntry 16 }

l3VpnTraceResultsHopRtt	OBJECT-TYPE
                    		SYNTAX  INTEGER
                    		MAX-ACCESS  read-only
                    		STATUS  current
                    		DESCRIPTION
                    			"The Round Trip Time of certain hop's echo packet.(unit:ms,-1 indicate that the RTT should not be shown)"
                    		::= { mplsl3VpnTraceResultsEntry 17 }

l3VpnTraceResultsStatus	OBJECT-TYPE
                    		SYNTAX  INTEGER {
                    			         tracerouteIsInProgress(1),
                    			          tracerouteHasFinished(2)
                    			        }
                    		MAX-ACCESS  read-only
                    		STATUS  current
                    		DESCRIPTION
                    			"Status of each MPLS traceroute entity:
                    			 traceroute is in progress(1)
                    			 traceroute has finished(2)"
                    		::= { mplsl3VpnTraceResultsEntry 18 }


------------------------------------------------------------------------------
mpRtLDP             	OBJECT IDENTIFIER ::= { mpRtMPLS 6 }

mpLDPStart          	OBJECT-TYPE
                    		SYNTAX  Integer32 {
                    			         start(1),
                    			          shutdown(2)
                    			        }
                    		MAX-ACCESS  read-write
                    		STATUS  current
                    		DESCRIPTION
                    			"start or shutdown ldp.
                    			 1 start
                    			 2 shutdown"
                    		::= { mpRtLDP 1 }

mpLDPRouterID       	OBJECT-TYPE
                    		SYNTAX  IpAddress
                    		MAX-ACCESS  read-write
                    		STATUS  current
                    		DESCRIPTION
                    			"add or delete ldp router-id configuration."
                    		::= { mpRtLDP 2 }

mpLDPTransAddr      	OBJECT-TYPE
                    		SYNTAX  IpAddress
                    		MAX-ACCESS  read-write
                    		STATUS  current
                    		DESCRIPTION
                    			"add or delete ldp transport-address configuration."
                    		::= { mpRtLDP 3 }

mpLDPIfTable        	OBJECT-TYPE
                    		SYNTAX  SEQUENCE OF   MpLDPIfEntry
                    		MAX-ACCESS  not-accessible
                    		STATUS  current
                    		DESCRIPTION
                    			"ldp interface information table."
                    		::= { mpRtLDP 4 }

mpLDPIfEntry        	OBJECT-TYPE
                    		SYNTAX  MpLDPIfEntry
                    		MAX-ACCESS  not-accessible
                    		STATUS  current
                    		DESCRIPTION
                    			"ldp interface information table."
                    		INDEX  { mpLDPIfIndex }
                    		::= { mpLDPIfTable 1 }

MpLDPIfEntry        	::= SEQUENCE {
                    			mpLDPIfIndex           Integer32,
                    			mpLDPIfEnable          INTEGER,
                    			mpLDPIfRowstatus       RowStatus
                    	             }


mpLDPIfIndex        	OBJECT-TYPE
                    		SYNTAX  Integer32
                    		MAX-ACCESS  read-only
                    		STATUS  current
                    		DESCRIPTION
                    			"ldp interface index."
                    		::= { mpLDPIfEntry 1 }

mpLDPIfEnable       	OBJECT-TYPE
                    		SYNTAX  INTEGER {
                    			         enable(1),
                    			          disable(2)
                    			        }
                    		MAX-ACCESS  read-create
                    		STATUS  current
                    		DESCRIPTION
                    			"enable or disable ldp on interface.
                    			 1 enable
                    			 2 disable"
                    		::= { mpLDPIfEntry 2 }

mpLDPIfRowstatus    	OBJECT-TYPE
                    		SYNTAX  RowStatus
                    		MAX-ACCESS  read-create
                    		STATUS  current
                    		DESCRIPTION
                    			"ldp interface rowstatus."
                    		::= { mpLDPIfEntry 3 }



END
------------------------------------------------------------------------------
-- ============================================================================
-- $Log: sysMib.mi2,v $
--
--
-- ============================================================================
