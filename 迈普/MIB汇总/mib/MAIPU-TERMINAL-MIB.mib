--------------------------------------------------------------------
-- MAIPU-TERMINAL-MIB:  Maipu Terminal Mgmt MIB file
--
-- March 2007, wangyg
-- Copyright (c) 2007 by MAIPU COMMUNICATION TECHNOLOGY CO.,LTD
-- All rights reserved.
-- 
--------------------------------------------------------------------

MAIPU-TERMINAL-MIB	DEFINITIONS ::= BEGIN
	IMPORTS
		RowStatus, DisplayString
			FROM SNMPv2-TC
		DisplayString
			FROM RFC1213-MIB
		MODULE-IDENTITY, OBJECT-IDENTITY, OBJECT-TYPE, Unsigned32, IpAddress, enterprises, Integer32
			FROM SNMPv2-SMI
		mpMgmt
			FROM MAIPU-SMI;

	mpTerminalMib	MODULE-IDENTITY
		LAST-UPDATED	"200703141507Z"
		ORGANIZATION	"Maipu Communication Technology Co., LTD."
		CONTACT-INFO	"E-mail: office@maipu.com"
		DESCRIPTION		""
		REVISION		"200703141507Z"
		DESCRIPTION		"Initial version of this MIB module."
		::=  {  mpMgmt  602  }

	mpTermMIBObjects	OBJECT IDENTIFIER	::=  {  mpTerminalMib  1  }

	mpTermConfigs	OBJECT IDENTIFIER	::=  {  mpTermMIBObjects  1  }

	mpTermInfo	OBJECT IDENTIFIER	::=  {  mpTermMIBObjects  2  }


-- mpTermStateTable 终端状态表

	mpTermStateTable	OBJECT-TYPE
		SYNTAX		SEQUENCE  OF  MpTermStateEntry
		MAX-ACCESS	not-accessible
		STATUS		current
		DESCRIPTION	"终端连接状态表。"
		::=  { mpTermInfo  1 }

	mpTermStateEntry	OBJECT-TYPE
		SYNTAX		MpTermStateEntry
		MAX-ACCESS	not-accessible
		STATUS		current
		DESCRIPTION	"终端连接状态行。"
		INDEX		{  mpTermStateInterface  }
		::=  { mpTermStateTable 1 }

	MpTermStateEntry  ::=  SEQUENCE {
		mpTermStateInterface  DisplayString,
		mpTermStateTermType  INTEGER,
		mpTermStateCOM  Integer32,
		mpTermStateTERM  Integer32,
		mpTermStateTcpServerPort  Integer32,
		mpTermStateTerminalState  INTEGER,
		mpTermStateTemplateName  DisplayString,
		mpTermStateActiveRHIndex	Integer32
		}


	mpTermStateInterface	OBJECT-TYPE	
		SYNTAX			DisplayString  ( SIZE ( 1 .. 59  ) ) 
		MAX-ACCESS		read-only
		STATUS			current
		DESCRIPTION		"终端接口或者地址。"
		::=  {  mpTermStateEntry  1  }


	mpTermStateTermType	OBJECT-TYPE	
		SYNTAX			INTEGER  { 
							terminal ( 1 ) , 
							mpdlc ( 2 )  , 
							pad ( 3 )
						} 
		MAX-ACCESS		read-only
		STATUS			current
		DESCRIPTION		"终端类型。"
		::=  {  mpTermStateEntry  2  }


	mpTermStateCOM	OBJECT-TYPE	
		SYNTAX			Integer32
		MAX-ACCESS		read-only
		STATUS			current
		DESCRIPTION		"终端COM号。"
		::=  {  mpTermStateEntry  3  }


	mpTermStateTERM	OBJECT-TYPE	
		SYNTAX			Integer32
		MAX-ACCESS		read-only
		STATUS			current
		DESCRIPTION		"终端TERM号。"
		::=  {  mpTermStateEntry  4  }


	mpTermStateTcpServerPort	OBJECT-TYPE	
		SYNTAX			Integer32  ( 0 .. 65535  ) 
		MAX-ACCESS		read-only
		STATUS			current
		DESCRIPTION		"服务器类型终端监听的本地TCP端口号。"
		::=  {  mpTermStateEntry  5  }


	mpTermStateTerminalState	OBJECT-TYPE	
		SYNTAX			INTEGER  { 
							closed ( 1 ) , 
							initial ( 2 ) , 
							prompt ( 3 ) , 
							running ( 4 ) , 
							waiting ( 5 ) 
						} 
		MAX-ACCESS		read-only
		STATUS			current
		DESCRIPTION		"终端状态。"
		::=  {  mpTermStateEntry  6  }


	mpTermStateTemplateName	OBJECT-TYPE	
		SYNTAX			DisplayString  ( SIZE ( 0 .. 31  ) ) 
		MAX-ACCESS		read-only
		STATUS			current
		DESCRIPTION		"终端上应用的模板名字。"
		::=  {  mpTermStateEntry  7  }

	mpTermStateActiveRHIndex	OBJECT-TYPE	
		SYNTAX			Integer32  ( -1 .. 9 ) 
		MAX-ACCESS		read-only
		STATUS			current
		DESCRIPTION		"终端上当前处于激活状态的主机序号。
		                 －1 表示当前没有处于激活状态的主机。"
		::=  {  mpTermStateEntry  8  }

-- mpTermStateTable end


-- mpTermRHStateTable 远端连接表

	mpTermRHStateTable	OBJECT-TYPE
		SYNTAX		SEQUENCE  OF  MpTermRHStateEntry
		MAX-ACCESS	not-accessible
		STATUS		current
		DESCRIPTION	"远端连接状态表。"
		::=  { mpTermInfo  2 }

	mpTermRHStateEntry	OBJECT-TYPE
		SYNTAX		MpTermRHStateEntry
		MAX-ACCESS	not-accessible
		STATUS		current
		DESCRIPTION	"远端连接状态行。"
		INDEX		{  mpTermRHStateInterface, mpTermRHStateRHIndex  }
		::=  { mpTermRHStateTable 1 }

	MpTermRHStateEntry  ::=  SEQUENCE {
		mpTermRHStateInterface  DisplayString,
		mpTermRHStateRHIndex  Integer32,
		mpTermRHStateTemplateName  DisplayString,
		mpTermRHStateRemoteState  INTEGER
		}


	mpTermRHStateInterface	OBJECT-TYPE	
		SYNTAX			DisplayString	( SIZE ( 1 .. 59 ) )
		MAX-ACCESS		read-only
		STATUS			current
		DESCRIPTION		"远端连接所属的接口或者设备。"
		::=  {  mpTermRHStateEntry  1  }


	mpTermRHStateRHIndex	OBJECT-TYPE	
		SYNTAX			Integer32  ( 0 .. 9  ) 
		MAX-ACCESS		read-only
		STATUS			current
		DESCRIPTION		"远端主机序号。"
		::=  {  mpTermRHStateEntry  2  }


	mpTermRHStateTemplateName	OBJECT-TYPE	
		SYNTAX			DisplayString  ( SIZE ( 0 .. 31  ) ) 
		MAX-ACCESS		read-only
		STATUS			current
		DESCRIPTION		"该接口上应用的终端模板名字。"
		::=  {  mpTermRHStateEntry  3  }


	mpTermRHStateRemoteState	OBJECT-TYPE	
		SYNTAX			INTEGER  { 
							disconnect ( 1 ) , 
							connecting ( 2 ) , 
							connected ( 3 ) 
						} 
		MAX-ACCESS		read-only
		STATUS			current
		DESCRIPTION		"与远端主机的TCP连接状态。"
		::=  {  mpTermRHStateEntry  4  }

-- mpTermRHStateTable end


END
