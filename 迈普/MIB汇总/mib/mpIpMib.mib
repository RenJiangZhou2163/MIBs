------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPIPMIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;



mpIpMib             	MODULE-IDENTITY
                    		LAST-UPDATED 	"0703191040Z"
                    		ORGANIZATION 	"四川迈普数据通信股份有限公司,
                    		             	 Maipu (Sichuan) Communication Technology Co. LTD."
                    		CONTACT-INFO
                    			"编 写 人：LM
                    			 联系地址：四川省 成都市 高新区 九兴大道16号
                    			 邮    编：610041
                    			 电    话：
                    			 传    真：
                    			 电子邮件："
                    		DESCRIPTION
                      			"IP相关信息管理"
                    		::= { mpMgmt  700 }



mpIpTable           	OBJECT-TYPE
                    		SYNTAX  SEQUENCE OF   MpIpEntry
                    		MAX-ACCESS  not-accessible
                    		STATUS  current
                    		DESCRIPTION
                    			"对设备的IP地址进行管理"
                    		::= { mpIpMib 1 }

mpIpEntry           	OBJECT-TYPE
                    		SYNTAX  MpIpEntry
                    		MAX-ACCESS  not-accessible
                    		STATUS  current
                    		DESCRIPTION
                    			"对设备的IP地址进行管理"
                    		INDEX  { mpIpTIfName, mpIpTAddress, mpIpTMask }
                    		::= { mpIpTable 1 }

MpIpEntry           	::= SEQUENCE {
                    			mpIpTIfName            DisplayString,
                    			mpIpTAddress           IpAddress,
                    			mpIpTMask              IpAddress,
                    			mpIpTBPAddress         IpAddress,
                    			mpIpTType              INTEGER,
                    			mpIpTWay               INTEGER,
                    			mpIpTRowStatus         RowStatus
                    	             }


mpIpTIfName         	OBJECT-TYPE
                    		SYNTAX  DisplayString(SIZE(0..40))
                    		MAX-ACCESS  not-accessible
                    		STATUS  current
                    		DESCRIPTION
                    			"配置IP地址的接口名称"
                    		::= { mpIpEntry 1 }

mpIpTAddress        	OBJECT-TYPE
                    		SYNTAX  IpAddress
                    		MAX-ACCESS  not-accessible
                    		STATUS  current
                    		DESCRIPTION
                    			"IP地址"
                    		::= { mpIpEntry 2 }

mpIpTMask           	OBJECT-TYPE
                    		SYNTAX  IpAddress
                    		MAX-ACCESS  not-accessible
                    		STATUS  current
                    		DESCRIPTION
                    			"IP地址的掩码"
                    		::= { mpIpEntry 3 }

mpIpTBPAddress      	OBJECT-TYPE
                    		SYNTAX  IpAddress
                    		MAX-ACCESS  read-only
                    		STATUS  current
                    		DESCRIPTION
                    			"如果是广播接口则代表广播地址（Broadcast）
                    			 如果是点到点接口则代表对端地址（Peer）"
                    		::= { mpIpEntry 4 }

mpIpTType           	OBJECT-TYPE
                    		SYNTAX  INTEGER {
                    			         primary(1),
                    			          secondary(2)
                    			        }
                    		MAX-ACCESS  read-write
                    		STATUS  current
                    		DESCRIPTION
                    			"IP地址的类型:主地址或者从地址"
                    		::= { mpIpEntry 5 }

mpIpTWay            	OBJECT-TYPE
                    		SYNTAX  INTEGER {
                    			         manual(1),
                    			          dhcp(2),
                    			          negotiated(3),
                    			          unnumbered(4),
                    			          virtual(5)
                    			        }
                    		MAX-ACCESS  read-only
                    		STATUS  current
                    		DESCRIPTION
                    			"获取IP地址的方式"
                    		::= { mpIpEntry 6 }

mpIpTRowStatus      	OBJECT-TYPE
                    		SYNTAX  RowStatus
                    		MAX-ACCESS  read-create
                    		STATUS  current
                    		DESCRIPTION
                    			""
                    		::= { mpIpEntry 7 }



END
------------------------------------------------------------------------------
-- ============================================================================
-- $Log: mpIpMib.mib,v $
-- Revision 1.1  2010/06/21 11:18:46  liyh
-- first commit
--
-- Revision 1.1.2.2  2007/05/18 08:04:26  linmao
-- ROUTER-8157: Add IpTWay type for VR(B)RP
--
-- Revision 1.1.2.1  2007/03/21 06:46:21  linmao
-- ROUTER-7966: Support MIB wirte IP information
--
--
--
-- ============================================================================
