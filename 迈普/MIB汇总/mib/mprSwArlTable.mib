DEFINITIONS ::= BEGIN

mprSwArlTable  OBJECT-TYPE
    SYNTAX  SEQUENCE OF mprSwArlEntry
    ACCESS  not-accessible
    STATUS  5
    DESCRIPTION
            "ARL information table"
    ::= {mpSwPort 2}

mprSwArlEntry  OBJECT-TYPE
    SYNTAX  mprSwArlEntry
    ACCESS  not-accessible
    STATUS  5
    DESCRIPTION
            "ARL information table entry"
    INDEX   {mprSwArlMac}
    ::= {mprSwArlTable 1}

mprSwArlMac  OBJECT-TYPE
    SYNTAX  PhysAddress
    ACCESS  read-only
    STATUS  5
    DESCRIPTION
            "ARL table index"
    ::= {mprSwArlEntry 1}

mprSwArlPortSlot  OBJECT-TYPE
    SYNTAX  INTEGER
    ACCESS  read-only
    STATUS  5
    DESCRIPTION
            "Related port's slot number"
    ::= {mprSwArlEntry 2}

mprSwArlPortIndex  OBJECT-TYPE
    SYNTAX  INTEGER
    ACCESS  read-only
    STATUS  5
    DESCRIPTION
            "Related port's number"
    ::= {mprSwArlEntry 3}

mprSwArlAge  OBJECT-TYPE
    SYNTAX  INTEGER
    ACCESS  read-only
    STATUS  5
    DESCRIPTION
            "existed time"
    ::= {mprSwArlEntry 4}
END
