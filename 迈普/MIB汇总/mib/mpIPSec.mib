-- *****************************************************************
-- mpIPsec.mib:  Maipu enterprise device IPsec MIB file
--
-- version 1.0.0.1, Sep 28, 2004 liuyu
--
-- Copyright (c)  by Maipu Communication Inc.
-- All rights reserved.
-- 
-- *****************************************************************

	
MAIPU-SECURITY-IPSEC-MIB DEFINITIONS ::= BEGIN

IMPORTS
        MODULE-IDENTITY, OBJECT-TYPE, Counter32,
       	IpAddress, Unsigned32		FROM SNMPv2-SMI
       	RowStatus			FROM SNMPv2-TC
       	mpSecurity			FROM MAIPU-SMI;
       
mpSecurityRouter 	MODULE-IDENTITY
        LAST-UPDATED "200501120932Z"      -- Wednesday Jan 12 09:32:35 PDT 2005
        ORGANIZATION "Maipu Communication"
        CONTACT-INFO
          	"       liu Yu
          	Postal: Maipu Inc
                  Tel: (028)85148048
          	E-Mail: office@maipu.com "
          
        DESCRIPTION
	 	"The MIB module describes the IPSec protocol for Maipu Security Router. "          
        ::= { mpSecurity 3 }

-- *****************************************************************

ipsecModule		OBJECT IDENTIFIER ::= { mpSecurityRouter 1 }

ipsecConfigGroup	OBJECT IDENTIFIER ::= { IPsecModule 1 }
ipsecDebugGroup		OBJECT IDENTIFIER ::= { IPsecModule 2 }
ipsecMonitorGroup	OBJECT IDENTIFIER ::= { IPsecModule 3 }

-- *****************************************************************

-- *****************************************************************
-- IKETunnel Table

ikeTunnelTable	OBJECT-TYPE
    	SYNTAX SEQUENCE OF IKETunnelEntry
    	MAX-ACCESS not-accessible
    	STATUS current
    	DESCRIPTION
		"The table contains all the crypto tunnels using IKE negotiation, which is configured by the operator."
    	::={ IPsecConfigGroup 1 }
    
ikeTunnelEntry	OBJECT-TYPE
    	SYNTAX IKETunnelEntry
    	MAX-ACCESS not-accessible
    	STATUS current
    	DESCRIPTION
		"Each entry contains the attributes associated with one crypto tunnel."
    	INDEX { IKETunnelName }
    	::= { IKETunnelTable 1 }
    
IKETunnelEntry	::=
	SEQUENCE {
		ikeTunnelName			OCTET STRING,
		ikeTunnelPeerAddr		IpAddress,
		ikeTunnelPeerName		OCTET STRING,
		ikeTunnelLocalAddr		IpAddress,
		ikeTunnelLocalIfName		OCTET STRING,
		ikeTunnelPeerIdType		INTEGER,
		ikeTunnelPeerID			OCTET STRING,
		ikeTunnelLocalID		OCTET STRING,
		ikeTunnelShareLimit		INTEGER,
		ikeTunnelSecDomain		OCTET STRING,
		ikeTunnelPhaseOneMode		INTEGER,
		ikeTunnelNATActiveTime		INTEGER,
		ikeTunnelAuthMeans		INTEGER,
		ikeTunnelDPDPeriod		INTEGER,
		ikeTunnelDPDRetry		INTEGER,
		ikeTunnelDPDAction		INTEGER,
		ikeTunnelSecLevel		INTEGER,
		ikeTunnelIKEProp1		OCTET STRING,
		ikeTunnelIKEProp2		OCTET STRING,
		ikeTunnelIKEProp3		OCTET STRING,
		ikeTunnelIKEProp4		OCTET STRING,
		ikeTunnelIPsecProp1		OCTET STRING,
		ikeTunnelIPsecProp2		OCTET STRING,
		ikeTunnelIPsecProp3		OCTET STRING,
		ikeTunnelIPsecProp4		OCTET STRING,
		ikeTunnelIdleTime		INTEGER,
		ikeTunnelAutoUp			INTEGER,
		ikeTunnelType			INTEGER,
		ikeTunnelDHCPoIPsec		INTEGER,
		ikeTunnelParentName		OCTET STRING,
		ikeTunnelSetNMS			INTEGER,
		ikeTunnelAdmin			INTEGER,
		ikeTunnelStatus			RowStatus
		}	

ikeTunnelName			OBJECT-TYPE
	SYNTAX	OCTET STRING
	MAX-ACCESS	read-write
	STATUS	current
	DESCRIPTION
		"This object defines the name of one crypto tunnel."
	::= { IKETunnelEntry 1 }
	
ikeTunnelPeerAddr		OBJECT-TYPE
	SYNTAX	IpAddress
	MAX-ACCESS	read-write
	STATUS	current
	DESCRIPTION
		"This object defines the IP address of the peer used by a crypto tunnel."
	::= { IKETunnelEntry 2 }

ikeTunnelPeerName		OBJECT-TYPE
	SYNTAX	OCTET STRING
	MAX-ACCESS	read-write
	STATUS	current
	DESCRIPTION
		"This object defines the hostname of the peer used by a crypto tunnel."
	::= { IKETunnelEntry 3 }
	
ikeTunnelLocalAddr		OBJECT-TYPE
	SYNTAX	IpAddress
	MAX-ACCESS	read-write
	STATUS	current
	DESCRIPTION
		"This object defines the local IP address used by a crypto tunnel."
	::= { IKETunnelEntry 4 }
	
ikeTunnelLocalIfName		OBJECT-TYPE
	SYNTAX	OCTET STRING
	MAX-ACCESS	read-write
	STATUS	current
	DESCRIPTION
		"This object defines the local interface name used by a crypto tunnel."
	::= { IKETunnelEntry 5 }

ikeTunnelPeerIdType		OBJECT-TYPE
	SYNTAX	INTEGER{
			id_ALIAS(1),
			id_GROUP(2),
			id_OTHER(3)
			}
	MAX-ACCESS	read-write
	STATUS	current
	DESCRIPTION
		"This object defines the peer's id used by a crypto tunnel."
	::= { IKETunnelEntry 6 }
		
ikeTunnelPeerID		OBJECT-TYPE
	SYNTAX	OCTET STRING
	MAX-ACCESS	read-write
	STATUS	current
	DESCRIPTION
		"This object defines the peer's id used by a crypto tunnel."
	::= { IKETunnelEntry 7 }
	
ikeTunnelLocalID		OBJECT-TYPE
	SYNTAX	OCTET STRING
	MAX-ACCESS	read-write
	STATUS	current
	DESCRIPTION
		"This object defines the local id used by a crypto tunnel."
	::= { IKETunnelEntry 8 }
	
ikeTunnelShareLimit		OBJECT-TYPE
	SYNTAX	INTEGER(0..100000)
	MAX-ACCESS	read-write
	STATUS	current
	DESCRIPTION
		"This object defines the maximum number of the connections sharing this crypto tunnel." 
	::= { IKETunnelEntry 9 }
	
ikeTunnelSecDomain		OBJECT-TYPE
	SYNTAX	OCTET STRING
	MAX-ACCESS	read-write
	STATUS	current
	DESCRIPTION
		"This object defines the name of the virtual security domain used by a crypto tunnel."
	::= { IKETunnelEntry 10 }
	
ikeTunnelPhaseOneMode		OBJECT-TYPE
	SYNTAX	INTEGER {
				mainMode(1),
				aggressiveMode(2)
				}
	MAX-ACCESS	read-write
	STATUS	current
	DESCRIPTION
		"This object defines the exchange mode used in IKE phase one negotiation."
	DEFVAL { MainMode }
	::= { IKETunnelEntry 11 }
	
ikeTunnelNATActiveTime		OBJECT-TYPE
	SYNTAX	INTEGER(10..3600)
	MAX-ACCESS	read-write
	STATUS	current
	DESCRIPTION
		"This object defines the period for keeping alive when carrying ong NAT traversal."
	::= { IKETunnelEntry 12 }

ikeTunnelAuthMeans		OBJECT-TYPE
	SYNTAX	INTEGER {
				presharedKey(1),
				rsaSignature(2)
				}
	MAX-ACCESS	read-write
	STATUS	current
	DESCRIPTION
		"This object defines the authentication mode used in IKE phase one negotiation."
	DEFVAL { PreSharedKey }
	::= { IKETunnelEntry 13 }

ikeTunnelDPDPeriod		OBJECT-TYPE
	SYNTAX	INTEGER(10..3600)
	MAX-ACCESS	read-write
	STATUS	current
	DESCRIPTION
		"This object defines the period for sending DPD message."
	::= { IKETunnelEntry 14 }

ikeTunnelDPDRetry		OBJECT-TYPE
	SYNTAX	INTEGER(2..100)
	MAX-ACCESS	read-write
	STATUS	current
	DESCRIPTION
		"This object defines the times for trying to detect if the peer is alive using the DPD message."
	::= { IKETunnelEntry 15 }

ikeTunnelDPDAction		OBJECT-TYPE
	SYNTAX	INTEGER {
				hold(1),
				clear(2),
				none(3)
				}
	MAX-ACCESS	read-write
	STATUS	current
	DESCRIPTION
		"This object defines the action will be executed when finding peer is dead using the DPD message.
		Note: none means no DPD."
	DEFVAL { hold }
	::= { IKETunnelEntry 16 }

ikeTunnelSecLevel		OBJECT-TYPE
	SYNTAX	INTEGER {
				basic(1),
				standard(2),
				high(3)
				}
	MAX-ACCESS	read-write
	STATUS	current
	DESCRIPTION
		"This object defines the security level used by this tunnel in negotiation."
	DEFVAL { standard }
	::= { IKETunnelEntry 17 }

ikeTunnelIKEProp1		OBJECT-TYPE
	SYNTAX	OCTET STRING
	MAX-ACCESS	read-write
	STATUS	current
	DESCRIPTION
		"This object defines the IKE proposal used by the tunnel in negotiation."
	::= { IKETunnelEntry 18 }

ikeTunnelIKEProp2		OBJECT-TYPE
	SYNTAX	OCTET STRING
	MAX-ACCESS	read-write
	STATUS	current
	DESCRIPTION
		"This object defines the IKE proposal used by the tunnel in negotiation."
	::= { IKETunnelEntry 19 }

ikeTunnelIKEProp3		OBJECT-TYPE
	SYNTAX	OCTET STRING
	MAX-ACCESS	read-write
	STATUS	current
	DESCRIPTION
		"This object defines the IKE proposal used by the tunnel in negotiation."
	::= { IKETunnelEntry 20 }

ikeTunnelIKEProp4		OBJECT-TYPE
	SYNTAX	OCTET STRING
	MAX-ACCESS	read-write
	STATUS	current
	DESCRIPTION
		"This object defines the IKE proposal used by the tunnel in negotiation."
	::= { IKETunnelEntry 21 }

ikeTunnelIPsecProp1		OBJECT-TYPE
	SYNTAX	OCTET STRING
	MAX-ACCESS	read-write
	STATUS	current
	DESCRIPTION
		"This object defines the IPsec proposal used by the tunnel in negotiation."
	::= { IKETunnelEntry 22 }

ikeTunnelIPsecProp2		OBJECT-TYPE
	SYNTAX	OCTET STRING
	MAX-ACCESS	read-write
	STATUS	current
	DESCRIPTION
		"This object defines the IPsec proposal used by the tunnel in negotiation."
	::= { IKETunnelEntry 23 }

ikeTunnelIPsecProp3		OBJECT-TYPE
	SYNTAX	OCTET STRING
	MAX-ACCESS	read-write
	STATUS	current
	DESCRIPTION
		"This object defines the IPsec proposal used by the tunnel in negotiation."
	::= { IKETunnelEntry 24 }

ikeTunnelIPsecProp4		OBJECT-TYPE
	SYNTAX	OCTET STRING
	MAX-ACCESS	read-write
	STATUS	current
	DESCRIPTION
		"This object defines the IPsec proposal used by the tunnel in negotiation."
	::= { IKETunnelEntry 25 }

ikeTunnelIdleTime		OBJECT-TYPE
	SYNTAX	INTEGER
	MAX-ACCESS	read-write
	STATUS	current
	DESCRIPTION
		"This object defines the idle time of the IPsec SAs constructed by the tunnel."
	::= { IKETunnelEntry 26 }

ikeTunnelAutoUp			OBJECT-TYPE
	SYNTAX	INTEGER {
				enable(1),
				disable(2)
				}
	MAX-ACCESS	read-write
	STATUS	current
	DESCRIPTION
		"This object defines whether IPsec SAs should have beening constructed by the tunnel right now or not."
	DEFVAL { disable }
	::= { IKETunnelEntry 27 }
	
ikeTunnelType			OBJECT-TYPE
	SYNTAX	INTEGER {
				permanent(1),
				template(2),
				instance(3)
				}
	MAX-ACCESS	read-only
	STATUS	current
	DESCRIPTION
		"This object defines the type of the tunnel."
	::= { IKETunnelEntry 28 }

ikeTunnelDHCPoIPsec		OBJECT-TYPE
	SYNTAX	INTEGER {
				enable(1),
				disable(2)
				}
	MAX-ACCESS	read-write
	STATUS	current
	DESCRIPTION
		"This object defines whether the tunnel can support the function DHCP over IPsec or not."
	::= { IKETunnelEntry 29 }

ikeTunnelParentName		OBJECT-TYPE
	SYNTAX	OCTET STRING
	MAX-ACCESS	read-only
	STATUS	current
	DESCRIPTION
		"This object defines the parent tunnel name of instance tunnel."
	::= { IKETunnelEntry 30 }
	
ikeTunnelSetNMS		OBJECT-TYPE
	SYNTAX	INTEGER{
			true(1),
			false(2)
			}
	MAX-ACCESS	read-write
	STATUS	current
	DESCRIPTION
		"This object defines the init-server property."
	::= { IKETunnelEntry 31 }		

ikeTunnelAdmin		OBJECT-TYPE
	SYNTAX	INTEGER{
			true(1),
			false(2)
			}
	MAX-ACCESS	read-write
	STATUS	current
	DESCRIPTION
		"This object defines the administrative property."
	::= { IKETunnelEntry 32 }
		
ikeTunnelStatus			OBJECT-TYPE
	SYNTAX		RowStatus
	MAX-ACCESS 	read-create
	STATUS 		current
    	DESCRIPTION
    		"The object defines the status of the table entry."
    	::= { IKETunnelEntry 33 }

-- *****************************************************************

-- *****************************************************************
-- Manual Tunnel Table

manTunnelTable	OBJECT-TYPE
    	SYNTAX SEQUENCE OF ManTunnelEntry
    	MAX-ACCESS not-accessible
    	STATUS current
    	DESCRIPTION
		"The table contains all the manual crypto tunnels configured by the operator."
    	::={ IPsecConfigGroup 2 }
    
manTunnelEntry	OBJECT-TYPE
    	SYNTAX ManTunnelEntry
    	MAX-ACCESS not-accessible
    	STATUS current
    	DESCRIPTION
		"Each entry contains the attributes associated with one manual crypto tunnel."
    	INDEX { ManTunnelName }
    	::= { ManTunnelTable 1 }
    
ManTunnelEntry	::=
	SEQUENCE {
		manTunnelName			OCTET STRING,
		manTunnelPeerAddr		IpAddress,
		manTunnelInAHSPI		INTEGER,
		manTunnelInAHKey		OCTET STRING,
		manTunnelInESPSPI		INTEGER,
		manTunnelInESPAuthKey		OCTET STRING,
		manTunnelInESPCiperKey		OCTET STRING,
		manTunnelOutAHSPI		INTEGER,
		manTunnelOutAHKey		OCTET STRING,
		manTunnelOutESPSPI		INTEGER,
		manTunnelOutESPAuthKey		OCTET STRING,
		manTunnelOutESPCiperKey		OCTET STRING,
		manTunnelInCPI			INTEGER,
		manTunnelOutCPI			INTEGER,
		manTunnelIPsecProp		OCTET STRING,
		manTunnelLocalIfName		OCTET STRING,
		manTunnelStatus			RowStatus
		}	

manTunnelName			OBJECT-TYPE
	SYNTAX	OCTET STRING
	MAX-ACCESS	read-write
	STATUS	current
	DESCRIPTION
		"This object defines the name of one manual crypto tunnel."
	::= { ManTunnelEntry 1 }
	
manTunnelPeerAddr		OBJECT-TYPE
	SYNTAX	IpAddress
	MAX-ACCESS	read-write
	STATUS	current
	DESCRIPTION
		"This object defines the IP address of the peer used by a crypto tunnel. "
	::= { ManTunnelEntry 2 }

manTunnelInAHSPI		OBJECT-TYPE
	SYNTAX	INTEGER(255..511)
	MAX-ACCESS	read-write
	STATUS	current
	DESCRIPTION
		"This object defines the SPI of the inbound SA on protocol AH. 
		Note: 255 means no AH."
	::= { ManTunnelEntry 3 }
	
manTunnelInAHKey		OBJECT-TYPE
	SYNTAX	OCTET STRING (SIZE(16..254))
	MAX-ACCESS	read-write
	STATUS	current
	DESCRIPTION
		"This object defines the key used by the inbound SA on protocol AH. "
	::= { ManTunnelEntry 4 }
	
manTunnelInESPSPI		OBJECT-TYPE
	SYNTAX	INTEGER(255..511)
	MAX-ACCESS	read-write
	STATUS	current
	DESCRIPTION
		"This object defines the SPI of the inbound SA on protocol ESP. 
		Note: 255 means no ESP."
	::= { ManTunnelEntry 5 }
	
manTunnelInESPAuthKey		OBJECT-TYPE
	SYNTAX	OCTET STRING (SIZE(16..254))
	MAX-ACCESS	read-write
	STATUS	current
	DESCRIPTION
		"This object defines the key used by the inbound SA about authentication algorithm on protocol ESP. "
	::= { ManTunnelEntry 6 }
	
manTunnelInESPCiperKey		OBJECT-TYPE
	SYNTAX	OCTET STRING (SIZE(16..254))
	MAX-ACCESS	read-write
	STATUS	current
	DESCRIPTION
		"This object defines the key used by the inbound SA about encryption algorithm on protocol ESP. "
	::= { ManTunnelEntry 7 }
	
manTunnelOutAHSPI		OBJECT-TYPE
	SYNTAX	INTEGER(255..511)
	MAX-ACCESS	read-write
	STATUS	current
	DESCRIPTION
		"This object defines the SPI of the outbound SA on protocol AH. 
		Note: 255 means no AH."
	::= { ManTunnelEntry 8 }
	
manTunnelOutAHKey		OBJECT-TYPE
	SYNTAX	OCTET STRING (SIZE(16..254))
	MAX-ACCESS	read-write
	STATUS	current
	DESCRIPTION
		"This object defines the key used by the outbound SA on protocol AH. "
	::= { ManTunnelEntry 9 }
	
manTunnelOutESPSPI		OBJECT-TYPE
	SYNTAX	INTEGER(255..511)
	MAX-ACCESS	read-write
	STATUS	current
	DESCRIPTION
		"This object defines the SPI of the outbound SA on protocol ESP. 
		Note: 255 means no ESP."
	::= { ManTunnelEntry 10 }
	
manTunnelOutESPAuthKey		OBJECT-TYPE
	SYNTAX	OCTET STRING (SIZE(16..254))
	MAX-ACCESS	read-write
	STATUS	current
	DESCRIPTION
		"This object defines the key used by the outbound SA about authentication algorithm on protocol ESP. "
	::= { ManTunnelEntry 11 }
	
manTunnelOutESPCiperKey		OBJECT-TYPE
	SYNTAX	OCTET STRING (SIZE(16..254))
	MAX-ACCESS	read-write
	STATUS	current
	DESCRIPTION
		"This object defines the key used by the outbound SA about encryption algorithm on protocol ESP. "
	::= { ManTunnelEntry 12 }

manTunnelInCPI		OBJECT-TYPE
	SYNTAX	INTEGER(255..511)
	MAX-ACCESS	read-write
	STATUS	current
	DESCRIPTION
		"This object defines the CPI of the inbound SA on protocol IPComp. 
		Note: 255 means no IPComp."
	::= { ManTunnelEntry 13 }

manTunnelOutCPI		OBJECT-TYPE
	SYNTAX	INTEGER(255..511)
	MAX-ACCESS	read-write
	STATUS	current
	DESCRIPTION
		"This object defines the CPI of the outbound SA on protocol IPComp. 
		Note: 255 means no IPComp."
	::= { ManTunnelEntry 14 }
		
manTunnelIPsecProp		OBJECT-TYPE
	SYNTAX	OCTET STRING
	MAX-ACCESS	read-write
	STATUS	current
	DESCRIPTION
		"This object defines the IPsec proposal used by the tunnel for constructing IPsec SAs."
	::= { ManTunnelEntry 15 }
	
manTunnelLocalIfName		OBJECT-TYPE
	SYNTAX	OCTET STRING
	MAX-ACCESS	read-write
	STATUS	current
	DESCRIPTION
		"This object defines the local interface name used by a crypto tunnel."
	::= { ManTunnelEntry 16 }
	
manTunnelStatus			OBJECT-TYPE
	SYNTAX		RowStatus
	MAX-ACCESS 	read-create
	STATUS 		current
    	DESCRIPTION
    		"The object defines the status of the table entry."
    	::= { ManTunnelEntry 17 }
		
-- *****************************************************************

-- *****************************************************************
-- IKE Proposal Table

ikePropTable	OBJECT-TYPE
    	SYNTAX SEQUENCE OF IKEPropEntry
    	MAX-ACCESS not-accessible
    	STATUS current
    	DESCRIPTION
		"The table contains all the IKE proposals configured by the operator."
    	::={ IPsecConfigGroup 3 }
    
ikePropEntry	OBJECT-TYPE
    	SYNTAX IKEPropEntry
    	MAX-ACCESS not-accessible
    	STATUS current
    	DESCRIPTION
		"Each entry contains the attributes associated with one IKE proposal."
    	INDEX { IKEPropName }
    	::= { IKEPropTable 1 }
    
IKEPropEntry	::=
	SEQUENCE {
		ikePropName			OCTET STRING,
		ikePropEncyptoAlg		INTEGER,
		ikePropAuthAlg			INTEGER,
		ikePropDHGroup			INTEGER,
		ikePropLifetime			INTEGER,
		ikePropStatus			RowStatus
		}	

ikePropName			OBJECT-TYPE
	SYNTAX	OCTET STRING
	MAX-ACCESS	read-write
	STATUS	current
	DESCRIPTION
		"This object defines the name of one IKE proposal. "
	::= { IKEPropEntry 1 }
	
ikePropEncyptoAlg		OBJECT-TYPE
	SYNTAX	INTEGER {
				trides(1),
				des(2),
				aes128(3),
				aes192(4),
				aes256(5),
				blowfish(6),
				cast(7)
				}
	MAX-ACCESS	read-write
	STATUS	current
	DESCRIPTION
		"This object defines the encryption algorithm for one IKE proposal. "
	DEFVAL { des }
	::= { IKEPropEntry 2 }
	
ikePropAuthAlg			OBJECT-TYPE
	SYNTAX	INTEGER {
				md5(1),
				sha1(2),
				sha256(3),
				sha512(4)
				}
	MAX-ACCESS	read-write
	STATUS	current
	DESCRIPTION
		"This object defines the authenticaion algorithm for one IKE proposal. "
	DEFVAL { sha1 }
	::= { IKEPropEntry 3 }
	
ikePropDHGroup			OBJECT-TYPE
	SYNTAX	INTEGER {
				group1(1),
				group2(2),
				group5(3),
				group14(4),
				group15(5),
				group16(6),
				group17(7),
				group18(8)
				}
	MAX-ACCESS	read-write
	STATUS	current
	DESCRIPTION
		"This object defines the DH groupware for one IKE proposal. "
	DEFVAL { group1 }
	::= { IKEPropEntry 4 }
	
ikePropLifetime			OBJECT-TYPE
	SYNTAX	INTEGER(180..31536000)
	MAX-ACCESS	read-write
	STATUS	current
	DESCRIPTION
		"This object defines the lifetime for one IKE proposal. "
	DEFVAL	{ 86400}
	::= { IKEPropEntry 5 }
	
ikePropStatus			OBJECT-TYPE
	SYNTAX		RowStatus
	MAX-ACCESS 	read-create
	STATUS 		current
    	DESCRIPTION
    		"The object defines the status of the table entry."
    	::= { IKEPropEntry 6 }

-- *****************************************************************

-- *****************************************************************
-- IPsec Proposal Table

ipsecPropTable	OBJECT-TYPE
    	SYNTAX SEQUENCE OF IPsecPropEntry
    	MAX-ACCESS not-accessible
    	STATUS current
    	DESCRIPTION
		"The table contains all the IPsec proposals configured by the operator."
    	::={ IPsecConfigGroup 4 }
    
ipsecPropEntry	OBJECT-TYPE
    	SYNTAX IPsecPropEntry
    	MAX-ACCESS not-accessible
    	STATUS current
    	DESCRIPTION
		"Each entry contains the attributes associated with one IPsec proposal."
    	INDEX { IPsecPropName }
    	::= { IPsecPropTable 1 }
    
IPsecPropEntry	::=
	SEQUENCE {
		ipsecPropName			OCTET STRING,		
		ipsecPropEncyptoAlg		INTEGER,
		ipsecPropESPAuthAlg		INTEGER,
		ipsecPropAHAuthAlg		INTEGER,
		ipsecPropCompAlg		INTEGER,
		ipsecPropEncapMode		INTEGER,
		ipsecPropDHGroup		INTEGER,
		ipsecPropLifeSeconds		INTEGER,
		ipsecPropLifeKBytes		INTEGER,
		ipsecPropStatus			RowStatus
		}	

ipsecPropName			OBJECT-TYPE
	SYNTAX	OCTET STRING
	MAX-ACCESS	read-write
	STATUS	current
	DESCRIPTION
		"This object defines the name of one IPsec proposal. "
	::= { IPsecPropEntry 1 }
	
ipsecPropEncyptoAlg		OBJECT-TYPE
	SYNTAX	INTEGER {
				trides(1),
				des(2),
				aes128(3),
				aes192(4),
				aes256(5),
				blowfish(6),
				cast(7),
				serpent(8),
				twofish(9),
				ssp02(10),
				null(11),
				none(12)
				}
	MAX-ACCESS	read-write
	STATUS	current
	DESCRIPTION
		"This object defines the encryption algorithm for one IPsec proposal. "
	DEFVAL { des }
	::= { IPsecPropEntry 2 }
	
ipsecPropESPAuthAlg		OBJECT-TYPE
	SYNTAX	INTEGER {
				md5(1),
				sha1(2),
				sha256(3),
				sha512(4),
				rmd160(5),
				aesmac(6),
				none(7)
				}
	MAX-ACCESS	read-write
	STATUS	current
	DESCRIPTION
		"This object defines the encryption algorithm for one IPsec proposal. "
	DEFVAL { md5 }
	::= { IPsecPropEntry 3 }
	
ipsecPropAHAuthAlg			OBJECT-TYPE
	SYNTAX	INTEGER {
				md5(1),
				sha1(2),
				sha256(3),
				sha512(4),
				none(5)
				}
	MAX-ACCESS	read-write
	STATUS	current
	DESCRIPTION
		"This object defines the authenticaion algorithm for one IPsec proposal. "
	DEFVAL { none }
	::= { IPsecPropEntry 4 }

ipsecPropCompAlg			OBJECT-TYPE
	SYNTAX	INTEGER {
				lzs(1),
				deflate(2),
				none(3)
				}
	MAX-ACCESS	read-write
	STATUS	current
	DESCRIPTION
		"This object defines the compression algorithm for one IPsec proposal. "
	DEFVAL { none }
	::= { IPsecPropEntry 5 }
	
ipsecPropEncapMode			OBJECT-TYPE
	SYNTAX	INTEGER {
				tunnel(1),
				transport(2)
				}
	MAX-ACCESS	read-write
	STATUS	current
	DESCRIPTION
		"This object defines the encapsulation mode for one IPsec proposal. "
	DEFVAL { tunnel }
	::= { IPsecPropEntry 6 }
	
ipsecPropDHGroup			OBJECT-TYPE
	SYNTAX	INTEGER {
				group1(1),
				group2(2),
				group5(3),
				group14(4),
				group15(5),
				group16(6),
				group17(7),
				group18(8),
				none(9)
				}
	MAX-ACCESS	read-write
	STATUS	current
	DESCRIPTION
		"This object defines the DH groupware for one IPsec proposal. "
	DEFVAL { group1 }
	::= { IPsecPropEntry 7 }
	
ipsecPropLifeSeconds			OBJECT-TYPE
	SYNTAX	INTEGER(180..31536000)
	MAX-ACCESS	read-write
	STATUS	current
	DESCRIPTION
		"This object defines the lifetime for one IPsec proposal. "
	::= { IPsecPropEntry 8 }
	
ipsecPropLifeKBytes			OBJECT-TYPE
	SYNTAX	INTEGER(204800..2147483647)
	MAX-ACCESS	read-write
	STATUS	current
	DESCRIPTION
		"This object defines the lifetime for one IPsec proposal. "
	::= { IPsecPropEntry 9 }
	
ipsecPropStatus			OBJECT-TYPE
	SYNTAX		RowStatus
	MAX-ACCESS 	read-create
	STATUS 		current
    	DESCRIPTION
    		"The object defines the status of the table entry."
    	::= { IPsecPropEntry 10 }

-- *****************************************************************

-- *****************************************************************
-- Security Level Table

secLevelTable	OBJECT-TYPE
    	SYNTAX SEQUENCE OF SecLevelEntry
    	MAX-ACCESS not-accessible
    	STATUS current
    	DESCRIPTION
		"The table contains all the security level suits which can be customed by the operator."
    	::={ IPsecConfigGroup 5 }
    
secLevelEntry	OBJECT-TYPE
    	SYNTAX SecLevelEntry
    	MAX-ACCESS not-accessible
    	STATUS current
    	DESCRIPTION
		"Each entry contains the attributes associated with one security level suit. "
    	INDEX { SecLevelID }
    	::= { SecLevelTable 1 }
    
SecLevelEntry	::=
	SEQUENCE {
		secLevelID			INTEGER,
		secLevelIKEProp1		OCTET STRING,
		secLevelIKEProp2		OCTET STRING,
		secLevelIKEProp3		OCTET STRING,
		secLevelIKEProp4		OCTET STRING,
		secLevelIPsecProp1		OCTET STRING,
		secLevelIPsecProp2		OCTET STRING,
		secLevelIPsecProp3		OCTET STRING,
		secLevelIpsecProp4		OCTET STRING,
		secLevelStatus			RowStatus
		}	

secLevelID			OBJECT-TYPE
	SYNTAX	INTEGER {
				basic(1),
				standard(2),
				high(3)
				}
	MAX-ACCESS	read-write
	STATUS	current
	DESCRIPTION
		"This object defines the index of one security level suit. "
	::= { SecLevelEntry 1 }

secLevelIKEProp1		OBJECT-TYPE
	SYNTAX	OCTET STRING
	MAX-ACCESS	read-write
	STATUS	current
	DESCRIPTION
		"This object defines the name of one IKE proposal in this security level suit. "
	::= { SecLevelEntry 2 }
	
secLevelIKEProp2		OBJECT-TYPE
	SYNTAX	OCTET STRING
	MAX-ACCESS	read-write
	STATUS	current
	DESCRIPTION
		"This object defines the name of one IKE proposal in this security level suit. "
	::= { SecLevelEntry 3 }

secLevelIKEProp3		OBJECT-TYPE
	SYNTAX	OCTET STRING
	MAX-ACCESS	read-write
	STATUS	current
	DESCRIPTION
		"This object defines the name of one IKE proposal in this security level suit. "
	::= { SecLevelEntry 4 }
	
secLevelIKEProp4		OBJECT-TYPE
	SYNTAX	OCTET STRING
	MAX-ACCESS	read-write
	STATUS	current
	DESCRIPTION
		"This object defines the name of one IKE proposal in this security level suit. "
	::= { SecLevelEntry 5 }
	
secLevelIPsecProp1		OBJECT-TYPE
	SYNTAX	OCTET STRING
	MAX-ACCESS	read-write
	STATUS	current
	DESCRIPTION
		"This object defines the name of one IPsec proposal in this security level suit. "
	::= { SecLevelEntry 6 }
	
secLevelIPsecProp2		OBJECT-TYPE
	SYNTAX	OCTET STRING
	MAX-ACCESS	read-write
	STATUS	current
	DESCRIPTION
		"This object defines the name of one IPsec proposal in this security level suit. "
	::= { SecLevelEntry 7 }

secLevelIPsecProp3		OBJECT-TYPE
	SYNTAX	OCTET STRING
	MAX-ACCESS	read-write
	STATUS	current
	DESCRIPTION
		"This object defines the name of one IPsec proposal in this security level suit. "
	::= { SecLevelEntry 8 }

secLevelIPsecProp4		OBJECT-TYPE
	SYNTAX	OCTET STRING
	MAX-ACCESS	read-write
	STATUS	current
	DESCRIPTION
		"This object defines the name of one IPsec proposal in this security level suit. "
	::= { SecLevelEntry 9 }

secLevelStatus			OBJECT-TYPE
	SYNTAX		RowStatus
	MAX-ACCESS 	read-create
	STATUS 		current
    	DESCRIPTION
    		"The object defines the status of the table entry."
    	::= { SecLevelEntry 10 }

-- *****************************************************************

-- *****************************************************************
-- PreShared Key Table

preshKeyTable	OBJECT-TYPE
    	SYNTAX SEQUENCE OF PreShKeyEntry
    	MAX-ACCESS not-accessible
    	STATUS current
    	DESCRIPTION
		"The table contains all the preshared keys configured by the operator."
    	::={ IPsecConfigGroup 6 }
    
preshKeyEntry	OBJECT-TYPE
    	SYNTAX PreShKeyEntry
    	MAX-ACCESS not-accessible
    	STATUS current
    	DESCRIPTION
		"Each entry contains the attributes associated with one preshared key. "
    	INDEX { PreShKeyID, PreShKeyAny }
    	::= { PreShKeyTable 1 }
    
PreShKeyEntry	::=
	SEQUENCE {
		preshKeyID			OCTET STRING,
		preshKeyAny			INTEGER,
		preshKeyData			OCTET STRING,
		preshKeySeed			INTEGER,
		preshKeyStatus			RowStatus
		}	

preshKeyID			OBJECT-TYPE
	SYNTAX	OCTET STRING
	MAX-ACCESS	read-write
	STATUS	current
	DESCRIPTION
		"This object defines the identity of one preshared key. "
	::= { PreShKeyEntry 1 }

preshKeyAny			OBJECT-TYPE
	SYNTAX	INTEGER {
				yes(1),
				no(2)
				}
	MAX-ACCESS	read-write
	STATUS	current
	DESCRIPTION
		"This object defines if the key is for any peer or not. "
	DEFVAL { no }
	::= { PreShKeyEntry 2 }

preshKeyData			OBJECT-TYPE
	SYNTAX	OCTET STRING
	MAX-ACCESS	read-write
	STATUS	current
	DESCRIPTION
		"This object defines the data of one preshared key. "
	::= { PreShKeyEntry 3 }
	
preshKeySeed			OBJECT-TYPE
	SYNTAX	INTEGER {
				yes(1),
				no(2)
				}
	MAX-ACCESS	read-write
	STATUS	current
	DESCRIPTION
		"This object defines if the key is seed one or not. "
	DEFVAL { no }
	::= { PreShKeyEntry 4 }

preshKeyStatus			OBJECT-TYPE
	SYNTAX		RowStatus
	MAX-ACCESS 	read-create
	STATUS 		current
    	DESCRIPTION
    		"The object defines the status of the table entry."
    	::= { PreShKeyEntry 5 }

-- *****************************************************************

-- *****************************************************************
-- IPsec Policy (Data Flow and Action) Table

ipsecPolTable	OBJECT-TYPE
    	SYNTAX SEQUENCE OF IPsecPolEntry
    	MAX-ACCESS not-accessible
    	STATUS current
    	DESCRIPTION
		"The table contains all the IPsec policies configured by the operator."
    	::={ IPsecConfigGroup 7 }
    
ipsecPolEntry	OBJECT-TYPE
    	SYNTAX IPsecPolEntry
    	MAX-ACCESS not-accessible
    	STATUS current
    	DESCRIPTION
		"Each entry contains the attributes associated with one IPsec policy. "
    	INDEX { IPsecPolName }
    	::= { IPsecPolTable 1 }
    
IPsecPolEntry	::=
	SEQUENCE {
		ipsecPolName			OCTET STRING,
		ipsecPolSrcAddr			OCTET STRING,
		ipsecPolSrcMask			OCTET STRING,
		ipsecPolDstAddr			OCTET STRING,
		ipsecPolDstMask			OCTET STRING,
		ipsecPolProto			INTEGER,
		ipsecPolSrcPortType		INTEGER,
		ipsecPolSrcPort1		INTEGER,
		ipsecPolSrcPort2		INTEGER,
		ipsecPolDstPortType		INTEGER,
		ipsecPolDstPort1		INTEGER,
		ipsecPolDstPort2		INTEGER,
		ipsecPolAction			INTEGER,
		ipsecPolTunnel1			OCTET STRING,
		ipsecPolTunnel2			OCTET STRING,
		ipsecPolTunnel3			OCTET STRING,
		ipsecPolTunnel4			OCTET STRING,
		ipsecPolLoadBalance		INTEGER,
		ipsecPolBypass			INTEGER,
		ipsecPolIPsecProp1		OCTET STRING,
		ipsecPolIPsecProp2		OCTET STRING,
		ipsecPolIPsecProp3		OCTET STRING,
		ipsecPolIPsecProp4		OCTET STRING,	
		ipsecPolType			INTEGER,
		ipsecPolParentName		OCTET STRING,
		ipsecPolTimeRange		OCTET STRING,	
		ipsecPolStatus			RowStatus,
		ipsecPolRTReverse		INTEGER
		}	

ipsecPolName			OBJECT-TYPE
	SYNTAX	OCTET STRING
	MAX-ACCESS	read-write
	STATUS	current
	DESCRIPTION
		"This object defines the name of one IPsec policy. "
	::= { IPsecPolEntry 1 }

ipsecPolSrcAddr			OBJECT-TYPE
	SYNTAX	OCTET STRING
	MAX-ACCESS	read-write
	STATUS	current
	DESCRIPTION
		"This object defines the source address for the IPsec policy. "
	::= { IPsecPolEntry 2 }

ipsecPolSrcMask			OBJECT-TYPE
	SYNTAX	OCTET STRING
	MAX-ACCESS	read-write
	STATUS	current
	DESCRIPTION
		"This object defines the source address mask for the IPsec policy. "
	::= { IPsecPolEntry 3 }
		
ipsecPolDstAddr			OBJECT-TYPE
	SYNTAX	OCTET STRING
	MAX-ACCESS	read-write
	STATUS	current
	DESCRIPTION
		"This object defines the destination address for the IPsec policy. "
	::= { IPsecPolEntry 4 }

ipsecPolDstMask			OBJECT-TYPE
	SYNTAX	OCTET STRING
	MAX-ACCESS	read-write
	STATUS	current
	DESCRIPTION
		"This object defines the destination address mask for the IPsec policy. "
	::= { IPsecPolEntry 5 }
	
ipsecPolProto			OBJECT-TYPE
	SYNTAX	INTEGER {
				ip(1),
				tcp(2),
				udp(3),
				icmp(4),
				igmp(5)
				}
	MAX-ACCESS	read-write
	STATUS	current
	DESCRIPTION
		"This object defines the protocol of the data flow for the IPsec policy. "
	DEFVAL { ip }
	::= { IPsecPolEntry 6 }
	
ipsecPolSrcPortType		OBJECT-TYPE
	SYNTAX	INTEGER {
				single(1),
				range(2),
				any(3)
				}
	MAX-ACCESS	read-write
	STATUS	current
	DESCRIPTION
		"This object defines the type of source port number of the flow for one IPsec policy, which 
		determined whether the following two source ports is meaningful or not. "
	::= { IPsecPolEntry 7 }

ipsecPolSrcPort1		OBJECT-TYPE
	SYNTAX	INTEGER(1..65535)
	MAX-ACCESS	read-write
	STATUS	current
	DESCRIPTION
		"This object defines the source port number of the flow for one IPsec policy. 
		If the prot range is specified, it is the first port for starting. "
	::= { IPsecPolEntry 8 }
	
ipsecPolSrcPort2		OBJECT-TYPE
	SYNTAX	INTEGER(1..65535)
	MAX-ACCESS	read-write
	STATUS	current
	DESCRIPTION
		"This object defines the source port number of the flow for one IPsec policy. 
		If the prot range is specified, it is the last port for ending. "
	::= { IPsecPolEntry 9 }

ipsecPolDstPortType		OBJECT-TYPE
	SYNTAX	INTEGER {
				single(1),
				range(2),
				any(3)
				}
	MAX-ACCESS	read-write
	STATUS	current
	DESCRIPTION
		"This object defines the type of destination port number of the flow for one IPsec policy, which 
		determined whether the following two dstination ports is meaningful or not. "
	::= { IPsecPolEntry 10 }
	
ipsecPolDstPort1		OBJECT-TYPE
	SYNTAX	INTEGER(1..65535)
	MAX-ACCESS	read-write
	STATUS	current
	DESCRIPTION
		"This object defines the dstination port number of the flow for one IPsec policy. 
		If the prot range is specified, it is the first port for starting. "
	::= { IPsecPolEntry 11 }
	
ipsecPolDstPort2		OBJECT-TYPE
	SYNTAX	INTEGER(1..65535)
	MAX-ACCESS	read-write
	STATUS	current
	DESCRIPTION
		"This object defines the destination port number of the flow for one IPsec policy. 
		If the prot range is specified, it is the last port for ending. "
	::= { IPsecPolEntry 12 }
	
ipsecPolAction			OBJECT-TYPE
	SYNTAX	INTEGER {
				permit(1),
				deny(2),
				tunnel(3)
				}
	MAX-ACCESS	read-write
	STATUS	current
	DESCRIPTION
		"This object defines what action will be executed for this IPsec policy. "
	DEFVAL { tunnel }
	::= { IPsecPolEntry 13 }
	
ipsecPolTunnel1			OBJECT-TYPE
	SYNTAX	OCTET STRING
	MAX-ACCESS	read-write
	STATUS	current
	DESCRIPTION
		"This object defines the IPsec tunnel for this policy. "
	::= { IPsecPolEntry 14 }
	
ipsecPolTunnel2			OBJECT-TYPE
	SYNTAX	OCTET STRING
	MAX-ACCESS	read-write
	STATUS	current
	DESCRIPTION
		"This object defines the IPsec tunnel for this policy. "
	::= { IPsecPolEntry 15 }

ipsecPolTunnel3			OBJECT-TYPE
	SYNTAX	OCTET STRING
	MAX-ACCESS	read-write
	STATUS	current
	DESCRIPTION
		"This object defines the IPsec tunnel for this policy. "
	::= { IPsecPolEntry 16 }

ipsecPolTunnel4			OBJECT-TYPE
	SYNTAX	OCTET STRING
	MAX-ACCESS	read-write
	STATUS	current
	DESCRIPTION
		"This object defines the IPsec tunnel for this policy. "
	::= { IPsecPolEntry 17 }
	
ipsecPolLoadBalance		OBJECT-TYPE
	SYNTAX	INTEGER {
				yes(1),
				no(2)
				}
	MAX-ACCESS	read-write
	STATUS	current
	DESCRIPTION
		"This object defines whether the IPsec tunnels is for payload balance on this policy. "
	DEFVAL { no }
	::= { IPsecPolEntry 18 }

ipsecPolBypass			OBJECT-TYPE
	SYNTAX	INTEGER {
				yes(1),
				no(2)
				}
	MAX-ACCESS	read-write
	STATUS	current
	DESCRIPTION
		"This object defines whether the packets could be bypass when the ipsec sa for it is not existed. "
	DEFVAL { no }
	::= { IPsecPolEntry 19 }
		
ipsecPolIPsecProp1		OBJECT-TYPE
	SYNTAX	OCTET STRING
	MAX-ACCESS	read-write
	STATUS	current
	DESCRIPTION
		"This object defines the IPsec proposal used by this policy. "
	::= { IPsecPolEntry 20 }
	
ipsecPolIPsecProp2		OBJECT-TYPE
	SYNTAX	OCTET STRING
	MAX-ACCESS	read-write
	STATUS	current
	DESCRIPTION
		"This object defines the IPsec proposal used by this policy. "
	::= { IPsecPolEntry 21 }

ipsecPolIPsecProp3		OBJECT-TYPE
	SYNTAX	OCTET STRING
	MAX-ACCESS	read-write
	STATUS	current
	DESCRIPTION
		"This object defines the IPsec proposal used by this policy. "
	::= { IPsecPolEntry 22 }

ipsecPolIPsecProp4		OBJECT-TYPE
	SYNTAX	OCTET STRING
	MAX-ACCESS	read-write
	STATUS	current
	DESCRIPTION
		"This object defines the IPsec proposal used by this policy. "
	::= { IPsecPolEntry 23 }

ipsecPolType		OBJECT-TYPE
	SYNTAX	INTEGER {
				original(1),
				subpolicy(2)
				}
	MAX-ACCESS	read-only
	STATUS	current
	DESCRIPTION
		"This object defines the type of this policy. Note: subpolicy means this policy is generated during IKE negotiation."
	::= { IPsecPolEntry 24 }
	
ipsecPolParentName		OBJECT-TYPE
	SYNTAX	OCTET STRING
	MAX-ACCESS	read-only
	STATUS	current
	DESCRIPTION
		"This object defines the parent policy name of sub-policy. "
	::= { IPsecPolEntry 25 }

ipsecPolTimeRange		OBJECT-TYPE
	SYNTAX	OCTET STRING
	MAX-ACCESS	read-write
	STATUS	current
	DESCRIPTION
		"This object defines the time range of the policy. "
	::= { IPsecPolEntry 26 }
		
ipsecPolStatus			OBJECT-TYPE
	SYNTAX		RowStatus
	MAX-ACCESS 	read-create
	STATUS 		current
    	DESCRIPTION
    		"The object defines the status of the table entry."
    	::= { IPsecPolEntry 27 }

ipsecPolRTReverse			OBJECT-TYPE
	SYNTAX	INTEGER {
				yes(1),
				no(2)
				}
	MAX-ACCESS	read-write
	STATUS	current
	DESCRIPTION
		"This object defines whether set the reverse route while sa is established . "
	DEFVAL { no }
	::= { IPsecPolEntry 28 }
-- *****************************************************************

-- *****************************************************************
-- IKE ID alias

idAliasTable	OBJECT-TYPE
    	SYNTAX SEQUENCE OF IdAliasEntry
    	MAX-ACCESS not-accessible
    	STATUS current
    	DESCRIPTION
		"The table contains all the ID alias configured by the operator."
    	::={ IPsecConfigGroup 8 }
    
idAliasEntry	OBJECT-TYPE
    	SYNTAX IdAliasEntry
    	MAX-ACCESS not-accessible
    	STATUS current
    	DESCRIPTION
		"Each entry contains the attributes associated with one ID alias. "
    	INDEX { IdAliasName }
    	::= { IdAliasTable 1 }
    
IdAliasEntry	::=
	SEQUENCE {
		idAliasName			OCTET STRING,
		idAliasId			OCTET STRING,
		idRsetPoolName			OCTET STRING,
		idRsetAddr			OCTET STRING,
		idRsetMask			OCTET STRING,
		idRsetFirstWinsAddr		OCTET STRING,
		idRsetSecondWinsAddr		OCTET STRING,
		idRsetFirstDnsAddr		OCTET STRING,
		idRsetSecondDnsAddr		OCTET STRING,
		idAuthListName			OCTET STRING,
		idAuthUserName			OCTET STRING,
		idAuthUserGroupName		OCTET STRING,
		idAuthorListName		OCTET STRING,
		idAliasDisable			INTEGER,
		idAliasRef			INTEGER,
		idAliasTimeRange		OCTET STRING,
		idAliasStatus			RowStatus,
		idAliasVrcCfgVer		INTEGER,
		idAliasVrcOption		INTEGER
		}	

idAliasName			OBJECT-TYPE
	SYNTAX	OCTET STRING
	MAX-ACCESS	read-write
	STATUS	current
	DESCRIPTION
		"This object defines the name of the ID alias. "
	::= { IdAliasEntry 1 }

idAliasId			OBJECT-TYPE
	SYNTAX	OCTET STRING
	MAX-ACCESS	read-write
	STATUS	current
	DESCRIPTION
		"This object defines the id of the ID alias. "
	::= { IdAliasEntry 2 }
		
idRsetPoolName			OBJECT-TYPE
	SYNTAX	OCTET STRING
	MAX-ACCESS	read-write
	STATUS	current
	DESCRIPTION
		"This object defines the name of the pool name in remote settings. "
	::= { IdAliasEntry 3 }
	
idRsetAddr			OBJECT-TYPE
	SYNTAX	OCTET STRING
	MAX-ACCESS	read-write
	STATUS	current
	DESCRIPTION
		"This object defines the ip address in remote settings. "
	::= { IdAliasEntry 4 }
	
idRsetMask			OBJECT-TYPE
	SYNTAX	OCTET STRING
	MAX-ACCESS	read-write
	STATUS	current
	DESCRIPTION
		"This object defines the ip address mask in remote settings. "
	::= { IdAliasEntry 5 }	
	
idRsetFirstWinsAddr		OBJECT-TYPE
	SYNTAX	OCTET STRING
	MAX-ACCESS	read-write
	STATUS	current
	DESCRIPTION
		"This object defines the first wins address in remote settings. "
	::= { IdAliasEntry 6 }
	
idRsetSecondWinsAddr		OBJECT-TYPE
	SYNTAX	OCTET STRING
	MAX-ACCESS	read-write
	STATUS	current
	DESCRIPTION
		"This object defines the second wins address in remote settings. "
	::= { IdAliasEntry 7 }
	
idRsetFirstDnsAddr		OBJECT-TYPE
	SYNTAX	OCTET STRING
	MAX-ACCESS	read-write
	STATUS	current
	DESCRIPTION
		"This object defines the first dns address in remote settings. "
	::= { IdAliasEntry 8 }
	
idRsetSecondDnsAddr		OBJECT-TYPE
	SYNTAX	OCTET STRING
	MAX-ACCESS	read-write
	STATUS	current
	DESCRIPTION
		"This object defines the second dns address in remote settings. "
	::= { IdAliasEntry 9 }
	
idAuthListName		OBJECT-TYPE
	SYNTAX	OCTET STRING
	MAX-ACCESS	read-write
	STATUS	current
	DESCRIPTION
		"This object defines the authentication list name in remote settings. "
	::= { IdAliasEntry 10 }
	
idAuthUserName		OBJECT-TYPE
	SYNTAX	OCTET STRING
	MAX-ACCESS	read-write
	STATUS	current
	DESCRIPTION
		"This object defines the user name of authentication in remote settings. "
	::= { IdAliasEntry 11 }
	
idAuthUserGroupName	OBJECT-TYPE
	SYNTAX	OCTET STRING
	MAX-ACCESS	read-write
	STATUS	current
	DESCRIPTION
		"This object defines the user group name of authentication in remote settings. "
	::= { IdAliasEntry 12 }
	
idAuthorListName	OBJECT-TYPE
	SYNTAX	OCTET STRING
	MAX-ACCESS	read-write
	STATUS	current
	DESCRIPTION
		"This object defines the authorization list name in remote settings. "
	::= { IdAliasEntry 13 }
	
idAliasDisable		OBJECT-TYPE
	SYNTAX	INTEGER {
			true(1),
			false(2)
			}
	MAX-ACCESS	read-write
	STATUS	current
	DESCRIPTION
		"This object defines the disable flag of ID alias. "
	::= { IdAliasEntry 14 }
	
idAliasRef		OBJECT-TYPE
	SYNTAX	INTEGER
	MAX-ACCESS	read-only
	STATUS	current
	DESCRIPTION
		"This object defines the reference number of ID alias. "
	::= { IdAliasEntry 15 }
	
idAliasTimeRange	OBJECT-TYPE
	SYNTAX	OCTET STRING
	MAX-ACCESS	read-write
	STATUS	current
	DESCRIPTION
		"This object defines the time range of alias. "
	::= { IdAliasEntry 16 }
	
idAliasStatus		OBJECT-TYPE
	SYNTAX		RowStatus
	MAX-ACCESS 	read-create
	STATUS 		current
    	DESCRIPTION
    		"The object defines the status of the table entry."
    	::= { IdAliasEntry 17 }
    	
idAliasVrcCfgVer		OBJECT-TYPE
	SYNTAX		INTEGER
	MAX-ACCESS 	read-write
	STATUS 		current
    	DESCRIPTION
    		"The object defines the version of the config_file of vrc."
    	::= { IdAliasEntry 18 }
    	
idAliasVrcOption		OBJECT-TYPE
	SYNTAX	INTEGER 
	MAX-ACCESS 	read-write
	STATUS 		current
    	DESCRIPTION
    		"The object defines the binding information of vrc."
    	::= { IdAliasEntry 19 }
    	
-- *****************************************************************

-- *****************************************************************
-- Excluded id table
excludedIdTable	OBJECT-TYPE
    	SYNTAX SEQUENCE OF ExcludedIdEntry
    	MAX-ACCESS not-accessible
    	STATUS current
    	DESCRIPTION
		"The table contains all the excluded ID in ID alias."
    	::={ IPsecConfigGroup 9 }
    
excludedIdEntry		OBJECT-TYPE
    	SYNTAX 	ExcludedIdEntry
    	MAX-ACCESS not-accessible
    	STATUS current
    	DESCRIPTION
		"Each entry contains the attributes associated with excluded ID. "
    	INDEX { IdAliasName, ExcludedId }
    	::= { ExcludedIdTable 1 }
    
ExcludedIdEntry	::=
	SEQUENCE {
		idAliasName			OCTET STRING,
		excludedId			OCTET STRING,
		excludedIdStatus		RowStatus
		}	

idAliasName			OBJECT-TYPE
	SYNTAX	OCTET STRING
	MAX-ACCESS	read-write
	STATUS	current
	DESCRIPTION
		"This object defines the name of the ID alias. "
	::= { ExcludedIdEntry 1 }    	

excludedId			OBJECT-TYPE
	SYNTAX	OCTET STRING
	MAX-ACCESS	read-write
	STATUS	current
	DESCRIPTION
		"This object defines the excluded ID. "
	::= { ExcludedIdEntry 2 }        	
	
excludedIdStatus		OBJECT-TYPE
	SYNTAX		RowStatus
	MAX-ACCESS 	read-create
	STATUS 		current
    	DESCRIPTION
    		"The object defines the status of the table entry."
    	::= { ExcludedIdEntry 3 }
-- *****************************************************************

-- *****************************************************************
-- ID group table
idGroupTable	OBJECT-TYPE
    	SYNTAX SEQUENCE OF IdGroupEntry
    	MAX-ACCESS not-accessible
    	STATUS current
    	DESCRIPTION
		"The table contains all the ID group."
    	::={ IPsecConfigGroup 10 }

idGroupEntry		OBJECT-TYPE
    	SYNTAX 	AliasInGroupEntry
    	MAX-ACCESS not-accessible
    	STATUS current
    	DESCRIPTION
		"Each entry contains the attributes associated with ID group. "
    	INDEX { IdGroupName }
    	::= { IdGroupTable 1 }
    
IdGroupEntry	::=
	SEQUENCE {
		idGroupName			OCTET STRING,
		idGroupRef			INTEGER,
		idGroupStatus			RowStatus
		}	

idGroupName			OBJECT-TYPE
	SYNTAX	OCTET STRING
	MAX-ACCESS	read-write
	STATUS	current
	DESCRIPTION
		"This object defines the name of the ID group. "
	::= { IdGroupEntry 1 }    
	
idGroupRef			OBJECT-TYPE
	SYNTAX	INTEGER
	MAX-ACCESS	read-only
	STATUS	current
	DESCRIPTION
		"This object defines the referenced number. "
	::= { IdGroupEntry 2 } 

idGroupStatus		OBJECT-TYPE
	SYNTAX		RowStatus
	MAX-ACCESS 	read-create
	STATUS 		current
    	DESCRIPTION
    		"The object defines the status of the table entry."
    	::= { IdGroupEntry 3 }
    			    		
-- *****************************************************************
-- alias in group table

aliasInGroupTable	OBJECT-TYPE
    	SYNTAX SEQUENCE OF AliasInGroupEntry
    	MAX-ACCESS not-accessible
    	STATUS current
    	DESCRIPTION
		"The table contains all the ID group."
    	::={ IPsecConfigGroup 11 }
    
aliasInGroupEntry		OBJECT-TYPE
    	SYNTAX 	AliasInGroupEntry
    	MAX-ACCESS not-accessible
    	STATUS current
    	DESCRIPTION
		"Each entry contains the alias used by group. "
    	INDEX { IdGroupName, IdAliasName }
    	::= { AliasInGroupTable 1 }
    
AliasInGroupEntry	::=
	SEQUENCE {
		idGroupName			OCTET STRING,
		idAliasName			OCTET STRING,
		aliasInGroupStatus		RowStatus
		}	

idGroupName			OBJECT-TYPE
	SYNTAX	OCTET STRING
	MAX-ACCESS	read-write
	STATUS	current
	DESCRIPTION
		"This object defines the name of the ID group. "
	::= { AliasInGroupEntry 1 }    	

idAliasName			OBJECT-TYPE
	SYNTAX	OCTET STRING
	MAX-ACCESS	read-write
	STATUS	current
	DESCRIPTION
		"This object defines the ID alias. "
	::= { AliasInGroupEntry 2 }        	
	
aliasInGroupStatus		OBJECT-TYPE
	SYNTAX		RowStatus
	MAX-ACCESS 	read-create
	STATUS 		current
    	DESCRIPTION
    		"The object defines the status of the table entry."
    	::= { AliasInGroupEntry 3 }
-- *****************************************************************
    	    	
-- *****************************************************************
-- IPsec Global Command Group

ipsecGlobalGroup	OBJECT IDENTIFIER ::= { IPsecConfigGroup 12 }

ipsecFastForward	OBJECT-TYPE
	SYNTAX	INTEGER { 
				disable(1),
				enable(2) 
			}
	MAX-ACCESS	read-write
	STATUS	current
	DESCRIPTION
		"The object defines the operation of IPsec fast-forward. "
	::= { IPsecGlobalGroup 1 }

ipsecPreFragment	OBJECT-TYPE
	SYNTAX	INTEGER{
				disable(1),
				enable(2)
			}
	MAX-ACCESS	read-write
	STATUS	current
	DESCRIPTION
		"The object defines the operation of IPsec pre-fragment."
	::= { IPsecGlobalGroup 2 }

mpInitConfUserName			OBJECT-TYPE
	SYNTAX	OCTET STRING
	MAX-ACCESS	read-only
	STATUS	current
	DESCRIPTION
		"This object defines the user name of init config. "
	::= { IPsecGlobalGroup 3 }   
			
-- *****************************************************************

-- *****************************************************************

clearSAGroup	OBJECT IDENTIFIER ::= { IPsecDebugGroup 1 }


clearSARebuild	OBJECT-TYPE
	SYNTAX	INTEGER { 
				yes(1),
				no(2) 
			}
	MAX-ACCESS	read-write
	STATUS	current
	DESCRIPTION
		"The object defines the operation clearing crypto SAs, and the value of it determines whether 
		the SAs need to be rebuilded after being cleared. "
	::= { ClearSAGroup 1 }
		
clearSATunnelName	OBJECT-TYPE
	SYNTAX		OCTET STRING
	MAX-ACCESS	read-write
	STATUS	current
	DESCRIPTION
		"The object defines the name of the tunnel"
	::= { ClearSAGroup 2 }

clearSATunnelId		OBJECT-TYPE
	SYNTAX		INTEGER
	MAX-ACCESS	read-write
	STATUS		current
	DESCRIPTION
		"The object defines the id number of the tunnel"
	::= { ClearSAGroup 3 }
	
clearSAPolicyName	OBJECT-TYPE
	SYNTAX		OCTET STRING
	MAX-ACCESS	read-write
	STATUS		current
	DESCRIPTION
		"The object defines the name of the policy. "
	::= { ClearSAGroup 4 }
	
clearSAPolicyId		OBJECT-TYPE
	SYNTAX		INTEGER
	MAX-ACCESS	read-write
	STATUS		current
	DESCRIPTION
		"The object defines the id number of the policy. "
	::= { ClearSAGroup 5 }
	
-- *****************************************************************

-- *****************************************************************

changePolicyOrderGroup	OBJECT IDENTIFIER ::= { IPsecDebugGroup 2 }

changePolicyOrderType	OBJECT-TYPE
	SYNTAX		INTEGER { 
					before(1),
					after(2),
					first(3),
					last(4) 
				}
	MAX-ACCESS	read-write
	STATUS		current
	DESCRIPTION
		"The type of the operation for changed policy position. "
	::= { ChangePolicyOrderGroup 1 }

changePolicyName	OBJECT-TYPE
	SYNTAX		OCTET STRING
	MAX-ACCESS	read-write
	STATUS		current
	DESCRIPTION
		"The name of the policy which should be changed. "
	::= { ChangePolicyOrderGroup 2 }

changePolicyIndexName	OBJECT-TYPE
	SYNTAX		OCTET STRING
	MAX-ACCESS	read-write
	STATUS		current
	DESCRIPTION
		"The name of the index policy. "
	::= { ChangePolicyOrderGroup 3 }	

-- *****************************************************************

-- *****************************************************************
specialActionTable	OBJECT-TYPE
    	SYNTAX SEQUENCE OF SpecialActionEntry
    	MAX-ACCESS not-accessible
    	STATUS current
    	DESCRIPTION
		"The table contains all of special action for IPsec module."
    	::={ IPsecDebugGroup 3 }
    
specialActionEntry		OBJECT-TYPE
    	SYNTAX 	SpecialActionEntry
    	MAX-ACCESS not-accessible
    	STATUS current
    	DESCRIPTION
		"Each entry contains the attributes associated with excluded ID. "
    	INDEX { mpSpecActObjName, mpSpecActOptCode }
    	::= { SpecialActionTable 1 }
    
SpecialActionEntry	::=
	SEQUENCE {
		mpSpecActObjName		OCTET STRING,
		mpSpecActOptCode		INTEGER,
		mpSpecActOptReturn		INTEGER,
		mpSpecActStatus			RowStatus
		}	

mpSpecActObjName		OBJECT-TYPE
	SYNTAX	OCTET STRING
	MAX-ACCESS	read-write
	STATUS	current
	DESCRIPTION
		"This object defines the object name of special action. "
	::= { SpecialActionEntry 1 }    
	
mpSpecActOptCode		OBJECT-TYPE
	SYNTAX	INTEGER {
			delete_tunnel(1)
			}
	MAX-ACCESS	read-write
	STATUS	current
	DESCRIPTION
		"This object defines the option code of special action. "
	::= { SpecialActionEntry 2 }    		

mpSpecActOptReturn		OBJECT-TYPE
	SYNTAX	INTEGER {
			executing(1)
			success(2),
			fail(3)						
			}
	MAX-ACCESS	read-write
	STATUS	current
	DESCRIPTION
		"This object defines the option code of special action. "
	::= { SpecialActionEntry 3 }   
	
mpSpecActStatus		OBJECT-TYPE
	SYNTAX		RowStatus
	MAX-ACCESS 	read-create
	STATUS 		current
    	DESCRIPTION
    		"The object defines the status of the table entry."
    	::= { SpecialActionEntry 4 }   
-- *****************************************************************

-- *****************************************************************
-- IPsec notify
ipsecTraps		OBJECT IDENTIFIER ::= { IPsecMonitorGroup 0 }

ipsecSAEsatbalishedTrap		NOTIFICATION-TYPE
	OBJECTS {
		estabSaTrapStateIndex,
		estabSaTrapReplacedStateIndex,
		estabSaTrapRemoteId,
		estabSaTrapLocalId,
		estabSaTrapRemoteAddress,
		estabSaTrapLocalAddress,
		estabSaTrapPolSrcAddr,
		estabSaTrapPolSrcMask,
		estabSaTrapPolDstAddr,
		estabSaTrapPolDstMask,
		estabSaTrapPolProto,
		estabSaTrapPolSrcPort,
		estabSaTrapPolDstPort		
		}	
	STATUS current
    	DESCRIPTION
		"IPsec SA建立的TRAP."
    	::={ IPsecTraps 1 }

ipsecSADeletedTrap		NOTIFICATION-TYPE
	OBJECTS {
		delSaTrapStateIndex,
		delSaTrapRemoteId,
		delSaTrapLocalId,
		delSaTrapDurationTime,
		delSaTrapOutboundKBytes,
		delSaTrapInboundKBytes				
		}	
	STATUS current
    	DESCRIPTION
		"IPsec SA删除的TRAP."
    	::={ IPsecTraps 2 }
    	
ipsecKeepAliveTrap		NOTIFICATION-TYPE
	OBJECTS {	
		mpInitConfUserName	
		}	
	STATUS current
    	DESCRIPTION
		"IPsec keep alive的TRAP."
    	::={ IPsecTraps 3 }
-- *****************************************************************

-- *****************************************************************
-- IKE SA table


ikeSaInfoTable	OBJECT-TYPE
    	SYNTAX SEQUENCE OF IkeSaInfoEntry
    	MAX-ACCESS not-accessible
    	STATUS current
    	DESCRIPTION
		"The table contains all the detail about ISAKMP SAs including the connected IPSec SAs.
		It corresponds to cmd: show crypto isa sa. When showing the simple information, it only 
		shows the four fields of the table: IkeSaLocalAddress, IkeSaRemoteAddress, IkeSaStatus, IkeSASerialNo. "
   	::= { IPsecMonitorGroup 1 }
    
ikeSaInfoEntry	OBJECT-TYPE
    	SYNTAX IkeSaInfoEntry
    	MAX-ACCESS not-accessible
    	STATUS current
    	DESCRIPTION
		"Each entry contains all the fields connected with one IKE SA."
    	INDEX { IkeSASerialNo }
    	::= { IkeSaInfoTable 1 }
    
IkeSaInfoEntry	::=
	SEQUENCE {
			ikeSASerialNo			Counter32,	
			ikeSaStatus			OCTET STRING,	
			ikeSaStatusDetail		OCTET STRING,	
			ikeSaState			INTEGER,
			ikeSaLocalAddress		IpAddress,	
			ikeSaRemoteAddress		IpAddress,	
			ikeSaTunnelName			OCTET STRING,	
			ikeSaRemoteCfgIdentity	OCTET STRING,
			ikeSaRemoteInstIdentity	OCTET STRING,
			ikeSaLocalCfgIdentity		OCTET STRING,
			ikeSaLocalInstIdentity		OCTET STRING,
			ikeFlowName			OCTET STRING,			
			ikeSaTimerEvent1			OCTET STRING,	
			ikeSaTimerRemain1		UInteger32,	
			ikeSaTimerEvent2			OCTET STRING,	
			ikeSaTimerRemain2		UInteger32,	
			ikeSaTimerEvent3			OCTET STRING,	
			ikeSaTimerRemain3		UInteger32,	
			ikeSaTimerEvent4			OCTET STRING,	
			ikeSaTimerRemain4		UInteger32,	
			ikeSaIpsecAhOutSpi		Counter32,
			ikeSaIpsecAhInSpi		Counter32,
			ikeSaIpsecEspOutSpi		Counter32,
			ikeSaIpsecEspInSpi		Counter32,
			}
			
ikeSASerialNo		OBJECT-TYPE
	SYNTAX		Counter32
	MAX-ACCESS	read-only
	STATUS 		current
    	DESCRIPTION
    		"The object defines serial number of an IKE SA, which is also the index of the table. "
	::= { IkeSaInfoEntry 1 }
	
ikeSaStatus		OBJECT-TYPE
	SYNTAX		OCTET STRING
	MAX-ACCESS	read-only
	STATUS 		current
    	DESCRIPTION
    		"The object defines the state of an IKE SA, which also shows the state of IKE exchange for building IPSec SA. "
	::= { IkeSaInfoEntry 2 }	
	
ikeSaStatusDetail	OBJECT-TYPE
	SYNTAX		OCTET STRING
	MAX-ACCESS	read-only
	STATUS 		current
    	DESCRIPTION
    		"The object defines the detail about IkeSaStatus object, which can be easily understood. "
	::= { IkeSaInfoEntry 3 }

ikeSaState		OBJECT-TYPE
	SYNTAX		INTEGER { 
					current(1),
					negotiation(2),
					replaced(3)
					}
	MAX-ACCESS	read-only
	STATUS 		current
    	DESCRIPTION
    		"The object defines three type of state. "
	::= { IkeSaInfoEntry 4 }	
	
ikeSaLocalAddress	OBJECT-TYPE
	SYNTAX		IpAddress
	MAX-ACCESS	read-only
	STATUS 		current
    	DESCRIPTION
    		"The object defines the local IP address of the tunnel. "
	::= { IkeSaInfoEntry 5 }	
	
ikeSaRemoteAddress	OBJECT-TYPE
	SYNTAX		IpAddress
	MAX-ACCESS	read-only
	STATUS 		current
    	DESCRIPTION
    		"The object defines the peer IP address of the tunnel. "
	::= { IkeSaInfoEntry 6 }
	
ikeSaTunnelName		OBJECT-TYPE
	SYNTAX		OCTET STRING
	MAX-ACCESS	read-only
	STATUS 		current
    	DESCRIPTION
    		"The object defines the identifier nubmer of the tunnel corresponding to the IKE SA. "
	::= { IkeSaInfoEntry 7 }	

ikeSaRemoteCfgIdentity	OBJECT-TYPE
	SYNTAX		OCTET STRING
	MAX-ACCESS	read-only
	STATUS 		current
    	DESCRIPTION
    		"The object defines the identity of the remote end. "
	::= { IkeSaInfoEntry 8 }

ikeSaRemoteInstIdentity	OBJECT-TYPE
	SYNTAX		OCTET STRING
	MAX-ACCESS	read-only
	STATUS 		current
    	DESCRIPTION
    		"The object defines the identity of the remote end. "
	::= { IkeSaInfoEntry 9 }

ikeSaLocalCfgIdentity	OBJECT-TYPE
	SYNTAX		OCTET STRING
	MAX-ACCESS	read-only
	STATUS 		current
    	DESCRIPTION
    		"The object defines the identity of the local end. "
	::= { IkeSaInfoEntry 10 }
	
ikeSaLocalInstIdentity	OBJECT-TYPE
	SYNTAX		OCTET STRING
	MAX-ACCESS	read-only
	STATUS 		current
    	DESCRIPTION
    		"The object defines the identity of the local end. "
	::= { IkeSaInfoEntry 11 }

ikeFlowName		OBJECT-TYPE
	SYNTAX		OCTET STRING
	MAX-ACCESS	read-only
	STATUS 		current
    	DESCRIPTION
    		"The object defines the identifier nubmer of the policy corresponding to the IKE SA. "
	::= { IkeSaInfoEntry 12 }	

ikeSaTimerEvent1		OBJECT-TYPE
	SYNTAX		OCTET STRING
	MAX-ACCESS	read-only
	STATUS 		current
    	DESCRIPTION
    		"The object defines the type of the timer event connected with an IKE SA. "
	::= { IkeSaInfoEntry 13 }	
	
ikeSaTimerRemain1	OBJECT-TYPE
	SYNTAX		UInteger32
	MAX-ACCESS	read-only
	STATUS 		current
    	DESCRIPTION
    		"The object defines the remainder time of the timer event connected with an IKE SA. "
	::= { IkeSaInfoEntry 14 }	

ikeSaTimerEvent2		OBJECT-TYPE
	SYNTAX		OCTET STRING
	MAX-ACCESS	read-only
	STATUS 		current
    	DESCRIPTION
    		"The object defines the type of the timer event connected with an IKE SA. "
	::= { IkeSaInfoEntry 15 }	
	
ikeSaTimerRemain2	OBJECT-TYPE
	SYNTAX		UInteger32
	MAX-ACCESS	read-only
	STATUS 		current
    	DESCRIPTION
    		"The object defines the remainder time of the timer event connected with an IKE SA. "
	::= { IkeSaInfoEntry 16 }	

ikeSaTimerEvent3		OBJECT-TYPE
	SYNTAX		OCTET STRING
	MAX-ACCESS	read-only
	STATUS 		current
    	DESCRIPTION
    		"The object defines the type of the timer event connected with an IKE SA. "
	::= { IkeSaInfoEntry 17 }	
	
ikeSaTimerRemain3	OBJECT-TYPE
	SYNTAX		UInteger32
	MAX-ACCESS	read-only
	STATUS 		current
    	DESCRIPTION
    		"The object defines the remainder time of the timer event connected with an IKE SA. "
	::= { IkeSaInfoEntry 18 }	

ikeSaTimerEvent4		OBJECT-TYPE
	SYNTAX		OCTET STRING
	MAX-ACCESS	read-only
	STATUS 		current
    	DESCRIPTION
    		"The object defines the type of the timer event connected with an IKE SA. "
	::= { IkeSaInfoEntry 19 }	
	
ikeSaTimerRemain4	OBJECT-TYPE
	SYNTAX		UInteger32
	MAX-ACCESS	read-only
	STATUS 		current
    	DESCRIPTION
    		"The object defines the remainder time of the timer event connected with an IKE SA. "
	::= { IkeSaInfoEntry 20 }	
	
ikeSaIpsecAhOutSpi		OBJECT-TYPE
	SYNTAX		Counter32
	MAX-ACCESS	read-only
	STATUS 		current
    	DESCRIPTION
    		"The object defines the SPI which is one part of an outbound IPSec SA identifier corresponding to
    		AH protocol when the IPSec SA is already builded, that is to say, the value of IkeSaState is newestIPSec. "
	::= { IkeSaInfoEntry 21 }	
	
ikeSaIpsecAhInSpi		OBJECT-TYPE
	SYNTAX		Counter32
	MAX-ACCESS	read-only
	STATUS 		current
    	DESCRIPTION
    		"The object defines the SPI which is one part of an inbound IPSec SA identifier corresponding to
    		AH protocol when the IPSec SA is already builded, that is to say, the value of IkeSaState is newestIPSec. "
	::= { IkeSaInfoEntry 22 }
	
ikeSaIpsecEspOutSpi		OBJECT-TYPE
	SYNTAX		Counter32
	MAX-ACCESS	read-only
	STATUS 		current
    	DESCRIPTION
    		"The object defines the SPI which is one part of an outbound IPSec SA identifier corresponding to
    		ESP protocol when the IPSec SA is already builded, that is to say, the value of IkeSaState is newestIPSec. "
	::= { IkeSaInfoEntry 23 }
	
ikeSaIpsecEspInSpi		OBJECT-TYPE
	SYNTAX		Counter32
	MAX-ACCESS	read-only
	STATUS 		current
    	DESCRIPTION
    		"The object defines the SPI which is one part of an inbound IPSec SA identifier corresponding to
    		ESP protocol when the IPSec SA is already builded, that is to say, the value of IkeSaState is newestIPSec. "
	::= { IkeSaInfoEntry 24 }

-- *****************************************************************

-- *****************************************************************
-- IPSec SA Information Table

ipsecSAInfoTable	OBJECT-TYPE
    	SYNTAX SEQUENCE OF IPSecSAInfoEntry
    	MAX-ACCESS not-accessible
    	STATUS current
    	DESCRIPTION
		"The table contains the detail information about all the IPSec SAs, which is only for being displayed. "
    	::={ IPsecMonitorGroup 2 }
    
ipsecSAInfoEntry	OBJECT-TYPE
    	SYNTAX IPSecSAInfoEntry
    	MAX-ACCESS not-accessible
    	STATUS current
    	DESCRIPTION
		"Each entry contains all the attributes about one pair of IPSec SAs. "
    	INDEX { IPSecSAIndex }
    	::= { IPSecSAInfoTable 1 }
    	
IPSecSAInfoEntry	::=
	SEQUENCE {	
			ipsecSAIndex			COUNTER32,
			ipsecSAStateIndex		COUNTER32,
			ipsecSAFlowName			OCTET STRING,
			ipsecSAProtoName		INTEGER,
			ipsecSAEncAlgName		OCTET STRING,
			ipsecSAAuthAlgName		OCTET STRING,
			ipsecSAIPCompAlgName		OCTET STRING,
			ipsecSAInSPI			Counter32,
			ipsecSAInExpTime		Counter32,
			ipsecSAInRemainTime		Counter32,
			ipsecSAInPackets		UInteger32,
			ipsecSAInKiloBytes		UInteger32,
			ipsecSAInLeftKBytes		UInteger32,
			ipsecSAInCompedBytes		UInteger32,
			ipsecSAInDecompedBytes		UInteger32,
			ipsecSAInGroupSASPI		Counter32,
			ipsecSAInGroupID		INTEGER,
			ipsecSAOutSPI			Counter32,
			ipsecSAOutExpTime		Counter32,
			ipsecSAOutRemainTime		Counter32,			
			ipsecSAOutPackets		UInteger32,
			ipsecSAOutKiloBytes		UInteger32,
			ipsecSAOutLeftKBytes		UInteger32,
			ipsecSAOutCompedBytes		UINTEGER32,
			ipsecSAOutDecompedBytes		UINTEGER32,
			ipsecSAOutGroupSASPI		Counter32,
			ipsecSAOutGroupID		INTEGER
		}
		
ipsecSAIndex			OBJECT-TYPE
	SYNTAX		COUNTER32
	MAX-ACCESS	read-only
	STATUS		current
	DESCRIPTION
		"The object defines the index of pairs of IPSec SAs, which is only the index of the table and not has actual meaning. "
	::= { IPSecSAInfoEntry 1 }
	
ipsecSAStateIndex		OBJECT-TYPE
	SYNTAX		COUNTER32
	MAX-ACCESS	read-only
	STATUS		current
	DESCRIPTION
		"The object defines the id number of the phase2 ike sa. "
	::= { IPSecSAInfoEntry 2 }
	
ipsecSAFlowName		OBJECT-TYPE
	SYNTAX		OCTET STRING
	MAX-ACCESS	read-only
	STATUS		current
	DESCRIPTION
		"The object defines the name of the flow corresponding to the IPSec SAs."
	::= { IPSecSAInfoEntry 3 }
	
ipsecSAProtoName		OBJECT-TYPE
	SYNTAX	INTEGER { 
				esp(1),
				ah(2),
				ipcomp(3)
				}
	MAX-ACCESS	read-only
	STATUS	current
	DESCRIPTION
		"The object defines the switch of anti-replaying associated with the IPSec SAs. "
	::= { IPSecSAInfoEntry 4 }
			
ipsecSAEncAlgName		OBJECT-TYPE
	SYNTAX		OCTET STRING
	MAX-ACCESS	read-only
	STATUS		current
	DESCRIPTION
		"The object defines the name of the encryption algorithm. "
	::= { IPSecSAInfoEntry 5 }
	
ipsecSAAuthAlgName		OBJECT-TYPE
	SYNTAX		OCTET STRING
	MAX-ACCESS	read-only
	STATUS		current
	DESCRIPTION
		"The object defines the name of the authentication algorithm. "
	::= { IPSecSAInfoEntry 6 }

ipsecSAIPCompAlgName		OBJECT-TYPE
	SYNTAX		OCTET STRING
	MAX-ACCESS	read-only
	STATUS		current
	DESCRIPTION
		"The object defines the name of the compression algorithm. "
	::= { IPSecSAInfoEntry 7 }
		
ipsecSAInSPI			OBJECT-TYPE
	SYNTAX	Counter32
	MAX-ACCESS	read-only
	STATUS	current
	DESCRIPTION
		"The object defines the SPI of the inbound IPSec SA. "
	::= { IPSecSAInfoEntry 8 }

ipsecSAInExpTime		OBJECT-TYPE
	SYNTAX	Counter32
	MAX-ACCESS	read-only
	STATUS	current
	DESCRIPTION
		"The object defines the expired time of the inbound IPSec SA. "
	::= { IPSecSAInfoEntry 9 }

ipsecSAInRemainTime		OBJECT-TYPE
	SYNTAX	Counter32
	MAX-ACCESS	read-only
	STATUS	current
	DESCRIPTION
		"The object defines the remaining time of the inbound IPSec SA. "
	::= { IPSecSAInfoEntry 10 }
				
ipsecSAInPackets		OBJECT-TYPE
	SYNTAX	UInteger32
	MAX-ACCESS	read-only
	STATUS	current
	DESCRIPTION
		"The object defines the total number of the input packets protected by the inbound IPSec SA. "
	::= { IPSecSAInfoEntry 11 }
	
ipsecSAInKiloBytes			OBJECT-TYPE
	SYNTAX	UInteger32
	MAX-ACCESS	read-only
	STATUS	current
	DESCRIPTION
		"The object defines all the input data protected by the inbound IPSec SA. "
	::= { IPSecSAInfoEntry 12 }

ipsecSAInLeftKBytes		OBJECT-TYPE
	SYNTAX	UInteger32
	MAX-ACCESS	read-only
	STATUS	current
	DESCRIPTION
		"The object defines the remained lifetime measured as kilobytes about the inbound IPSec SA. "
	::= { IPSecSAInfoEntry 13 }

ipsecSAInCompedBytes		OBJECT-TYPE
	SYNTAX		UInteger32
	MAX-ACCESS	read-only
	STATUS	current
	DESCRIPTION
		"The object defines all the input compressed data measured as kilobytes. "
	::= { IPSecSAInfoEntry 14 }

ipsecSAInDecompedBytes		OBJECT-TYPE
	SYNTAX		UInteger32
	MAX-ACCESS	read-only
	STATUS	current
	DESCRIPTION
		"The object defines all the input decompressed data measured as kilobytes. "
	::= { IPSecSAInfoEntry 15 }
		
ipsecSAInGroupSASPI		OBJECT-TYPE
	SYNTAX	Counter32
	MAX-ACCESS	read-only
	STATUS	current
	DESCRIPTION
		"The object defines the SPI of the IPSec SA which protects the same input data flow with the inbound IPSec SA. 
		In current its value is usually null. "
	::= { IPSecSAInfoEntry 16 }
	
ipsecSAInGroupID		OBJECT-TYPE
	SYNTAX	INTEGER(1..65535)
	MAX-ACCESS	read-only
	STATUS	current
	DESCRIPTION
		"The group identity of inbound SA. "
	::= { IPSecSAInfoEntry 17 }

ipsecSAOutSPI			OBJECT-TYPE
	SYNTAX	Counter32
	MAX-ACCESS	read-only
	STATUS	current
	DESCRIPTION
		"The object defines the SPI of the outbound IPSec SA. "
	::= { IPSecSAInfoEntry 18 }

ipsecSAOutExpTime		OBJECT-TYPE
	SYNTAX	Counter32
	MAX-ACCESS	read-only
	STATUS	current
	DESCRIPTION
		"The object defines the expired time of the outbound IPSec SA. "
	::= { IPSecSAInfoEntry 19 }

ipsecSAOutRemainTime		OBJECT-TYPE
	SYNTAX	Counter32
	MAX-ACCESS	read-only
	STATUS	current
	DESCRIPTION
		"The object defines the remaining time of the outbound IPSec SA. "
	::= { IPSecSAInfoEntry 20 }
			
ipsecSAOutPackets		OBJECT-TYPE
	SYNTAX	UInteger32
	MAX-ACCESS	read-only
	STATUS	current
	DESCRIPTION
		"The object defines the total number of the output packets protected by the outbound IPSec SA. "
	::= { IPSecSAInfoEntry 21 }
	
ipsecSAOutKiloBytes			OBJECT-TYPE
	SYNTAX		UInteger32
	MAX-ACCESS	read-only
	STATUS		current
	DESCRIPTION
		"The object defines all the output data measured as kilobytes protected by the outbound IPSec SA. "
	::= { IPSecSAInfoEntry 22 }
	
ipsecSAOutLeftKBytes		OBJECT-TYPE
	SYNTAX	UInteger32
	MAX-ACCESS	read-only
	STATUS	current
	DESCRIPTION
		"The object defines the remained lifetime measured as kilobytes about the outbound IPSec SA. "
	::= { IPSecSAInfoEntry 23 }

ipsecSAOutCompedBytes		OBJECT-TYPE
	SYNTAX		UInteger32
	MAX-ACCESS	read-only
	STATUS	current
	DESCRIPTION
		"The object defines all the output compressed data measured as kilobytes. "
	::= { IPSecSAInfoEntry 24 }

ipsecSAOutDecompedBytes		OBJECT-TYPE
	SYNTAX		UInteger32
	MAX-ACCESS	read-only
	STATUS	current
	DESCRIPTION
		"The object defines all the output decompressed data measured as kilobytes. "
	::= { IPSecSAInfoEntry 25 }
		
ipsecSAOutGroupSASPI		OBJECT-TYPE
	SYNTAX	Counter32
	MAX-ACCESS	read-only
	STATUS	current
	DESCRIPTION
		"The object defines the SPI of the IPSec SA which protects the same output data flow with the outbound IPSec SA. "
	::= { IPSecSAInfoEntry 26 }	

ipsecSAOutGroupID		OBJECT-TYPE
	SYNTAX	INTEGER(1..65535)
	MAX-ACCESS	read-only
	STATUS	current
	DESCRIPTION
		"The group identity of outbound SA. "
	::= { IPSecSAInfoEntry 27 }

-- *****************************************************************

-- *****************************************************************
-- IPSec SA Simple Information Table

ipsecSASimpleInfoTable	OBJECT-TYPE
    	SYNTAX SEQUENCE OF IPSecSASimpleInfoEntry
    	MAX-ACCESS not-accessible
    	STATUS current
    	DESCRIPTION
		"The table contains the detail information about all the IPSec SAs, which is only for being displayed. "
    	::={ IPsecMonitorGroup 3 }
    
ipsecSASimpleInfoEntry	OBJECT-TYPE
    	SYNTAX IPSecSASimpleInfoEntry
    	MAX-ACCESS not-accessible
    	STATUS current
    	DESCRIPTION
		"Each entry contains all the attributes about one pair of IPSec SAs. "
    	INDEX { mpIPsecSimpIndex }
    	::= { IPSecSASimpleInfoTable 1 }
    	
IPSecSASimpleInfoEntry	::=
	SEQUENCE {	
			mpIPsecSimpIndex			COUNTER32,
			mpIPsecSimpPeerAddr		OCTET STRING,
			mpIPsecSimpLocalAddr		OCTET STRING,
			mpIPsecSimpPeerID		OCTET STRING,
			mpIPsecSimpLocalID		OCTET STRING,
			mpIPsecSimpSrcAddr		OCTET STRING,
			mpIPsecSimpSrcMask		OCTET STRING,
			mpIPsecSimpDstAddr		OCTET STRING,
			mpIPsecSimpDstMask		OCTET STRING,
			mpIPsecSimpInExpTime		Counter32,
			mpIPsecSimpInRemainTime		Counter32,
			mpIPsecSimpInPackets		UInteger32,
			mpIPsecSimpInKiloBytes		UInteger32,
			mpIPsecSimpInLeftKBytes		UInteger32,
			mpIPsecSimpOutExpTime		Counter32,
			mpIPsecSimpOutRemainTime		Counter32,			
			mpIPsecSimpOutPackets		UInteger32,
			mpIPsecSimpOutKiloBytes		UInteger32,
			mpIPsecSimpOutLeftKBytes		UInteger32,
			mpIPsecSimpFlowName			OCTET STRING,
			mpIPsecStateId			COUNTER32,
			mpIPsecSimpPFlowName		OCTET STRING
		}
		
mpIPsecSimpIndex		OBJECT-TYPE
	SYNTAX		COUNTER32
	MAX-ACCESS	read-only
	STATUS		current
	DESCRIPTION
		"The object defines the index of pairs of IPSec SAs, which is only the index of the table and not has actual meaning. "
	::= { IPSecSASimpleInfoEntry 1 }
	
mpIPsecSimpPeerAddr		OBJECT-TYPE
	SYNTAX		OCTET STRING
	MAX-ACCESS	read-only
	STATUS		current
	DESCRIPTION
		"The object defines the peer address. "
	::= { IPSecSASimpleInfoEntry 2 }
	
mpIPsecSimpLocalAddr		OBJECT-TYPE
	SYNTAX		OCTET STRING
	MAX-ACCESS	read-only
	STATUS		current
	DESCRIPTION
		"The object defines the local address. "
	::= { IPSecSASimpleInfoEntry 3 }
	
mpIPsecSimpPeerID		OBJECT-TYPE
	SYNTAX		OCTET STRING
	MAX-ACCESS	read-only
	STATUS		current
	DESCRIPTION
		"The object defines the peer identity. "
	::= { IPSecSASimpleInfoEntry 4 }
	
mpIPsecSimpLocalID		OBJECT-TYPE
	SYNTAX		OCTET STRING
	MAX-ACCESS	read-only
	STATUS		current
	DESCRIPTION
		"The object defines the local identity. "
	::= { IPSecSASimpleInfoEntry 5 }
	
mpIPsecSimpSrcAddr		OBJECT-TYPE
	SYNTAX		OCTET STRING
	MAX-ACCESS	read-only
	STATUS		current
	DESCRIPTION
		"The object defines the source address. "
	::= { IPSecSASimpleInfoEntry 6 }
	
mpIPsecSimpSrcMask		OBJECT-TYPE
	SYNTAX		OCTET STRING
	MAX-ACCESS	read-only
	STATUS		current
	DESCRIPTION
		"The object defines the source mask. "
	::= { IPSecSASimpleInfoEntry 7 }
	
mpIPsecSimpDstAddr		OBJECT-TYPE
	SYNTAX		OCTET STRING
	MAX-ACCESS	read-only
	STATUS		current
	DESCRIPTION
		"The object defines the destination address. "
	::= { IPSecSASimpleInfoEntry 8 }
	
mpIPsecSimpDstMask		OBJECT-TYPE
	SYNTAX		OCTET STRING
	MAX-ACCESS	read-only
	STATUS		current
	DESCRIPTION
		"The object defines the destination mask. "
	::= { IPSecSASimpleInfoEntry 9 }
	
mpIPsecSimpInExpTime		OBJECT-TYPE
	SYNTAX		Counter32
	MAX-ACCESS	read-only
	STATUS		current
	DESCRIPTION
		"The object defines the expiration time of inbound IPsec SA. "
	::= { IPSecSASimpleInfoEntry 10 }
	
mpIPsecSimpInRemainTime		OBJECT-TYPE
	SYNTAX		Counter32
	MAX-ACCESS	read-only
	STATUS		current
	DESCRIPTION
		"The object defines the remaining time of inbound IPsec SA. "
	::= { IPSecSASimpleInfoEntry 11 }	
	
mpIPsecSimpInPackets		OBJECT-TYPE
	SYNTAX		UInteger32
	MAX-ACCESS	read-only
	STATUS		current
	DESCRIPTION
		"The object defines the packets number of inbound IPsec SA. "
	::= { IPSecSASimpleInfoEntry 12 }
	
mpIPsecSimpInKiloBytes			OBJECT-TYPE
	SYNTAX	UInteger32
	MAX-ACCESS	read-only
	STATUS	current
	DESCRIPTION
		"The object defines all the input data protected by the inbound IPSec SA. "
	::= { IPSecSASimpleInfoEntry 13 }

mpIPsecSimpInLeftKBytes		OBJECT-TYPE
	SYNTAX	UInteger32
	MAX-ACCESS	read-only
	STATUS	current
	DESCRIPTION
		"The object defines the remained lifetime measured as kilobytes about the inbound IPSec SA. "
	::= { IPSecSASimpleInfoEntry 14 }
	
mpIPsecSimpOutExpTime		OBJECT-TYPE
	SYNTAX	Counter32
	MAX-ACCESS	read-only
	STATUS	current
	DESCRIPTION
		"The object defines the expired time of the outbound IPSec SA. "
	::= { IPSecSASimpleInfoEntry 15 }

mpIPsecSimpOutRemainTime		OBJECT-TYPE
	SYNTAX	Counter32
	MAX-ACCESS	read-only
	STATUS	current
	DESCRIPTION
		"The object defines the remaining time of the outbound IPSec SA. "
	::= { IPSecSASimpleInfoEntry 16 }
			
mpIPsecSimpOutPackets		OBJECT-TYPE
	SYNTAX	UInteger32
	MAX-ACCESS	read-only
	STATUS	current
	DESCRIPTION
		"The object defines the total number of the output packets protected by the outbound IPSec SA. "
	::= { IPSecSASimpleInfoEntry 17 }
	
mpIPsecSimpOutKiloBytes			OBJECT-TYPE
	SYNTAX		UInteger32
	MAX-ACCESS	read-only
	STATUS		current
	DESCRIPTION
		"The object defines all the output data measured as kilobytes protected by the outbound IPSec SA. "
	::= { IPSecSASimpleInfoEntry 18 }
	
mpIPsecSimpOutLeftKBytes		OBJECT-TYPE
	SYNTAX	UInteger32
	MAX-ACCESS	read-only
	STATUS	current
	DESCRIPTION
		"The object defines the remained lifetime measured as kilobytes about the outbound IPSec SA. "
	::= { IPSecSASimpleInfoEntry 19 }

mpIPsecSimpFlowName		OBJECT-TYPE
	SYNTAX	OCTET STRING
	MAX-ACCESS	read-only
	STATUS	current
	DESCRIPTION
		"The object defines the policy name. "
	::= { IPSecSASimpleInfoEntry 20 }
	
mpIPsecStateId		OBJECT-TYPE
	SYNTAX	COUNTER32
	MAX-ACCESS	read-only
	STATUS	current
	DESCRIPTION
		"The object defines the state id of IPsec SA. "
	::= { IPSecSASimpleInfoEntry 21 }
	
mpIPsecSimpPFlowName		OBJECT-TYPE
	SYNTAX	OCTET STRING
	MAX-ACCESS	read-only
	STATUS	current
	DESCRIPTION
		"The object defines the parent policy name. "
	::= { IPSecSASimpleInfoEntry 22 }
-- *****************************************************************

-- *****************************************************************
ipsecTrapObjectsGroup		OBJECT IDENTIFIER ::= { IPsecMonitorGroup 4 }

estabSaTrapStateIndex	OBJECT-TYPE
	SYNTAX		COUNTER32
	MAX-ACCESS	read-write
	STATUS		current
	DESCRIPTION
		"阶段二state的索引. "
	::= { IPsecTrapObjectsGroup 1 }
	
estabSaTrapReplacedStateIndex	OBJECT-TYPE
	SYNTAX		COUNTER32
	MAX-ACCESS	read-write
	STATUS		current
	DESCRIPTION
		"被替换的阶段二state的索引. "
	::= { IPsecTrapObjectsGroup 2 }
	
estabSaTrapRemoteId	OBJECT-TYPE
	SYNTAX		OCTET STRING
	MAX-ACCESS	read-write
	STATUS		current
	DESCRIPTION
		"对端ID. "
	::= { IPsecTrapObjectsGroup 3 }
	
estabSaTrapLocalId	OBJECT-TYPE
	SYNTAX		OCTET STRING
	MAX-ACCESS	read-write
	STATUS		current
	DESCRIPTION
		"本地ID. "
	::= { IPsecTrapObjectsGroup 4 }

estabSaTrapRemoteAddress	OBJECT-TYPE
	SYNTAX		OCTET STRING
	MAX-ACCESS	read-write
	STATUS		current
	DESCRIPTION
		"对端IP. "
	::= { IPsecTrapObjectsGroup 5 }
	
estabSaTrapLocalAddress	OBJECT-TYPE
	SYNTAX		OCTET STRING
	MAX-ACCESS	read-write
	STATUS		current
	DESCRIPTION
		"本地IP. "
	::= { IPsecTrapObjectsGroup 6 }	
		
estabSaTrapPolSrcAddr	OBJECT-TYPE
	SYNTAX		OCTET STRING
	MAX-ACCESS	read-write
	STATUS		current
	DESCRIPTION
		"策略源地址. "
	::= { IPsecTrapObjectsGroup 7 }	
	
estabSaTrapPolSrcMask	OBJECT-TYPE
	SYNTAX		OCTET STRING
	MAX-ACCESS	read-write
	STATUS		current
	DESCRIPTION
		"策略源地址掩码. "
	::= { IPsecTrapObjectsGroup 8 }	
	
estabSaTrapPolDstAddr	OBJECT-TYPE
	SYNTAX		OCTET STRING
	MAX-ACCESS	read-write
	STATUS		current
	DESCRIPTION
		"策略目的地址. "
	::= { IPsecTrapObjectsGroup 9 }	

estabSaTrapPolDstMask	OBJECT-TYPE
	SYNTAX		OCTET STRING
	MAX-ACCESS	read-write
	STATUS		current
	DESCRIPTION
		"策略目的地址掩码. "
	::= { IPsecTrapObjectsGroup 10 }	

estabSaTrapPolProto	OBJECT-TYPE
	SYNTAX		INTEGER
	MAX-ACCESS	read-write
	STATUS		current
	DESCRIPTION
		"协议类型. "
	::= { IPsecTrapObjectsGroup 11 }	

estabSaTrapPolSrcPort	OBJECT-TYPE
	SYNTAX		INTEGER
	MAX-ACCESS	read-write
	STATUS		current
	DESCRIPTION
		"源端口. "
	::= { IPsecTrapObjectsGroup 12 }	

estabSaTrapPolDstPort	OBJECT-TYPE
	SYNTAX		INTEGER
	MAX-ACCESS	read-write
	STATUS		current
	DESCRIPTION
		"目的端口. "
	::= { IPsecTrapObjectsGroup 13 }			

delSaTrapStateIndex	OBJECT-TYPE
	SYNTAX		COUNTER32
	MAX-ACCESS	read-write
	STATUS		current
	DESCRIPTION
		"被删除的state索引. "
	::= { IPsecTrapObjectsGroup 14 }	

delSaTrapRemoteId	OBJECT-TYPE
	SYNTAX		OCTET STRING
	MAX-ACCESS	read-write
	STATUS		current
	DESCRIPTION
		"对端ID. "
	::= { IPsecTrapObjectsGroup 15 }	

delSaTrapLocalId	OBJECT-TYPE
	SYNTAX		OCTET STRING
	MAX-ACCESS	read-write
	STATUS		current
	DESCRIPTION
		"本端ID. "
	::= { IPsecTrapObjectsGroup 16 }	

delSaTrapDurationTime	OBJECT-TYPE
	SYNTAX		INTEGER
	MAX-ACCESS	read-write
	STATUS		current
	DESCRIPTION
		"存在时间长度. "
	::= { IPsecTrapObjectsGroup 17 }	

delSaTrapOutboundKBytes	OBJECT-TYPE
	SYNTAX		COUNTER64
	MAX-ACCESS	read-write
	STATUS		current
	DESCRIPTION
		"外出报文数. "
	::= { IPsecTrapObjectsGroup 18 }	

delSaTrapInboundKBytes	OBJECT-TYPE
	SYNTAX		COUNTER64
	MAX-ACCESS	read-write
	STATUS		current
	DESCRIPTION
		"内入报文数. "
	::= { IPsecTrapObjectsGroup 19 }	

-- *****************************************************************

-- *****************************************************************
-- IPsec Diagnostic Information Table

ipsecDiagInfoTable	OBJECT-TYPE
    	SYNTAX SEQUENCE OF IPsecDiagInfoEntry
    	MAX-ACCESS not-accessible
    	STATUS current
    	DESCRIPTION
		"The table contains all IPsec diagnostic informations for all policy-tunnel pairs."
    	::={ IPsecMonitorGroup 5 }
    
ipsecDiagInfoEntry	OBJECT-TYPE
    	SYNTAX IPsecDiagInfoEntry
    	MAX-ACCESS not-accessible
    	STATUS current
    	DESCRIPTION
		"Each entry contains the diagnostic informations for one policy-tunnel pair. "
    	INDEX { ipsecDiagInfoPolicyId, ipsecDiagInfoTunnelId }
    	::= { ipsecDiagInfoTable 1 }
    
IPsecDiagInfoEntry	::=
	SEQUENCE {	
			ipsecDiagInfoPolicyId		UInteger32,
			ipsecDiagInfoTunnelId		UInteger32,
			ipsecDiagInfoPolicyName	DisplayString,
			ipsecDiagInfoTunnelName	DisplayString,
			ipsecDiagInfoStatus		UInteger32
		}

ipsecDiagInfoPolicyId		OBJECT-TYPE
	SYNTAX		UInteger32
	MAX-ACCESS	read-only
	STATUS		current
	DESCRIPTION
		"The object defines the policy id. "
	::= { ipsecDiagInfoEntry 1 }

ipsecDiagInfoTunnelId		OBJECT-TYPE
	SYNTAX		UInteger32
	MAX-ACCESS	read-only
	STATUS		current
	DESCRIPTION
		"The object defines the tunnel id. "
	::= { ipsecDiagInfoEntry 2 }
		
ipsecDiagInfoPolicyName		OBJECT-TYPE
	SYNTAX		DisplayString (SIZE (0..32))
	MAX-ACCESS	read-only
	STATUS		current
	DESCRIPTION
		"The object defines the policy name. "
	::= { ipsecDiagInfoEntry 3 }
	
ipsecDiagInfoTunnelName		OBJECT-TYPE
	SYNTAX		DisplayString (SIZE (0..32))
	MAX-ACCESS	read-only
	STATUS		current
	DESCRIPTION
		"The object defines the tunnel name. "
	::= { ipsecDiagInfoEntry 4 }
	
ipsecDiagInfoStatus		OBJECT-TYPE
	SYNTAX		UInteger32
	MAX-ACCESS	read-only
	STATUS		current
	DESCRIPTION
		"The object defines the status of specify policy-tunnel pair. "
	::= { ipsecDiagInfoEntry 5 }
	
-- *****************************************************************

END
