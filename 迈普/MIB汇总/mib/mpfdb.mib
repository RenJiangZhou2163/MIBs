DEFINITIONS ::= BEGIN

mpSwFDB  OBJECT IDENTIFIER ::= {mpSwitchTech 12}

mpSwFDBAgingTime  OBJECT-TYPE
    SYNTAX  INTEGER(0..1000000)
    ACCESS  read-write
    STATUS  5
    DESCRIPTION
            "动态MAC地址老化时间"
    ::= {mpSwFDB 1}

mpSwFDBSytemMacLimit  OBJECT-TYPE
    SYNTAX  INTEGER(1..32767)
    ACCESS  read-write
    STATUS  5
    DESCRIPTION
            "允许系统学习MAC地址个数"
    ::= {mpSwFDB 2}

mpSwFDBVlanMacLearnTable  OBJECT-TYPE
    SYNTAX  SEQUENCE OF   mpSwFDBvlanMacLearnEntry
    ACCESS  not-accessible
    STATUS  5
    DESCRIPTION
            "VLAN学习MAC地址表"
    ::= {mpSwFDB 3}

mpSwFDBVlanMacLearnEntry  OBJECT-TYPE
    SYNTAX  mpSwFDBvlanMacLearnEntry
    ACCESS  not-accessible
    STATUS  5
    DESCRIPTION
            ""
    INDEX   {mpSwFDBmacLearnVlan}
    ::= {mpSwFDBVlanMacLearnTable 1}

mpSwFDBmacLearnVlan  OBJECT-TYPE
    SYNTAX  INTEGER
    ACCESS  read-only
    STATUS  5
    DESCRIPTION
            "端口"
    ::= {mpSwFDBVlanMacLearnEntry 1}

mpSwFDBmacLearnNum  OBJECT-TYPE
    SYNTAX  INTEGER(1..32767)
    ACCESS  read-write
    STATUS  5
    DESCRIPTION
            "允许学习MAC地址个数"
    ::= {mpSwFDBVlanMacLearnEntry 2}

mpSwFDBmacLearnStatus  OBJECT-TYPE
    SYNTAX  RowStatus
    ACCESS  read-write
    STATUS  5
    DESCRIPTION
            "状态行"
    ::= {mpSwFDBVlanMacLearnEntry 3}

mpSwFDBPortMacLearnTable  OBJECT-TYPE
    SYNTAX  SEQUENCE OF   mpSwFDBportMacLearnEntry
    ACCESS  not-accessible
    STATUS  5
    DESCRIPTION
            "端口学习MAC地址表"
    ::= {mpSwFDB 9}

mpSwFDBPortMacLearnEntry  OBJECT-TYPE
    SYNTAX  mpSwFDBportMacLearnEntry
    ACCESS  not-accessible
    STATUS  5
    DESCRIPTION
            ""
    INDEX   {mpSwFDBmacLearnPort}
    ::= {mpSwFDBPortMacLearnTable 1}

mpSwFDBmacLearnPort  OBJECT-TYPE
    SYNTAX  INTEGER
    ACCESS  read-only
    STATUS  5
    DESCRIPTION
            "端口"
    ::= {mpSwFDBPortMacLearnEntry 1}

mpSwFDBmacLearnNum  OBJECT-TYPE
    SYNTAX  INTEGER(1..32767)
    ACCESS  read-write
    STATUS  5
    DESCRIPTION
            "允许学习MAC地址个数"
    ::= {mpSwFDBPortMacLearnEntry 2}

mpSwFDBmacLearnStatus  OBJECT-TYPE
    SYNTAX  INTEGER(0..1)
    ACCESS  read-write
    STATUS  5
    DESCRIPTION
            "端口学习MAC地址状态  0-- disable,1--enable"
    ::= {mpSwFDBPortMacLearnEntry 3}

mpSwFDBFdbTable  OBJECT-TYPE
    SYNTAX  SEQUENCE OF   mpSwFDBfdbEntry
    ACCESS  not-accessible
    STATUS  5
    DESCRIPTION
            "FDB表"
    ::= {mpSwFDB 10}

mpSwFDBFdbEntry  OBJECT-TYPE
    SYNTAX  mpSwFDBfdbEntry
    ACCESS  not-accessible
    STATUS  5
    DESCRIPTION
            ""
    INDEX   {mpSwFDBfdbMacAddr, mpSwFDBfdbVlanId,mpSwFDBfdbPort,mpSwFDBfdbType}
    ::= {mpSwFDBFdbTable 1}

mpSwFDBfdbMacAddr  OBJECT-TYPE
    SYNTAX  MacAddress
    ACCESS  read-write
    STATUS  5
    DESCRIPTION
            "MAC地址"
    ::= {mpSwFDBFdbEntry 1}

mpSwFDBfdbVlanId  OBJECT-TYPE
    SYNTAX  INTEGER (1..4094)
    ACCESS  read-write
    STATUS  5
    DESCRIPTION
            "VLAN ID"
    ::= {mpSwFDBFdbEntry 2}

mpSwFDBfdbPort  OBJECT-TYPE
    SYNTAX  INTEGER
    ACCESS  read-write
    STATUS  5
    DESCRIPTION
            "端口号"
    ::= {mpSwFDBFdbEntry 3}

mpSwFDBfdbType  OBJECT-TYPE
    SYNTAX  INTEGER(1..3)
    ACCESS  read-write
    STATUS  5
    DESCRIPTION
            "MAC地址类型,1:静态MAC地址 2：过滤MAC地址 3：动态MAC地址"
    ::= {mpSwFDBFdbEntry 4}

mpSwFDBfdbState  OBJECT-TYPE
    SYNTAX  INTEGER(0..3)
    ACCESS  read-only
    STATUS  5
    DESCRIPTION
            "MAC地址的状态 0: 丢弃MAC地址 1:转发MAC地址 2：仅上CPU静态MAC地址 3：既转发又上CPU的静态MAC地址"
    ::= {mpSwFDBFdbEntry 5}

mpSwFDBfdbStatus  OBJECT-TYPE
    SYNTAX  RowStatus
    ACCESS  read-only
    STATUS  5
    DESCRIPTION
            "状态行"
    ::= {mpSwFDBFdbEntry 6}

mpSwFDBDelPortindex  OBJECT-TYPE
    SYNTAX  INTEGER(1..32768)
    ACCESS  read-write
    STATUS  5
    DESCRIPTION
            "logic port"
    ::= {mpSwFDB 13}

mpSwFDBDelVlanindex  OBJECT-TYPE
    SYNTAX  INTEGER(1..4094)
    ACCESS  read-write
    STATUS  5
    DESCRIPTION
            "vid index"
    ::= {mpSwFDB 14}

mpSwFDBDelPortVlanindex  OBJECT-TYPE
    SYNTAX  DisplayString (SIZE (3..10))
    ACCESS  read-write
    STATUS  current
    DESCRIPTION
            "logic port index and vid index"
    ::= {mpSwFDB 15}
END
