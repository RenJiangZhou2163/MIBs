------------------------------------------------------------------------------
--
--  File         : mpRtL3Multicast.mib
--  Description  : 
--  Version      :  
--  Date         : March 3, 2003
-- 	Copyright    : 2003 by maipu (sichuan) communication technology co.,ltd.
--					All rights reserved.
--
-- $Id:
-- 
------------------------------------------------------------------------------

------------------------------------------------------------------------------
MPRTL3MULTICAST DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;


maipu               	OBJECT IDENTIFIER ::= { enterprises 5651 }
mpMgmt2             	OBJECT IDENTIFIER ::= { maipu 6 }
mpRouterTech        	OBJECT IDENTIFIER ::= { mpMgmt2 2 }



mpRtL3Multicast     	MODULE-IDENTITY
                    		LAST-UPDATED 	"1004130915Z"
                    		ORGANIZATION 	"Maipu (Sichuan) Communication Technology Co. LTD."
                    		CONTACT-INFO
                    		DESCRIPTION
                      			""
                    		::= { mpRouterTech  7 }




------------------------------------------------------------------------------
mpMcastMib          	OBJECT IDENTIFIER ::= { mpRtL3Multicast 1 }

mpMcastConfigTable  	OBJECT-TYPE
                    		SYNTAX  SEQUENCE OF   MpMcastConfigEntry
                    		MAX-ACCESS  not-accessible
                    		STATUS  current
                    		DESCRIPTION
                    			""
                    		::= { mpMcastMib 1 }

mpMcastConfigEntry  	OBJECT-TYPE
                    		SYNTAX  MpMcastConfigEntry
                    		MAX-ACCESS  not-accessible
                    		STATUS  current
                    		DESCRIPTION
                    			""
                    		INDEX  { mpMcastVrfId }
                    		::= { mpMcastConfigTable 1 }

MpMcastConfigEntry  	::= SEQUENCE {
                    			mpMcastVrfId           INTEGER,
                    			mpMcastEnable          INTEGER,
                    			mpMcastStatus          RowStatus
                    	             }


mpMcastVrfId        	OBJECT-TYPE
                    		SYNTAX  INTEGER
                    		MAX-ACCESS  read-only
                    		STATUS  current
                    		DESCRIPTION
                    			""
                    		::= { mpMcastConfigEntry 1 }

mpMcastEnable       	OBJECT-TYPE
                    		SYNTAX  INTEGER {
                    			         disable (1),
                    			          enable (2)
                    			        }
                    		MAX-ACCESS  read-create
                    		STATUS  current
                    		DESCRIPTION
                    			""
                    		::= { mpMcastConfigEntry 2 }

mpMcastStatus       	OBJECT-TYPE
                    		SYNTAX  RowStatus
                    		MAX-ACCESS  read-create
                    		STATUS  current
                    		DESCRIPTION
                    			""
                    		::= { mpMcastConfigEntry 3 }


------------------------------------------------------------------------------
mpPimMib            	OBJECT IDENTIFIER ::= { mpRtL3Multicast 2 }

mpPimGlobalConfigTable	OBJECT-TYPE
                    		SYNTAX  SEQUENCE OF   MpPimGlobalConfigEntry
                    		MAX-ACCESS  not-accessible
                    		STATUS  current
                    		DESCRIPTION
                    			""
                    		::= { mpPimMib 1 }

mpPimGlobalConfigEntry	OBJECT-TYPE
                    		SYNTAX  MpPimGlobalConfigEntry
                    		MAX-ACCESS  not-accessible
                    		STATUS  current
                    		DESCRIPTION
                    			""
                    		INDEX  { mpPimVrfId }
                    		::= { mpPimGlobalConfigTable 1 }

MpPimGlobalConfigEntry	::= SEQUENCE {
                    			mpPimVrfId             INTEGER,
                    			mpPimStaticRP          IpAddress,
                    			mpPimGlobalStatus      RowStatus
                    	             }


mpPimVrfId          	OBJECT-TYPE
                    		SYNTAX  INTEGER
                    		MAX-ACCESS  read-only
                    		STATUS  current
                    		DESCRIPTION
                    			""
                    		::= { mpPimGlobalConfigEntry 1 }

mpPimStaticRP       	OBJECT-TYPE
                    		SYNTAX  IpAddress
                    		MAX-ACCESS  read-create
                    		STATUS  current
                    		DESCRIPTION
                    			"ip pim rp-address xxx"
                    		::= { mpPimGlobalConfigEntry 2 }

mpPimGlobalStatus   	OBJECT-TYPE
                    		SYNTAX  RowStatus
                    		MAX-ACCESS  read-create
                    		STATUS  current
                    		DESCRIPTION
                    			""
                    		::= { mpPimGlobalConfigEntry 3 }

mpPimInterfaceConfigTable	OBJECT-TYPE
                    		SYNTAX  SEQUENCE OF   MpPimInterfaceConfigEntry
                    		MAX-ACCESS  not-accessible
                    		STATUS  current
                    		DESCRIPTION
                    			""
                    		::= { mpPimMib 2 }

mpPimInterfaceConfigEntry	OBJECT-TYPE
                    		SYNTAX  MpPimInterfaceConfigEntry
                    		MAX-ACCESS  not-accessible
                    		STATUS  current
                    		DESCRIPTION
                    			""
                    		INDEX  { mpPimIfindex }
                    		::= { mpPimInterfaceConfigTable 1 }

MpPimInterfaceConfigEntry	::= SEQUENCE {
                    			mpPimIfindex           INTEGER,
                    			mpPimMode              INTEGER,
                    			mpPimInterfaceStatus   RowStatus
                    	             }


mpPimIfindex        	OBJECT-TYPE
                    		SYNTAX  INTEGER
                    		MAX-ACCESS  read-only
                    		STATUS  current
                    		DESCRIPTION
                    			""
                    		::= { mpPimInterfaceConfigEntry 1 }

mpPimMode           	OBJECT-TYPE
                    		SYNTAX  INTEGER {
                    			         none (1),
                    			          sparse (2),
                    			          sparsepassive (3)
                    			        }
                    		MAX-ACCESS  read-create
                    		STATUS  current
                    		DESCRIPTION
                    			""
                    		::= { mpPimInterfaceConfigEntry 2 }

mpPimInterfaceStatus	OBJECT-TYPE
                    		SYNTAX  RowStatus
                    		MAX-ACCESS  read-create
                    		STATUS  current
                    		DESCRIPTION
                    			""
                    		::= { mpPimInterfaceConfigEntry 3 }


------------------------------------------------------------------------------
mpMvpnMib           	OBJECT IDENTIFIER ::= { mpRtL3Multicast 3 }

mpMvpnConfigTable   	OBJECT-TYPE
                    		SYNTAX  SEQUENCE OF   MpMvpnConfigEntry
                    		MAX-ACCESS  not-accessible
                    		STATUS  current
                    		DESCRIPTION
                    			""
                    		::= { mpMvpnMib 1 }

mpMvpnConfigEntry   	OBJECT-TYPE
                    		SYNTAX  MpMvpnConfigEntry
                    		MAX-ACCESS  not-accessible
                    		STATUS  current
                    		DESCRIPTION
                    			""
                    		INDEX  { mpMvpnVrfId }
                    		::= { mpMvpnConfigTable 1 }

MpMvpnConfigEntry   	::= SEQUENCE {
                    			mpMvpnVrfId            INTEGER,
                    			mpMvpnDefaultMdt       IpAddress,
                    			mpMvpnDataMdt          IpAddress,
                    			mpMvpnDataMdtWildcardBit   IpAddress,
                    			mpMvpnDataMdtThreshold   INTEGER,
                    			mpMvpnDataMdtAcl       DisplayString,
                    			mpMvpnConfigStatus     RowStatus
                    	             }


mpMvpnVrfId         	OBJECT-TYPE
                    		SYNTAX  INTEGER
                    		MAX-ACCESS  read-only
                    		STATUS  current
                    		DESCRIPTION
                    			""
                    		::= { mpMvpnConfigEntry 1 }

mpMvpnDefaultMdt    	OBJECT-TYPE
                    		SYNTAX  IpAddress
                    		MAX-ACCESS  read-create
                    		STATUS  current
                    		DESCRIPTION
                    			""
                    		::= { mpMvpnConfigEntry 2 }

mpMvpnDataMdt       	OBJECT-TYPE
                    		SYNTAX  IpAddress
                    		MAX-ACCESS  read-create
                    		STATUS  current
                    		DESCRIPTION
                    			""
                    		::= { mpMvpnConfigEntry 3 }

mpMvpnDataMdtWildcardBit	OBJECT-TYPE
                    		SYNTAX  IpAddress
                    		MAX-ACCESS  read-create
                    		STATUS  current
                    		DESCRIPTION
                    			""
                    		::= { mpMvpnConfigEntry 4 }

mpMvpnDataMdtThreshold	OBJECT-TYPE
                    		SYNTAX  INTEGER(0..4294967)
                    		MAX-ACCESS  read-create
                    		STATUS  current
                    		DESCRIPTION
                    			""
                    		::= { mpMvpnConfigEntry 5 }

mpMvpnDataMdtAcl    	OBJECT-TYPE
                    		SYNTAX  DisplayString(SIZE(0..32))
                    		MAX-ACCESS  read-create
                    		STATUS  current
                    		DESCRIPTION
                    			""
                    		::= { mpMvpnConfigEntry 6 }

mpMvpnConfigStatus  	OBJECT-TYPE
                    		SYNTAX  RowStatus
                    		MAX-ACCESS  read-create
                    		STATUS  current
                    		DESCRIPTION
                    			""
                    		::= { mpMvpnConfigEntry 7 }



END
------------------------------------------------------------------------------
-- ============================================================================
-- $Log: mpRtL3Multicast.mib,v $
--
--
-- ============================================================================
