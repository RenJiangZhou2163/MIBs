-- *****************************************************************
-- mpIPsec.mib:  Maipu enterprise device IPsec MIB file
--
-- version 1.0.0.1, Mar 2, 2006 wang wenyu
--
-- Copyright (c)  by Maipu Communication Inc.
-- All rights reserved.
-- 
-- *****************************************************************

	
MAIPU-SECURITY-PKI-MIB DEFINITIONS ::= BEGIN

IMPORTS
        MODULE-IDENTITY, OBJECT-TYPE, Counter32,
       	IpAddress, Unsigned32		FROM SNMPv2-SMI
       	RowStatus			FROM SNMPv2-TC
       	mpSecurity			FROM MAIPU-SMI;
       
mpOrayDdnsModule 	MODULE-IDENTITY
        LAST-UPDATED "200603020932Z"      -- Thu Mar 2 09:32:35 PDT 2006
        ORGANIZATION "Maipu Communication"
        CONTACT-INFO
          	"       Wang wenyu
          	Postal: Maipu Inc
                  Tel: (028)85148048
          	E-Mail: office@maipu.com "
          
        DESCRIPTION
	 	"The MIB module describes the downlaod configuration file. "          
        ::= { mpMgmt 97 }

-- *****************************************************************

-- *****************************************************************
-- Config ddns Table

mpOrayDdnsUserTable		OBJECT-TYPE
    	SYNTAX SEQUENCE OF mpOrayDdnsUserEntry
    	MAX-ACCESS not-accessible
    	STATUS current
    	DESCRIPTION
		"The table contains all the configuration of ddns user."
    	::={ mpOrayDdnsModule 1 }
    
mpOrayDdnsUserEntry	OBJECT-TYPE
    	SYNTAX mpOrayDdnsUserEntry
    	MAX-ACCESS not-accessible
    	STATUS current
    	DESCRIPTION
		"Each entry contains the attributes associated with ddns user.
		配置文件表"
    	INDEX { ddnsUserName }
    	::= { mpOrayDdnsUserTable 1 }
    
mpOrayDdnsUserEntry	::=
	SEQUENCE {
		ddnsUserName		OCTET STRING,
		ddnsFirstServConfType	INTEGER,
		ddnsFirstServConf	OCTET STRING,
		ddnsSecondServConfType	INTEGER,
		ddnsSecondServConf	OCTET STRING,
		ddnsThirdServConfType	INTEGER,
		ddnsThirdServConf	OCTET STRING,
		ddnsFourthServConfType	INTEGER,
		ddnsFourthServConf	OCTET STRING,
		ddnsPassword		OCTET STRING,
		ddnsFirstDN		OCTET STRING,
		ddnsSecondDN		OCTET STRING,
		ddnsThirdDN		OCTET STRING,
		ddnsFourthDN		OCTET STRING,
		ddnsFifthDN		OCTET STRING,
		ddnsSixthDN		OCTET STRING,
		ddnsUserRowStatus	RowStatus
		}	

ddnsUserName			OBJECT-TYPE
	SYNTAX	OCTET STRING
	MAX-ACCESS	read-write
	STATUS	current
	DESCRIPTION
		"This object defines the user name.
		用户名称"
	::= { mpOrayDdnsUserEntry 1 }

ddnsFirstServConfType		OBJECT-TYPE
	SYNTAX	INTEGER {
			  NONE(0),
			  ADDR(1),
			  DomainName(2)
			}
	MAX-ACCESS	read-write
	STATUS	current
	DESCRIPTION
		"定义第一个服务器配置类型"
	::= { mpOrayDdnsUserEntry 2 }

ddnsFirstServConf		OBJECT-TYPE
	SYNTAX	OCTET STRING
	MAX-ACCESS	read-write
	STATUS	current
	DESCRIPTION
		"服务器域名或地址"
	::= { mpOrayDdnsUserEntry 3 }

ddnsSecondServConfType		OBJECT-TYPE
	SYNTAX	INTEGER {
			  NONE(0),
			  ADDR(1),
			  DomainName(2)
			}
	MAX-ACCESS	read-write
	STATUS	current
	DESCRIPTION
		"定义第二个服务器配置类型"
	::= { mpOrayDdnsUserEntry 4 }

ddnsSecondServConf		OBJECT-TYPE
	SYNTAX	OCTET STRING
	MAX-ACCESS	read-write
	STATUS	current
	DESCRIPTION
		"服务器域名或地址"
	::= { mpOrayDdnsUserEntry 5 }

ddnsThirdServConfType		OBJECT-TYPE
	SYNTAX	INTEGER {
			  NONE(0),
			  ADDR(1),
			  DomainName(2)
			}
	MAX-ACCESS	read-write
	STATUS	current
	DESCRIPTION
		"定义第三个服务器配置类型"
	::= { mpOrayDdnsUserEntry 6 }

ddnsThirdServConf		OBJECT-TYPE
	SYNTAX	OCTET STRING
	MAX-ACCESS	read-write
	STATUS	current
	DESCRIPTION
		"服务器域名或地址"
	::= { mpOrayDdnsUserEntry 7 }

ddnsFourthServConfType		OBJECT-TYPE
	SYNTAX	INTEGER {
			  NONE(0),
			  ADDR(1),
			  DomainName(2)
			}
	MAX-ACCESS	read-write
	STATUS	current
	DESCRIPTION
		"定义第四个服务器配置类型"
	::= { mpOrayDdnsUserEntry 8 }
	
ddnsFourthServConf		OBJECT-TYPE
	SYNTAX	OCTET STRING
	MAX-ACCESS	read-write
	STATUS	current
	DESCRIPTION
		"服务器域名或地址"
	::= { mpOrayDdnsUserEntry 9 }

ddnsPassword		OBJECT-TYPE
	SYNTAX	OCTET STRING
	MAX-ACCESS	read-write
	STATUS	current
	DESCRIPTION
		"注册用口令"
	::= { mpOrayDdnsUserEntry 10 }	
	
ddnsFirstDN		OBJECT-TYPE
	SYNTAX	OCTET STRING
	MAX-ACCESS	read-write
	STATUS	current
	DESCRIPTION
		"注册的第一个域名"
	::= { mpOrayDdnsUserEntry 11 }	
	
ddnsSecondDN		OBJECT-TYPE
	SYNTAX	OCTET STRING
	MAX-ACCESS	read-write
	STATUS	current
	DESCRIPTION
		"注册的第二个域名"
	::= { mpOrayDdnsUserEntry 12 }

ddnsThirdDN		OBJECT-TYPE
	SYNTAX	OCTET STRING
	MAX-ACCESS	read-write
	STATUS	current
	DESCRIPTION
		"注册的第三个域名"
	::= { mpOrayDdnsUserEntry 13 }
	
ddnsFourthDN		OBJECT-TYPE
	SYNTAX	OCTET STRING
	MAX-ACCESS	read-write
	STATUS	current
	DESCRIPTION
		"注册的第四个域名"
	::= { mpOrayDdnsUserEntry 14 }

ddnsFifthDN		OBJECT-TYPE
	SYNTAX	OCTET STRING
	MAX-ACCESS	read-write
	STATUS	current
	DESCRIPTION
		"注册的第五个域名"
	::= { mpOrayDdnsUserEntry 15 }

ddnsSixthDN		OBJECT-TYPE
	SYNTAX	OCTET STRING
	MAX-ACCESS	read-write
	STATUS	current
	DESCRIPTION
		"注册的第六个域名"
	::= { mpOrayDdnsUserEntry 16 }							
	
ddnsUserRowStatus	OBJECT-TYPE
	SYNTAX		RowStatus
	MAX-ACCESS 	read-create
	STATUS 		current
    	DESCRIPTION
    		"The object defines the status of the table entry."
	::= { mpOrayDdnsUserEntry 17 }
	
-- *****************************************************************

-- *****************************************************************
mpOrayDdnsRegStatusTable		OBJECT-TYPE
    	SYNTAX SEQUENCE OF mpOrayDdnsRegStatusEntry
    	MAX-ACCESS not-accessible
    	STATUS current
    	DESCRIPTION
		"The table contains all the registration status of ddns user."
    	::={ mpOrayDdnsModule 2 }
    
mpOrayDdnsRegStatusEntry	OBJECT-TYPE
    	SYNTAX mpOrayDdnsRegStatusEntry
    	MAX-ACCESS not-accessible
    	STATUS current
    	DESCRIPTION
		"注册状态表"
    	INDEX { ddnsUserName }
    	::= { mpOrayDdnsRegStatusTable 1 }
    
mpOrayDdnsRegStatusEntry	::=
	SEQUENCE {
		ddnsUserName		OCTET STRING,
		ddnsRegStatus		INTEGER
		}
		
ddnsUserName			OBJECT-TYPE
	SYNTAX	OCTET STRING
	MAX-ACCESS	read-only
	STATUS	current
	DESCRIPTION
		"This object defines the user name.
		用户名称"
	::= { mpOrayDdnsRegStatusEntry 1 }
	
ddnsRegStatus			OBJECT-TYPE
	SYNTAX	INTEGER{
			unsuccess(0),
			success(1)
			}
	MAX-ACCESS	read-only
	STATUS	current
	DESCRIPTION
		"This object defines the user name.
		用户名称"
	::= { mpOrayDdnsRegStatusEntry 2 }
-- *****************************************************************
	
-- *****************************************************************
mpOrayDdnsClearGroup		OBJECT IDENTIFIER ::= { mpOrayDdnsModule 3 }

ddnsUserName			OBJECT-TYPE
	SYNTAX	OCTET STRING
	MAX-ACCESS	read-write
	STATUS	current
	DESCRIPTION
		"This object defines the user name.
		用户名称"
	::= { mpOrayDdnsClearGroup 1 }	
-- *****************************************************************		
END
