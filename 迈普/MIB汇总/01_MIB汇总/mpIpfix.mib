------------------------------------------------------------------------------
--
--  File         : mpIPFix.mib
--  Description  : 
--  Version      :  
--  Date         : Dec. 21, 2007
-- 	Copyright    : 2007 by maipu (sichuan) communication technology co.,ltd.
--					All rights reserved.
--
-- $Id:
-- 
------------------------------------------------------------------------------

------------------------------------------------------------------------------
MPIPFIX DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;


maipu               	OBJECT IDENTIFIER ::= { enterprises 1 }
mpMgmt2             	OBJECT IDENTIFIER ::= { maipu 5651 }
mpApp               	OBJECT IDENTIFIER ::= { mpMgmt2 6 }



mpIPFix             	MODULE-IDENTITY
                    		LAST-UPDATED 	"0712211023Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			"Subtree for Switch IPFix MIB."
                    		::= { mpApp  1 }



ipfixIfTable        	OBJECT-TYPE
                    		SYNTAX  SEQUENCE OF   IpfixIfEntry
                    		MAX-ACCESS  not-accessible
                    		STATUS  current
                    		DESCRIPTION
                    			""
                    		::= { mpIPFix 1 }

ipfixIfEntry        	OBJECT-TYPE
                    		SYNTAX  IpfixIfEntry
                    		MAX-ACCESS  not-accessible
                    		STATUS  current
                    		DESCRIPTION
                    			""
                    		INDEX  { ixsitIfName }
                    		::= { ipfixIfTable 1 }

IpfixIfEntry        	::= SEQUENCE {
                    			ixsitIfName            DisplayString,
                    			ixsitIngress           INTEGER,
                    			ixsitEgress            INTEGER,
                    			ixsitRowStatus         RowStatus
                    	             }


ixsitIfName         	OBJECT-TYPE
                    		SYNTAX  DisplayString(SIZE(1..35))
                    		MAX-ACCESS  read-only
                    		STATUS  current
                    		DESCRIPTION
                    			""
                    		::= { ipfixIfEntry 1 }

ixsitIngress        	OBJECT-TYPE
                    		SYNTAX  INTEGER {
                    			         disable(1),
                    			          enable(2)
                    			        }
                    		MAX-ACCESS  read-write
                    		STATUS  current
                    		DESCRIPTION
                    			""
                    		::= { ipfixIfEntry 2 }

ixsitEgress         	OBJECT-TYPE
                    		SYNTAX  INTEGER {
                    			         disable(1),
                    			          enable(2)
                    			        }
                    		MAX-ACCESS  read-write
                    		STATUS  current
                    		DESCRIPTION
                    			""
                    		::= { ipfixIfEntry 3 }

ixsitRowStatus      	OBJECT-TYPE
                    		SYNTAX  RowStatus
                    		MAX-ACCESS  read-write
                    		STATUS  current
                    		DESCRIPTION
                    			""
                    		::= { ipfixIfEntry 4 }

ipfixDstTable       	OBJECT-TYPE
                    		SYNTAX  SEQUENCE OF   IpfixDstEntry
                    		MAX-ACCESS  not-accessible
                    		STATUS  current
                    		DESCRIPTION
                    			""
                    		::= { mpIPFix 2 }

ipfixDstEntry       	OBJECT-TYPE
                    		SYNTAX  IpfixDstEntry
                    		MAX-ACCESS  not-accessible
                    		STATUS  current
                    		DESCRIPTION
                    			""
                    		INDEX  { ixsdtVrfName, ixsdtDstAddr, ixsdtPort }
                    		::= { ipfixDstTable 1 }

IpfixDstEntry       	::= SEQUENCE {
                    			ixsdtVrfName           DisplayString,
                    			ixsdtDstAddr           IpAddress,
                    			ixsdtPort              INTEGER,
                    			ixsdtRowStatus         RowStatus
                    	             }


ixsdtVrfName        	OBJECT-TYPE
                    		SYNTAX  DisplayString(SIZE(1..35))
                    		MAX-ACCESS  read-only
                    		STATUS  current
                    		DESCRIPTION
                    			""
                    		::= { ipfixDstEntry 1 }

ixsdtDstAddr        	OBJECT-TYPE
                    		SYNTAX  IpAddress
                    		MAX-ACCESS  read-only
                    		STATUS  current
                    		DESCRIPTION
                    			""
                    		::= { ipfixDstEntry 2 }

ixsdtPort           	OBJECT-TYPE
                    		SYNTAX  INTEGER(0..65535)
                    		MAX-ACCESS  read-only
                    		STATUS  current
                    		DESCRIPTION
                    			""
                    		::= { ipfixDstEntry 3 }

ixsdtRowStatus      	OBJECT-TYPE
                    		SYNTAX  RowStatus
                    		MAX-ACCESS  read-write
                    		STATUS  current
                    		DESCRIPTION
                    			""
                    		::= { ipfixDstEntry 4 }



END
------------------------------------------------------------------------------
-- ============================================================================
-- $Log: mpIpfix.mib,v $
-- Revision 1.1  2010/06/21 11:18:46  liyh
-- first commit
--
--
--
-- ============================================================================
