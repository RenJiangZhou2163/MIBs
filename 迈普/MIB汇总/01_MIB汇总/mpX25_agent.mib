-- *****************************************************************
-- MAIPU-X25.mib:  Maipu enterprise device X.25 MIB file
--
--version 1.0.0.0, Feb 26, 2001 Huanglulu
--
-- Copyright (c)  by Maipu DataComm Inc.
-- All rights reserved.
-- 
-- *****************************************************************
--

MAIPU-X25-MIB DEFINITIONS ::= BEGIN

IMPORTS
    RowStatus, DisplayString
                                                 	FROM SNMPv2-TC
    MODULE-IDENTITY, OBJECT-TYPE, Counter32, IpAddress
						FROM SNMPv2-SMI
    mpMgmt                              	FROM MAIPU-SMI;

mpX25Mib MODULE-IDENTITY
    LAST-UPDATED "0102260000Z"
    ORGANIZATION "Maipu DataComm"
    CONTACT-INFO
	"   Maipu DataComm
		Customer Service

		Postal: Consulate Drive
			Chengdu, Sichuan  610041
			China

		Tel: 86-028-5161006

		E-mail: office@maipu.com"
    DESCRIPTION
		"The assignments for Maipu router's MIB of X.25 infomation!"
    ::= {mpMgmt 7 }

    x25IfMib     OBJECT IDENTIFIER ::= { mpX25Mib 1 }
    x25MapMib    OBJECT IDENTIFIER ::= { mpX25Mib 2 }
    x25VcMib      OBJECT IDENTIFIER ::= { mpX25Mib 3 }
    x25RouteMib          OBJECT IDENTIFIER ::= { mpX25Mib 4 }
    x25AgentMib          OBJECT IDENTIFIER ::= { mpX25Mib 5 }

--x25IfMib	OBJECT-IDENTITY
--	STATUS	current
--	DESCRIPTION
--		"X.25协议第三层."
--	::= { mpX25Mib 1 }
--
--x25MapMib	OBJECT-IDENTITY
--	STATUS	current
--	DESCRIPTION
--		"X.25协议地址映射表."
--	::= { mpX25Mib 2 }
--
--x25VcMib	OBJECT-IDENTITY
--	STATUS	current
--	DESCRIPTION
--		"X.25协议虚电路."
--	::= { mpX25Mib 3 }
	
--x25RouteMib	OBJECT-IDENTITY
--	STATUS	current
--	DESCRIPTION
--		"X.25路由表."
--	::= { mpX25Mib 4 }

--x25AgentMib	OBJECT-IDENTITY
--	STATUS	current
--	DESCRIPTION
--		"X.25代理，该模块实现TCP之上的应用层数据与X.25分组层数据之间的相互转换。"
--	::= { mpX25Mib 5 }

--//******** if configuration *******//
x25ConfTable	OBJECT-TYPE
	SYNTAX	SEQUENCE OF X25ConfEntry
	MAX-ACCESS	not-accessible
	STATUS	current
	DESCRIPTION
		"X.25协议在接口上的配置表。"
	::= { x25IfMib 1 }
	
x25ConfEntry 	OBJECT-TYPE
	SYNTAX	X25ConfEntry
	MAX-ACCESS	not-accessible
	STATUS	current
	DESCRIPTION
		"X.25协议在接口上的配置表条目。"
	INDEX { x25ConfIfIndex }
	::= { x25ConfTable 1 }	
	
X25ConfEntry ::=
	SEQUENCE {
		x25ConfIfIndex
			INTEGER,
		x25ConfMode
			INTEGER,
		x25ConfStat
			INTEGER,
		x25ConfAddress
			OCTET STRING,
		x25ConfHtc
			INTEGER,
		x25ConfLtc
			INTEGER,
		x25ConfHoldQueue
			INTEGER,
		x25ConfIdle
			INTEGER,
		x25ConfIps
			INTEGER,
		x25ConfOps
			INTEGER,
		x25ConfModulo
			INTEGER,
		x25ConfNvc
			INTEGER,
		x25ConfWin
			INTEGER,
		x25ConfWout
			INTEGER,
		x25ConfT20
			INTEGER,
		x25ConfT21
			INTEGER,
		x25ConfT22
			INTEGER,
		x25ConfT23
			INTEGER,
		x25ConfHic
			INTEGER,
		x25ConfHoc
			INTEGER
				}
		
x25ConfIfIndex	OBJECT-TYPE
	SYNTAX	INTEGER
	MAX-ACCESS	read-only
	STATUS	current
	DESCRIPTION
		"接口上的X.25协议配置表索引，与ifIndex相同。"
	::= { x25ConfEntry 1 }
	
x25ConfMode	OBJECT-TYPE
	SYNTAX	INTEGER {
				dte(1),
				dce(2)
					}
	MAX-ACCESS	read-write
	STATUS	current
	DESCRIPTION
		"X.25接口模式。"
	DEFVAL { dte }
	::= { x25ConfEntry 2 }

x25ConfState	OBJECT-TYPE
	SYNTAX	INTEGER {
				r0(0),
				r1(1),
				r23(2)
					}
	MAX-ACCESS	read-only
	STATUS	current
	DESCRIPTION
		"X.25分组层状态：r0表示分组层处于初始化状态；r1表示分组层处于就绪状态；r23表示分组层处于重新启动状态。"
	DEFVAL { dte }
	::= { x25ConfEntry 3 }
	
x25ConfAddress	OBJECT-TYPE
	SYNTAX	OCTET STRING (SIZE(1..14))
	MAX-ACCESS	read-write
	STATUS	current
	DESCRIPTION
		"X.25协议地址，采用X.121格式，即最多15位的数字字符串。"
	::= { x25ConfEntry 4 }
	
x25ConfHtc	OBJECT-TYPE
	SYNTAX	INTEGER (1..1024)
	MAX-ACCESS	read-write
	STATUS	current
	DESCRIPTION
		"X.25协议最高双向虚电路。"
	::= { x25ConfEntry 5 }
	
x25ConfLtc	OBJECT-TYPE
	SYNTAX	INTEGER (1..1024)
	MAX-ACCESS	read-write
	STATUS	current
	DESCRIPTION
		"X.25协议最低双向虚电路。"
	::= { x25ConfEntry 6 }
	
x25ConfHoldQueue	OBJECT-TYPE
	SYNTAX	INTEGER (0..9999)
	MAX-ACCESS	read-write
	STATUS	current
	DESCRIPTION
		"X.25协议虚电路分组保持队列长度，即当一条虚电路不能发送数据时能保持的最大分组个数。"
	::= { x25ConfEntry 7 }
	
x25ConfIdle	OBJECT-TYPE
	SYNTAX	INTEGER (0..255)
	MAX-ACCESS	read-write
	STATUS	current
	DESCRIPTION
		"X.25协议封装虚电路空闲时间，使虚电路一段时间不工作后，软件能清除一个SVC。"
	::= { x25ConfEntry 8 }
	
x25ConfIps	OBJECT-TYPE
	SYNTAX	INTEGER (16..4096)
	MAX-ACCESS	read-write
	STATUS	current
	DESCRIPTION
		"X.25协议最大输入分组大小。"
	DEFVAL { 128 }
	::= { x25ConfEntry 9 }
	
x25ConfOps	OBJECT-TYPE
	SYNTAX	INTEGER (16..4096)
	MAX-ACCESS	read-write
	STATUS	current
	DESCRIPTION
		"X.25协议最大输出分组大小。"
	::= { x25ConfEntry 10 }
	
x25ConfModulo	OBJECT-TYPE
	SYNTAX	INTEGER {
				modulo8(1),
				modulo128(2)
					}
	MAX-ACCESS	read-write
	STATUS	current
	DESCRIPTION
		"X.25协议工作模式。"
	DEFVAL { modulo8 }
	::= { x25ConfEntry 11 }
	
x25ConfNvc	OBJECT-TYPE
	SYNTAX	INTEGER (1..8)
	MAX-ACCESS	read-write
	STATUS	current
	DESCRIPTION
		"X.25协议上能建立的虚电路的最大数。"
	::= { x25ConfEntry 12 }
	
x25ConfWin	OBJECT-TYPE
	SYNTAX	INTEGER (1..127)
	MAX-ACCESS	read-write
	STATUS	current
	DESCRIPTION
		"X.25协议输入窗口大小。"
	DEFVAL { 2 }
	::= { x25ConfEntry 13 }
	
x25ConfWout	OBJECT-TYPE
	SYNTAX	INTEGER (1..127)
	MAX-ACCESS	read-write
	STATUS	current
	DESCRIPTION
		"X.25协议输出窗口大小。"
	DEFVAL { 2 }
	::= { x25ConfEntry 14 }

x25ConfT20	OBJECT-TYPE
	SYNTAX	INTEGER (1..1000)
	MAX-ACCESS	read-write
	STATUS	current
	DESCRIPTION
		"X.25协议DTE/DCE重新启动定时器时延值。"
	DEFVAL { 10 }
	::= { x25ConfEntry 15 }
	
x25ConfT21	OBJECT-TYPE
	SYNTAX	INTEGER (1..1000)
	MAX-ACCESS	read-write
	STATUS	current
	DESCRIPTION
		"X.25协议DTE/DCE呼叫规程定时器时延值。"
	DEFVAL { 10 }
	::= { x25ConfEntry 16 }
	
x25ConfT22	OBJECT-TYPE
	SYNTAX	INTEGER (1..1000)
	MAX-ACCESS	read-write
	STATUS	current
	DESCRIPTION
		"X.25协议DTE/DCE复原规程定时器时延值。"
	DEFVAL { 10 }
	::= { x25ConfEntry 17 }
	
x25ConfT23	OBJECT-TYPE
	SYNTAX	INTEGER (1..1000)
	MAX-ACCESS	read-write
	STATUS	current
	DESCRIPTION
		"X.25协议DTE/DCE清除规程定时器时延值。"
	DEFVAL { 10 }
	::= { x25ConfEntry 18 }
	
x25ConfHic	OBJECT-TYPE
	SYNTAX	INTEGER (1..1024)
	MAX-ACCESS	read-write
	STATUS	current
	DESCRIPTION
		"X.25协议最高呼入虚电路。"
	DEFVAL { 10 }
	::= { x25ConfEntry 19 }
	
x25ConfHoc	OBJECT-TYPE
	SYNTAX	INTEGER (1..1024)
	MAX-ACCESS	read-write
	STATUS	current
	DESCRIPTION
		"X.25协议最高呼出虚电路。"
	DEFVAL { 10 }
	::= { x25ConfEntry 20 }
	
lapbConfTable	OBJECT-TYPE
	SYNTAX	SEQUENCE OF LapbConfEntry
	MAX-ACCESS	not-accessible
	STATUS	current
	DESCRIPTION
		"LAPB协议配置表。"
	::= { x25IfMib 3 }
	
lapbConfEntry	OBJECT-TYPE
	SYNTAX	LapbConfEntry
	MAX-ACCESS	not-accessible
	STATUS	current
	DESCRIPTION
		"LAPB配置表条目。"
	INDEX { lapbIfIndex }
	::= { lapbConfTable 1 }
	
LapbConfEntry ::=
	SEQUENCE {
		lapbIfIndex
			INTEGER,
		lapbMode
			INTEGER,
		lapbState
			INTEGER,
		lapbModulo
			INTEGER,
		lapbN1
			INTEGER,
		lapbN2
			INTEGER,
		lapbT1
			INTEGER,
		lapbT2
			INTEGER,
		lapbT4
			INTEGER,
		lapbK
			INTEGER
				}
				
lapbIfIndex	OBJECT-TYPE
	SYNTAX	INTEGER
	MAX-ACCESS	read-only
	STATUS	current
	DESCRIPTION
		"LAPB配置表索引，与ifIndex相同。"
	::= { lapbConfEntry 1 }
	
lapbMode	OBJECT-TYPE
	SYNTAX	INTEGER {
				dte(1),
				dce(2)
					}
	MAX-ACCESS	read-write
	STATUS	current
	DESCRIPTION
		"LAPB的工作模式。"
	DEFVAL { dte }
	::= { lapbConfEntry 2 }

lapbState	OBJECT-TYPE
	SYNTAX	INTEGER {
				init(0),
				dm_sent(1),
				sabm_sent(2),
				abm(3),
				wait_sabm(4),
				wait_ua(5),
				disc_sent(6),
				disconnected(7),
				init_start(8)
					}
	MAX-ACCESS	read-only
	STATUS	current
	DESCRIPTION
		"LAPB的状态。"
	DEFVAL { dte }
	::= { lapbConfEntry 3 }
	
lapbModulo	OBJECT-TYPE
	SYNTAX	INTEGER {
				modulo8(1),
				modulo128(2)
					}
	MAX-ACCESS	read-write
	STATUS	current
	DESCRIPTION
		"LAPB协议的工作模式。"
	DEFVAL { modulo8 }
	::= { lapbConfEntry 4 }
	
lapbN1	OBJECT-TYPE
	SYNTAX	INTEGER (137..1513)
	MAX-ACCESS	read-write
	STATUS	current
	DESCRIPTION
		"LAPB的接收I帧的最大比特数。"
	::= { lapbConfEntry 5 }
	
lapbN2	OBJECT-TYPE
	SYNTAX	INTEGER (1..255)
	MAX-ACCESS	read-write
	STATUS	current
	DESCRIPTION
		"LAPB发送帧的最大尝试次数。"
	DEFVAL { 10 }
	::= { lapbConfEntry 6 }
	
lapbT1	OBJECT-TYPE
	SYNTAX	INTEGER (1..64000)
	MAX-ACCESS	read-write
	STATUS	current
	DESCRIPTION
		"LAPB的重发计时器。"
	DEFVAL { 3 }
	::= { lapbConfEntry 7 }
	
lapbT2	OBJECT-TYPE
	SYNTAX	INTEGER (1..32000)
	MAX-ACCESS	read-write
	STATUS	current
	DESCRIPTION
		"LAPB的接收计时器，到时就发送证实帧。"
	DEFVAL { 1 }
	::= { lapbConfEntry 8 }

lapbT4	OBJECT-TYPE
	SYNTAX	INTEGER (0..255)
	MAX-ACCESS	read-write
	STATUS	current
	DESCRIPTION
		"LAPB的保活计时器，到时就发送保活帧。"
	DEFVAL { 15 }
	::= { lapbConfEntry 9 }
	
lapbK	OBJECT-TYPE
	SYNTAX	INTEGER (1..127)
	MAX-ACCESS	read-write
	STATUS	current
	DESCRIPTION
		"LAPB的窗口大小。如果lapbModulo的值是modulo8则设置范围是1..7，如果是modulo128则设置范围是1..127。"
	DEFVAL { 7 }
	::= { lapbConfEntry 10 }
	
--//*********** map **********//
x25MapConfTable	OBJECT-TYPE
	SYNTAX	SEQUENCE OF X25MapConfEntry
	MAX-ACCESS	not-accessible
	STATUS	current
	DESCRIPTION
		"X.25协议地址映射配置表。"
	::= { x25MapMib 1 }
	
x25MapConfEntry	OBJECT-TYPE
	SYNTAX	X25MapConfEntry
	MAX-ACCESS	not-accessible
	STATUS	current
	DESCRIPTION
		"X.25协议地址映射配置表条目。"
	INDEX { x25MapConfIfIndex, x25MapConfMode, x25MapConfAddr }
	::= { x25MapConfTable 1 }
	
X25MapConfEntry ::=
	SEQUENCE {
		x25MapConfIfIndex
			INTEGER,
		x25MapConfMode
			INTEGER,
		x25MapConfAddr
			OCTET STRING,
		x25MapConfX121Addr
			OCTET STRING,
		x25MapConfLimite
			BITS,
		x25MapConfBridgeIfIndex
			INTEGER,
		x25MapConfBridgePort
			INTEGER,
		x25MapConfBridgeType
			INTEGER,
		x25MapConfType
			INTEGER,
		x25MapConfStatus
			RowStatus
				}
				
x25MapConfIfIndex	OBJECT-TYPE
	SYNTAX	INTEGER
	MAX-ACCESS	read-create
	STATUS	current
	DESCRIPTION
		"X.25协议地址映射的接口索引，与ifIndex相同。"
	::= { x25MapConfEntry 1 }
	
x25MapConfMode	OBJECT-TYPE
	SYNTAX	INTEGER {
				ip(1),
				compressedIp(2),
				qllc(3),
				bridge(4)
					}
	MAX-ACCESS	read-create
	STATUS	current
	DESCRIPTION
		"X.25协议地址映射的协议类型。"
	DEFVAL { ip }
	::= { x25MapConfEntry 2 }
	
x25MapConfAddr	OBJECT-TYPE
	SYNTAX	OCTET STRING (SIZE(1..64))
	MAX-ACCESS	read-create
	STATUS	current
	DESCRIPTION
		"X.121地址映射的上层协议地址。"
	::= { x25MapConfEntry 3 }
	
x25MapConfX121Addr	OBJECT-TYPE
	SYNTAX	OCTET STRING (SIZE(1..14))
	MAX-ACCESS	read-create
	STATUS	current
	DESCRIPTION
		"X.25协议地址映射的X.121地址。"
	::= { x25MapConfEntry 4 }
	
x25MapConfLimite	OBJECT-TYPE
	SYNTAX	INTEGER
	MAX-ACCESS	read-create
	STATUS	current
	DESCRIPTION
		"X.25协议地址映射的限制，按位配置。"
	DEFVAL { {none} }
	::= { x25MapConfEntry 5 }
	
x25MapConfBridgeIfIndex	OBJECT-TYPE
	SYNTAX	INTEGER
	MAX-ACCESS	read-create
	STATUS	current
	DESCRIPTION
		"X.25协议地址映射桥接的接口索引，与ifIndex相同。"
	::= { x25MapConfEntry 6 }	
	
x25MapConfBridgePort	OBJECT-TYPE
	SYNTAX	INTEGER (0..65535)
	MAX-ACCESS	read-create
	STATUS	current
	DESCRIPTION
		"X.25协议地址映射桥接的端口号。"
	::= { x25MapConfEntry 7 }	
	
x25MapConfBridgeType	OBJECT-TYPE
	SYNTAX	INTEGER {
				tp-tcp(1),
				none(2)
					}
	MAX-ACCESS	read-create
	STATUS	current
	DESCRIPTION
		"X.25协议地址映射桥接的标志。"
	::= { x25MapConfEntry 8 }	
	
x25MapConfType	OBJECT-TYPE
	SYNTAX	INTEGER {
				static(1),
				pvc(2)
					}
	MAX-ACCESS	read-only
	STATUS	current
	DESCRIPTION
		"X.25协议地址映射的类型，一种是手工配置的，另一种是配置PVC时生成的。"
	::= { x25MapConfEntry 9 }
	
x25MapConfStatus	OBJECT-TYPE
	SYNTAX	RowStatus
	MAX-ACCESS	read-create
	STATUS	current
	DESCRIPTION
		"X.25协议地址映射表的行状态，用于增加、删除或修改一行的内容。"
	::= { x25MapConfEntry 10 }
	
--x25MapStatTable	OBJECT-TYPE
--	SYNTAX	SEQUENCE OF X25MapStatEntry
--	MAX-ACCESS	not-accessible
--	STATUS	current
--	DESCRIPTION
--		"X.25协议地址映射统计表."
--	::= { x25MapMib 2 }
	
--x25MapStatEntry	OBJECT-TYPE
--	SYNTAX	X25MapStatEntry
--	MAX-ACCESS	not-accessible
--	STATUS	current
--	DESCRIPTION
--		"X.25协议地址映射统计表条目."
--	INDEX { x25MapStatIfIndex, x25MapStatIpAddr }
--	::= { x25MapStatTable 1 }
	
--X25MapStatEntry ::=
--	SEQUENCE {
--		x25MapStatIfIndex
--			INTEGER,
--		x25MapStatIpAddr
--			IpAddress,
--		x25MapStatX121Addr
--			OCTET STRING,
--		x25MapStatType
--			INTEGER
--				}
--				
--x25MapStatIfIndex	OBJECT-TYPE
--	SYNTAX	INTEGER
--	MAX-ACCESS	read-only
--	STATUS	current
--	DESCRIPTION
--		"X.25协议地址映射统计表的接口索引,与ifIndex相同."
--	::= { x25MapStatEntry 1 }
--	
--x25MapStatIpAddr	OBJECT-TYPE
--	SYNTAX	IpAddress
--	MAX-ACCESS	read-only
--	STATUS	current
--	DESCRIPTION
--		"X.25协议地址映射的上层协议地址."
--	::= { x25MapStatEntry 2 }
--	
--x25MapStatX121Addr	OBJECT-TYPE
--	SYNTAX	OCTET STRING (SIZE(0..14))
--	MAX-ACCESS	read-only
--	STATUS	current
--	DESCRIPTION
--		"X.25协议地址映射的X.121地址."
--	::= { x25MapStatEntry 3 }
	
--x25MapStatType	OBJECT-TYPE
--	SYNTAX	INTEGER {
--				static(1),
--				pvc(2)
--					}
--	MAX-ACCESS	read-only
--	STATUS	current
--	DESCRIPTION
--		"X.25协议地址映射的类型,一是手工配置的,一是配置PVC是生成的."
--	::= { x25MapStatEntry 4 }
	
--//*********** pvc *********//
x25PvcConfTable	OBJECT-TYPE
	SYNTAX	SEQUENCE OF X25PvcConfEntry
	MAX-ACCESS	not-accessible
	STATUS	current
	DESCRIPTION
		"X.25协议永久虚电路配置表。"
	::= { x25VcMib 1 }
	
x25PvcConfEntry	OBJECT-TYPE
	SYNTAX	X25PvcConfEntry
	MAX-ACCESS	not-accessible
	STATUS	current
	DESCRIPTION
		"X.25协议永久虚电路配置表条目。"
	INDEX { x25PvcConfIfIndex, x25PvcConfNum }
	::= { x25PvcConfTable 1 }
	
X25PvcConfEntry ::=
	SEQUENCE {
		x25PvcConfIfIndex
			INTEGER,
		x25PvcConfNum
			INTEGER,
		x25PvcConfMode
			INTEGER,
		x25PvcConfAddr
			OCTET STRING,
		x25PvcConfX121Addr
			OCTET STRING,
		x25PvcConfLimite
			INTEGER,
		x25PvcConfXotIpAddr
			IpAddress,
		x25PvcConfRouteIntf
			OCTET STRING,
		x25PvcConfRouteNum
			INTEGER,
		x25PvcConfStatus
			RowStatus
				}
				
x25PvcConfIfIndex	OBJECT-TYPE
	SYNTAX	INTEGER
	MAX-ACCESS	read-create
	STATUS	current
	DESCRIPTION
		"X.25协议永久虚电路配置的接口索引，与ifIndex相同。"
	::= { x25PvcConfEntry 1 }

x25PvcConfNum	OBJECT-TYPE
	SYNTAX	INTEGER (1..4095)
	MAX-ACCESS	read-create
	STATUS	current
	DESCRIPTION
		"X.25协议永久虚电路的虚电路号，值在0-x25ConfLtc之间。"
	::= { x25PvcConfEntry 2 }
	
x25PvcConfMode	OBJECT-TYPE
	SYNTAX	INTEGER {	
				ip(1),
				compressedIp(2),
				qllc(3),
				xot(4),
				interface(5)
					}
	MAX-ACCESS	read-create
	STATUS	current
	DESCRIPTION
		"X.25协议永久虚电路的协议类型。"
	DEFVAL { ip }
	::= { x25PvcConfEntry 3 }
	
x25PvcConfAddr	OBJECT-TYPE
	SYNTAX	OCTET STRING(SIZE(1..64))
	MAX-ACCESS	read-create
	STATUS	current
	DESCRIPTION
		"X.25协议永久虚电路的上层协议地址。"
	::= { x25PvcConfEntry 4 }
	
x25PvcConfX121Addr	OBJECT-TYPE
	SYNTAX	OCTET STRING (SIZE(0..14))
	MAX-ACCESS	read-create
	STATUS	current
	DESCRIPTION
		"X.25协议永久虚电路的X.121地址，可以不配置，这时字符串长度为0。"
	::= { x25PvcConfEntry 5 }
	
x25PvcConfLimite	OBJECT-TYPE
	SYNTAX	INTEGER {
				broadcast(1),
				passive(2),
				none(3)
					}
	MAX-ACCESS	read-create
	STATUS	current
	DESCRIPTION
		"X.25协议永久虚电路的限制。对于ip协议来说是broadcast/none，对于compressedIp来说是passive/none。"
	DEFVAL { none }
	::= { x25PvcConfEntry 6 }
	
x25PvcConfXotIpAddr	OBJECT-TYPE
	SYNTAX	IpAddress
	MAX-ACCESS	read-create
	STATUS	current
	DESCRIPTION
		"XOT服务器的IP地址。"
	::= { x25PvcConfEntry 7 }

x25PvcConfRouteIntf	OBJECT-TYPE
	SYNTAX	OCTET STRING (0..128)
	MAX-ACCESS	read-create
	STATUS	current
	DESCRIPTION
		"X.25协议交换PVC的接口索引，与ifIndex相同。"
	::= { x25PvcConfEntry 8 }

x25PvcConfRouteNum	OBJECT-TYPE
	SYNTAX	INTEGER (1..4095)
	MAX-ACCESS	read-create
	STATUS	current
	DESCRIPTION
		"X.25协议交换PVC的目标PVC索引，值在目标接口上的0-x25ConfLtc之间。"
	::= { x25PvcConfEntry 9 }
	
x25PvcConfStatus	OBJECT-TYPE
	SYNTAX	RowStatus
	MAX-ACCESS	read-create
	STATUS	current
	DESCRIPTION
		"X.25永久虚电路配置表的行状态，用于增加、删除或修改一行的内容。"
	::= { x25PvcConfEntry 10 }
	
x25VcStatTable	OBJECT-TYPE
	SYNTAX	SEQUENCE OF X25VcStatEntry
	MAX-ACCESS	not-accessible
	STATUS	current
	DESCRIPTION
		"X.25协议虚电路统计表。"
	::= { x25VcMib 2 }
	
x25VcStatEntry	OBJECT-TYPE
	SYNTAX	X25VcStatEntry
	MAX-ACCESS	not-accessible
	STATUS	current
	DESCRIPTION
		"X.25协议虚电路统计表条目。"
	INDEX { x25VcStatIfIndex, x25VcStatNum }
	::= { x25VcStatTable 1 }
	
X25VcStatEntry ::=
	SEQUENCE {
		x25VcStatIfIndex
			INTEGER,
		x25VcStatNum
			INTEGER,
		x25VcStatType
			INTEGER,
		x25VcStatTime
			DisplayString,
		x25VcStatLocalX121Addr
			OCTET STRING,
		x25VcStatRemoteX121Addr
			OCTET STRING,
		x25VcStatRemoteAddr
			OCTET STRING,
		x25VcStatFlowState
			INTEGER,
		x25VcStatSwin
			INTEGER,
		x25VcStatRwin
			INTEGER,
		x25VcStatSMaxPktSize
			INTEGER,
		x25VcStatRMaxPktSize
			INTEGER,
		x25VcStatVr
			Counter32,
		x25VcStatVs
			Counter32,
		x25VcStatNr
			Counter32,
		x25VcStatNs
			Counter32,
		x25VcStatLastNr
			Counter32,
		x25VcStatNoRsp
			Counter32,
		x25VcStatStxqPriority
			INTEGER,
		x25VcStatStxqCnt
			Counter32,
		x25VcStatStxqMax
			Counter32,
		x25VcStatStxqSmax
			Counter32,
		x25VcStatStxqQw
			Counter32,
		x25VcStatStxqQwmax
			Counter32,
		x25VcStatTxqPriority
			INTEGER,
		x25VcStatTxqCnt
			Counter32,
		x25VcStatTxqMax
			Counter32,
		x25VcStatTxqSmax
			Counter32,
		x25VcStatTxqQw
			Counter32,
		x25VcStatTxqQwmax
			Counter32
				}
				
x25VcStatIfIndex	OBJECT-TYPE
	SYNTAX	INTEGER
	MAX-ACCESS	read-only
	STATUS	current
	DESCRIPTION
		"X.25协议虚电路统计表的接口索引，与ifIndex相同。"
	::= { x25VcStatEntry 1 }
	
x25VcStatNum	OBJECT-TYPE
	SYNTAX	INTEGER (1..4095)
	MAX-ACCESS	read-only
	STATUS	current
	DESCRIPTION
		"X.25协议虚电路的虚电路号。"
	::= { x25VcStatEntry 2 }
	
x25VcStatType	OBJECT-TYPE
	SYNTAX	INTEGER {
				pvc(1),
				svc(2)
					}
	MAX-ACCESS	read-only
	STATUS	current
	DESCRIPTION
		"X.25协议虚电路是否是永久的。"
	::= { x25VcStatEntry 3 }
	
x25VcStatTime	OBJECT-TYPE
	SYNTAX	DisplayString
	MAX-ACCESS	read-only
	STATUS	current
	DESCRIPTION
		"虚电路建立的时间。"
	::= { x25VcStatEntry 4 }
	
x25VcStatLocalX121Addr	OBJECT-TYPE
	SYNTAX	OCTET STRING (SIZE(1..14))
	MAX-ACCESS	read-only
	STATUS	current
	DESCRIPTION
		"虚电路对应的本地X.121地址。"
	::= { x25VcStatEntry 5 }
	
x25VcStatRemoteX121Addr	OBJECT-TYPE
	SYNTAX	OCTET STRING (SIZE(0..14))
	MAX-ACCESS	read-only
	STATUS	current
	DESCRIPTION
		"虚电路对应的远端X.121地址。"
	::= { x25VcStatEntry 6 }
	
x25VcStatRemoteAddr	OBJECT-TYPE
	SYNTAX	OCTET STRING
	MAX-ACCESS	read-only
	STATUS	current
	DESCRIPTION
		"虚电路对应的远端IP地址。"
	::= { x25VcStatEntry 7 }
	
x25VcStatFlowState	OBJECT-TYPE
	SYNTAX	INTEGER {
				readyD1(1),
				dteResetingD2(2),
				dceResetingD3(3),
				error(4)
					}
	MAX-ACCESS	read-only
	STATUS	current
	DESCRIPTION
		"虚电路的流状态。"
	::= { x25VcStatEntry 8 }
	
x25VcStatSwin	OBJECT-TYPE
	SYNTAX	INTEGER
	MAX-ACCESS	read-only
	STATUS	current
	DESCRIPTION
		"虚电路发送窗口大小。"
	::= { x25VcStatEntry 9 }
	
x25VcStatRwin	OBJECT-TYPE
	SYNTAX	INTEGER
	MAX-ACCESS	read-only
	STATUS	current
	DESCRIPTION
		"虚电路接收窗口大小。"
	::= { x25VcStatEntry 10 }
	
x25VcStatSMaxPktSize	OBJECT-TYPE
	SYNTAX	INTEGER
	MAX-ACCESS	read-only
	STATUS	current
	DESCRIPTION
		"虚电路发送的最大分组尺寸。"
	::= { x25VcStatEntry 11 }
	
x25VcStatRMaxPktSize	OBJECT-TYPE
	SYNTAX	INTEGER
	MAX-ACCESS	read-only
	STATUS	current
	DESCRIPTION
		"虚电路接收的最大分组尺寸。"
	::= { x25VcStatEntry 12 }
	
x25VcStatVr	OBJECT-TYPE
	SYNTAX	Counter32
	MAX-ACCESS	read-only
	STATUS	current
	DESCRIPTION
		"虚电路的接收变量。"
	::= { x25VcStatEntry 13 }
	
x25VcStatVs	OBJECT-TYPE
	SYNTAX	Counter32
	MAX-ACCESS	read-only
	STATUS	current
	DESCRIPTION
		"虚电路的发送变量。"
	::= { x25VcStatEntry 14 }
	
x25VcStatNr	OBJECT-TYPE
	SYNTAX	Counter32
	MAX-ACCESS	read-only
	STATUS	current
	DESCRIPTION
		"虚电路期望收到的下一个分组的发送序列号。"
	::= { x25VcStatEntry 15 }
	
x25VcStatNs	OBJECT-TYPE
	SYNTAX	Counter32
	MAX-ACCESS	read-only
	STATUS	current
	DESCRIPTION
		"虚电路要发送的下一个分组的发送序列号。"
	::= { x25VcStatEntry 16 }
	
x25VcStatLastNr	OBJECT-TYPE
	SYNTAX	Counter32
	MAX-ACCESS	read-only
	STATUS	current
	DESCRIPTION
		"虚电路要确认的对方的下一个序列号。"
	::= { x25VcStatEntry 17 }
	
x25VcStatNoRsp	OBJECT-TYPE
	SYNTAX	Counter32
	MAX-ACCESS	read-only
	STATUS	current
	DESCRIPTION
		"虚电路没有得到对方确认的分组个数。"
	::= { x25VcStatEntry 18 }
	
x25VcStatStxqPriority	OBJECT-TYPE
	SYNTAX	INTEGER
	MAX-ACCESS	read-only
	STATUS	current
	DESCRIPTION
		""
	::= { x25VcStatEntry 19 }
	
x25VcStatStxqCnt	OBJECT-TYPE
	SYNTAX	Counter32
	MAX-ACCESS	read-only
	STATUS	current
	DESCRIPTION
		""
	::= { x25VcStatEntry 20 }
	
x25VcStatStxqMax	OBJECT-TYPE
	SYNTAX	Counter32
	MAX-ACCESS	read-only
	STATUS	current
	DESCRIPTION
		""
	::= { x25VcStatEntry 21 }
	
x25VcStatStxqSmax	OBJECT-TYPE
	SYNTAX	Counter32
	MAX-ACCESS	read-only
	STATUS	current
	DESCRIPTION
		""
	::= { x25VcStatEntry 22 }
	
x25VcStatStxqQw	OBJECT-TYPE
	SYNTAX	Counter32
	MAX-ACCESS	read-only
	STATUS	current
	DESCRIPTION
		""
	::= { x25VcStatEntry 23 }
	
x25VcStatStxqQwmax	OBJECT-TYPE
	SYNTAX	Counter32
	MAX-ACCESS	read-only
	STATUS	current
	DESCRIPTION
		""
	::= { x25VcStatEntry 24 }
	
x25VcStatTxqPriority	OBJECT-TYPE
	SYNTAX	INTEGER
	MAX-ACCESS	read-only
	STATUS	current
	DESCRIPTION
		""
	::= { x25VcStatEntry 25 }
	
x25VcStatTxqCnt	OBJECT-TYPE
	SYNTAX	Counter32
	MAX-ACCESS	read-only
	STATUS	current
	DESCRIPTION
		""
	::= { x25VcStatEntry 26 }
	
x25VcStatTxqMax	OBJECT-TYPE
	SYNTAX	Counter32
	MAX-ACCESS	read-only
	STATUS	current
	DESCRIPTION
		""
	::= { x25VcStatEntry 27 }
	
x25VcStatTxqSmax	OBJECT-TYPE
	SYNTAX	Counter32
	MAX-ACCESS	read-only
	STATUS	current
	DESCRIPTION
		""
	::= { x25VcStatEntry 28 }
	
x25VcStatTxqQw	OBJECT-TYPE
	SYNTAX	Counter32
	MAX-ACCESS	read-only
	STATUS	current
	DESCRIPTION
		""
	::= { x25VcStatEntry 29 }
	
x25VcStatTxqQwmax	OBJECT-TYPE
	SYNTAX	Counter32
	MAX-ACCESS	read-only
	STATUS	current
	DESCRIPTION
		""
	::= { x25VcStatEntry 30 }

--//*********** route *********//
x25RoutingConfSwitch	OBJECT-TYPE
	SYNTAX	INTEGER {
				close(1),
				open(2)
					}
	MAX-ACCESS	read-write
	STATUS	current
	DESCRIPTION
		"X.25协议交换开关。"
	DEFVAL { open }
	::= { x25RouteMib 1 }
	
x25RouteConfTable	OBJECT-TYPE
	SYNTAX	SEQUENCE OF X25RouteConfEntry
	MAX-ACCESS	not-accessible
	STATUS	current
	DESCRIPTION
		"X.25协议路由配置表。"
	::= { x25RouteMib 2 }
	
x25RouteConfEntry	OBJECT-TYPE
	SYNTAX	X25RouteConfEntry
	MAX-ACCESS	not-accessible
	STATUS	current
	DESCRIPTION
		"X.25协议路由配置表条目。"
	INDEX { x25RouteConfX121Addr }
	::= { x25RouteConfTable 1 }

X25RouteConfEntry ::=
	SEQUENCE {
		x25RouteConfX121Addr
			OCTET STRING,
		x25RouteConfType
			INTEGER,
		x25RouteConfIfIndex
			INTEGER,
		x25RouteConfXotIpAddr
			OCTET STRING,
		x25RouteConfStatus
			RowStatus
				}
				
x25RouteConfX121Addr	OBJECT-TYPE
	SYNTAX	OCTET STRING (SIZE(0..14))
	MAX-ACCESS	read-create
	STATUS	current
	DESCRIPTION
		"X.25协议路由表的X.121地址。"
	::= { x25RouteConfEntry 1 }
	
x25RouteConfType	OBJECT-TYPE
	SYNTAX	INTEGER {
				interface(1),
				xot(2)
					}
	MAX-ACCESS	read-create
	STATUS	current
	DESCRIPTION
		"X.25协议路由表的类型。"
	DEFVAL { interface }
	::= { x25RouteConfEntry 2 }
	
x25RouteConfIfIndex	OBJECT-TYPE
	SYNTAX	INTEGER
	MAX-ACCESS	read-create
	STATUS	current
	DESCRIPTION
		"X.25协议接口路由表的接口索引，与ifIndex相同。"
	::= { x25RouteConfEntry 3 }
	
x25RouteConfXotIpAddr	OBJECT-TYPE
	SYNTAX	OCTET STRING(SIZE(0..64))
	MAX-ACCESS	read-create
	STATUS	current
	DESCRIPTION
		"X.25协议XOT路由表的IP地址。"
	::= { x25RouteConfEntry 4 }
	
x25RouteConfStatus	OBJECT-TYPE
	SYNTAX	RowStatus
	MAX-ACCESS	read-create
	STATUS	current
	DESCRIPTION
		"X.25路由表的行状态，用于增加、删除或修改一行的内容。"
	::= { x25RouteConfEntry 5 }
	
--x25RouteStatTable	OBJECT-TYPE
--	SYNTAX	SEQUENCE OF X25RouteStatEntry
--	MAX-ACCESS	not-accessible
--	STATUS	current
--	DESCRIPTION
--		"X.25路由状态表。"
--	::= { x25RouteMib 3 }
				
x25AgentTcpPort     	OBJECT-TYPE
                    		SYNTAX  Unsigned32(5000..10000)
                    		MAX-ACCESS  read-write
                    		STATUS  current
                    		DESCRIPTION
                    			"X.25代理TCP服务器端口号。"
                    		::= { x25AgentMib 1 }

x25AgentInitTimeout 	OBJECT-TYPE
                    		SYNTAX  Unsigned32(2..30)
                    		MAX-ACCESS  read-write
                    		STATUS  current
                    		DESCRIPTION
                    			"X.25代理初始化超时时间。"
                    		::= { x25AgentMib 2 }

x25AgentBufferFlush 	OBJECT-TYPE
                    		SYNTAX  Unsigned32(30..180)
                    		MAX-ACCESS  read-write
                    		STATUS  current
                    		DESCRIPTION
                    			"X.25代理缓冲区数据保留时间。"
                    		::= { x25AgentMib 3 }

x25AgentAddressTable	OBJECT-TYPE
                    		SYNTAX  SEQUENCE OF   X25AgentAddressEntry
                    		MAX-ACCESS  not-accessible
                    		STATUS  current
                    		DESCRIPTION
                    			"X.25代理逻辑地址与物理地址对应表。"
                    		::= { x25AgentMib 4 }

x25AgentAddressEntry	OBJECT-TYPE
                    		SYNTAX  X25AgentAddressEntry
                    		MAX-ACCESS  not-accessible
                    		STATUS  current
                    		DESCRIPTION
                    			"X.25代理逻辑地址与物理地址对应表条目。"
                    		INDEX  { x25AgentLogicAddr }
                    		::= { x25AgentAddressTable 1 }

X25AgentAddressEntry	::= SEQUENCE {
                    			x25AgentLogicAddr      DisplayString,
                    			x25AgentX121Addr0      DisplayString,
                    			x25AgentX121Addr1      DisplayString,
                    			x25AgentX121Addr2      DisplayString,
                    			x25AgentX121Addr3      DisplayString,
                    			x25AgentX121Addr4      DisplayString,
                    			x25AgentAddressRowStatus   RowStatus
                    	             }


x25AgentLogicAddr   	OBJECT-TYPE
                    		SYNTAX  DisplayString(SIZE(0..8))
                    		MAX-ACCESS  read-only
                    		STATUS  current
                    		DESCRIPTION
                    			"X.25代理逻辑地址。"
                    		::= { x25AgentAddressEntry 1 }

x25AgentX121Addr0   	OBJECT-TYPE
                    		SYNTAX  DisplayString(SIZE(0..15))
                    		MAX-ACCESS  read-write
                    		STATUS  current
                    		DESCRIPTION
                    			"X.25代理逻辑地址对应的第一个网络的X.121地址。"
                    		::= { x25AgentAddressEntry 2 }

x25AgentX121Addr1   	OBJECT-TYPE
                    		SYNTAX  DisplayString(SIZE(0..15))
                    		MAX-ACCESS  read-write
                    		STATUS  current
                    		DESCRIPTION
                    			"X.25代理逻辑地址对应的第二个网络的X.121地址。"
                    		::= { x25AgentAddressEntry 3 }

x25AgentX121Addr2   	OBJECT-TYPE
                    		SYNTAX  DisplayString(SIZE(0..15))
                    		MAX-ACCESS  read-write
                    		STATUS  current
                    		DESCRIPTION
                    			"X.25代理逻辑地址对应的第三个网络的X.121地址。"
                    		::= { x25AgentAddressEntry 4 }

x25AgentX121Addr3   	OBJECT-TYPE
                    		SYNTAX  DisplayString(SIZE(0..15))
                    		MAX-ACCESS  read-write
                    		STATUS  current
                    		DESCRIPTION
                    			"X.25代理逻辑地址对应的第四个网络的X.121地址。"
                    		::= { x25AgentAddressEntry 5 }

x25AgentX121Addr4   	OBJECT-TYPE
                    		SYNTAX  DisplayString(SIZE(0..15))
                    		MAX-ACCESS  read-write
                    		STATUS  current
                    		DESCRIPTION
                    			"X.25代理逻辑地址对应的第五个网络的X.121地址。"
                    		::= { x25AgentAddressEntry 6 }

x25AgentAddressRowStatus	OBJECT-TYPE
                    		SYNTAX  RowStatus
                    		MAX-ACCESS  read-write
                    		STATUS  current
                    		DESCRIPTION
                    			"X.25代理逻辑地址与物理地址对应表的行状态，用于增加、删除或修改一行的内容。"
                    		::= { x25AgentAddressEntry 7 }

x25AgentInterfaceTable	OBJECT-TYPE
                    		SYNTAX  SEQUENCE OF   X25AgentInterfaceEntry
                    		MAX-ACCESS  not-accessible
                    		STATUS  current
                    		DESCRIPTION
                    			"X.25代理接口和网络对应表。"
                    		::= { x25AgentMib 5 }

x25AgentInterfaceEntry	OBJECT-TYPE
                    		SYNTAX  X25AgentInterfaceEntry
                    		MAX-ACCESS  not-accessible
                    		STATUS  current
                    		DESCRIPTION
                    			"X.25代理接口和网络对应表条目。"
                    		INDEX  { x25AgentIfIndex }
                    		::= { x25AgentInterfaceTable 1 }

X25AgentInterfaceEntry	::= SEQUENCE {
                    			x25AgentIfIndex        INTEGER,
                    			x25AgentNetworkNumber   INTEGER,
                    			x25AgentInterfaceRowStatus   RowStatus
                    	             }


x25AgentIfIndex     	OBJECT-TYPE
                    		SYNTAX  INTEGER
                    		MAX-ACCESS  read-only
                    		STATUS  current
                    		DESCRIPTION
                    			"X.25代理接口索引，与ifIndex相同。"
                    		::= { x25AgentInterfaceEntry 1 }

x25AgentNetworkNumber	OBJECT-TYPE
                    		SYNTAX  INTEGER(0..4) {
                    			         
                    			        }
                    		MAX-ACCESS  read-write
                    		STATUS  current
                    		DESCRIPTION
                    			"X.25代理接口对应的网络号。"
                    		::= { x25AgentInterfaceEntry 2 }

x25AgentInterfaceRowStatus	OBJECT-TYPE
                    		SYNTAX  RowStatus
                    		MAX-ACCESS  accessible-for-notify
                    		STATUS  current
                    		DESCRIPTION
                    			"X.25代理接口与网络对应表的行状态，用于增加、删除或修改一行的内容。"
                    		::= { x25AgentInterfaceEntry 3 }

				
END
