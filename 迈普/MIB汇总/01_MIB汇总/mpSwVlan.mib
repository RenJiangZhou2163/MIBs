------------------------------------------------------------------------------
--
--  File         : mpSwVlan.mib
--  Description  : 
--  Version      :  
--  Date         : March 3, 2003
-- 	Copyright    : 2003 by maipu (sichuan) communication technology co.,ltd.
--					All rights reserved.
--
-- $Id:
-- 
------------------------------------------------------------------------------

------------------------------------------------------------------------------
MPSWVLAN DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;


maipu               	OBJECT IDENTIFIER ::= { enterprises 5651 }
mpMgmt2             	OBJECT IDENTIFIER ::= { maipu 6 }
mpSwitchTech        	OBJECT IDENTIFIER ::= { mpMgmt2 3 }



mpSwVlan            	MODULE-IDENTITY
                    		LAST-UPDATED 	"0806061454Z"
                    		ORGANIZATION 	"Maipu (Sichuan) Communication Technology Co. LTD."
                    		CONTACT-INFO
                    			""
                    		DESCRIPTION
                      			"Subtree for SwVlan MIB."
                    		::= { mpSwitchTech  2 }




------------------------------------------------------------------------------
mpVlanTrap          	OBJECT IDENTIFIER ::= { mpSwVlan 0 }

mpVlanAddTrap       	NOTIFICATION-TYPE
                    		OBJECTS {
                    		         dot1qVlanIndex
                    		        }
                    		STATUS  current
                    		DESCRIPTION
                    			"This notification is generated when system creates a VLAN."
                    		::= { mpVlanTrap 1 }

mpVlanDeleteTrap    	NOTIFICATION-TYPE
                    		OBJECTS {
                    		         dot1qVlanIndex
                    		        }
                    		STATUS  current
                    		DESCRIPTION
                    			"This notification is generated when system deletes a VLAN."
                    		::= { mpVlanTrap 2 }

mpVlanPortsAddTrap  	NOTIFICATION-TYPE
                    		OBJECTS {
                    		         dot1qVlanIndex,
                    		         mpVlanPortChangeList
                    		        }
                    		STATUS  current
                    		DESCRIPTION
                    			"This notification is generated when system adds ports to a VLAN."
                    		::= { mpVlanTrap 3 }

mpVlanPortsDeleteTrap	NOTIFICATION-TYPE
                    		OBJECTS {
                    		         dot1qVlanIndex,
                    		         mpVlanPortChangeList
                    		        }
                    		STATUS  current
                    		DESCRIPTION
                    			"This notification is generated when system deletes ports from a VLAN."
                    		::= { mpVlanTrap 4 }

mpPortVlanTable     	OBJECT-TYPE
                    		SYNTAX  SEQUENCE OF   MpPortVlanEntry
                    		MAX-ACCESS  not-accessible
                    		STATUS  current
                    		DESCRIPTION
                    			""
                    		::= { mpSwVlan 2 }

mpPortVlanEntry     	OBJECT-TYPE
                    		SYNTAX  MpPortVlanEntry
                    		MAX-ACCESS  not-accessible
                    		STATUS  current
                    		DESCRIPTION
                    			""
                    		INDEX  {  }
                    		::= { mpPortVlanTable 1 }

MpPortVlanEntry     	::= SEQUENCE {
                    			mpVlanPortIndex        Unsigned32,
                    			mpVlanPortMode         INTEGER,
                    			mpTrunkVlanList        OCTET STRING
                    	             }


mpVlanPortIndex     	OBJECT-TYPE
                    		SYNTAX  Unsigned32
                    		MAX-ACCESS  read-only
                    		STATUS  current
                    		DESCRIPTION
                    			"port index"
                    		::= { mpPortVlanEntry 1 }

mpVlanPortMode      	OBJECT-TYPE
                    		SYNTAX  INTEGER {
                    			         access(1),
                    			          trunk(2),
                    			          hybrid(3)
                    			        }
                    		MAX-ACCESS  read-write
                    		STATUS  current
                    		DESCRIPTION
                    			"Port mode types refer to VLAN.Access is the default type."
                    		::= { mpPortVlanEntry 2 }

mpTrunkVlanList     	OBJECT-TYPE
                    		SYNTAX  OCTET STRING(SIZE(0..512))
                    		MAX-ACCESS  read-only
                    		STATUS  current
                    		DESCRIPTION
                    			"VLAN list which trunk port allowed pass."
                    		::= { mpPortVlanEntry 3 }

mpVlanPortChangeList	OBJECT-TYPE
                    		SYNTAX  OCTET STRING
                    		MAX-ACCESS  read-only
                    		STATUS  current
                    		DESCRIPTION
                    			"PortList used by mpVlanPortsAddTrap and mpVlanPortsDeleteTrap."
                    		::= { mpSwVlan 3 }



END
------------------------------------------------------------------------------
-- ============================================================================
-- $Log: mpSwVlan.mib,v $
-- Revision 1.1.4.1  2008/06/24 08:28:31  zhuyf
-- VRSP-7141合入MIB分支代码(VlanMIB/qinqEvc/qinqMib)
--
-- Revision 1.1.2.2  2008/06/12 00:55:52  zhuyf
-- no message
--
-- Revision 1.1.2.1  2008/06/06 07:28:03  zhuyf
-- no message
--
--
--
-- ============================================================================
