------------------------------------------------------------------------------
--
--  File         : mpSysClock.mib
--  Description  : The system clock configuration MIB
--  Version      : 1.0
--  Date         : sept. 28, 2008
--  Copyright    : 2003 by maipu (sichuan) communication technology co.,ltd.
--			All rights reserved.
--
-- 
------------------------------------------------------------------------------

------------------------------------------------------------------------------
MPSYSTEMTIME DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;

-- mpSystem  OBJECT-IDENTITY ::= { mpMgmt2 1 }
-- mpSysClock OBJECT-IDENTITY ::= { mpSystem 1 }

mpSysClock        	MODULE-IDENTITY
                    		LAST-UPDATED 	"0809241724Z"
                    		ORGANIZATION 	"Maipu (Sichuan) Communication Technology Co. LTD."
                    		CONTACT-INFO
                    			"Writer:      yangtian
                    			 Address    : Chengdu Sichuan China
                    			 Postalcode : 610041"
                    		DESCRIPTION
                      			"The MIB of system clock configuration for maipu device"
                    		::= { mpSystem  1 }


mpSysClockCurrent       	OBJECT-TYPE
                    		SYNTAX  DateAndTime
                    		MAX-ACCESS  read-only
                    		STATUS  current
                    		DESCRIPTION
                    			"The System clock, the format is designed by SNMP-TC, for example:
                    			 2001-5-26,13:30:15.0,-4:0"
                    		::= { mpSysClock 1 }

mpSysClockYear          	OBJECT-TYPE
                    		SYNTAX  INTEGER(1993..2035)
                    		MAX-ACCESS  read-write
                    		STATUS  current
                    		DESCRIPTION
                    			"The number of year"
                    		::= { mpSysClock 2 }

mpSysClockMonth         	OBJECT-TYPE
                    		SYNTAX  INTEGER(1..12)
                    		MAX-ACCESS  read-write
                    		STATUS  current
                    		DESCRIPTION
                    			"The number of month"
                    		::= { mpSysClock 3 }

mpSysClockDay           	OBJECT-TYPE
                    		SYNTAX  INTEGER(1.31)
                    		MAX-ACCESS  read-write
                    		STATUS  current
                    		DESCRIPTION
                    			"The number of date"
                    		::= { mpSysClock 4 }

mpSysClockHour          	OBJECT-TYPE
                    		SYNTAX  INTEGER(0..23)
                    		MAX-ACCESS  read-write
                    		STATUS  current
                    		DESCRIPTION
                    			"The number of hour"
                    		::= { mpSysClock 5 }

mpSysClockMinute        	OBJECT-TYPE
                    		SYNTAX  INTEGER(0..59)
                    		MAX-ACCESS  read-write
                    		STATUS  current
                    		DESCRIPTION
                    			"The number of minute"
                    		::= { mpSysClock 6 }

mpSysClockSecond        	OBJECT-TYPE
                    		SYNTAX  INTEGER(0..59)
                    		MAX-ACCESS  read-write
                    		STATUS  current
                    		DESCRIPTION
                    			"The number of second"
                    		::= { mpSysClock 7 }

mpSysClockZoneName      	OBJECT-TYPE
                    		SYNTAX  DisplayString(SIZE(1..19))
                    		MAX-ACCESS  read-write
                    		STATUS  current
                    		DESCRIPTION
                    			"The time zone name"
                    		::= { mpSysClock 10 }

mpSysClockZoneHourOffset	OBJECT-TYPE
                    		SYNTAX  INTEGER(-23..23)
                    		MAX-ACCESS  read-write
                    		STATUS  current
                    		DESCRIPTION
                    			"The offset of the time zone in hour"
                    		::= { mpSysClock 11 }

mpSysClockZoneMinuteOffset	OBJECT-TYPE
                    		SYNTAX  INTEGER(0..59)
                    		MAX-ACCESS  read-write
                    		STATUS  current
                    		DESCRIPTION
                    			"The offset of the time zone in minute"
                    		::= { mpSysClock 12 }



END
------------------------------------------------------------------------------
-- ============================================================================
-- $Log: mpSysClock.mib,v $
-- Revision 1.1  2010/06/21 11:18:46  liyh
-- first commit
--
-- Revision 1.1.6.1  2009/12/28 06:39:26  shenjie
-- router-13838,sla mib合入RM7B
--
-- Revision 1.1.4.1  2009/11/25 01:02:34  shenjie
-- router-13291,提交MIB相关文件
--
-- Revision 1.1.2.1.4.1  2009/04/19 08:29:23  shenjie
-- vrsp-11622，时区houroff设置问题
--
-- Revision 1.1.2.1  2008/10/10 08:59:54  yangtian
-- VRSP-7834
-- H02提交系统时钟和IP-MAC绑定MIB代码
--
--
--
-- ============================================================================
