-- *****************************************************************
-- MAIPU-DLSw.mib:  Maipu enterprise device DLSw MIB file
--
--version 1.0.0.0, Apr 25, 2002 Huanglulu, RogerHu
--
-- Copyright (c)  by Maipu DataComm Inc.
-- All rights reserved.
-- 
-- *****************************************************************
--

MAIPU-DLSw-MIB DEFINITIONS ::= BEGIN

IMPORTS
    RowStatus					FROM SNMPv2-TC
    MODULE-IDENTITY, OBJECT-TYPE, Counter32, IpAddress,  OBJECT-IDENTITY
    						FROM SNMPv2-SMI
    mpMgmt                              	FROM MAIPU-SMI;

mpDLSwMib MODULE-IDENTITY
    LAST-UPDATED "0204250000Z"
    ORGANIZATION "Maipu DataComm"
    CONTACT-INFO
	"   Maipu DataComm
		Customer Service
		E-mail: office@maipu.com"
    DESCRIPTION
		"The assignments for Maipu router's MIB of DLSw infomation!"
    ::= { mpMgmt 22 }


-- ***********************************
dlswCktTable OBJECT-TYPE
    SYNTAX SEQUENCE OF DLSwCktEntry
    MAX-ACCESS not-accessible
    STATUS current
    DESCRIPTION
		"DLSwCktTable"
    ::= { mpDLSwMib 1 }

dlswCktEntry OBJECT-TYPE
    SYNTAX DLSwCktEntry
    MAX-ACCESS not-accessible
    STATUS current
    DESCRIPTION
		"DLSwCktEntry"
    INDEX { cktIndex }    
    ::= { dlswCktTable 1 }
    
DLSwCktEntry ::=
	SEQUENCE {
		cktIndex
			Counter32,
		cktPeer
			OCTET STRING,
		cktState
			INTEGER,
		cktTarMac
			OCTET STRING,
		cktOrgMac
			OCTET STRING,
		cktTarSap
			INTEGER,
		cktOrgSap
			INTEGER,
		cktUpTime
			OCTET STRING,
		cktRxBytes
			Counter32,
		cktTxBytes
			Counter32,
		cktRxIFrames
			Counter32,
		cktTxIFrames
			Counter32,
		cktRxXIDFrames
			Counter32,
		cktTxXIDFrames
			Counter32,
		cktRxUIFrames
			Counter32,
		cktTxUIFrames
			Counter32,
		cktRxCurWin
			Counter32,
		cktRxGrantUnits
			Counter32,
		cktTxCurWin
			Counter32,
		cktTxGrantUnits
			Counter32
		
		}
				
cktIndex	OBJECT-TYPE
	SYNTAX	Counter32
	MAX-ACCESS	read-only
	STATUS	current
	DESCRIPTION
		"CktIndex"
	::= { dlswCktEntry 1 }

cktPeer		OBJECT-TYPE
	SYNTAX	OCTET STRING
	MAX-ACCESS	read-only
	STATUS	current
	DESCRIPTION
		"PeerIpAddr"
	::= { dlswCktEntry 2 }

cktState	OBJECT-TYPE
	SYNTAX	INTEGER {
			disconnect(1),
			resov-pending(2),
			ckt-start(3),
			ckt-pending(4),
			connect-pending(5),
			ckt-established(6),
			connected(7),
			ckt-restart(8),
			ckt-disconnect-pending(9),
			ckt-restart-pending(10),
			ckt-halt-pending(11),
			ckt-halt-pendin-noack(12)
			}
	MAX-ACCESS	read-only
	STATUS	current
	DESCRIPTION
		"cktState"
	::= { dlswCktEntry 3 }

cktTarMac	OBJECT-TYPE
	SYNTAX	OCTET STRING
	MAX-ACCESS	read-only
	STATUS	current
	DESCRIPTION
		"TargetMac"
	::= { dlswCktEntry 4 }

cktOrgMac	OBJECT-TYPE
	SYNTAX	OCTET STRING
	MAX-ACCESS	read-only
	STATUS	current
	DESCRIPTION
		"OriginMac"
	::= { dlswCktEntry 5 }

cktTarSap	OBJECT-TYPE
	SYNTAX	INTEGER
	MAX-ACCESS	read-only
	STATUS	current
	DESCRIPTION
		"TargetSap"
	::= { dlswCktEntry 6 }

cktOrgSap	OBJECT-TYPE
	SYNTAX	INTEGER
	MAX-ACCESS	read-only
	STATUS	current
	DESCRIPTION
		"OriginSap"
	::= { dlswCktEntry 7 }

cktUpTime	OBJECT-TYPE
	SYNTAX	OCTET STRING
	MAX-ACCESS	read-only
	STATUS	current
	DESCRIPTION
		"CktUpTime"
	::= { dlswCktEntry 8 }

cktRxBytes	OBJECT-TYPE
	SYNTAX	Counter32
	MAX-ACCESS	read-only
	STATUS	current
	DESCRIPTION
		"RxBytes"
	::= { dlswCktEntry 9 }

cktTxBytes	OBJECT-TYPE
	SYNTAX	Counter32
	MAX-ACCESS	read-only
	STATUS	current
	DESCRIPTION
		"TxBytes"
	::= { dlswCktEntry 10 }
	
cktRxIFrames	OBJECT-TYPE
	SYNTAX	Counter32
	MAX-ACCESS	read-only
	STATUS	current
	DESCRIPTION
		"RxIFrames"
	::= { dlswCktEntry 11 }
	
cktTxIFrames	OBJECT-TYPE
	SYNTAX	Counter32
	MAX-ACCESS	read-only
	STATUS	current
	DESCRIPTION
		"TxIFrames"
	::= { dlswCktEntry 12 }
	
cktRxXIDFrames	OBJECT-TYPE
	SYNTAX	Counter32
	MAX-ACCESS	read-only
	STATUS	current
	DESCRIPTION
		"RxXidFrames"
	::= { dlswCktEntry 13 }

cktTxXIDFrames	OBJECT-TYPE
	SYNTAX	Counter32
	MAX-ACCESS	read-only
	STATUS	current
	DESCRIPTION
		"TxXidFrames"
	::= { dlswCktEntry 14 }
	
cktRxUIFrames	OBJECT-TYPE
	SYNTAX	Counter32
	MAX-ACCESS	read-only
	STATUS	current
	DESCRIPTION
		"RxUIFrames"
	::= { dlswCktEntry 15 }
	
cktTxUIFrames	OBJECT-TYPE
	SYNTAX	Counter32
	MAX-ACCESS	read-only
	STATUS	current
	DESCRIPTION
		"TxUIFrames"
	::= { dlswCktEntry 16 }
	
cktRxCurWin	OBJECT-TYPE
	SYNTAX	Counter32
	MAX-ACCESS	read-only
	STATUS	current
	DESCRIPTION
		"RxCurWin"
	::= { dlswCktEntry 17 }
	
cktRxGrantUnits	OBJECT-TYPE
	SYNTAX	Counter32
	MAX-ACCESS	read-only
	STATUS	current
	DESCRIPTION
		"RxGrantUnits"
	::= { dlswCktEntry 18 }
	

cktTxCurWin	OBJECT-TYPE
	SYNTAX	Counter32
	MAX-ACCESS	read-only
	STATUS	current
	DESCRIPTION
		"TxCurWin"
	::= { dlswCktEntry 19 }
	
cktTxGrantUnits	OBJECT-TYPE
	SYNTAX	Counter32
	MAX-ACCESS	read-only
	STATUS	current
	DESCRIPTION
		"TxGrantUnits"
	::= { dlswCktEntry 20 }

	
-- **************************************
dlswPeerTable	OBJECT-TYPE
	SYNTAX	SEQUENCE OF DLSwPeerEntry
	MAX-ACCESS not-accessible
	STATUS	current
	DESCRIPTION
		"DLSwPeerTable"
	::= { mpDLSwMib 2 }
	
dlswPeerEntry	OBJECT-TYPE
	SYNTAX	DLSwPeerEntry
	MAX-ACCESS	not-accessible
	STATUS	current
	DESCRIPTION
		"DLSwPeerEntry"
	INDEX { peerIndex }
	::= { dlswPeerTable 1 }
	
DLSwPeerEntry ::=
	SEQUENCE {
		peerIndex
			Counter32,
		peerIpAddr
			IpAddress,
		peerCost
			INTEGER,
		peerKeepalive
			INTEGER,
		peerType
			INTEGER,
		peerState
			INTEGER,
		peerUpTick
			OCTET STRING,
		peerRxPacks
			Counter32,
		peerTxPacks
			Counter32,
		peerDropPacks
			Counter32,
		peerVendorID
			INTEGER,
		peerVersion
			INTEGER,
		peerRelease
			INTEGER,
		peerGloblInitWin
			INTEGER,
		peerSupportSap
			OCTET STRING,
		peerTcpSessionNum
			INTEGER,
		peerMulticastCapable
			INTEGER,
		peerUdpUnicastSupport
			INTEGER,
		peerBorderPeerCapable
			INTEGER,
		peerCapCost
			INTEGER,
		peerBiuSegment
			INTEGER,
		peerGroup
			INTEGER,
		peerLocalAck
			INTEGER,
		peerPriority
			INTEGER,
		peerVersionString
			OCTET STRING,
		peerStatus
			RowStatus
				}

peerIndex	OBJECT-TYPE
	SYNTAX	Counter32
	MAX-ACCESS	not-accessible
	STATUS	current
	DESCRIPTION
		"peerIndex"
	::= { dlswPeerEntry 1 }

peerIpAddr	OBJECT-TYPE
	SYNTAX	IpAddress
	MAX-ACCESS	read-create
	STATUS	current
	DESCRIPTION
		"IpAddr"
	::= { dlswPeerEntry 2 }
	
peerCost	OBJECT-TYPE
	SYNTAX	INTEGER ( 1..5 )
	MAX-ACCESS	read-create
	STATUS	current
	DESCRIPTION
		"peerCost"
	::= { dlswPeerEntry 3 }
	
peerKeepalive 	OBJECT-TYPE
	SYNTAX	INTEGER ( 0..1200 )
	MAX-ACCESS	read-create
	STATUS	current
	DESCRIPTION
		"peerKeepalive"
	::= { dlswPeerEntry 4 }
	

peerType	OBJECT-TYPE
	SYNTAX	INTEGER {
			conf(1),
			prom(2)
			}
	MAX-ACCESS	read-only
	STATUS	current
	DESCRIPTION
		"RemoteType"
	::= { dlswPeerEntry 5 }

peerState	OBJECT-TYPE
	SYNTAX	INTEGER {
			disconnect(1),
			wait-wr(2),
			wait-rd(3),
			connecting(4),
			connect(5)
			}
	MAX-ACCESS	read-only
	STATUS	current
	DESCRIPTION
		"State"
	::= { dlswPeerEntry 6 }

peerUpTick	OBJECT-TYPE
	SYNTAX	OCTET STRING
	MAX-ACCESS	read-only
	STATUS	current
	DESCRIPTION
		"UpTick"
	::= { dlswPeerEntry 7 }

peerRxPacks	OBJECT-TYPE
	SYNTAX	Counter32
	MAX-ACCESS	read-only
	STATUS	current
	DESCRIPTION
		"RxPacks"
	::= { dlswPeerEntry 8 }

peerTxPacks	OBJECT-TYPE
	SYNTAX	Counter32
	MAX-ACCESS	read-only
	STATUS	current
	DESCRIPTION
		"TxPacks"
	::= { dlswPeerEntry 9 }

peerDropPacks	OBJECT-TYPE
	SYNTAX	Counter32
	MAX-ACCESS	read-only
	STATUS	current
	DESCRIPTION
		"DropPacks"
	::= { dlswPeerEntry 10 }

peerVendorID	OBJECT-TYPE
	SYNTAX	INTEGER
	MAX-ACCESS	read-only
	STATUS	current
	DESCRIPTION
		"VendorID"
	::= { dlswPeerEntry 11 }

peerVersion	OBJECT-TYPE
	SYNTAX	INTEGER
	MAX-ACCESS	read-only
	STATUS	current
	DESCRIPTION
		"Version"
	::= { dlswPeerEntry 12 }

peerRelease	OBJECT-TYPE
	SYNTAX	INTEGER
	MAX-ACCESS	read-only
	STATUS	current
	DESCRIPTION
		"Version"
	::= { dlswPeerEntry 13 }

peerGloblInitWin	OBJECT-TYPE
	SYNTAX	INTEGER
	MAX-ACCESS	read-only
	STATUS	current
	DESCRIPTION
		"peerGloblInitWin"
	::= { dlswPeerEntry 14 }
	
peerSupportSap		OBJECT-TYPE
	SYNTAX	OCTET STRING
	MAX-ACCESS	read-only
	STATUS	current
	DESCRIPTION
		"peerSupportSap"
	::= { dlswPeerEntry 15 }

peerTcpSessionNum	OBJECT-TYPE
	SYNTAX	INTEGER
	MAX-ACCESS	read-only
	STATUS	current
	DESCRIPTION
		"peerTcpSessionNum"
	::= { dlswPeerEntry 16 }
	
peerMulticastCapable	OBJECT-TYPE
	SYNTAX	INTEGER
	MAX-ACCESS	read-only
	STATUS	current
	DESCRIPTION
		"peerMulticastCapable"
	::= { dlswPeerEntry 17 }

peerUdpUnicastSupport	OBJECT-TYPE
	SYNTAX	INTEGER
	MAX-ACCESS	read-only
	STATUS	current
	DESCRIPTION
		"peerUdpUnicastSupport"
	::= { dlswPeerEntry 18 }

peerBorderPeerCapable	OBJECT-TYPE
	SYNTAX	INTEGER
	MAX-ACCESS	read-only
	STATUS	current
	DESCRIPTION
		"peerBorderPeerCapable"
	::= { dlswPeerEntry 19 }

peerCapCost	OBJECT-TYPE
	SYNTAX	INTEGER
	MAX-ACCESS	read-only
	STATUS	current
	DESCRIPTION
		"peerCapCost"
	::= { dlswPeerEntry 20 }

peerBiuSegment	OBJECT-TYPE
	SYNTAX	INTEGER
	MAX-ACCESS	read-only
	STATUS	current
	DESCRIPTION
		"peerBiuSegment"
	::= { dlswPeerEntry 21 }

peerGroup	OBJECT-TYPE
	SYNTAX	INTEGER
	MAX-ACCESS	read-only
	STATUS	current
	DESCRIPTION
		"peerGroup"
	::= { dlswPeerEntry 22 }

peerLocalAck	OBJECT-TYPE
	SYNTAX	INTEGER
	MAX-ACCESS	read-only
	STATUS	current
	DESCRIPTION
		"peerLocalAck"
	::= { dlswPeerEntry 23 }

peerPriority	OBJECT-TYPE
	SYNTAX	INTEGER
	MAX-ACCESS	read-only
	STATUS	current
	DESCRIPTION
		"peerPriority"
	::= { dlswPeerEntry 24 }

peerVersionString	OBJECT-TYPE
	SYNTAX	OCTET STRING
	MAX-ACCESS	read-only
	STATUS	current
	DESCRIPTION
		"PeerVersionString"
	::= { dlswPeerEntry 25 }

peerStatus	OBJECT-TYPE
	SYNTAX	RowStatus
	MAX-ACCESS	read-create
	STATUS	current
	DESCRIPTION
		"Version"
	::= { dlswPeerEntry 26 }


-- **************************************

dlswLocal	OBJECT-IDENTITY
	STATUS	current
	DESCRIPTION
		""
	::= { mpDLSwMib 3 }

localIpAddr	OBJECT-TYPE
	SYNTAX	OCTET STRING
	MAX-ACCESS	read-write
	STATUS	current
	DESCRIPTION
		"localIpAddr"
	::= { dlswLocal 1 }

localPeerType	OBJECT-TYPE
	SYNTAX	INTEGER {
			conf(1),
			prom(2)
			}
	MAX-ACCESS	read-write
	STATUS	current
	DESCRIPTION
		"localPeerType"
	::= { dlswLocal 2 }

localDisable	OBJECT-TYPE
	SYNTAX	INTEGER {
			enable(1),
			disable(2)
			}
	MAX-ACCESS	read-write
	STATUS	current
	DESCRIPTION
		"localDisable"
	::= { dlswLocal 3 }

localKeepalive	OBJECT-TYPE
	SYNTAX	INTEGER (0..1200)
	MAX-ACCESS	read-write
	STATUS	current
	DESCRIPTION
		"localKeepalive"
	::= { dlswLocal 4 }

localBrGrp	OBJECT-TYPE
	SYNTAX	OCTET STRING
	MAX-ACCESS	read-write
	STATUS	current
	DESCRIPTION
		"localBrGrp"
	::= { dlswLocal 5 }

localGlobalInitWin 	OBJECT-TYPE
	SYNTAX	INTEGER (1..2000)
	MAX-ACCESS	read-write
	STATUS	current
	DESCRIPTION
		"localGlobalInitWin"
	::= { dlswLocal 6 }

localSupportSap 	OBJECT-TYPE
	SYNTAX	OCTET STRING
	MAX-ACCESS	read-write
	STATUS	current
	DESCRIPTION
		"localSupportSap"
	::= { dlswLocal 7 }

localICanReach  OBJECT-TYPE
	SYNTAX	INTEGER
	MAX-ACCESS	read-write
	STATUS	current
	DESCRIPTION
		"localICanReach"
	::={ dlswLocal 8 }

localVersion	OBJECT-TYPE
	SYNTAX	INTEGER 
	MAX-ACCESS	read-only
	STATUS	current
	DESCRIPTION
		"localVersion"
	::= { dlswLocal 9 }

localVendorId	OBJECT-TYPE
	SYNTAX	OCTET STRING 
	MAX-ACCESS	read-only
	STATUS	current
	DESCRIPTION
		"localVendorId"
	::= { dlswLocal 10 }

localVersionString OBJECT-TYPE
	SYNTAX	OCTET STRING
	MAX-ACCESS	read-only
	STATUS	current
	DESCRIPTION
		"localVersionString"
	::= { dlswLocal 11 }

END
