------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPRTBGP DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;


maipu               	OBJECT IDENTIFIER ::= { enterprises 1 }
mpMgmt2             	OBJECT IDENTIFIER ::= { maipu 5651 }
mpRouterTech        	OBJECT IDENTIFIER ::= { mpMgmt2 6 }
mpRtL3Unicast       	OBJECT IDENTIFIER ::= { mpRouterTech 2 }



mpRtBGP             	MODULE-IDENTITY
                    		LAST-UPDATED 	"1103100858Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { mpRtL3Unicast  1 }



mpBgpInsTable       	OBJECT-TYPE
                    		SYNTAX  SEQUENCE OF   MpBgpInsEntry
                    		MAX-ACCESS  not-accessible
                    		STATUS  current
                    		DESCRIPTION
                    			""
                    		::= { mpRtBGP 1 }

mpBgpInsEntry       	OBJECT-TYPE
                    		SYNTAX  MpBgpInsEntry
                    		MAX-ACCESS  not-accessible
                    		STATUS  current
                    		DESCRIPTION
                    			""
                    		INDEX  { mpBgpLocalAs }
                    		::= { mpBgpInsTable 1 }

MpBgpInsEntry       	::= SEQUENCE {
                    			mpBgpLocalAs           INTEGER,
                    			mpBgpInsRowStatus      RowStatus
                    	             }


mpBgpLocalAs        	OBJECT-TYPE
                    		SYNTAX  INTEGER(1..65535)
                    		MAX-ACCESS  read-create
                    		STATUS  current
                    		DESCRIPTION
                    			"bgp local as number"
                    		::= { mpBgpInsEntry 1 }

mpBgpInsRowStatus   	OBJECT-TYPE
                    		SYNTAX  RowStatus
                    		MAX-ACCESS  read-create
                    		STATUS  current
                    		DESCRIPTION
                    			"row status"
                    		::= { mpBgpInsEntry 2 }

mpBgpPeerTable      	OBJECT-TYPE
                    		SYNTAX  SEQUENCE OF   MpBgpPeerEntry
                    		MAX-ACCESS  not-accessible
                    		STATUS  current
                    		DESCRIPTION
                    			"bgp peer"
                    		::= { mpRtBGP 2 }

mpBgpPeerEntry      	OBJECT-TYPE
                    		SYNTAX  MpBgpPeerEntry
                    		MAX-ACCESS  not-accessible
                    		STATUS  current
                    		DESCRIPTION
                    			"bgp peer"
                    		INDEX  { mpBgpPeerAf, mpBgpPeerSaf, mpBgpPeerVrf, mpBgpPeerRemoteIPAddress }
                    		::= { mpBgpPeerTable 1 }

MpBgpPeerEntry      	::= SEQUENCE {
                    			mpBgpPeerAf            INTEGER,
                    			mpBgpPeerSaf           INTEGER,
                    			mpBgpPeerVrf           MVrfName,
                    			mpBgpPeerRemoteIPAddress   IpAddress,
                    			mpBgpPeerActivate      INTEGER,
                    			mpBgpPeerSendCommunity   INTEGER,
                    			mpBgpPeerRowStatus     RowStatus
                    	             }


mpBgpPeerAf         	OBJECT-TYPE
                    		SYNTAX  INTEGER {
                    			         ipv4       (1),
                    			          ipv6       (2),
                    			          vpnv4      (3),
                    			          vpnv6      (4)
                    			        }
                    		MAX-ACCESS  read-create
                    		STATUS  current
                    		DESCRIPTION
                    			""
                    		::= { mpBgpPeerEntry 1 }

mpBgpPeerSaf        	OBJECT-TYPE
                    		SYNTAX  INTEGER {
                    			         unicast      (1),
                    			          mulicast     (2),
                    			          mdt          (3)
                    			        }
                    		MAX-ACCESS  read-create
                    		STATUS  current
                    		DESCRIPTION
                    			""
                    		::= { mpBgpPeerEntry 2 }

mpBgpPeerVrf        	OBJECT-TYPE
                    		SYNTAX  MVrfName
                    		MAX-ACCESS  read-create
                    		STATUS  current
                    		DESCRIPTION
                    			""
                    		::= { mpBgpPeerEntry 3 }

mpBgpPeerRemoteIPAddress	OBJECT-TYPE
                    		SYNTAX  IpAddress
                    		MAX-ACCESS  read-create
                    		STATUS  current
                    		DESCRIPTION
                    			""
                    		::= { mpBgpPeerEntry 4 }

mpBgpPeerActivate   	OBJECT-TYPE
                    		SYNTAX  INTEGER {
                    			         enable     (1),
                    			          disable    (2)
                    			        }
                    		MAX-ACCESS  read-create
                    		STATUS  current
                    		DESCRIPTION
                    			""
                    		::= { mpBgpPeerEntry 5 }

mpBgpPeerSendCommunity	OBJECT-TYPE
                    		SYNTAX  INTEGER {
                    			         standard        (1),
                    			          extended        (2),
                    			          both            (3),
                    			          no_standard     (4),
                    			          no_extended     (5),
                    			          no_both         (6)
                    			        }
                    		MAX-ACCESS  read-create
                    		STATUS  current
                    		DESCRIPTION
                    			""
                    		::= { mpBgpPeerEntry 6 }

mpBgpPeerRowStatus  	OBJECT-TYPE
                    		SYNTAX  RowStatus
                    		MAX-ACCESS  read-create
                    		STATUS  current
                    		DESCRIPTION
                    			""
                    		::= { mpBgpPeerEntry 7 }

mpBgpRedistTable    	OBJECT-TYPE
                    		SYNTAX  SEQUENCE OF   MpBgpRedistEntry
                    		MAX-ACCESS  not-accessible
                    		STATUS  current
                    		DESCRIPTION
                    			"bgp redistribute"
                    		::= { mpRtBGP 3 }

mpBgpRedistEntry    	OBJECT-TYPE
                    		SYNTAX  MpBgpRedistEntry
                    		MAX-ACCESS  not-accessible
                    		STATUS  current
                    		DESCRIPTION
                    			"bgp redistribute"
                    		INDEX  { mpBgpRedistAf, mpBgpRedistSaf, mpBgpRedistVrf, mpBgpRedistProto, mpBgpRedistProtoName }
                    		::= { mpBgpRedistTable 1 }

MpBgpRedistEntry    	::= SEQUENCE {
                    			mpBgpRedistAf          INTEGER,
                    			mpBgpRedistSaf         INTEGER,
                    			mpBgpRedistVrf         MVrfName,
                    			mpBgpRedistProto       INTEGER,
                    			mpBgpRedistProtoName   DisplayString,
                    			mpBgpRedistRouteMap    DisplayString,
                    			mpBgpRedistMetric      Unsigned32,
                    			mpBgpRedistMatch       INTEGER,
                    			mpBgpRedistRowStatus   RowStatus
                    	             }


mpBgpRedistAf       	OBJECT-TYPE
                    		SYNTAX  INTEGER {
                    			         ipv4      (1),
                    			          ipv6      (2),
                    			          vpnv4     (3),
                    			          vpnv6     (4)
                    			        }
                    		MAX-ACCESS  read-create
                    		STATUS  current
                    		DESCRIPTION
                    			""
                    		::= { mpBgpRedistEntry 1 }

mpBgpRedistSaf      	OBJECT-TYPE
                    		SYNTAX  INTEGER {
                    			         unicast      (1),
                    			          mulicast     (2),
                    			          mdt          (3)
                    			        }
                    		MAX-ACCESS  read-create
                    		STATUS  current
                    		DESCRIPTION
                    			""
                    		::= { mpBgpRedistEntry 2 }

mpBgpRedistVrf      	OBJECT-TYPE
                    		SYNTAX  MVrfName
                    		MAX-ACCESS  read-create
                    		STATUS  current
                    		DESCRIPTION
                    			""
                    		::= { mpBgpRedistEntry 3 }

mpBgpRedistProto    	OBJECT-TYPE
                    		SYNTAX  INTEGER {
                    			         connected     (1),
                    			          static        (2),
                    			          rip           (3),
                    			          irmp          (4),
                    			          ospf          (5),
                    			          isis          (6)
                    			        }
                    		MAX-ACCESS  read-create
                    		STATUS  current
                    		DESCRIPTION
                    			""
                    		::= { mpBgpRedistEntry 4 }

mpBgpRedistProtoName	OBJECT-TYPE
                    		SYNTAX  DisplayString(SIZE(0..63))
                    		MAX-ACCESS  read-create
                    		STATUS  current
                    		DESCRIPTION
                    			""
                    		::= { mpBgpRedistEntry 5 }

mpBgpRedistRouteMap 	OBJECT-TYPE
                    		SYNTAX  DisplayString(SIZE(0..31))
                    		MAX-ACCESS  read-create
                    		STATUS  current
                    		DESCRIPTION
                    			""
                    		::= { mpBgpRedistEntry 6 }

mpBgpRedistMetric   	OBJECT-TYPE
                    		SYNTAX  Unsigned32(0..4294967295)
                    		MAX-ACCESS  read-create
                    		STATUS  current
                    		DESCRIPTION
                    			""
                    		::= { mpBgpRedistEntry 7 }

mpBgpRedistMatch    	OBJECT-TYPE
                    		SYNTAX  INTEGER
                    		MAX-ACCESS  read-create
                    		STATUS  current
                    		DESCRIPTION
                    			"nssaexternal-1   (0x1)
                    			 nssaexternal-2   (0x2)
                    			 external-1       (0x4)
                    			 external-2       (0x8)
                    			 internal         (0x10)
                    			 level-1          (0x20)
                    			 level-2          (0x40)
                    			 level-1-2        (0x80)
                    			 interarea        (0x100)"
                    		::= { mpBgpRedistEntry 8 }

mpBgpRedistRowStatus	OBJECT-TYPE
                    		SYNTAX  RowStatus
                    		MAX-ACCESS  read-create
                    		STATUS  current
                    		DESCRIPTION
                    			""
                    		::= { mpBgpRedistEntry 9 }



END
------------------------------------------------------------------------------
-- ============================================================================
-- $Log: sysMib.mi2,v $
--
--
-- ============================================================================
