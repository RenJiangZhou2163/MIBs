-- ============================================================================================
-- 	EPAS网管NB110E/FT160/NB110B/NB110F/NB110G mib库定义
--
-- ============================================================================================

DEFINITIONS ::= BEGIN

IMPORTS
    DisplayString			FROM SNMPv2-TC
	mpMgmt			        FROM MAIPU-SMI
	MODULE-IDENTITY, OBJECT-TYPE, Integer32, Unsigned32
							FROM SNMPv2-SMI;

-- ============================================================================================
-- 	VETH网管mib库定义
-- ============================================================================================
mpVeth	MODULE-IDENTITY 
    LAST-UPDATED "0101050000Z"
    ORGANIZATION "Maipu DataComm"
    CONTACT-INFO
        "	Maipu DataComm
		Customer Service

		Postal: Consulate Drive
			Chengdu, Sichuan  610041
			China

	        Tel: 86-028-5161006

		E-mail: office@maipu.com"
    DESCRIPTION
        "The process and memory information of MP2600 infomation!"
::= { mpMgmt 499 }

-- ============================================================================================
-- TRAP
-- ============================================================================================
VethTrap  OBJECT IDENTIFIER ::= {mpVeth 0}

VethMemberIfMultiIDTrapNotify  OBJECT-TYPE
    SYNTAX  INTEGER
    ACCESS  read-only
    STATUS  mandatory
    DESCRIPTION
            "虚拟以太成员接口收到多个对端ID的告警信息"
    ::= {VethTrap 1}
     
VethMemberIfLoopTrapNotify  OBJECT-TYPE
    SYNTAX  INTEGER
    ACCESS  read-only
    STATUS  mandatory
    DESCRIPTION
            "虚拟以太成员接口环回告警信息"
    ::= {VethTrap 2}

-- ============================================================================================
-- 	EPAS网管远端设备 mib库定义
-- ============================================================================================
mpVethRemoteType	MODULE-IDENTITY 
    LAST-UPDATED "0101050000Z"
    ORGANIZATION "Maipu DataComm"
    CONTACT-INFO
        "	Maipu DataComm
		Customer Service

		Postal: Consulate Drive
			Chengdu, Sichuan  610041
			China

	        Tel: 86-028-5161006

		E-mail: office@maipu.com"
    DESCRIPTION
        "The process and memory information of MP2600 infomation!"
::= { mpVeth 1 }

-- ============================================================================================

-- ============================================================================================
VethRemoteType OBJECT IDENTIFIER ::= {mpVethRemoteType 1}

VethRemoteTypeTable  OBJECT-TYPE
    SYNTAX  SEQUENCE OF VethRemoteTypeEntry
    ACCESS  not-accessible
    STATUS  mandatory
    DESCRIPTION
            "远端设备类型状态"
    ::= {VethRemoteType 1}

VethRemoteTypeEntry  OBJECT-TYPE
    SYNTAX  VethRemoteTypeEntry
    ACCESS  not-accessible
    STATUS  mandatory
    DESCRIPTION
            "远端设备类型状态表项"
    INDEX   {VethRemoteTypeIndex}
    ::= {VethRemoteTypeTable 1}

VethRemoteTypeIndex  OBJECT-TYPE
    SYNTAX  INTEGER(1..16)
    ACCESS  read-only
    STATUS  mandatory
    DESCRIPTION
            "接口索引"
    ::= {VethRemoteTypeEntry 1}

VethDeviceType  OBJECT-TYPE
    SYNTAX  INTEGER
    ACCESS  read-only
    STATUS  mandatory
    DESCRIPTION
            "远端设备类型 0x00:无设备 0x01: Old-NB110B 0x02: New-NB110B 0x03:NB110E 0x04:NB110F 0x05:FT160 0x06:NB110G 0x10:Router 0x11:EPAS"
    ::= {VethRemoteTypeEntry 2}

VethDeviceState  OBJECT-TYPE
    SYNTAX  INTEGER
    ACCESS  read-only
    STATUS  mandatory
    DESCRIPTION
            "远端设备状态（Alive/Dead） 1：Alive，0：Dead"
    ::= {VethRemoteTypeEntry 3}

-- ============================================================================================
-- 	EPAS网管NB110E mib库定义
-- ============================================================================================
			
mpNB110	MODULE-IDENTITY 
    LAST-UPDATED "0101050000Z"
    ORGANIZATION "Maipu DataComm"
    CONTACT-INFO
        "	Maipu DataComm
		Customer Service

		Postal: Consulate Drive
			Chengdu, Sichuan  610041
			China

	        Tel: 86-028-5161006

		E-mail: office@maipu.com"
    DESCRIPTION
        "The process and memory information of MP2600 infomation!"
::= { mpVeth 2 }

-- ============================================================================================
-- 	EPAS网管NB110 mib库定义
-- ============================================================================================

NB110  OBJECT IDENTIFIER ::= {mpNB110 1}

NB110Table  OBJECT-TYPE
    SYNTAX  SEQUENCE OF NB110Entry
    ACCESS  not-accessible
    STATUS  mandatory
    DESCRIPTION
            "NB110配置"
    ::= {NB110 1}

NB110Entry  OBJECT-TYPE
    SYNTAX  NB110Entry
    ACCESS  not-accessible
    STATUS  current
    DESCRIPTION
            "NB110配置表项"
    INDEX   {NB110Index}
    ::= {NB110Table 1}

NB110Index  OBJECT-TYPE
    SYNTAX  INTEGER(1..16)
    ACCESS  read-only
    STATUS  mandatory
    DESCRIPTION
            "接口索引"
    ::= {NB110Entry 1}

NB110Conf  OBJECT-TYPE
    SYNTAX  INTEGER(1..2)
    ACCESS  read-write
    STATUS  mandatory
    DESCRIPTION
            "远端配置使能： 1：不配置； 2：配置"
    ::= {NB110Entry 2}

NB110Ether  OBJECT-TYPE
    SYNTAX  INTEGER
    ACCESS  read-write
    STATUS  mandatory
    DESCRIPTION
            "以太时隙配置：第一字节：起始时隙； 第二字节：时隙数"
    ::= {NB110Entry 3}

NB110V35  OBJECT-TYPE
    SYNTAX  INTEGER
    ACCESS  read-write
    STATUS  mandatory
    DESCRIPTION
            "V35时隙配置：第一字节：起始时隙； 第二字节：时隙数"
    ::= {NB110Entry 4}

NB110OtherConf  OBJECT-TYPE
    SYNTAX  INTEGER
    ACCESS  read-write
    STATUS  mandatory
    DESCRIPTION
            "bit0：系统时钟；bit1：广域网通道检测；bit2：G703阻抗； bit3：以太全双工；bit4：10/100M设置； bit5：自动协商； bit6：V35发送时钟反转；bit7：V35接收时钟反转"
    ::= {NB110Entry 5}

NB110Res1  OBJECT-TYPE
    SYNTAX  INTEGER
    ACCESS  read-write
    STATUS  mandatory
    DESCRIPTION
            "保留字段1"
    ::= {NB110Entry 6}

NB110Res2  OBJECT-TYPE
    SYNTAX  INTEGER
    ACCESS  read-write
    STATUS  mandatory
    DESCRIPTION
            "保留字段2"
    ::= {NB110Entry 7}

NB110RemoteStatusTable  OBJECT-TYPE
    SYNTAX  SEQUENCE OF NB110RemoteStatusEntry
    ACCESS  not-accessible
    STATUS  mandatory
    DESCRIPTION
            "远端设备状态表"
    ::= {NB110 2}

NB110RemoteStatusEntry  OBJECT-TYPE
    SYNTAX  NB110RemoteStatusEntry
    ACCESS  not-accessible
    STATUS  current
    DESCRIPTION
            "远端设备状态表项"
    INDEX   {NB110RemoteStatusIndex}
    ::= {NB110RemoteStatusTable 1}

NB110RemoteStatusIndex  OBJECT-TYPE
    SYNTAX  INTEGER(1..16)
    ACCESS  read-only
    STATUS  mandatory
    DESCRIPTION
            "接口索引"
    ::= {NB110RemoteStatusEntry 1}

NB110RemoteStatus1  OBJECT-TYPE
    SYNTAX  INTEGER
    ACCESS  read-only
    STATUS  mandatory
    DESCRIPTION
            "第一字节代表远端设备类型：0:没有远端设备 1：老NB110B； 2：新NB110B； 3：NB110E；（若为0和1，则下面的字节无意义）； 第二、三、四字节分别代表DIP开关1、2、3的状态，一个bit代表一个开关；"
    ::= {NB110RemoteStatusEntry 2}

NB110RemoteStatus2  OBJECT-TYPE
    SYNTAX  INTEGER
    ACCESS  read-only
    STATUS  mandatory
    DESCRIPTION
            "第一、二、三字节分别代表DIP开关4、5、6的状态，一个bit代表一个开关； 若远端为老NB110B，则这个整数的四个字节表示其远端状态 第四字节保留"
    ::= {NB110RemoteStatusEntry 3}

NB110RemoteStatus3  OBJECT-TYPE
    SYNTAX  INTEGER
    ACCESS  read-only
    STATUS  mandatory
    DESCRIPTION
            "第一字节：远端设备以及E1灯状态，从最低bit开始，分别有：AIS、LOS、RCL、LOOP、SLT、PWR，其他bit位保留； 第二字节：V35灯状态，从低bit位开始，目前有：TXD、RXD、DCD、CTS、RTS、DSR、DTR，其他bit位保留； 第三、四字节保留"
    ::= {NB110RemoteStatusEntry 4}

NB110RemoteStatus4  OBJECT-TYPE
    SYNTAX  INTEGER
    ACCESS  read-only
    STATUS  mandatory
    DESCRIPTION
            "第一字节：以太灯状态，从低bit开始，目前有：WANCHL-1、FDX-1、100M-1、LINK/ACT-1、WANCHL-0、FDX-0、100M-0、LINK/ACT-0； 第二、三、四字节保留；"
    ::= {NB110RemoteStatusEntry 5}

-- ============================================================================================
-- 	EPAS网管FT160 mib库定义
-- ============================================================================================
mpFT160	MODULE-IDENTITY 
    LAST-UPDATED "0101050000Z"
    ORGANIZATION "Maipu DataComm"
    CONTACT-INFO
        "	Maipu DataComm
		Customer Service

		Postal: Consulate Drive
			Chengdu, Sichuan  610041
			China

	        Tel: 86-028-5161006

		E-mail: office@maipu.com"
    DESCRIPTION
        "The process and memory information of MP2600 infomation!"
::= { mpVeth 3 }


-- ============================================================================================
-- 	EPAS网管FT160 mib库定义
-- ============================================================================================
FT160  OBJECT IDENTIFIER ::= {mpFT160 1}

FT160Table  OBJECT-TYPE
    SYNTAX  SEQUENCE OF FT160Entry
    ACCESS  not-accessible
    STATUS  mandatory
    DESCRIPTION
            "FT160参数配置信息"
    ::= {FT160 1}

FT160Entry  OBJECT-TYPE
    SYNTAX  FT160Entry
    ACCESS  not-accessible
    STATUS  mandatory
    DESCRIPTION
            "FT160端口表的表项"
    INDEX   {FT160Index}
    ::= {FT160Table 1}

FT160Index  OBJECT-TYPE
    SYNTAX  INTEGER(1..16)
    ACCESS  read-only
    STATUS  mandatory
    DESCRIPTION
            "接口索引"
    ::= {FT160Entry 1}

FT160Conf  OBJECT-TYPE
    SYNTAX  INTEGER(1..2)
    ACCESS  read-write
    STATUS  current
    DESCRIPTION
            "远端配置使能 1:不配置; 2:配置"
    ::= {FT160Entry 2}

FT160ClkSrc  OBJECT-TYPE
    SYNTAX  INTEGER
    ACCESS  read-write
    STATUS  current
    DESCRIPTION
            "FT160时钟 1:内时钟; 		2:光口时钟;   3:V35外时钟; 4:E1外时钟; FT160B-1FESAC只能配1,2"
    ::= {FT160Entry 3}

FT160EtherDuplex  OBJECT-TYPE
    SYNTAX  INTEGER
    ACCESS  read-write
    STATUS  current
    DESCRIPTION
            "以太口的工作模式  bit2:以太全双工(0:half,1:full) bit1:10/100M设置(0:10,1:100) bit0:自动协商(0:非自,1:自动"
    ::= {FT160Entry 4}

FT160ChannelNum  OBJECT-TYPE
    SYNTAX  INTEGER
    ACCESS  read-write
    STATUS  current
    DESCRIPTION
            "通道装载数 Bit7-Bit6: V35通道 00:不装载,01:装载; Bit5-bit3: E1通道 000:不装载,001:1,010:2,011:3,100:4; Bit2-bit0: 以太通道 000:不装载,001:1,010:2,011:3,100:4"
    ::= {FT160Entry 5}

FT160LoopMode  OBJECT-TYPE
    SYNTAX  INTEGER
    ACCESS  read-write
    STATUS  current
    DESCRIPTION
            "FT160环回方式  Bit2: V35环回 00:不环回, 01:环回 Bit1-bit0: 光口环回 00:不环回, 01:LL环, 10:RL环, 11:双向环"
    ::= {FT160Entry 6}

FT160V35Config  OBJECT-TYPE
    SYNTAX  INTEGER
    ACCESS  read-write
    STATUS  current
    DESCRIPTION
            "V35配置 BIT7: V35发送时钟(1:反转, 0:不反转) BIT6: V35接收时钟(1:反转, 0:不反转) BIT5: DTE/DCE设备选择(1:DTE, 0:DCE) BIT4-BIT0: V35带宽选择(00000--11111)×64K,其中00000表示2M(在装载了V35通道后才有效)"
    ::= {FT160Entry 7}

FT160E1Config  OBJECT-TYPE
    SYNTAX  INTEGER
    ACCESS  read-write
    STATUS  current
    DESCRIPTION
            "E1配置 BIT1: 阻抗设置(1:120, 0:75) BIT0: E1 RESET(0:不RESET, 1:RESET)"
    ::= {FT160Entry 8}

FT160E1LoopMode  OBJECT-TYPE
    SYNTAX  INTEGER
    ACCESS  read-write
    STATUS  current
    DESCRIPTION
            "E1环回  Bit7-Bit6: E11(00:不环回, 01:LL环, 10:RL环, 11:双向环) Bit5-bit4: E12(00:不环回, 01:LL环, 10:RL环, 11:双向环) Bit3-bit2: E13(00:不环回, 01:LL环, 10:RL环, 11:双向环) Bit1-bit0: E14(00:不环回, 01:LL环, 10:RL环, 11:双向环)"
    ::= {FT160Entry 9}
   
FT160Res1  OBJECT-TYPE
    SYNTAX  INTEGER
    ACCESS  read-write
    STATUS  current
    DESCRIPTION
            "保留"
    ::= {FT160Entry 10}

FT160Res2  OBJECT-TYPE
    SYNTAX  INTEGER
    ACCESS  read-write
    STATUS  current
    DESCRIPTION
            "保留"
    ::= {FT160Entry 11}

FT160Cmd  OBJECT-TYPE
    SYNTAX  INTEGER
    ACCESS  read-write
    STATUS  current
    DESCRIPTION
            "FT160远端复位 1:复位  0:不复位"
    ::= {FT160Entry 12}

FT160RemoteStatusTable  OBJECT-TYPE
    SYNTAX  SEQUENCE OF FT160RemoteStatusEntry
    ACCESS  not-accessible
    STATUS  mandatory
    DESCRIPTION
            "FT160状态信息表"
    ::= {FT160 2}

FT160RemoteStatusEntry  OBJECT-TYPE
    SYNTAX  FT160RemoteStatusEntry
    ACCESS  not-accessible
    STATUS  mandatory
    DESCRIPTION
            "FT160状态表项"
    INDEX   {FT160RemoteStatusIndex}
    ::= {FT160RemoteStatusTable 1}

FT160RemoteStatusIndex  OBJECT-TYPE
    SYNTAX  INTEGER(1..16)
    ACCESS  read-only
    STATUS  mandatory
    DESCRIPTION
            "接口索引"
    ::= {FT160RemoteStatusEntry 1}

FT160Type  OBJECT-TYPE
    SYNTAX  INTEGER(0..10)
    ACCESS  read-only
    STATUS  mandatory
    DESCRIPTION
            "FT160类型 0: 无设备 1: 老NB110B  2: 新NB110B  3: NB110E 	4: NB110F 5: FT160B-1FESAC"
    ::= {FT160RemoteStatusEntry 2}

FT160Dip  OBJECT-TYPE
    SYNTAX  INTEGER
    ACCESS  read-only
    STATUS  mandatory
    DESCRIPTION
            "FT160 DIP 三组DIP开关,FT160B-1FESAC的DIP开关一组4位,我们仍用8位来表示,用高4位,低4位保留"
    ::= {FT160RemoteStatusEntry 3}

FT160Led1  OBJECT-TYPE
    SYNTAX  INTEGER
    ACCESS  read-only
    STATUS  mandatory
    DESCRIPTION
            "FT160 LED灯状态 PWR, SLT, SD, ALM, ACT, LINK, 100M, FDX(从低到高BIT0--BIT7)"
    ::= {FT160RemoteStatusEntry 4}

FT160Led2  OBJECT-TYPE
    SYNTAX  INTEGER
    ACCESS  read-only
    STATUS  mandatory
    DESCRIPTION
            "FT160 LED灯状态(保留)"
    ::= {FT160RemoteStatusEntry 5}

FT160HwVersion  OBJECT-TYPE
    SYNTAX  INTEGER
    ACCESS  read-only
    STATUS  mandatory
    DESCRIPTION
            "远端FT160硬件版本号是以三位的16进制形式进行显示，比如FT160HwVersion取值为48， 则显示硬件版本号位030。"
    ::= {FT160RemoteStatusEntry 6}

FT160SwVersion  OBJECT-TYPE
    SYNTAX  INTEGER
    ACCESS  read-only
    STATUS  mandatory
    DESCRIPTION
            "远端FT160软件版本号是以三位的十进制形式进行显示，比如FT160SwVersion取值为48， 则显示软件版本号位048。"
    ::= {FT160RemoteStatusEntry 7}

FT160FpgaVersion  OBJECT-TYPE
    SYNTAX  INTEGER
    ACCESS  read-only
    STATUS  mandatory
    DESCRIPTION
            "远端FT160的FPGA版本号是以三位的十进制形式进行显示，比如FT160FpgaVersion取值为48， 则显示FPGA版本号位048。"
    ::= {FT160RemoteStatusEntry 8}

FT160ClkSrc  OBJECT-TYPE
    SYNTAX  INTEGER
    ACCESS  read-only
    STATUS  mandatory
    DESCRIPTION
            "FT160时钟源方式 1:内时钟		2:光口时钟  3:V35外时钟	4:E1外时钟"
    ::= {FT160RemoteStatusEntry 9}

FT160ChannelNum  OBJECT-TYPE
    SYNTAX  INTEGER
    ACCESS  read-only
    STATUS  mandatory
    DESCRIPTION
            "FT160通道装载数 Bit7-Bit6: V35通道(00:不装载, 01:装载) Bit5-bit3: E1通道(000:不装载, 001:1, 010:2, 011:3, 100:4) Bit2-bit0: 以太通道(000:不装载, 001:1, 010:2, 011:3, 100:4)"
    ::= {FT160RemoteStatusEntry 10}

FT160V35Status  OBJECT-TYPE
    SYNTAX  INTEGER
    ACCESS  read-only
    STATUS  mandatory
    DESCRIPTION
            "V35状态 BIT7: V35发送时钟(1:反转, 0:不反转) BIT6: V35接收时钟(1:反转, 0:不反转) BIT5: DTE/DCE设备选择(1:DTE, 0:DCE) BIT4-BIT0: V35带宽选择(00000--11111)×64K,其中00000表示2M(在装载了V35通道后才有效)"
    ::= {FT160RemoteStatusEntry 11}

FT160SysMode  OBJECT-TYPE
    SYNTAX  INTEGER
    ACCESS  read-only
    STATUS  mandatory
    DESCRIPTION
            "FT160工作模式 0:非正常模式 1:DIP模式  2:远程网管模式"
    ::= {FT160RemoteStatusEntry 12}

FT160E1Status  OBJECT-TYPE
    SYNTAX  INTEGER
    ACCESS  read-only
    STATUS  mandatory
    DESCRIPTION
            "FT160 E1状态 BIT1: E1阻抗(1:120, 0:75)  BIT0: E1 CarryWave(0:同步, 1:不同步)"
    ::= {FT160RemoteStatusEntry 13}

FT160LoopMode  OBJECT-TYPE
    SYNTAX  INTEGER
    ACCESS  read-only
    STATUS  mandatory
    DESCRIPTION
            "环回模式  Bit2: V35环回(00:不环回, 01:环回)  Bit1-bit0: 光口环回(00:不环回, 01:LL环, 10:RL环, 11:双向环)"
    ::= {FT160RemoteStatusEntry 14}

FT160E1LoopMode  OBJECT-TYPE
    SYNTAX  INTEGER
    ACCESS  read-only
    STATUS  mandatory
    DESCRIPTION
            "E1环回模式  Bit7-Bit6: E11(00:不环回, 01:LL环, 10:RL环, 11：双向环)  Bit5-bit4: E12(00:不环回, 01:LL环, 10:RL环, 11:双向环)  Bit3-bit2: E13(00:不环回，01:LL环, 10:RL环, 11:双向环)  Bit1-bit0: E14(00:不环回，01:LL环, 10:RL环, 11:双向环)"
    ::= {FT160RemoteStatusEntry 15}

FT160EtherStatus  OBJECT-TYPE
    SYNTAX  INTEGER
    ACCESS  read-only
    STATUS  mandatory
    DESCRIPTION
            "以太口状态  bit2: 以太全双工(0:half, 1:full)  bit1: 10/100M设置(0:10M, 1:100M)  bit0: 自动协商(0:非自, 1:自动)"
    ::= {FT160RemoteStatusEntry 16}

FT160Res1  OBJECT-TYPE
    SYNTAX  INTEGER
    ACCESS  read-only
    STATUS  mandatory
    DESCRIPTION
            "保留"
    ::= {FT160RemoteStatusEntry 17}

FT160Res2  OBJECT-TYPE
    SYNTAX  INTEGER
    ACCESS  read-only
    STATUS  mandatory
    DESCRIPTION
            "保留"
    ::= {FT160RemoteStatusEntry 18}

-- ============================================================================================
-- 	EPAS网管NB110G mib库定义
-- ============================================================================================
mpNB110G MODULE-IDENTITY 
    LAST-UPDATED "0101050000Z"
    ORGANIZATION "Maipu DataComm"
    CONTACT-INFO
        "	Maipu DataComm
		Customer Service

		Postal: Consulate Drive
			Chengdu, Sichuan  610041
			China

	        Tel: 86-028-5161006

		E-mail: office@maipu.com"
    DESCRIPTION
        "The process and memory information of MP2600 infomation!"
::= { mpVeth 4 }

-- ============================================================================================
-- 	EPAS网管NB110G mib库定义
-- ============================================================================================
NB110G  		OBJECT IDENTIFIER ::= {mpNB110G 1}
NB110GGlobal  		OBJECT IDENTIFIER ::= {mpNB110G 2}

NB110GConfTable  OBJECT-TYPE
    SYNTAX  SEQUENCE OF NB110GConfEntry
    ACCESS  not-accessible
    STATUS  mandatory
    DESCRIPTION
            "NB110G参数配置"
    ::= {NB110G 1}

NB110GConfEntry  OBJECT-TYPE
    SYNTAX  NB110GConfEntry
    ACCESS  not-accessible
    STATUS  mandatory
    DESCRIPTION
            "NB110G配置表项"
    INDEX   {NB110GIndex}
    ::= {NB110GConfTable 1}

NB110GIndex  OBJECT-TYPE
    SYNTAX  INTEGER(1..14)
    ACCESS  read-only
    STATUS  mandatory
    DESCRIPTION
            "接口索引"
    ::= {NB110GConfEntry 1}

NB110GConfig  OBJECT-TYPE
    SYNTAX  INTEGER(1..4)
    ACCESS  read-write
    STATUS  mandatory
    DESCRIPTION
            "配置使能 1:不配置; 2:配置"
    ::= {NB110GConfEntry 2}

NB110GClock  OBJECT-TYPE
    SYNTAX  INTEGER
    ACCESS  read-write
    STATUS  current
    DESCRIPTION
            "线路时钟 0:内时钟； 1:外时钟"
    ::= {NB110GConfEntry 3}

NB110GE1Impedance  OBJECT-TYPE
    SYNTAX  INTEGER 
    ACCESS  read-write
    STATUS  current
    DESCRIPTION
            "线路阻抗 0:120欧； 1:75欧"
    ::= {NB110GConfEntry 4}

NB110GEtherProtocol  OBJECT-TYPE
    SYNTAX  INTEGER
    ACCESS  read-write
    STATUS  current
    DESCRIPTION
            "以太口是否自动协商 0:关闭； 1:打开"
    ::= {NB110GConfEntry 5}

NB110GEtherRate  OBJECT-TYPE
    SYNTAX  INTEGER 
    ACCESS  read-write
    STATUS  current
    DESCRIPTION
            "以太口的工作速率 0:10M； 1:100M"
    ::= {NB110GConfEntry 6}

NB110GEtherDuplex  OBJECT-TYPE
    SYNTAX  INTEGER 
    ACCESS  read-write
    STATUS  current
    DESCRIPTION
            "以太口的工作模式 0:全双工； 1:半双工"
    ::= {NB110GConfEntry 7}

NB110GRes  OBJECT-TYPE
    SYNTAX  INTEGER 
    ACCESS  read-write
    STATUS  current
    DESCRIPTION
            "保留"
    ::= {NB110GConfEntry 8}

NB110GLoop  OBJECT-TYPE
    SYNTAX  INTEGER 
    ACCESS  read-write
    STATUS  current
    DESCRIPTION
            "环回模式"
    ::= {NB110GConfEntry 9}

NB110GRemoteStatusTable  OBJECT-TYPE
    SYNTAX  SEQUENCE OF NB110GRemoteStatusEntry
    ACCESS  not-accessible
    STATUS  mandatory
    DESCRIPTION
            "NB110G状态信息"
    ::= {NB110G 2}

NB110GRemoteStatusEntry  OBJECT-TYPE
    SYNTAX  NB110GRemoteStatusEntry
    ACCESS  not-accessible
    STATUS  mandatory
    DESCRIPTION
            "NB110G远端状态表项"
    INDEX   {NB110GIndex}
    ::= {NB110GRemoteStatusTable 1}

NB110GIndex  OBJECT-TYPE
    SYNTAX  INTEGER(1..14)
    ACCESS  read-only
    STATUS  mandatory
    DESCRIPTION
            "接口索引"
    ::= {NB110GRemoteStatusEntry 1}

NB110GType  OBJECT-TYPE
    SYNTAX  INTEGER
    ACCESS  read-only
    STATUS  current
    DESCRIPTION
            "对端设备类型"
    ::= {NB110GRemoteStatusEntry 2}

NB110GDip1  OBJECT-TYPE
    SYNTAX  INTEGER
    ACCESS  read-only
    STATUS  current
    DESCRIPTION
            "开关1 0:ON，1:OFF"
    ::= {NB110GRemoteStatusEntry 3}

NB110GDip2  OBJECT-TYPE
    SYNTAX  INTEGER
    ACCESS  read-only
    STATUS  current
    DESCRIPTION
            "开关2 0:ON，1:OFF"
    ::= {NB110GRemoteStatusEntry 4}

NB110GLED1  OBJECT-TYPE
    SYNTAX  INTEGER
    ACCESS  read-only
    STATUS  current
    DESCRIPTION
            "PWR 0:ON，1:OFF"
    ::= {NB110GRemoteStatusEntry 5}

NB110GE1LED  OBJECT-TYPE
    SYNTAX  INTEGER
    ACCESS  read-only
    STATUS  current
    DESCRIPTION
            "E1灯 0:ON，1:OFF"
    ::= {NB110GRemoteStatusEntry 6}

NB110GEtherLED  OBJECT-TYPE
    SYNTAX  INTEGER
    ACCESS  read-only
    STATUS  current
    DESCRIPTION
            "ethernet灯 0:ON，1:OFF"
    ::= {NB110GRemoteStatusEntry 7}
    
NB110GLoopLED  OBJECT-TYPE
    SYNTAX  INTEGER
    ACCESS  read-only
    STATUS  current
    DESCRIPTION
            "Loop灯 0:ON，1:OFF"
    ::= {NB110GRemoteStatusEntry 8}

NB110GClock  OBJECT-TYPE
    SYNTAX  INTEGER
    ACCESS  read-only
    STATUS  current
    DESCRIPTION
            "时钟模式 0:内时钟；1:外时钟"
    ::= {NB110GRemoteStatusEntry 9}

NB110GE1Impedance  OBJECT-TYPE
    SYNTAX  INTEGER 
    ACCESS  read-only
    STATUS  current
    DESCRIPTION
            "线路阻抗 0:120欧；1:75欧"
    ::= {NB110GRemoteStatusEntry 10}

NB110GEtherProtocol  OBJECT-TYPE
    SYNTAX  INTEGER 
    ACCESS  read-only
    STATUS  current
    DESCRIPTION
            "以太口是否自动协商 0:关闭；1:打开"
    ::= {NB110GRemoteStatusEntry 11}

NB110GEtherRate  OBJECT-TYPE
    SYNTAX  INTEGER 
    ACCESS  read-only
    STATUS  current
    DESCRIPTION
            "以太口的工作速率 0:10M；1:100M"
    ::= {NB110GRemoteStatusEntry 12}

NB110GEtherDuplex  OBJECT-TYPE
    SYNTAX  INTEGER 
    ACCESS  read-only
    STATUS  current
    DESCRIPTION
            "以太口的工作模式 0:全双工；1:半双工"
    ::= {NB110GRemoteStatusEntry 13}

NB110GMode  OBJECT-TYPE
    SYNTAX  INTEGER
    ACCESS  read-only
    STATUS  current
    DESCRIPTION
            "运行模式 0:正常运行；1:远端环回"
    ::= {NB110GRemoteStatusEntry 14}

NB110GhwVersion  OBJECT-TYPE
    SYNTAX  INTEGER
    ACCESS  read-only
    STATUS  current
    DESCRIPTION
            "NB110G的硬件ID号，用3个字节表示(低字节表示低位字符,高字节表示高位字符)。 在网管界面上需要用字符形式表示硬件版本号。"
    ::= {NB110GRemoteStatusEntry 15}

NB110GswVersion  OBJECT-TYPE
    SYNTAX  INTEGER
    ACCESS  read-only
    STATUS  current
    DESCRIPTION
            "NB110G的软件ID号"
    ::= {NB110GRemoteStatusEntry 16}

NB110GFPGAVersion  OBJECT-TYPE
    SYNTAX  INTEGER
    ACCESS  read-only
    STATUS  current
    DESCRIPTION
            "NB110G的FPGA号"
    ::= {NB110GRemoteStatusEntry 17}
    
NB110GResetIndex  OBJECT-TYPE
    SYNTAX  INTEGER
    ACCESS  read-write
    STATUS  mandatory
    DESCRIPTION
            "接口索引"
    ::= {NB110GGlobal 1}


END
