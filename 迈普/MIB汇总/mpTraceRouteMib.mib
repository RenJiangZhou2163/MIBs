------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPTRACEROUTEMIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;



mpTraceRouteMib     	MODULE-IDENTITY
                    		LAST-UPDATED 	"0412270859Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { mpMgmt  114 }




------------------------------------------------------------------------------
mpTraceRouteMIBObjects	OBJECT IDENTIFIER ::= { mpTraceRouteMib 1 }

mpTraceTrConfTable  	OBJECT-TYPE
                    		SYNTAX  SEQUENCE OF   MpTraceTrConfEntry
                    		MAX-ACCESS  not-accessible
                    		STATUS  current
                    		DESCRIPTION
                    			"TraceRoute的配置表，工作站要开始一个从设备出发的TraceRoute，则首先在此表建立一行，在行状态设备为Active时则开始TraceRoute操作。工作站也可以删除建立的行。这些行是有老化时间的（5分钟）。"
                    		::= { mpTraceRouteMIBObjects 2 }

mpTraceTrConfEntry  	OBJECT-TYPE
                    		SYNTAX  MpTraceTrConfEntry
                    		MAX-ACCESS  not-accessible
                    		STATUS  current
                    		DESCRIPTION
                    			"TraceRoute的配置表，工作站要开始一个从设备出发的TraceRoute，则首先在此表建立一行，在行状态设备为Active时则开始TraceRoute操作。工作站也可以删除建立的行。这些行是有老化时间的（5分钟）。"
                    		INDEX  { mpTraceRtSerialNum }
                    		::= { mpTraceTrConfTable 1 }

MpTraceTrConfEntry  	::= SEQUENCE {
                    			mpTraceRtSerialNum     Integer32,
                    			mpTraceRtIPAddress     IpAddress,
                    			mpTraceRtVrfname       MInterfaceName,
                    			mpTraceRtTimeout       Integer32,
                    			mpTraceRtCompleted     TruthValue,
                    			mpTraceRtRowStatus     RowStatus
                    	             }


mpTraceRtSerialNum  	OBJECT-TYPE
                    		SYNTAX  Integer32(1..2147483647)
                    		MAX-ACCESS  not-accessible
                    		STATUS  current
                    		DESCRIPTION
                    			"全局唯一值，工作站在新建行时首先产生一个伪随机数，然后用此数为索引建立行，若此索引的行已存在则返回错误。"
                    		::= { mpTraceTrConfEntry 1 }

mpTraceRtIPAddress  	OBJECT-TYPE
                    		SYNTAX  IpAddress
                    		MAX-ACCESS  read-create
                    		STATUS  current
                    		DESCRIPTION
                    			"目标地址"
                    		::= { mpTraceTrConfEntry 2 }

mpTraceRtVrfname    	OBJECT-TYPE
                    		SYNTAX  DisplayString(SIZE(0..40))
                    		MAX-ACCESS  read-create
                    		STATUS  current
                    		DESCRIPTION
                    			""
                    		::= { mpTraceTrConfEntry 3 }

mpTraceRtTimeout    	OBJECT-TYPE
                    		SYNTAX  Integer32(0..3600000)
                    		MAX-ACCESS  read-create
                    		STATUS  current
                    		DESCRIPTION
                    			""
                    		::= { mpTraceTrConfEntry 4 }

mpTraceRtCompleted  	OBJECT-TYPE
                    		SYNTAX  integer32
                    		MAX-ACCESS  read-only
                    		STATUS  current
                    		DESCRIPTION
                    			""
                    		::= { mpTraceTrConfEntry 5 }

mpTraceRtRowStatus  	OBJECT-TYPE
                    		SYNTAX  RowStatus
                    		MAX-ACCESS  read-create
                    		STATUS  current
                    		DESCRIPTION
                    			""
                    		::= { mpTraceTrConfEntry 10 }

mpTraceRtHopsTable  	OBJECT-TYPE
                    		SYNTAX  SEQUENCE OF   MpTraceRtHopsEntry
                    		MAX-ACCESS  not-accessible
                    		STATUS  current
                    		DESCRIPTION
                    			"TraceRoute的结果存放表。此表的行有两个索引对象，一个是mpTraceRtSerialNum，实现与mpTraceRtConfTable一行的关联；另一个是mpTraceRtHopsIndex，标识TraceRoute操作结果中的多个结果。"
                    		::= { mpTraceRouteMIBObjects 3 }

mpTraceRtHopsEntry  	OBJECT-TYPE
                    		SYNTAX  MpTraceRtHopsEntry
                    		MAX-ACCESS  not-accessible
                    		STATUS  current
                    		DESCRIPTION
                    			"TraceRoute的结果存放表。此表的行有两个索引对象，一个是mpTraceRtSerialNum，实现与mpTraceRtConfTable一行的关联；另一个是mpTraceRtHopsIndex，标识TraceRoute操作结果中的多个结果。"
                    		INDEX  { mpTraceRtSerialNum, mpTraceRtHopsHopIndex }
                    		::= { mpTraceRtHopsTable 1 }

MpTraceRtHopsEntry  	::= SEQUENCE {
                    			mpTraceRtHopsHopSerialNum   Integer32,
                    			mpTraceRtHopsHopIndex   Integer32,
                    			mpTraceRtHopsHopAddr   IpAddress,
                    			mpTraceRtHopsHopLatencyValid   TruthValue,
                    			mpTraceRtHopsHopLatency   Unsigned32
                    	             }


mpTraceRtHopsHopSerialNum	OBJECT-TYPE
                    		SYNTAX  Integer32(1..2147483647)
                    		MAX-ACCESS  not-accessible
                    		STATUS  current
                    		DESCRIPTION
                    			"与mpTraceRtSerialNum一致，表明与mpTraceRtSerialNum的对应关系"
                    		::= { mpTraceRtHopsEntry 1 }

mpTraceRtHopsHopIndex	OBJECT-TYPE
                    		SYNTAX  Integer32
                    		MAX-ACCESS  not-accessible
                    		STATUS  current
                    		DESCRIPTION
                    			""
                    		::= { mpTraceRtHopsEntry 2 }

mpTraceRtHopsHopAddr	OBJECT-TYPE
                    		SYNTAX  IpAddress
                    		MAX-ACCESS  read-only
                    		STATUS  current
                    		DESCRIPTION
                    			"与此hop相关的地址"
                    		::= { mpTraceRtHopsEntry 3 }

mpTraceRtHopsHopLatencyValid	OBJECT-TYPE
                    		SYNTAX  integer32
                    		MAX-ACCESS  read-only
                    		STATUS  current
                    		DESCRIPTION
                    			"This object indicates whether the corresponding instance of mpTraceRtHopsHopLatency object contains a valid value. If the value of this object is 'true', then the corresponding instance of mpTraceRtHopsHopLatency contains a valid value. If the value of this object is 'false', then the corresponding instance of mpTraceRtHopsHopLatency does not contain a valid value and should be ignored."
                    		::= { mpTraceRtHopsEntry 4 }

mpTraceRtHopsHopLatency	OBJECT-TYPE
                    		SYNTAX  Unsigned32(0..25000000)
                    		MAX-ACCESS  read-only
                    		STATUS  current
                    		DESCRIPTION
                    			"This object reports the round trip time associated with this hop."
                    		::= { mpTraceRtHopsEntry 5 }



END
------------------------------------------------------------------------------
-- ============================================================================
-- $Log: mpTraceRouteMib.mib,v $
-- Revision 1.1  2010/06/21 11:18:46  liyh
-- first commit
--
--
--
-- ============================================================================
