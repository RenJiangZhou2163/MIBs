DEFINITIONS ::= BEGIN

ospf  OBJECT IDENTIFIER ::= {mib-2 14}

ospfGeneralGroup  OBJECT IDENTIFIER ::= {ospf 1}

ospfRouterId  OBJECT-TYPE
    SYNTAX  RouterID
    ACCESS  read-write
    STATUS  current
    DESCRIPTION
            "A  32-bit  integer  uniquely  identifying  the router in the Autonomous System. By  convention,  to  ensure  uniqueness,   this should  default  to  the  value  of  one of the router's IP interface addresses."
    ::= {ospfGeneralGroup 1}

ospfAdminStat  OBJECT-TYPE
    SYNTAX  Status
    ACCESS  read-write
    STATUS  current
    DESCRIPTION
            "The  administrative  status  of  OSPF  in  the router.   The  value 'enabled' denotes that the OSPF Process is active on at least  one  inter- face;  'disabled'  disables  it  on  all inter- faces."
    ::= {ospfGeneralGroup 2}

ospfVersionNumber  OBJECT-TYPE
    SYNTAX  INTEGER    
            }
    ACCESS  read-only
    STATUS  current
    DESCRIPTION
            "Baker & Coltun              Standards Track                    [Page 13] RFC 1850                        OSPF MIB                   November 1995 "The current version number of the OSPF  proto- col is 2.""
    ::= {ospfGeneralGroup 3}

ospfAreaBdrRtrStatus  OBJECT-TYPE
    SYNTAX  TruthValue
    ACCESS  read-only
    STATUS  current
    DESCRIPTION
            "A flag to note whether this router is an  area border router."
    ::= {ospfGeneralGroup 4}

ospfASBdrRtrStatus  OBJECT-TYPE
    SYNTAX  TruthValue
    ACCESS  read-write
    STATUS  current
    DESCRIPTION
            "A flag to note whether this router is  config- ured as an Autonomous System border router."
    ::= {ospfGeneralGroup 5}

ospfExternLsaCount  OBJECT-TYPE
    SYNTAX  Gauge32
    ACCESS  read-only
    STATUS  current
    DESCRIPTION
            "The number of external (LS type 5)  link-state advertisements in the link-state database."
    ::= {ospfGeneralGroup 6}

ospfExternLsaCksumSum  OBJECT-TYPE
    SYNTAX  Integer32
    ACCESS  read-only
    STATUS  current
    DESCRIPTION
            "The 32-bit unsigned sum of the LS checksums of the  external  link-state  advertisements  con- tained in the link-state  database.   This  sum can  be  used  to determine if there has been a change in a router's link state  database,  and to  compare  the  link-state  database  of  two routers."
    ::= {ospfGeneralGroup 7}

ospfTOSSupport  OBJECT-TYPE
    SYNTAX  TruthValue
    ACCESS  read-write
    STATUS  current
    DESCRIPTION
            "The router's support for type-of-service rout- ing."
    ::= {ospfGeneralGroup 8}

ospfOriginateNewLsas  OBJECT-TYPE
    SYNTAX  Counter32
    ACCESS  read-only
    STATUS  current
    DESCRIPTION
            "The number of  new  link-state  advertisements that  have been originated.  This number is in- cremented each time the router originates a new LSA."
    ::= {ospfGeneralGroup 9}

ospfRxNewLsas  OBJECT-TYPE
    SYNTAX  Counter32
    ACCESS  read-only
    STATUS  current
    DESCRIPTION
            "The number of  link-state  advertisements  re- ceived  determined  to  be  new instantiations. This number does not include  newer  instantia- tions  of self-originated link-state advertise- ments."
    ::= {ospfGeneralGroup 10}

ospfExtLsdbLimit  OBJECT-TYPE
    SYNTAX  Integer32 (-1..'7FFFFFFF'h)
    ACCESS  read-write
    STATUS  current
    DESCRIPTION
            "The  maximum   number   of   non-default   AS- external-LSAs entries that can be stored in the link-state database.  If the value is -1,  then there is no limit. When the number of non-default AS-external-LSAs in   a  router's  link-state  database  reaches ospfExtLsdbLimit, the router  enters  Overflow- State.   The   router  never  holds  more  than ospfExtLsdbLimit  non-default  AS-external-LSAs in  its  database. OspfExtLsdbLimit MUST be set identically in all routers attached to the OSPF backbone  and/or  any regular OSPF area. (i.e., OSPF stub areas and NSSAs are excluded)."
    ::= {ospfGeneralGroup 11}

ospfMulticastExtensions  OBJECT-TYPE
    SYNTAX  Integer32
    ACCESS  read-write
    STATUS  current
    DESCRIPTION
            "A Bit Mask indicating whether  the  router  is forwarding  IP  multicast  (Class  D) datagrams based on the algorithms defined in  the  Multi- cast Extensions to OSPF. Bit 0, if set, indicates that  the  router  can forward  IP multicast datagrams in the router's directly attached areas (called intra-area mul- ticast routing). Bit 1, if set, indicates that  the  router  can forward  IP  multicast  datagrams  between OSPF areas (called inter-area multicast routing). Bit 2, if set, indicates that  the  router  can forward  IP  multicast  datagrams between Auto- nomous Systems (called inter-AS multicast rout- ing). Only certain combinations of bit  settings  are allowed,  namely: 0 (no multicast forwarding is Baker & Coltun              Standards Track                    [Page 16] RFC 1850                        OSPF MIB                   November 1995 enabled), 1 (intra-area multicasting  only),  3 (intra-area  and  inter-area  multicasting),  5 (intra-area and inter-AS  multicasting)  and  7 (multicasting  everywhere). By default, no mul- ticast forwarding is enabled."
    ::= {ospfGeneralGroup 12}

ospfExitOverflowInterval  OBJECT-TYPE
    SYNTAX  PositiveInteger
    ACCESS  read-write
    STATUS  current
    DESCRIPTION
            "The number of  seconds  that,  after  entering OverflowState,  a  router will attempt to leave OverflowState. This allows the router to  again originate  non-default  AS-external-LSAs.  When set to 0, the router will not  leave  Overflow- State until restarted."
    ::= {ospfGeneralGroup 13}

ospfDemandExtensions  OBJECT-TYPE
    SYNTAX  TruthValue
    ACCESS  read-write
    STATUS  current
    DESCRIPTION
            "The router's support for demand routing."
    ::= {ospfGeneralGroup 14}

ospfAreaTable  OBJECT-TYPE
    SYNTAX  SEQUENCE OF OspfAreaEntry
    ACCESS  not-accessible
    STATUS  current
    DESCRIPTION
            "Information describing the configured  parame- ters  and cumulative statistics of the router's attached areas."
    ::= {ospf 2}

ospfAreaEntry  OBJECT-TYPE
    SYNTAX  ospfAreaEntry
    ACCESS  not-accessible
    STATUS  current
    DESCRIPTION
            "Information describing the configured  parame- ters  and  cumulative  statistics of one of the router's attached areas."
    INDEX   {ospfAreaId}
    ::= {ospfAreaTable 1}

ospfAreaId  OBJECT-TYPE
    SYNTAX  AreaID
    ACCESS  read-only
    STATUS  current
    DESCRIPTION
            "A 32-bit integer uniquely identifying an area. Area ID 0.0.0.0 is used for the OSPF backbone."
    ::= {ospfAreaEntry 1}

ospfAuthType  OBJECT-TYPE
    SYNTAX  Integer32
    ACCESS  read-only
    STATUS  current
    DESCRIPTION
            "The authentication type specified for an area. Additional authentication types may be assigned locally on a per Area basis."
    ::= {ospfAreaEntry 2}

ospfImportAsExtern  OBJECT-TYPE
    SYNTAX  INTEGER    
            }
    ACCESS  read-only
    STATUS  current
    DESCRIPTION
            "The area's support for importing  AS  external link- state advertisements."
    ::= {ospfAreaEntry 3}

ospfSpfRuns  OBJECT-TYPE
    SYNTAX  Counter32
    ACCESS  read-only
    STATUS  current
    DESCRIPTION
            "The number of times that the intra-area  route table  has  been  calculated  using this area's link-state database.  This  is  typically  done using Dijkstra's algorithm."
    ::= {ospfAreaEntry 4}

ospfAreaBdrRtrCount  OBJECT-TYPE
    SYNTAX  Gauge32
    ACCESS  read-only
    STATUS  current
    DESCRIPTION
            "The total number of area border routers reach- able within this area.  This is initially zero, and is calculated in each SPF Pass."
    ::= {ospfAreaEntry 5}

ospfAsBdrRtrCount  OBJECT-TYPE
    SYNTAX  Gauge32
    ACCESS  read-only
    STATUS  current
    DESCRIPTION
            "The total number of Autonomous  System  border routers  reachable  within  this area.  This is initially zero, and is calculated in  each  SPF Pass."
    ::= {ospfAreaEntry 6}

ospfAreaLsaCount  OBJECT-TYPE
    SYNTAX  Gauge32
    ACCESS  read-only
    STATUS  current
    DESCRIPTION
            "The total number of link-state  advertisements in  this  area's link-state database, excluding AS External LSA's."
    ::= {ospfAreaEntry 7}

ospfAreaLsaCksumSum  OBJECT-TYPE
    SYNTAX  Integer32
    ACCESS  read-only
    STATUS  current
    DESCRIPTION
            "The 32-bit unsigned sum of the link-state  ad- vertisements'  LS  checksums  contained in this area's link-state database.  This sum  excludes external (LS type 5) link-state advertisements. The sum can be used to determine if  there  has been  a  change  in a router's link state data- base, and to compare the link-state database of Baker & Coltun              Standards Track                    [Page 20] RFC 1850                        OSPF MIB                   November 1995 two routers."
    ::= {ospfAreaEntry 8}

ospfAreaSummary  OBJECT-TYPE
    SYNTAX  INTEGER    
            }
    ACCESS  read-only
    STATUS  current
    DESCRIPTION
            "The variable ospfAreaSummary controls the  im- port  of  summary LSAs into stub areas.  It has no effect on other areas. If it is noAreaSummary, the router will neither originate  nor  propagate summary LSAs into the stub area.  It will rely entirely  on  its  de- fault route. If it is sendAreaSummary, the router will  both summarize and propagate summary LSAs."
    ::= {ospfAreaEntry 9}

ospfAreaStatus  OBJECT-TYPE
    SYNTAX  RowStatus
    ACCESS  read-only
    STATUS  current
    DESCRIPTION
            "This variable displays the status of  the  en- try.  Setting it to 'invalid' has the effect of rendering it inoperative.  The internal  effect (row removal) is implementation dependent."
    ::= {ospfAreaEntry 10}

ospfStubAreaTable  OBJECT-TYPE
    SYNTAX  SEQUENCE OF OspfStubAreaEntry
    ACCESS  not-accessible
    STATUS  current
    DESCRIPTION
            "The set of metrics that will be advertised  by a default Area Border Router into a stub area."
    ::= {ospf 3}

ospfStubAreaEntry  OBJECT-TYPE
    SYNTAX  ospfStubAreaEntry
    ACCESS  not-accessible
    STATUS  current
    DESCRIPTION
            "The metric for a given Type  of  Service  that will  be  advertised  by  a default Area Border Router into a stub area."
    INDEX   {ospfStubAreaId, ospfStubTOS}
    ::= {ospfStubAreaTable 1}

ospfStubAreaId  OBJECT-TYPE
    SYNTAX  AreaID
    ACCESS  read-only
    STATUS  current
    DESCRIPTION
            "The 32 bit identifier for the Stub  Area.   On creation,  this  can  be  derived  from the in- stance."
    ::= {ospfStubAreaEntry 1}

ospfStubTOS  OBJECT-TYPE
    SYNTAX  TOSType
    ACCESS  read-only
    STATUS  current
    DESCRIPTION
            "The  Type  of  Service  associated  with   the metric.   On creation, this can be derived from the instance."
    ::= {ospfStubAreaEntry 2}

ospfStubMetric  OBJECT-TYPE
    SYNTAX  BigMetric
    ACCESS  read-only
    STATUS  current
    DESCRIPTION
            "The metric value applied at the indicated type of  service.  By default, this equals the least metric at the type of service among the  inter- faces to other areas."
    ::= {ospfStubAreaEntry 3}

ospfStubStatus  OBJECT-TYPE
    SYNTAX  RowStatus
    ACCESS  read-only
    STATUS  current
    DESCRIPTION
            "This variable displays the status of  the  en- try.  Setting it to 'invalid' has the effect of rendering it inoperative.  The internal  effect (row removal) is implementation dependent."
    ::= {ospfStubAreaEntry 4}

ospfStubMetricType  OBJECT-TYPE
    SYNTAX  INTEGER    
            }
    ACCESS  read-only
    STATUS  current
    DESCRIPTION
            "This variable displays the type of metric  ad- vertised as a default route."
    ::= {ospfStubAreaEntry 5}

ospfLsdbTable  OBJECT-TYPE
    SYNTAX  SEQUENCE OF OspfLsdbEntry
    ACCESS  not-accessible
    STATUS  current
    DESCRIPTION
            "The OSPF Process's Link State Database."
    ::= {ospf 4}

ospfLsdbEntry  OBJECT-TYPE
    SYNTAX  ospfLsdbEntry
    ACCESS  not-accessible
    STATUS  current
    DESCRIPTION
            "A single Link State Advertisement."
    INDEX   {ospfLsdbAreaId, ospfLsdbType,ospfLsdbLsid, ospfLsdbRouterId}
    ::= {ospfLsdbTable 1}

ospfLsdbAreaId  OBJECT-TYPE
    SYNTAX  AreaID
    ACCESS  read-only
    STATUS  current
    DESCRIPTION
            "The 32 bit identifier of the Area  from  which the LSA was received."
    ::= {ospfLsdbEntry 1}

ospfLsdbType  OBJECT-TYPE
    SYNTAX  INTEGER    
            }
    ACCESS  read-only
    STATUS  current
    DESCRIPTION
            "The type  of  the  link  state  advertisement. Each  link state type has a separate advertise- ment format."
    ::= {ospfLsdbEntry 2}

ospfLsdbLsid  OBJECT-TYPE
    SYNTAX  IpAddress
    ACCESS  read-only
    STATUS  current
    DESCRIPTION
            "The Link State ID is an LS Type Specific field containing either a Router ID or an IP Address; it identifies the piece of the  routing  domain that is being described by the advertisement."
    ::= {ospfLsdbEntry 3}

ospfLsdbRouterId  OBJECT-TYPE
    SYNTAX  RouterID
    ACCESS  read-only
    STATUS  current
    DESCRIPTION
            "The 32 bit number that uniquely identifies the originating router in the Autonomous System."
    ::= {ospfLsdbEntry 4}

ospfLsdbSequence  OBJECT-TYPE
    SYNTAX  Integer32
    ACCESS  read-only
    STATUS  current
    DESCRIPTION
            "The sequence number field is a  signed  32-bit integer.   It  is used to detect old and dupli- cate link state advertisements.  The  space  of sequence  numbers  is  linearly  ordered.   The larger the sequence number the more recent  the advertisement."
    ::= {ospfLsdbEntry 5}

ospfLsdbAge  OBJECT-TYPE
    SYNTAX  Integer32
    ACCESS  read-only
    STATUS  current
    DESCRIPTION
            "This field is the age of the link state adver- tisement in seconds."
    ::= {ospfLsdbEntry 6}

ospfLsdbChecksum  OBJECT-TYPE
    SYNTAX  Integer32
    ACCESS  read-only
    STATUS  current
    DESCRIPTION
            "This field is the  checksum  of  the  complete contents  of  the  advertisement, excepting the age field.  The age field is excepted  so  that an   advertisement's  age  can  be  incremented without updating the  checksum.   The  checksum used  is  the same that is used for ISO connec- tionless datagrams; it is commonly referred  to as the Fletcher checksum."
    ::= {ospfLsdbEntry 7}

ospfLsdbAdvertisement  OBJECT-TYPE
    SYNTAX  OCTET STRING (SIZE (1..65535))
    ACCESS  read-only
    STATUS  current
    DESCRIPTION
            "The entire Link State Advertisement, including its header."
    ::= {ospfLsdbEntry 8}

ospfAreaRangeTable  OBJECT-TYPE
    SYNTAX  SEQUENCE OF OspfAreaRangeEntry
    ACCESS  not-accessible
    STATUS  current
    DESCRIPTION
            "A range if IP addresses  specified  by  an  IP address/IP  network  mask  pair.   For example, class B address range of X.X.X.X with a network mask  of  255.255.0.0 includes all IP addresses from X.X.0.0 to X.X.255.255"
    ::= {ospf 5}

ospfAreaRangeEntry  OBJECT-TYPE
    SYNTAX  ospfAreaRangeEntry
    ACCESS  not-accessible
    STATUS  current
    DESCRIPTION
            "A range if IP addresses  specified  by  an  IP address/IP  network  mask  pair.   For example, class B address range of X.X.X.X with a network mask  of  255.255.0.0 includes all IP addresses from X.X.0.0 to X.X.255.255"
    INDEX   {ospfAreaRangeAreaId, ospfAreaRangeNet}
    ::= {ospfAreaRangeTable 1}

ospfAreaRangeAreaId  OBJECT-TYPE
    SYNTAX  AreaID
    ACCESS  read-only
    STATUS  current
    DESCRIPTION
            "The Area the Address  Range  is  to  be  found within."
    ::= {ospfAreaRangeEntry 1}

ospfAreaRangeNet  OBJECT-TYPE
    SYNTAX  IpAddress
    ACCESS  read-only
    STATUS  current
    DESCRIPTION
            "The IP Address of the Net or Subnet  indicated by the range."
    ::= {ospfAreaRangeEntry 2}

ospfAreaRangeMask  OBJECT-TYPE
    SYNTAX  IpAddress
    ACCESS  read-only
    STATUS  current
    DESCRIPTION
            "The Subnet Mask that pertains to  the  Net  or Subnet."
    ::= {ospfAreaRangeEntry 3}

ospfAreaRangeStatus  OBJECT-TYPE
    SYNTAX  RowStatus
    ACCESS  read-only
    STATUS  current
    DESCRIPTION
            "This variable displays the status of  the  en- try.  Setting it to 'invalid' has the effect of rendering it inoperative.  The internal  effect (row removal) is implementation dependent."
    ::= {ospfAreaRangeEntry 4}

ospfAreaRangeEffect  OBJECT-TYPE
    SYNTAX  INTEGER    
            }
    ACCESS  read-only
    STATUS  current
    DESCRIPTION
            "Subnets subsumed by ranges either trigger  the advertisement  of the indicated summary (adver- tiseMatching), or result in  the  subnet's  not being advertised at all outside the area."
    ::= {ospfAreaRangeEntry 5}

ospfHostTable  OBJECT-TYPE
    SYNTAX  SEQUENCE OF OspfHostEntry
    ACCESS  not-accessible
    STATUS  current
    DESCRIPTION
            "The list of Hosts, and their metrics, that the router will advertise as host routes."
    ::= {ospf 6}

ospfHostEntry  OBJECT-TYPE
    SYNTAX  ospfHostEntry
    ACCESS  not-accessible
    STATUS  current
    DESCRIPTION
            "A metric to be advertised, for a given type of service, when a given host is reachable."
    INDEX   {ospfHostIpAddress, ospfHostTOS}
    ::= {ospfHostTable 1}

ospfHostIpAddress  OBJECT-TYPE
    SYNTAX  IpAddress
    ACCESS  read-only
    STATUS  current
    DESCRIPTION
            "The IP Address of the Host."
    ::= {ospfHostEntry 1}

ospfHostTOS  OBJECT-TYPE
    SYNTAX  TOSType
    ACCESS  read-only
    STATUS  current
    DESCRIPTION
            "The Type of Service of the route being config- ured."
    ::= {ospfHostEntry 2}

ospfHostMetric  OBJECT-TYPE
    SYNTAX  Metric
    ACCESS  read-only
    STATUS  current
    DESCRIPTION
            "The Metric to be advertised."
    ::= {ospfHostEntry 3}

ospfHostStatus  OBJECT-TYPE
    SYNTAX  RowStatus
    ACCESS  read-only
    STATUS  current
    DESCRIPTION
            "This variable displays the status of  the  en- try.  Setting it to 'invalid' has the effect of rendering it inoperative.  The internal  effect (row removal) is implementation dependent."
    ::= {ospfHostEntry 4}

ospfHostAreaID  OBJECT-TYPE
    SYNTAX  AreaID
    ACCESS  read-only
    STATUS  current
    DESCRIPTION
            "The Area the Host Entry is to be found within. By  default, the area that a subsuming OSPF in- terface is in, or 0.0.0.0"
    ::= {ospfHostEntry 5}

ospfIfTable  OBJECT-TYPE
    SYNTAX  SEQUENCE OF OspfIfEntry
    ACCESS  not-accessible
    STATUS  current
    DESCRIPTION
            "The OSPF Interface Table describes the  inter- faces from the viewpoint of OSPF."
    ::= {ospf 7}

ospfIfEntry  OBJECT-TYPE
    SYNTAX  ospfIfEntry
    ACCESS  not-accessible
    STATUS  current
    DESCRIPTION
            "The OSPF Interface Entry describes one  inter- face from the viewpoint of OSPF."
    INDEX   {ospfIfIpAddress, ospfAddressLessIf}
    ::= {ospfIfTable 1}

ospfIfIpAddress  OBJECT-TYPE
    SYNTAX  IpAddress
    ACCESS  read-only
    STATUS  current
    DESCRIPTION
            "The IP address of this OSPF interface."
    ::= {ospfIfEntry 1}

ospfAddressLessIf  OBJECT-TYPE
    SYNTAX  Integer32
    ACCESS  read-only
    STATUS  current
    DESCRIPTION
            "For the purpose of easing  the  instancing  of addressed   and  addressless  interfaces;  This variable takes the value 0 on  interfaces  with IP  Addresses,  and  the corresponding value of ifIndex for interfaces having no IP Address."
    ::= {ospfIfEntry 2}

ospfIfAreaId  OBJECT-TYPE
    SYNTAX  AreaID
    ACCESS  read-only
    STATUS  current
    DESCRIPTION
            "A 32-bit integer uniquely identifying the area to  which  the  interface  connects.   Area  ID 0.0.0.0 is used for the OSPF backbone."
    ::= {ospfIfEntry 3}

ospfIfType  OBJECT-TYPE
    SYNTAX  INTEGER    
            }
    ACCESS  read-only
    STATUS  current
    DESCRIPTION
            "The OSPF interface type. By way of a default, this field may be intuited from the corresponding value of ifType.  Broad- cast LANs, such as  Ethernet  and  IEEE  802.5, take  the  value  'broadcast', X.25 and similar technologies take the value 'nbma',  and  links that  are  definitively point to point take the value 'pointToPoint'."
    ::= {ospfIfEntry 4}

ospfIfAdminStat  OBJECT-TYPE
    SYNTAX  Status
    ACCESS  read-only
    STATUS  current
    DESCRIPTION
            "The OSPF  interface's  administrative  status. The  value formed on the interface, and the in- terface will be advertised as an internal route to  some  area.   The  value 'disabled' denotes that the interface is external to OSPF."
    ::= {ospfIfEntry 5}

ospfIfRtrPriority  OBJECT-TYPE
    SYNTAX  DesignatedRouterPriority
    ACCESS  read-only
    STATUS  current
    DESCRIPTION
            "The  priority  of  this  interface.   Used  in multi-access  networks,  this  field is used in the designated router election algorithm.   The value 0 signifies that the router is not eligi- ble to become the  designated  router  on  this particular  network.   In the event of a tie in this value, routers will use their Router ID as a tie breaker."
    ::= {ospfIfEntry 6}

ospfIfTransitDelay  OBJECT-TYPE
    SYNTAX  UpToMaxAge
    ACCESS  read-only
    STATUS  current
    DESCRIPTION
            "The estimated number of seconds  it  takes  to transmit  a  link state update packet over this interface."
    ::= {ospfIfEntry 7}

ospfIfRetransInterval  OBJECT-TYPE
    SYNTAX  UpToMaxAge
    ACCESS  read-only
    STATUS  current
    DESCRIPTION
            "The number of seconds between  link-state  ad- vertisement  retransmissions,  for  adjacencies belonging to this  interface.   This  value  is also used when retransmitting database descrip- tion and link-state request packets."
    ::= {ospfIfEntry 8}

ospfIfHelloInterval  OBJECT-TYPE
    SYNTAX  HelloRange
    ACCESS  read-only
    STATUS  current
    DESCRIPTION
            "The length of time, in  seconds,  between  the Hello  packets that the router sends on the in- Baker & Coltun              Standards Track                    [Page 35] RFC 1850                        OSPF MIB                   November 1995 terface.  This value must be the same  for  all routers attached to a common network."
    ::= {ospfIfEntry 9}

ospfIfRtrDeadInterval  OBJECT-TYPE
    SYNTAX  PositiveInteger
    ACCESS  read-only
    STATUS  current
    DESCRIPTION
            "The number of seconds that  a  router's  Hello packets  have  not been seen before it's neigh- bors declare the router down.  This  should  be some  multiple  of  the  Hello  interval.  This value must be the same for all routers attached to a common network."
    ::= {ospfIfEntry 10}

ospfIfPollInterval  OBJECT-TYPE
    SYNTAX  PositiveInteger
    ACCESS  read-only
    STATUS  current
    DESCRIPTION
            "The larger time interval, in seconds,  between the  Hello  packets  sent  to  an inactive non- broadcast multi- access neighbor."
    ::= {ospfIfEntry 11}

ospfIfState  OBJECT-TYPE
    SYNTAX  INTEGER    
            }
    ACCESS  read-only
    STATUS  current
    DESCRIPTION
            "The OSPF Interface State."
    ::= {ospfIfEntry 12}

ospfIfDesignatedRouter  OBJECT-TYPE
    SYNTAX  IpAddress
    ACCESS  read-only
    STATUS  current
    DESCRIPTION
            "The IP Address of the Designated Router."
    ::= {ospfIfEntry 13}

ospfIfBackupDesignatedRouter  OBJECT-TYPE
    SYNTAX  IpAddress
    ACCESS  read-only
    STATUS  current
    DESCRIPTION
            "The  IP  Address  of  the  Backup   Designated Router."
    ::= {ospfIfEntry 14}

ospfIfEvents  OBJECT-TYPE
    SYNTAX  Counter32
    ACCESS  read-only
    STATUS  current
    DESCRIPTION
            "The number of times this  OSPF  interface  has changed its state, or an error has occurred."
    ::= {ospfIfEntry 15}

ospfIfAuthKey  OBJECT-TYPE
    SYNTAX  OCTET STRING (SIZE (0..256))
    ACCESS  read-only
    STATUS  current
    DESCRIPTION
            "The Authentication Key.  If the Area's Author- ization  Type  is  simplePassword,  and the key length is shorter than 8 octets, the agent will left adjust and zero fill to 8 octets. Note that unauthenticated  interfaces  need  no authentication key, and simple password authen- tication cannot use a key of more  than  8  oc- tets.  Larger keys are useful only with authen- tication mechanisms not specified in this docu- Baker & Coltun              Standards Track                    [Page 37] RFC 1850                        OSPF MIB                   November 1995 ment. When read, ospfIfAuthKey always returns an  Oc- tet String of length zero."
    ::= {ospfIfEntry 16}

ospfIfStatus  OBJECT-TYPE
    SYNTAX  RowStatus
    ACCESS  read-only
    STATUS  current
    DESCRIPTION
            "This variable displays the status of  the  en- try.  Setting it to 'invalid' has the effect of rendering it inoperative.  The internal  effect (row removal) is implementation dependent."
    ::= {ospfIfEntry 17}

ospfIfMulticastForwarding  OBJECT-TYPE
    SYNTAX  INTEGER    
            }
    ACCESS  read-only
    STATUS  current
    DESCRIPTION
            "The way multicasts should  forwarded  on  this interface;  not  forwarded,  forwarded  as data link multicasts, or forwarded as data link uni- casts.   Data link multicasting is not meaning- ful on point to point and NBMA interfaces,  and setting ospfMulticastForwarding to 0 effective- ly disables all multicast forwarding."
    ::= {ospfIfEntry 18}

ospfIfDemand  OBJECT-TYPE
    SYNTAX  TruthValue
    ACCESS  read-only
    STATUS  current
    DESCRIPTION
            "Indicates whether Demand OSPF procedures (hel- Baker & Coltun              Standards Track                    [Page 38] RFC 1850                        OSPF MIB                   November 1995 lo supression to FULL neighbors and setting the DoNotAge flag on proogated LSAs) should be per- formed on this interface."
    ::= {ospfIfEntry 19}

ospfIfAuthType  OBJECT-TYPE
    SYNTAX  INTEGER (0..255)
    ACCESS  read-only
    STATUS  current
    DESCRIPTION
            "The authentication type specified for  an  in- terface.   Additional  authentication types may be assigned locally."
    ::= {ospfIfEntry 20}

ospfIfMetricTable  OBJECT-TYPE
    SYNTAX  SEQUENCE OF OspfIfMetricEntry
    ACCESS  not-accessible
    STATUS  current
    DESCRIPTION
            "The TOS metrics for  a  non-virtual  interface identified by the interface index."
    ::= {ospf 8}

ospfIfMetricEntry  OBJECT-TYPE
    SYNTAX  ospfIfMetricEntry
    ACCESS  not-accessible
    STATUS  current
    DESCRIPTION
            "A particular TOS metric for a non-virtual  in- terface identified by the interface index."
    INDEX   {ospfIfMetricIpAddress,ospfIfMetricAddressLessIf,ospfIfMetricTOS}
    ::= {ospfIfMetricTable 1}

ospfIfMetricIpAddress  OBJECT-TYPE
    SYNTAX  IpAddress
    ACCESS  read-only
    STATUS  current
    DESCRIPTION
            "The IP address of this OSPF interface.  On row creation,  this  can  be  derived  from the in- stance."
    ::= {ospfIfMetricEntry 1}

ospfIfMetricAddressLessIf  OBJECT-TYPE
    SYNTAX  Integer32
    ACCESS  read-only
    STATUS  current
    DESCRIPTION
            "For the purpose of easing  the  instancing  of addressed   and  addressless  interfaces;  This variable takes the value 0 on  interfaces  with IP  Addresses, and the value of ifIndex for in- terfaces having no IP Address.   On  row  crea- tion, this can be derived from the instance."
    ::= {ospfIfMetricEntry 2}

ospfIfMetricTOS  OBJECT-TYPE
    SYNTAX  TOSType
    ACCESS  read-only
    STATUS  current
    DESCRIPTION
            "The type of service metric  being  referenced. On  row  creation, this can be derived from the instance."
    ::= {ospfIfMetricEntry 3}

ospfIfMetricValue  OBJECT-TYPE
    SYNTAX  Metric
    ACCESS  read-only
    STATUS  current
    DESCRIPTION
            "The metric of using this type  of  service  on this interface.  The default value of the TOS 0 Metric is 10^8 / ifSpeed."
    ::= {ospfIfMetricEntry 4}

ospfIfMetricStatus  OBJECT-TYPE
    SYNTAX  RowStatus
    ACCESS  read-only
    STATUS  current
    DESCRIPTION
            "This variable displays the status of  the  en- try.  Setting it to 'invalid' has the effect of rendering it inoperative.  The internal  effect (row removal) is implementation dependent."
    ::= {ospfIfMetricEntry 5}

ospfVirtIfTable  OBJECT-TYPE
    SYNTAX  SEQUENCE OF OspfVirtIfEntry
    ACCESS  not-accessible
    STATUS  current
    DESCRIPTION
            "Information about this router's virtual inter- faces."
    ::= {ospf 9}

ospfVirtIfEntry  OBJECT-TYPE
    SYNTAX  ospfVirtIfEntry
    ACCESS  not-accessible
    STATUS  current
    DESCRIPTION
            "Information about a single Virtual Interface."
    INDEX   {ospfVirtIfAreaId, ospfVirtIfNeighbor}
    ::= {ospfVirtIfTable 1}

ospfVirtIfAreaId  OBJECT-TYPE
    SYNTAX  AreaID
    ACCESS  read-only
    STATUS  current
    DESCRIPTION
            "The  Transit  Area  that  the   Virtual   Link traverses.  By definition, this is not 0.0.0.0"
    ::= {ospfVirtIfEntry 1}

ospfVirtIfNeighbor  OBJECT-TYPE
    SYNTAX  RouterID
    ACCESS  read-only
    STATUS  current
    DESCRIPTION
            "The Router ID of the Virtual Neighbor."
    ::= {ospfVirtIfEntry 2}

ospfVirtIfTransitDelay  OBJECT-TYPE
    SYNTAX  UpToMaxAge
    ACCESS  read-only
    STATUS  current
    DESCRIPTION
            "The estimated number of seconds  it  takes  to transmit  a link- state update packet over this interface."
    ::= {ospfVirtIfEntry 3}

ospfVirtIfRetransInterval  OBJECT-TYPE
    SYNTAX  UpToMaxAge
    ACCESS  read-only
    STATUS  current
    DESCRIPTION
            "The number of seconds between  link-state  ad- vertisement  retransmissions,  for  adjacencies belonging to this  interface.   This  value  is also used when retransmitting database descrip- tion  and  link-state  request  packets.   This value  should  be well over the expected round- trip time."
    ::= {ospfVirtIfEntry 4}

ospfVirtIfHelloInterval  OBJECT-TYPE
    SYNTAX  HelloRange
    ACCESS  read-only
    STATUS  current
    DESCRIPTION
            "The length of time, in  seconds,  between  the Hello  packets that the router sends on the in- terface.  This value must be the same  for  the virtual neighbor."
    ::= {ospfVirtIfEntry 5}

ospfVirtIfRtrDeadInterval  OBJECT-TYPE
    SYNTAX  PositiveInteger
    ACCESS  read-only
    STATUS  current
    DESCRIPTION
            "The number of seconds that  a  router's  Hello packets  have  not been seen before it's neigh- bors declare the router down.  This  should  be some  multiple  of  the  Hello  interval.  This value must be the same for the  virtual  neigh- bor."
    ::= {ospfVirtIfEntry 6}

ospfVirtIfState  OBJECT-TYPE
    SYNTAX  INTEGER    
            }
    ACCESS  read-only
    STATUS  current
    DESCRIPTION
            "OSPF virtual interface states."
    ::= {ospfVirtIfEntry 7}

ospfVirtIfEvents  OBJECT-TYPE
    SYNTAX  Counter32
    ACCESS  read-only
    STATUS  current
    DESCRIPTION
            "The number of state changes or error events on this Virtual Link"
    ::= {ospfVirtIfEntry 8}

ospfVirtIfAuthKey  OBJECT-TYPE
    SYNTAX  OCTET STRING (SIZE(0..256))
    ACCESS  read-only
    STATUS  current
    DESCRIPTION
            "If Authentication Type is simplePassword,  the device  will left adjust and zero fill to 8 oc- tets. Note that unauthenticated  interfaces  need  no authentication key, and simple password authen- tication cannot use a key of more  than  8  oc- tets.  Larger keys are useful only with authen- tication mechanisms not specified in this docu- ment. When  read,  ospfVifAuthKey  always  returns  a string of length zero."
    ::= {ospfVirtIfEntry 9}

ospfVirtIfStatus  OBJECT-TYPE
    SYNTAX  RowStatus
    ACCESS  read-only
    STATUS  current
    DESCRIPTION
            "This variable displays the status of  the  en- try.  Setting it to 'invalid' has the effect of rendering it inoperative.  The internal  effect (row removal) is implementation dependent."
    ::= {ospfVirtIfEntry 10}

ospfVirtIfAuthType  OBJECT-TYPE
    SYNTAX  INTEGER (0..255)
    ACCESS  read-only
    STATUS  current
    DESCRIPTION
            "The authentication type specified for a virtu- al  interface.  Additional authentication types may be assigned locally."
    ::= {ospfVirtIfEntry 11}

ospfNbrTable  OBJECT-TYPE
    SYNTAX  SEQUENCE OF OspfNbrEntry
    ACCESS  not-accessible
    STATUS  current
    DESCRIPTION
            "A table of non-virtual neighbor information."
    ::= {ospf 10}

ospfNbrEntry  OBJECT-TYPE
    SYNTAX  ospfNbrEntry
    ACCESS  not-accessible
    STATUS  current
    DESCRIPTION
            "Baker & Coltun              Standards Track                    [Page 46] RFC 1850                        OSPF MIB                   November 1995 "The information regarding a single neighbor.""
    INDEX   {ospfNbrIpAddr, ospfNbrAddressLessIndex}
    ::= {ospfNbrTable 1}

ospfNbrIpAddr  OBJECT-TYPE
    SYNTAX  IpAddress
    ACCESS  read-only
    STATUS  current
    DESCRIPTION
            "The IP address this neighbor is using  in  its IP  Source  Address.  Note that, on addressless links, this will not be 0.0.0.0,  but  the  ad- dress of another of the neighbor's interfaces."
    ::= {ospfNbrEntry 1}

ospfNbrAddressLessIndex  OBJECT-TYPE
    SYNTAX  InterfaceIndex
    ACCESS  read-only
    STATUS  current
    DESCRIPTION
            "On an interface having an  IP  Address,  zero. On  addressless  interfaces,  the corresponding value of ifIndex in the Internet Standard  MIB. On  row  creation, this can be derived from the instance."
    ::= {ospfNbrEntry 2}

ospfNbrRtrId  OBJECT-TYPE
    SYNTAX  RouterID
    ACCESS  read-only
    STATUS  current
    DESCRIPTION
            "A 32-bit integer (represented as a type  IpAd- dress)  uniquely  identifying  the  neighboring router in the Autonomous System."
    ::= {ospfNbrEntry 3}

ospfNbrOptions  OBJECT-TYPE
    SYNTAX  Integer32
    ACCESS  read-only
    STATUS  current
    DESCRIPTION
            "A Bit Mask corresponding to the neighbor's op- tions field. Bit 0, if set, indicates that the  system  will operate  on  Type of Service metrics other than TOS 0.  If zero, the neighbor will  ignore  all metrics except the TOS 0 metric. Bit 1, if set, indicates  that  the  associated area  accepts and operates on external informa- tion; if zero, it is a stub area. Bit 2, if set, indicates that the system is ca- pable  of routing IP Multicast datagrams; i.e., that it implements the Multicast Extensions  to OSPF. Bit 3, if set, indicates  that  the  associated area  is  an  NSSA.  These areas are capable of carrying type 7 external advertisements,  which are  translated into type 5 external advertise- Baker & Coltun              Standards Track                    [Page 48] RFC 1850                        OSPF MIB                   November 1995 ments at NSSA borders."
    ::= {ospfNbrEntry 4}

ospfNbrPriority  OBJECT-TYPE
    SYNTAX  DesignatedRouterPriority
    ACCESS  read-only
    STATUS  current
    DESCRIPTION
            "The priority of this neighbor in the designat- ed router election algorithm.  The value 0 sig- nifies that the neighbor is not eligible to be- come  the  designated router on this particular network."
    ::= {ospfNbrEntry 5}

ospfNbrState  OBJECT-TYPE
    SYNTAX  INTEGER    
            }
    ACCESS  read-only
    STATUS  current
    DESCRIPTION
            "The State of the relationship with this Neigh- bor."
    ::= {ospfNbrEntry 6}

ospfNbrEvents  OBJECT-TYPE
    SYNTAX  Counter32
    ACCESS  read-only
    STATUS  current
    DESCRIPTION
            "Baker & Coltun              Standards Track                    [Page 49] RFC 1850                        OSPF MIB                   November 1995 "The number of times this neighbor relationship has changed state, or an error has occurred.""
    ::= {ospfNbrEntry 7}

ospfNbrLsRetransQLen  OBJECT-TYPE
    SYNTAX  Gauge32
    ACCESS  read-only
    STATUS  current
    DESCRIPTION
            "The  current  length  of  the   retransmission queue."
    ::= {ospfNbrEntry 8}

ospfNbmaNbrStatus  OBJECT-TYPE
    SYNTAX  RowStatus
    ACCESS  read-only
    STATUS  current
    DESCRIPTION
            "This variable displays the status of  the  en- try.  Setting it to 'invalid' has the effect of rendering it inoperative.  The internal  effect (row removal) is implementation dependent."
    ::= {ospfNbrEntry 9}

ospfNbmaNbrPermanence  OBJECT-TYPE
    SYNTAX  INTEGER    
            }
    ACCESS  read-only
    STATUS  current
    DESCRIPTION
            "This variable displays the status of  the  en- try.   'dynamic'  and  'permanent' refer to how the neighbor became known."
    ::= {ospfNbrEntry 10}

ospfNbrHelloSuppressed  OBJECT-TYPE
    SYNTAX  TruthValue
    ACCESS  read-only
    STATUS  current
    DESCRIPTION
            "Indicates whether Hellos are being  suppressed Baker & Coltun              Standards Track                    [Page 50] RFC 1850                        OSPF MIB                   November 1995 to the neighbor"
    ::= {ospfNbrEntry 11}

ospfVirtNbrTable  OBJECT-TYPE
    SYNTAX  SEQUENCE OF OspfVirtNbrEntry
    ACCESS  not-accessible
    STATUS  current
    DESCRIPTION
            "A table of virtual neighbor information."
    ::= {ospf 11}

ospfVirtNbrEntry  OBJECT-TYPE
    SYNTAX  ospfVirtNbrEntry
    ACCESS  not-accessible
    STATUS  current
    DESCRIPTION
            "Virtual neighbor information."
    INDEX   {ospfVirtNbrArea, ospfVirtNbrRtrId}
    ::= {ospfVirtNbrTable 1}

ospfVirtNbrArea  OBJECT-TYPE
    SYNTAX  AreaID
    ACCESS  read-only
    STATUS  current
    DESCRIPTION
            "The Transit Area Identifier."
    ::= {ospfVirtNbrEntry 1}

ospfVirtNbrRtrId  OBJECT-TYPE
    SYNTAX  RouterID
    ACCESS  read-only
    STATUS  current
    DESCRIPTION
            "A  32-bit  integer  uniquely  identifying  the neighboring router in the Autonomous System."
    ::= {ospfVirtNbrEntry 2}

ospfVirtNbrIpAddr  OBJECT-TYPE
    SYNTAX  IpAddress
    ACCESS  read-only
    STATUS  current
    DESCRIPTION
            "The IP address this Virtual  Neighbor  is  us- ing."
    ::= {ospfVirtNbrEntry 3}

ospfVirtNbrOptions  OBJECT-TYPE
    SYNTAX  Integer32
    ACCESS  read-only
    STATUS  current
    DESCRIPTION
            "A Bit Mask corresponding to the neighbor's op- tions field. Bit 1, if set, indicates that the  system  will operate  on  Type of Service metrics other than TOS 0.  If zero, the neighbor will  ignore  all metrics except the TOS 0 metric. Bit 2, if set, indicates  that  the  system  is Network  Multicast  capable; ie, that it imple- ments OSPF Multicast Routing."
    ::= {ospfVirtNbrEntry 4}

ospfVirtNbrState  OBJECT-TYPE
    SYNTAX  INTEGER    
            }
    ACCESS  read-only
    STATUS  current
    DESCRIPTION
            "The state of the  Virtual  Neighbor  Relation- ship."
    ::= {ospfVirtNbrEntry 5}

ospfVirtNbrEvents  OBJECT-TYPE
    SYNTAX  Counter32
    ACCESS  read-only
    STATUS  current
    DESCRIPTION
            "The number of  times  this  virtual  link  has changed its state, or an error has occurred."
    ::= {ospfVirtNbrEntry 6}

ospfVirtNbrLsRetransQLen  OBJECT-TYPE
    SYNTAX  Gauge32
    ACCESS  read-only
    STATUS  current
    DESCRIPTION
            "The  current  length  of  the   retransmission queue."
    ::= {ospfVirtNbrEntry 7}

ospfVirtNbrHelloSuppressed  OBJECT-TYPE
    SYNTAX  TruthValue
    ACCESS  read-only
    STATUS  current
    DESCRIPTION
            "Indicates whether Hellos are being  suppressed to the neighbor"
    ::= {ospfVirtNbrEntry 8}

ospfExtLsdbTable  OBJECT-TYPE
    SYNTAX  SEQUENCE OF OspfExtLsdbEntry
    ACCESS  not-accessible
    STATUS  current
    DESCRIPTION
            "The OSPF Process's Links State Database."
    ::= {ospf 12}

ospfExtLsdbEntry  OBJECT-TYPE
    SYNTAX  ospfExtLsdbEntry
    ACCESS  not-accessible
    STATUS  current
    DESCRIPTION
            "A single Link State Advertisement."
    INDEX   {ospfExtLsdbType, ospfExtLsdbLsid, ospfExtLsdbRouterId}
    ::= {ospfExtLsdbTable 1}

ospfExtLsdbType  OBJECT-TYPE
    SYNTAX  INTEGER    
            }
    ACCESS  read-only
    STATUS  current
    DESCRIPTION
            "The type  of  the  link  state  advertisement. Each  link state type has a separate advertise- ment format."
    ::= {ospfExtLsdbEntry 1}

ospfExtLsdbLsid  OBJECT-TYPE
    SYNTAX  IpAddress
    ACCESS  read-only
    STATUS  current
    DESCRIPTION
            "The Link State ID is an LS Type Specific field containing either a Router ID or an IP Address; it identifies the piece of the  routing  domain that is being described by the advertisement."
    ::= {ospfExtLsdbEntry 2}

ospfExtLsdbRouterId  OBJECT-TYPE
    SYNTAX  RouterID
    ACCESS  read-only
    STATUS  current
    DESCRIPTION
            "The 32 bit number that uniquely identifies the originating router in the Autonomous System."
    ::= {ospfExtLsdbEntry 3}

ospfExtLsdbSequence  OBJECT-TYPE
    SYNTAX  Integer32
    ACCESS  read-only
    STATUS  current
    DESCRIPTION
            "The sequence number field is a  signed  32-bit integer.   It  is used to detect old and dupli- cate link state advertisements.  The  space  of sequence  numbers  is  linearly  ordered.   The larger the sequence number the more recent  the advertisement."
    ::= {ospfExtLsdbEntry 4}

ospfExtLsdbAge  OBJECT-TYPE
    SYNTAX  Integer32
    ACCESS  read-only
    STATUS  current
    DESCRIPTION
            "This field is the age of the link state adver- tisement in seconds."
    ::= {ospfExtLsdbEntry 5}

ospfExtLsdbChecksum  OBJECT-TYPE
    SYNTAX  Integer32
    ACCESS  read-only
    STATUS  current
    DESCRIPTION
            "This field is the  checksum  of  the  complete contents  of  the  advertisement, excepting the age field.  The age field is excepted  so  that an   advertisement's  age  can  be  incremented without updating the  checksum.   The  checksum used  is  the same that is used for ISO connec- tionless datagrams; it is commonly referred  to as the Fletcher checksum."
    ::= {ospfExtLsdbEntry 6}

ospfExtLsdbAdvertisement  OBJECT-TYPE
    SYNTAX  OCTET STRING (SIZE(36))
    ACCESS  read-only
    STATUS  current
    DESCRIPTION
            "The entire Link State Advertisement, including its header."
    ::= {ospfExtLsdbEntry 7}

ospfRouteGroup  OBJECT IDENTIFIER ::= {ospf 13}

ospfIntraArea  OBJECT IDENTIFIER ::= {ospfRouteGroup 1}

ospfInterArea  OBJECT IDENTIFIER ::= {ospfRouteGroup 2}

ospfExternalType1  OBJECT IDENTIFIER ::= {ospfRouteGroup 3}

ospfExternalType2  OBJECT IDENTIFIER ::= {ospfRouteGroup 4}

ospfAreaAggregateTable  OBJECT-TYPE
    SYNTAX  SEQUENCE OF OspfAreaAggregateEntry
    ACCESS  not-accessible
    STATUS  current
    DESCRIPTION
            "A range of IP addresses  specified  by  an  IP address/IP  network  mask  pair.   For example, class B address range of X.X.X.X with a network mask  of  255.255.0.0 includes all IP addresses from X.X.0.0  to  X.X.255.255.   Note  that  if ranges  are configured such that one range sub- sumes  another  range  (e.g.,   10.0.0.0   mask 255.0.0.0  and  10.1.0.0 mask 255.255.0.0), the most specific match is the preferred one."
    ::= {ospf 14}

ospfAreaAggregateEntry  OBJECT-TYPE
    SYNTAX  ospfAreaAggregateEntry
    ACCESS  not-accessible
    STATUS  current
    DESCRIPTION
            "A range of IP addresses  specified  by  an  IP address/IP  network  mask  pair.   For example, class B address range of X.X.X.X with a network mask  of  255.255.0.0 includes all IP addresses from X.X.0.0  to  X.X.255.255.   Note  that  if ranges are range configured such that one range subsumes another  range  (e.g.,  10.0.0.0  mask 255.0.0.0  and  10.1.0.0 mask 255.255.0.0), the Baker & Coltun              Standards Track                    [Page 58] RFC 1850                        OSPF MIB                   November 1995 most specific match is the preferred one."
    INDEX   {ospfAreaAggregateAreaID, ospfAreaAggregateLsdbType,ospfAreaAggregateNet, ospfAreaAggregateMask}
    ::= {ospfAreaAggregateTable 1}

ospfAreaAggregateAreaID  OBJECT-TYPE
    SYNTAX  AreaID
    ACCESS  read-only
    STATUS  current
    DESCRIPTION
            "The Area the Address Aggregate is to be  found within."
    ::= {ospfAreaAggregateEntry 1}

ospfAreaAggregateLsdbType  OBJECT-TYPE
    SYNTAX  INTEGER    
            }
    ACCESS  read-only
    STATUS  current
    DESCRIPTION
            "The type of the Address Aggregate.  This field specifies  the  Lsdb type that this Address Ag- gregate applies to."
    ::= {ospfAreaAggregateEntry 2}

ospfAreaAggregateNet  OBJECT-TYPE
    SYNTAX  IpAddress
    ACCESS  read-only
    STATUS  current
    DESCRIPTION
            "The IP Address of the Net or Subnet  indicated by the range."
    ::= {ospfAreaAggregateEntry 3}

ospfAreaAggregateMask  OBJECT-TYPE
    SYNTAX  IpAddress
    ACCESS  read-only
    STATUS  current
    DESCRIPTION
            "The Subnet Mask that pertains to  the  Net  or Subnet."
    ::= {ospfAreaAggregateEntry 4}

ospfAreaAggregateStatus  OBJECT-TYPE
    SYNTAX  RowStatus
    ACCESS  read-only
    STATUS  current
    DESCRIPTION
            "This variable displays the status of  the  en- try.  Setting it to 'invalid' has the effect of rendering it inoperative.  The internal  effect (row removal) is implementation dependent."
    ::= {ospfAreaAggregateEntry 5}

ospfAreaAggregateEffect  OBJECT-TYPE
    SYNTAX  INTEGER    
            }
    ACCESS  read-only
    STATUS  current
    DESCRIPTION
            "Subnets subsumed by ranges either trigger  the advertisement  of  the indicated aggregate (ad- vertiseMatching), or result in the subnet's not being advertised at all outside the area."
    ::= {ospfAreaAggregateEntry 6}

ospfConformance  OBJECT IDENTIFIER ::= {ospf 15}

ospfGroups  OBJECT IDENTIFIER ::= {ospfConformance 1}

ospfCompliances  OBJECT IDENTIFIER ::= {ospfConformance 2}
END
