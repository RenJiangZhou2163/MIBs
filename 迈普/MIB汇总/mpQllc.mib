-- *****************************************************************
-- MAIPU-QLLC.mib:  Maipu enterprise device SDLC MIB file
--
--version 1.0.0.0, April 27, 2002  Huanglulu, Rogerhu
--
-- Copyright (c)  by Maipu DataComm Inc.
-- All rights reserved.
-- 
-- *****************************************************************
--

MAIPU-QLLC-MIB DEFINITIONS ::= BEGIN

IMPORTS
    RowStatus						FROM SNMPv2-TC
    MODULE-IDENTITY, OBJECT-TYPE 	FROM SNMPv2-SMI
    mpMgmt                          FROM MAIPU-SMI;

mpQllcMib MODULE-IDENTITY
    LAST-UPDATED "0204270000Z"
    ORGANIZATION "Maipu DataComm"
    CONTACT-INFO
	"   Maipu DataComm
		Customer Service

		Postal: Consulate Drive
			Chengdu, Sichuan  610041
			China

		Tel: 86-028-5161006

		E-mail: office@maipu.com"
    DESCRIPTION
		"The assignments for Maipu router's MIB of QLLC infomation!"
    ::= {mpMgmt 100 }

-- ***********************************
qllcConfTable OBJECT-TYPE
    SYNTAX SEQUENCE OF QllcConfEntry
    MAX-ACCESS not-accessible
    STATUS current
    DESCRIPTION
		"QLLC的配置表."
    ::= { mpQllcMib 1 }

qllcConfEntry OBJECT-TYPE
    SYNTAX QllcConfEntry
    MAX-ACCESS not-accessible
    STATUS current
    DESCRIPTION
		"QLLC配置表条目."
    INDEX { qllcIndex }    
    ::= { qllcConfTable 1 }

QllcConfEntry ::=
	SEQUENCE {
		qllcIndex
			INTEGER,
		qllcFlag
			INTEGER,
		qllcPartner
			OCTET STRING,
		qllcXidDivert
			INTEGER,
		qllcPvc
			INTEGER,
		qllcOrigin
			OCTET STRING,
		qllcStatus
			RowStatus
				}
				
qllcIndex	OBJECT-TYPE
	SYNTAX	INTEGER
	MAX-ACCESS	read-only
	STATUS	current
	DESCRIPTION
		"qllcIndex"
	::= { qllcConfEntry 1 }
	
qllcFlag	OBJECT-TYPE
	SYNTAX	INTEGER	{
			default(1),
			pvc(2),
			vmacaddr(3)
				}
	MAX-ACCESS	read-create
	STATUS	current
	DESCRIPTION
		"qllcFlag"
	::= { qllcConfEntry 2 }
				
qllcPartner	OBJECT-TYPE
	SYNTAX	OCTET STRING (SIZE(14))
	MAX-ACCESS	read-create
	STATUS	current
	DESCRIPTION
		"qllcPartner"
	::= { qllcConfEntry 3 }
	
qllcXidDivert	OBJECT-TYPE
	SYNTAX	INTEGER {
			normal(1),
			divert(2)
				}
	MAX-ACCESS	read-create
	STATUS	current
	DESCRIPTION
		"qllcXidDivert"
	::= { qllcConfEntry 4 }
	
qllcPvc		OBJECT-TYPE
	SYNTAX	INTEGER (1..4095)
	MAX-ACCESS	read-create
	STATUS	current
	DESCRIPTION
		"qllcXidDivert"
	::= { qllcConfEntry 5 }
	

qllcOrigin	OBJECT-TYPE
	SYNTAX	OCTET STRING (SIZE(14))
	MAX-ACCESS	read-create
	STATUS	current
	DESCRIPTION
		"qllcOrigin"
	::= { qllcConfEntry 6 }

qllcStatus	OBJECT-TYPE
	SYNTAX	RowStatus
	MAX-ACCESS	read-create
	STATUS	current
	DESCRIPTION
		""
	::= { qllcConfEntry 7 }

END
