-- *****************************************************************
-- MAIPU-BACKUP.mib:  Maipu enterprise device backup MIB file
--
--version 1.0.0.1, Sep 24, 2002 Huanglulu
--
-- Copyright (c)  by Maipu DataComm Inc.
-- All rights reserved.
-- 
-- *****************************************************************
--

MAIPU-BACKUP-MIB DEFINITIONS ::= BEGIN

IMPORTS
    RowStatus							FROM SNMPv2-TC
    MODULE-IDENTITY, OBJECT-TYPE        FROM SNMPv2-SMI
    mpMgmt                              FROM MAIPU-SMI;

mpBackupMib MODULE-IDENTITY
    LAST-UPDATED "0102200000Z"
    ORGANIZATION "Maipu DataComm"
    CONTACT-INFO
	"   Maipu DataComm
		Customer Service

		Postal: Consulate Drive
			Chengdu, Sichuan  610041
			China

		Tel: 86-028-5161006

		E-mail: office@maipu.com"
    DESCRIPTION
		"The assignments for Maipu router's MIB of backup infomation!"
    ::= { mpMgmt 29 }

-- ****************

mpBackupConf	OBJECT IDENTIFIER ::= { mpBackupMib 1 }

-- ****************

mpBackupConfTable	OBJECT-TYPE
    SYNTAX SEQUENCE OF MpBackupConfEntry
    MAX-ACCESS not-accessible
    STATUS current
    DESCRIPTION
		"backup的配置表."
    ::= { mpBackupConf 1 }

mpBackupConfEntry	OBJECT-TYPE
    SYNTAX MpBackupConfEntry
    MAX-ACCESS not-accessible
    STATUS current
    DESCRIPTION
		"backup配置表条目."
    INDEX { backupIfIndex }
    ::= { mpBackupConfTable 1 }

ModemConfEntry ::=
	SEQUENCE {
		backupIfIndex		INTEGER,
		backupIfName		OCTET STRING,
		backupFlag			OCTET STRING,
		backupDelayAct		Unsigned32,
		backupDelayDeact	Unsigned32,
		backupLoadAct		INTEGER,
		backupLoadDeact		INTEGER,
		backupRowStatus		RowStatus
			}

backupIfIndex	OBJECT-TYPE
    SYNTAX INTEGER
    MAX-ACCESS read-create
    STATUS current
    DESCRIPTION
		"配置拨号备份的接口."
    ::= { mpBackupConfEntry 1 }

backupIfName	OBJECT-TYPE
    SYNTAX OCTET STRING
    MAX-ACCESS read-create
    STATUS current
    DESCRIPTION
		"配置的备份接口名."
    ::= { mpBackupConfEntry 2 }

backupFlag	OBJECT-TYPE
    SYNTAX OCTET STRING (SIZE OF(1))
    MAX-ACCESS read-create
    STATUS current
    DESCRIPTION
		"位表示，0x02表示不起用备份口，0x04表示不挂断备份口，
		 0x08表示负载不起用备份，0x10表示负载不挂断备份."
    ::= { mpBackupConfEntry 3 }

backupDelayAct	OBJECT-TYPE
    SYNTAX Unsigned32
    MAX-ACCESS read-create
    STATUS current
    DESCRIPTION
		"主口失效几秒后启用备份口."
    ::= { mpBackupConfEntry 4 }

backupDelayDeact	OBJECT-TYPE
    SYNTAX Unsigned32
    MAX-ACCESS read-create
    STATUS current
    DESCRIPTION
		"主口恢复几秒后挂断备份口."
    ::= { mpBackupConfEntry 5 }

backupLoadAct	OBJECT-TYPE
    SYNTAX INTEGER (0..100)
    MAX-ACCESS read-create
    STATUS current
    DESCRIPTION
		"主口负载达到百分之几的时候启用备份口."
    ::= { mpBackupConfEntry 6 }

backupLoadDeact	OBJECT-TYPE
    SYNTAX INTEGER (0..100)
    MAX-ACCESS read-create
    STATUS current
    DESCRIPTION
		"主口和备份口的负载之和低于主口总负载的百分之几时挂断备份口."
    ::= { mpBackupConfEntry 7 }

backupRowStatus	OBJECT-TYPE
    SYNTAX RowStatus
    MAX-ACCESS read-create
    STATUS current
    DESCRIPTION
		"."
    ::= { mpBackupConfEntry 8 }

END
