-- ***************************************************************************
-- MAIPU-PRODUCTS.mib:  Maipu Product Object Identifier Assignments

-- V2.0,2004.11.15， 在mpProducts下增加了不同产品的节点

-- December 2000, Maipu Network Management Team

-- Copyright(c) 1999-2001 by Maipu Data Communication, Inc.
-- 
-- ***************************************************************************

MAIPU-PRODUCTS DEFINITIONS ::= BEGIN

IMPORTS
	mpProducts	FROM MAIPU-SMI;

mpProducts 	OBJECT IDENTIFIER ::= { maipu 1 }


--该部分定义Maipu的产品系列，以后的新产品全部在各自的系列下分配节点。
accessServer  	OBJECT IDENTIFIER ::= { mpProducts 6 }   --综合接入产品线
mpIPPhone	OBJECT IDENTIFIER ::= { mpProducts 31 }  --IP语音产品系列
mpSecure	OBJECT IDENTIFIER ::= { mpProducts 35 }  --安全产品线
mpGDO		OBJECT IDENTIFIER ::= { mpProducts 75 }  --OEM的产品系列
mpNMS           OBJECT IDENTIFIER ::= { mpProducts 100 } --网管产品系列，2004.8.20分配 网管管理其他设备SysOid节点
mpRouter        OBJECT IDENTIFIER ::= { mpProducts 101 } --路由产品系列，2004.11.15
mpSwitch        OBJECT IDENTIFIER ::= { mpProducts 102 } --交换产品系列，2004.11.15
--------------------------------------------------------------------------------------------------


--该部分用来定义综合接入系列的产品
mp9400		OBJECT IDENTIFIER ::= { accessServer 1 }
mp9600		OBJECT IDENTIFIER ::= { accessServer 2 }
mp9700		OBJECT IDENTIFIER ::= { accessServer 3 }
mp9900		OBJECT IDENTIFIER ::= { accessServer 5 }  --mp9900
mpNmsa		OBJECT IDENTIFIER ::= { accessServer 6 }  --mp9400new
mp9700Small	OBJECT IDENTIFIER ::= { accessServer 7 }

--------------------------------------------------------------------------------------------------


--该部分用来定义新路由器系列的产品

mp1700E     OBJECT IDENTIFIER ::= { mpRouter 1 }    --2005.3.23分配
mp2600C     OBJECT IDENTIFIER ::= { mpRouter 2 }    --2005.3.23分配
mp2600D     OBJECT IDENTIFIER ::= { mpRouter 3 }    --2005.3.23分配
 
--------------------------------------------------------------------------------------------------


--该部分用来定义新交换机系列的产品
mpS4152M     OBJECT IDENTIFIER ::= { mpSwitch 1 }    --2005.1.20分配
mpS4112M     OBJECT IDENTIFIER ::= { mpSwitch 2 }    --2005.1.20分配

--------------------------------------------------------------------------------------------------


--该部分用来定义IP语音系列的产品
mpVEP200	OBJECT IDENTIFIER ::= { mpIPPhone 1 }
mpVGK2002	OBJECT IDENTIFIER ::= { mpIPPhone 2 }
mpVG2000	OBJECT IDENTIFIER ::= { mpIPPhone 3 }
mpVG800		OBJECT IDENTIFIER ::= { mpIPPhone 4 }
mpVEP210	OBJECT IDENTIFIER ::= { mpIPPhone 5 }
mpVG1016	OBJECT IDENTIFIER ::= { mpIPPhone 6 }  --MyPower VG1016
mpA600          OBJECT IDENTIFIER ::= { mpIPPhone 7 }
mpMTS1000       OBJECT IDENTIFIER ::= { mpIPPhone 8 }
mpVG6016        OBJECT IDENTIFIER ::= { mpIPPhone 9 }
mpVG2000vgp     OBJECT IDENTIFIER ::= { mpIPPhone 10 } --2004.10.25分配 VGP软件平台的2000网关
mpVG800vgp      OBJECT IDENTIFIER ::= { mpIPPhone 11 } --2004.10.25分配 VGP软件平台的800网关
mpA600vgp       OBJECT IDENTIFIER ::= { mpIPPhone 12 } --2004.10.25分配 VGP软件平台的600网关
mpVG800G        OBJECT IDENTIFIER ::= { mpIPPhone 13 } --2004.12.6分配  由于市场需要由A600改成的VG800版本
mpVGK3X         OBJECT IDENTIFIER ::= { mpIPPhone 14 } --2005.1.12分配  新的网守版本

---------------------------------------------------------------------------------------------------


--该部分用来定义安全系列的产品
mpFw520		OBJECT IDENTIFIER ::= { mpSecure 1 }
mpFw505		OBJECT IDENTIFIER ::= { mpSecure 2 }  --停产
mpVPN3020	OBJECT IDENTIFIER ::= { mpSecure 3 }
mpVPN3005	OBJECT IDENTIFIER ::= { mpSecure 4 }  --停产
mpSecCms	OBJECT IDENTIFIER ::= { mpSecure 5 }
--mpSecSProxy	OBJECT IDENTIFIER ::= { mpSecure 6 }
mpSSL600	OBJECT IDENTIFIER ::= { mpSecure 6 }
mpFw510		OBJECT IDENTIFIER ::= { mpSecure 7 }  --无此型号
mpFw3010	OBJECT IDENTIFIER ::= { mpSecure 8 }  --无此型号
mpVPN3005B      OBJECT IDENTIFIER ::= { mpSecure 31 }
mpVPN3010	OBJECT IDENTIFIER ::= { mpSecure 32 }
mpVPN3020B	OBJECT IDENTIFIER ::= { mpSecure 33 }
mpVPN3010E      OBJECT IDENTIFIER ::= { mpSecure 34 } --2004.8.4分配

--------------------------------------------------------------------------------------------------


--该部分用来定义网管系列的产品



--------------------------------------------------------------------------------------------------




--该部分用来定义OEM系列的产品
mp8616		OBJECT IDENTIFIER ::= { mpGDO 1 }
mp8608		OBJECT IDENTIFIER ::= { mpGDO 2 }
mp8602		OBJECT IDENTIFIER ::= { mpGDO 3 }  --停产
mp8602A	        OBJECT IDENTIFIER ::= { mpGDO 4 }
mp8602B	        OBJECT IDENTIFIER ::= { mpGDO 5 }
mp8620		OBJECT IDENTIFIER ::= { mpGDO 6 }

--------------------------------------------------------------------------------------------------



--2004.11.15，现在需要全局整理Maipu的MIB库组织方式，已有的路由器和交换机就直接放在mpProducts节点下。
mp2600		OBJECT IDENTIFIER ::= { mpProducts 1 }  --停产
mp2600M 	OBJECT IDENTIFIER ::= { mpProducts 2 }
mp1600		OBJECT IDENTIFIER ::= { mpProducts 3 }  --停产
mp2500		OBJECT IDENTIFIER ::= { mpProducts 4 }  --停产
mp800		OBJECT IDENTIFIER ::= { mpProducts 5 }  --停产，定义错误
mp1700		OBJECT IDENTIFIER ::= { mpProducts 7 }
mp2100		OBJECT IDENTIFIER ::= { mpProducts 8 }  --停产
mp2200		OBJECT IDENTIFIER ::= { mpProducts 9 }  --停产
mp2690		OBJECT IDENTIFIER ::= { mpProducts 10 }  --停产
mp5008		OBJECT IDENTIFIER ::= { mpProducts 11 }
mp5016		OBJECT IDENTIFIER ::= { mpProducts 12 }
mp5024		OBJECT IDENTIFIER ::= { mpProducts 13 }
mp5108		OBJECT IDENTIFIER ::= { mpProducts 14 }
mp5116		OBJECT IDENTIFIER ::= { mpProducts 15 }
mp5124		OBJECT IDENTIFIER ::= { mpProducts 16 }
mp5124A		OBJECT IDENTIFIER ::= { mpProducts 17 }
mp5108A		OBJECT IDENTIFIER ::= { mpProducts 18 }
mp5116A		OBJECT IDENTIFIER ::= { mpProducts 19 }
mp4126		OBJECT IDENTIFIER ::= { mpProducts 23 }
mp3126		OBJECT IDENTIFIER ::= { mpProducts 25 }
mp3600		OBJECT IDENTIFIER ::= { mpProducts 26 }
mp3600M		OBJECT IDENTIFIER ::= { mpProducts 27 }
mpBridge	OBJECT IDENTIFIER ::= { mpProducts 28 }	
mp3116		OBJECT IDENTIFIER ::= { mpProducts 29 }	
mp3124		OBJECT IDENTIFIER ::= { mpProducts 30 }	
mp3026G		OBJECT IDENTIFIER ::= { mpProducts 32 }
mp4312G		OBJECT IDENTIFIER ::= { mpProducts 33 }
mp4326G		OBJECT IDENTIFIER ::= { mpProducts 34 }
mp3150		OBJECT IDENTIFIER ::= { mpProducts 36 }
mp2692		OBJECT IDENTIFIER ::= { mpProducts 37 }
mp4396		OBJECT IDENTIFIER ::= { mpProducts 38 }
mp3024		OBJECT IDENTIFIER ::= { mpProducts 39 }
mp2691		OBJECT IDENTIFIER ::= { mpProducts 40 }
mp1761		OBJECT IDENTIFIER ::= { mpProducts 41 }
mp1762		OBJECT IDENTIFIER ::= { mpProducts 42 }
mp801		OBJECT IDENTIFIER ::= { mpProducts 43 }
mp803		OBJECT IDENTIFIER ::= { mpProducts 44 }
mp9800B		OBJECT IDENTIFIER ::= { mpProducts 45 }
mp3680		OBJECT IDENTIFIER ::= { mpProducts 46 }
mp2631		OBJECT IDENTIFIER ::= { mpProducts 47 }
mp2632		OBJECT IDENTIFIER ::= { mpProducts 48 }
mp2692F		OBJECT IDENTIFIER ::= { mpProducts 49 }
mpAC		OBJECT IDENTIFIER ::= { mpProducts 50 }
mp2200B		OBJECT IDENTIFIER ::= { mpProducts 51 }
mp2500B		OBJECT IDENTIFIER ::= { mpProducts 52 }
mp1600B		OBJECT IDENTIFIER ::= { mpProducts 53 }
mp3640B		OBJECT IDENTIFIER ::= { mpProducts 54 }
mp3680E		OBJECT IDENTIFIER ::= { mpProducts 55 }
mp3024B		OBJECT IDENTIFIER ::= { mpProducts 56 }  --MyPower S3024B
mp3016B		OBJECT IDENTIFIER ::= { mpProducts 57 }  --MyPower S3016B
mp3008B		OBJECT IDENTIFIER ::= { mpProducts 58 }  --MyPower S3008B
mp3740          OBJECT IDENTIFIER ::= { mpProducts 66 }
mp3780          OBJECT IDENTIFIER ::= { mpProducts 67 }
mp7204          OBJECT IDENTIFIER ::= { mpProducts 68 }
mp7208          OBJECT IDENTIFIER ::= { mpProducts 69 }
mp4126E         OBJECT IDENTIFIER ::= { mpProducts 70 }  --2004.7.26分配
mpS6803         OBJECT IDENTIFIER ::= { mpProducts 71 }  --2004.7.30分配
mpS6805         OBJECT IDENTIFIER ::= { mpProducts 72 }  --2004.7.30分配
mpS6812         OBJECT IDENTIFIER ::= { mpProducts 73 }  --2004.7.30分配
mp2600E         OBJECT IDENTIFIER ::= { mpProducts 74 }  --2004.8.26分配


END
