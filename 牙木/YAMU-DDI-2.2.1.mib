--
-- YAMU-DDI-2.2.1.mib
-- MIB generated by ddi@ymutech
-- Tue Mar 12 14:33:04 CST 2019
--

	YAMU-DDI-MIB DEFINITIONS ::= BEGIN

		IMPORTS
		MODULE-COMPLIANCE,OBJECT-GROUP, NOTIFICATION-GROUP
				FROM SNMPv2-CONF
		MODULE-IDENTITY,OBJECT-TYPE,NOTIFICATION-TYPE,
		enterprises, IpAddress, Unsigned32,Integer32,Counter32,Gauge32,Counter64
				FROM SNMPv2-SMI
		TEXTUAL-CONVENTION,TruthValue,TimeStamp,DisplayString
				FROM SNMPv2-TC;


		-- .1.3.6.1.4.1.47032
		yamu MODULE-IDENTITY
			LAST-UPDATED "201903121433Z"		--Tue Mar 12 14:33:04 CST 2019
			ORGANIZATION "SHANGHAI YAMU NETWORKS CO.,LTD."
			CONTACT-INFO "yamu@yamu.com"
			DESCRIPTION "Yamu SmartDDI DMS MIB."
			::= { enterprises 47032 }


--
--
-- OBJECT IDENTIFIER definitions
--

		-- .1.3.6.1.4.1.47032.1
		smartDDI OBJECT IDENTIFIER ::= { yamu 1 }
		-- .1.3.6.1.4.1.47032.1.1
		configs OBJECT IDENTIFIER ::= { smartDDI 1 }
		-- .1.3.6.1.4.1.47032.1.2
		stats OBJECT IDENTIFIER ::= { smartDDI 2 }
		-- .1.3.6.1.4.1.47032.1.3
		traps OBJECT IDENTIFIER ::= { smartDDI 3 }
		-- .1.3.6.1.4.1.47032.1.4
		definitions OBJECT IDENTIFIER ::= { smartDDI 4 }

--
-- OBJECT-TYPE definitions
--

		-- .1.3.6.1.4.1.47032.1.4.1
		ddiDefault OBJECT-TYPE
			SYNTAX DisplayString
			MAX-ACCESS read-write
			STATUS current
			DESCRIPTION "Default."
			::= { definitions 1 }

		-- .1.3.6.1.4.1.47032.1.4.2
		ddiDeviceName OBJECT-TYPE
			SYNTAX DisplayString
			MAX-ACCESS read-write
			STATUS current
			DESCRIPTION "DeviceName."
			::= { definitions 2 }

		-- .1.3.6.1.4.1.47032.1.4.3
		ddiDeviceIp OBJECT-TYPE
			SYNTAX IpAddress
			MAX-ACCESS read-write
			STATUS current
			DESCRIPTION "DeviceIp."
			::= { definitions 3 }

		-- .1.3.6.1.4.1.47032.1.4.4
		ddiDeviceQps OBJECT-TYPE
			SYNTAX Integer32
			MAX-ACCESS read-write
			STATUS current
			DESCRIPTION "DeviceQps."
			::= { definitions 4 }

		-- .1.3.6.1.4.1.47032.1.4.5
		ddiIp OBJECT-TYPE
			SYNTAX IpAddress
			MAX-ACCESS read-write
			STATUS current
			DESCRIPTION "Ip."
			::= { definitions 5 }

		-- .1.3.6.1.4.1.47032.1.4.6
		ddiQps OBJECT-TYPE
			SYNTAX Integer32
			MAX-ACCESS read-write
			STATUS current
			DESCRIPTION "Qps."
			::= { definitions 6 }

		-- .1.3.6.1.4.1.47032.1.4.7
		ddiDomain OBJECT-TYPE
			SYNTAX DisplayString
			MAX-ACCESS read-write
			STATUS current
			DESCRIPTION "Domain."
			::= { definitions 7 }

		-- .1.3.6.1.4.1.47032.1.4.8
		ddiDName OBJECT-TYPE
			SYNTAX DisplayString
			MAX-ACCESS read-write
			STATUS current
			DESCRIPTION "DName."
			::= { definitions 8 }

		-- .1.3.6.1.4.1.47032.1.4.9
		ddiDNameType OBJECT-TYPE
			SYNTAX DisplayString
			MAX-ACCESS read-write
			STATUS current
			DESCRIPTION "DNameType."
			::= { definitions 9 }

		-- .1.3.6.1.4.1.47032.1.4.10
		ddiIpExp OBJECT-TYPE
			SYNTAX DisplayString
			MAX-ACCESS read-write
			STATUS current
			DESCRIPTION "IpExp."
			::= { definitions 10 }

		-- .1.3.6.1.4.1.47032.1.4.11
		ddiIpCur OBJECT-TYPE
			SYNTAX DisplayString
			MAX-ACCESS read-write
			STATUS current
			DESCRIPTION "IpCur."
			::= { definitions 11 }

		-- .1.3.6.1.4.1.47032.1.4.12
		ddiCpuUsage OBJECT-TYPE
			SYNTAX Integer32
			MAX-ACCESS read-write
			STATUS current
			DESCRIPTION "CpuUsage."
			::= { definitions 12 }

		-- .1.3.6.1.4.1.47032.1.4.13
		ddiMemoryUsage OBJECT-TYPE
			SYNTAX Integer32
			MAX-ACCESS read-write
			STATUS current
			DESCRIPTION "MemoryUsage."
			::= { definitions 13 }

		-- .1.3.6.1.4.1.47032.1.4.14
		ddiDiskUsage OBJECT-TYPE
			SYNTAX Integer32
			MAX-ACCESS read-write
			STATUS current
			DESCRIPTION "DiskUsage."
			::= { definitions 14 }

		-- .1.3.6.1.4.1.47032.1.4.15
		ddinicFlow OBJECT-TYPE
			SYNTAX Integer32
			MAX-ACCESS read-write
			STATUS current
			DESCRIPTION "nicFlow."
			::= { definitions 15 }

		-- .1.3.6.1.4.1.47032.1.4.16
		ddiProcessName OBJECT-TYPE
			SYNTAX DisplayString
			MAX-ACCESS read-write
			STATUS current
			DESCRIPTION "ProcessName."
			::= { definitions 16 }

		-- .1.3.6.1.4.1.47032.1.4.17
		ddiservfailRate OBJECT-TYPE
			SYNTAX Integer32
			MAX-ACCESS read-write
			STATUS current
			DESCRIPTION "servfailRate."
			::= { definitions 17 }

		-- .1.3.6.1.4.1.47032.1.4.18
		ddiMessage OBJECT-TYPE
			SYNTAX DisplayString
			MAX-ACCESS read-write
			STATUS current
			DESCRIPTION "Message."
			::= { definitions 18 }

		-- .1.3.6.1.4.1.47032.1.4.19
		ddiServerName OBJECT-TYPE
			SYNTAX DisplayString
			MAX-ACCESS read-write
			STATUS current
			DESCRIPTION "ServerName."
			::= { definitions 19 }

		-- .1.3.6.1.4.1.47032.1.4.20
		ddiServerTarget OBJECT-TYPE
			SYNTAX DisplayString
			MAX-ACCESS read-write
			STATUS current
			DESCRIPTION "ServerTarget."
			::= { definitions 20 }

		-- .1.3.6.1.4.1.47032.1.4.21
		ddiDhcpIpPool OBJECT-TYPE
			SYNTAX DisplayString
			MAX-ACCESS read-write
			STATUS current
			DESCRIPTION "DhcpIpPool."
			::= { definitions 21 }

		-- .1.3.6.1.4.1.47032.1.4.22
		ddiDhcpIpUseage OBJECT-TYPE
			SYNTAX Integer32
			MAX-ACCESS read-write
			STATUS current
			DESCRIPTION "DhcpIpUseage."
			::= { definitions 22 }

		-- .1.3.6.1.4.1.47032.1.4.23
		ddiDhcpIpConflict OBJECT-TYPE
			SYNTAX DisplayString
			MAX-ACCESS read-write
			STATUS current
			DESCRIPTION "DhcpIpConflict."
			::= { definitions 23 }

		-- .1.3.6.1.4.1.47032.1.4.24
		ddiDhcpQps OBJECT-TYPE
			SYNTAX IpAddress
			MAX-ACCESS read-write
			STATUS current
			DESCRIPTION "DhcpQps."
			::= { definitions 24 }

		-- .1.3.6.1.4.1.47032.1.4.25
		ddiDhcpIllegalServer OBJECT-TYPE
			SYNTAX DisplayString
			MAX-ACCESS read-write
			STATUS current
			DESCRIPTION "DhcpIllegalServer."
			::= { definitions 25 }

		-- .1.3.6.1.4.1.47032.1.4.26
		ddiDdnsName OBJECT-TYPE
			SYNTAX DisplayString
			MAX-ACCESS read-write
			STATUS current
			DESCRIPTION "DdnsName."
			::= { definitions 26 }

		-- .1.3.6.1.4.1.47032.1.4.27
		ddiHaIp OBJECT-TYPE
			SYNTAX IpAddress
			MAX-ACCESS read-write
			STATUS current
			DESCRIPTION "HaIp."
			::= { definitions 27 }

		-- .1.3.6.1.4.1.47032.1.4.28
		ddiHaVip OBJECT-TYPE
			SYNTAX IpAddress
			MAX-ACCESS read-write
			STATUS current
			DESCRIPTION "HaVip."
			::= { definitions 28 }

		-- .1.3.6.1.4.1.47032.1.4.29
		ddiDataCenter OBJECT-TYPE
			SYNTAX DisplayString
			MAX-ACCESS read-write
			STATUS current
			DESCRIPTION "DataCenter."
			::= { definitions 29 }

		-- .1.3.6.1.4.1.47032.1.4.30
		ddiDelay OBJECT-TYPE
			SYNTAX Integer32
			MAX-ACCESS read-write
			STATUS current
			DESCRIPTION "Delay."
			::= { definitions 30 }

		-- .1.3.6.1.4.1.47032.1.4.31
		ddiForwardIps OBJECT-TYPE
			SYNTAX DisplayString
			MAX-ACCESS read-write
			STATUS current
			DESCRIPTION "ForwardIps."
			::= { definitions 31 }

		-- .1.3.6.1.4.1.47032.1.4.32
		ddiProxyIps OBJECT-TYPE
			SYNTAX DisplayString
			MAX-ACCESS read-write
			STATUS current
			DESCRIPTION "ProxyIps."
			::= { definitions 32 }

		-- .1.3.6.1.4.1.47032.1.4.42
		ddiObjectTypeGroup OBJECT-GROUP
			OBJECTS {
			    ddiDefault,
			    ddiDeviceName,
			    ddiDeviceIp,
			    ddiDeviceQps,
			    ddiIp,
			    ddiQps,
			    ddiDomain,
			    ddiDName,
			    ddiDNameType,
			    ddiIpExp,
			    ddiIpCur,
			    ddiCpuUsage,
			    ddiMemoryUsage,
			    ddiDiskUsage,
			    ddinicFlow,
			    ddiProcessName,
			    ddiservfailRate,
			    ddiMessage,
			    ddiServerName,
			    ddiServerTarget,
			    ddiDhcpIpPool,
			    ddiDhcpIpUseage,
			    ddiDhcpIpConflict,
			    ddiDhcpQps,
			    ddiDhcpIllegalServer,
			    ddiDdnsName,
			    ddiHaIp,
			    ddiHaVip,
			    ddiDataCenter,
			    ddiDelay,
			    ddiForwardIps,
			    ddiProxyIps
			}
			STATUS current
			DESCRIPTION "Description."
			::= { definitions 42 }



--
-- NOTIFICATION-TYPE definitions
--

		-- .1.3.6.1.4.1.47032.1.3.1
		ddiDNSysDeviceQpsOverClearedNotification NOTIFICATION-TYPE
		OBJECTS{
			    ddiDeviceName,
			    ddiDeviceIp,
			    ddiDeviceQps
			}
			STATUS current
			DESCRIPTION "设备QPS清除"
			::= { traps 1 }


		-- .1.3.6.1.4.1.47032.1.3.2
		ddiDNSysDeviceQpsOverAlarmedNotification NOTIFICATION-TYPE
		OBJECTS{
			    ddiDeviceName,
			    ddiDeviceIp,
			    ddiDeviceQps
			}
			STATUS current
			DESCRIPTION "设备QPS产生"
			::= { traps 2 }


		-- .1.3.6.1.4.1.47032.1.3.3
		ddiDNSysDeviceRequestIpOverClearedNotification NOTIFICATION-TYPE
		OBJECTS{
			    ddiDeviceName,
			    ddiDeviceIp,
			    ddiIp,
			    ddiQps
			}
			STATUS current
			DESCRIPTION "设备IP请求清除"
			::= { traps 3 }


		-- .1.3.6.1.4.1.47032.1.3.4
		ddiDNSysDeviceRequestIpOverAlarmedNotification NOTIFICATION-TYPE
		OBJECTS{
			    ddiDeviceName,
			    ddiDeviceIp,
			    ddiIp,
			    ddiQps
			}
			STATUS current
			DESCRIPTION "设备IP请求产生"
			::= { traps 4 }


		-- .1.3.6.1.4.1.47032.1.3.5
		ddiDNSysDeviceDomainQpsOverClearedNotification NOTIFICATION-TYPE
		OBJECTS{
			    ddiDeviceName,
			    ddiDeviceIp,
			    ddiDomain,
			    ddiQps
			}
			STATUS current
			DESCRIPTION "设备域请求QPS清除"
			::= { traps 5 }


		-- .1.3.6.1.4.1.47032.1.3.6
		ddiDNSysDeviceDomainQpsOverAlarmedNotification NOTIFICATION-TYPE
		OBJECTS{
			    ddiDeviceName,
			    ddiDeviceIp,
			    ddiDomain,
			    ddiQps
			}
			STATUS current
			DESCRIPTION "设备域请求QPS产生"
			::= { traps 6 }


		-- .1.3.6.1.4.1.47032.1.3.7
		ddiDNSysDeviceDnameQpsOverClearedNotification NOTIFICATION-TYPE
		OBJECTS{
			    ddiDeviceName,
			    ddiDeviceIp,
			    ddiDName,
			    ddiQps
			}
			STATUS current
			DESCRIPTION "设备域名请求QPS清除"
			::= { traps 7 }


		-- .1.3.6.1.4.1.47032.1.3.8
		ddiDNSysDeviceDnameQpsOverAlarmedNotification NOTIFICATION-TYPE
		OBJECTS{
			    ddiDeviceName,
			    ddiDeviceIp,
			    ddiDName,
			    ddiQps
			}
			STATUS current
			DESCRIPTION "设备域名请求QPS产生"
			::= { traps 8 }


		-- .1.3.6.1.4.1.47032.1.3.9
		ddiDNSysDeviceFocusDomainClearedNotification NOTIFICATION-TYPE
		OBJECTS{
			    ddiDeviceName,
			    ddiDeviceIp,
			    ddiDName,
			    ddiDNameType
			}
			STATUS current
			DESCRIPTION "设备重点域名监控清除"
			::= { traps 9 }


		-- .1.3.6.1.4.1.47032.1.3.10
		ddiDNSysDeviceFocusDomainAlarmedNotification NOTIFICATION-TYPE
		OBJECTS{
			    ddiDeviceName,
			    ddiDeviceIp,
			    ddiDName,
			    ddiDNameType,
			    ddiIpExp,
			    ddiIpCur
			}
			STATUS current
			DESCRIPTION "设备重点域名监控产生"
			::= { traps 10 }


		-- .1.3.6.1.4.1.47032.1.3.11
		ddiDeviceCpuUsageClearedNotification NOTIFICATION-TYPE
		OBJECTS{
			    ddiDeviceName,
			    ddiDeviceIp,
			    ddiDomain
			}
			STATUS current
			DESCRIPTION "CPU清除"
			::= { traps 11 }


		-- .1.3.6.1.4.1.47032.1.3.12
		ddiDeviceCpuUsageAlarmedNotification NOTIFICATION-TYPE
		OBJECTS{
			    ddiDeviceName,
			    ddiDeviceIp,
			    ddiDomain
			}
			STATUS current
			DESCRIPTION "CPU产生"
			::= { traps 12 }


		-- .1.3.6.1.4.1.47032.1.3.13
		ddiDeviceMemoryUsageClearedNotification NOTIFICATION-TYPE
		OBJECTS{
			    ddiDeviceName,
			    ddiDeviceIp,
			    ddiMemoryUsage
			}
			STATUS current
			DESCRIPTION "内存清除"
			::= { traps 13 }


		-- .1.3.6.1.4.1.47032.1.3.14
		ddiDeviceMemoryUsageAlarmedNotification NOTIFICATION-TYPE
		OBJECTS{
			    ddiDeviceName,
			    ddiDeviceIp,
			    ddiMemoryUsage
			}
			STATUS current
			DESCRIPTION "内存产生"
			::= { traps 14 }


		-- .1.3.6.1.4.1.47032.1.3.15
		ddiDevicePartitionUsageClearedNotification NOTIFICATION-TYPE
		OBJECTS{
			    ddiDeviceName,
			    ddiDeviceIp,
			    ddiDiskUsage
			}
			STATUS current
			DESCRIPTION "数据磁盘使用率清除"
			::= { traps 15 }


		-- .1.3.6.1.4.1.47032.1.3.16
		ddiDevicePartitionUsageAlarmedNotification NOTIFICATION-TYPE
		OBJECTS{
			    ddiDeviceName,
			    ddiDeviceIp,
			    ddiDiskUsage
			}
			STATUS current
			DESCRIPTION "数据磁盘使用率产生"
			::= { traps 16 }


		-- .1.3.6.1.4.1.47032.1.3.17
		ddiDeviceNicFlowOverClearedNotification NOTIFICATION-TYPE
		OBJECTS{
			    ddiDeviceName,
			    ddiDeviceIp,
			    ddinicFlow
			}
			STATUS current
			DESCRIPTION "网卡流量清除"
			::= { traps 17 }


		-- .1.3.6.1.4.1.47032.1.3.18
		ddiDeviceNicFlowOverAlarmedNotification NOTIFICATION-TYPE
		OBJECTS{
			    ddiDeviceName,
			    ddiDeviceIp,
			    ddinicFlow
			}
			STATUS current
			DESCRIPTION "网卡流量产生"
			::= { traps 18 }


		-- .1.3.6.1.4.1.47032.1.3.19
		ddiNoneDeviceConnectionClearedNotification NOTIFICATION-TYPE
		OBJECTS{
			    ddiDeviceName,
			    ddiDeviceIp,
			    ddiIp
			}
			STATUS current
			DESCRIPTION "管理口通信清除"
			::= { traps 19 }


		-- .1.3.6.1.4.1.47032.1.3.20
		ddiNoneDeviceConnectionAlarmedNotification NOTIFICATION-TYPE
		OBJECTS{
			    ddiDeviceName,
			    ddiDeviceIp,
			    ddiIp
			}
			STATUS current
			DESCRIPTION "管理口通信产生"
			::= { traps 20 }


		-- .1.3.6.1.4.1.47032.1.3.21
		ddiDeviceProcessClearedNotification NOTIFICATION-TYPE
		OBJECTS{
			    ddiDeviceName,
			    ddiDeviceIp,
			    ddiProcessName
			}
			STATUS current
			DESCRIPTION "业务进程监控清除"
			::= { traps 21 }


		-- .1.3.6.1.4.1.47032.1.3.22
		ddiDeviceProcessAlarmedNotification NOTIFICATION-TYPE
		OBJECTS{
			    ddiDeviceName,
			    ddiDeviceIp,
			    ddiProcessName
			}
			STATUS current
			DESCRIPTION "业务进程监控产生"
			::= { traps 22 }


		-- .1.3.6.1.4.1.47032.1.3.23
		ddiDNSysDeviceServfailOverClearedNotification NOTIFICATION-TYPE
		OBJECTS{
			    ddiDeviceName,
			    ddiDeviceIp,
			    ddiservfailRate
			}
			STATUS current
			DESCRIPTION "设备servfail占比清除"
			::= { traps 23 }


		-- .1.3.6.1.4.1.47032.1.3.24
		ddiDNSysDeviceServfailOverAlarmedNotification NOTIFICATION-TYPE
		OBJECTS{
			    ddiDeviceName,
			    ddiDeviceIp,
			    ddiservfailRate
			}
			STATUS current
			DESCRIPTION "设备servfail占比产生"
			::= { traps 24 }


		-- .1.3.6.1.4.1.47032.1.3.25
		ddiForwardFailClearedNotification NOTIFICATION-TYPE
		OBJECTS{
			    ddiDeviceName,
			    ddiDeviceIp,
			    ddiForwardIps
			}
			STATUS current
			DESCRIPTION "Forward服务器清除"
			::= { traps 25 }


		-- .1.3.6.1.4.1.47032.1.3.26
		ddiForwardFailAlarmedNotification NOTIFICATION-TYPE
		OBJECTS{
			    ddiDeviceName,
			    ddiDeviceIp,
			    ddiForwardIps
			}
			STATUS current
			DESCRIPTION "Forward服务器产生"
			::= { traps 26 }


		-- .1.3.6.1.4.1.47032.1.3.27
		ddiProxyFailClearedNotification NOTIFICATION-TYPE
		OBJECTS{
			    ddiDeviceName,
			    ddiDeviceIp,
			    ddiProxyIps
			}
			STATUS current
			DESCRIPTION "智能调度服务器清除"
			::= { traps 27 }


		-- .1.3.6.1.4.1.47032.1.3.28
		ddiProxyFailAlarmedNotification NOTIFICATION-TYPE
		OBJECTS{
			    ddiDeviceName,
			    ddiDeviceIp,
			    ddiProxyIps
			}
			STATUS current
			DESCRIPTION "智能调度服务器产生"
			::= { traps 28 }


		-- .1.3.6.1.4.1.47032.1.3.29
		ddiServiceFailClearedNotification NOTIFICATION-TYPE
		OBJECTS{
			    ddiDeviceName,
			    ddiDeviceIp
			}
			STATUS current
			DESCRIPTION "业务工作状态清除"
			::= { traps 29 }


		-- .1.3.6.1.4.1.47032.1.3.30
		ddiServiceFailAlarmedNotification NOTIFICATION-TYPE
		OBJECTS{
			    ddiDeviceName,
			    ddiDeviceIp
			}
			STATUS current
			DESCRIPTION "业务工作状态产生"
			::= { traps 30 }


		-- .1.3.6.1.4.1.47032.1.3.31
		ddiDiskFailClearedNotification NOTIFICATION-TYPE
		OBJECTS{
			    ddiDeviceName,
			    ddiDeviceIp
			}
			STATUS current
			DESCRIPTION "硬盘状态清除"
			::= { traps 31 }


		-- .1.3.6.1.4.1.47032.1.3.32
		ddiDiskFailAlarmedNotification NOTIFICATION-TYPE
		OBJECTS{
			    ddiDeviceName,
			    ddiDeviceIp
			}
			STATUS current
			DESCRIPTION "硬盘状态产生"
			::= { traps 32 }


		-- .1.3.6.1.4.1.47032.1.3.34
		ddiLogAlarmedNotification NOTIFICATION-TYPE
		OBJECTS{
			    ddiDeviceName,
			    ddiDeviceIp,
			    ddiMessage
			}
			STATUS current
			DESCRIPTION "通用告警产生"
			::= { traps 34 }


		-- .1.3.6.1.4.1.47032.1.3.33
		ddiLogClearedNotification NOTIFICATION-TYPE
		OBJECTS{
			    ddiDeviceName,
			    ddiDeviceIp,
			    ddiMessage
			}
			STATUS current
			DESCRIPTION "通用告警清除"
			::= { traps 33 }


		-- .1.3.6.1.4.1.47032.1.3.35
		ddiRecordialFailClearedNotification NOTIFICATION-TYPE
		OBJECTS{
			    ddiDeviceName,
			    ddiDeviceIp,
			    ddiDName,
			    ddiIp
			}
			STATUS current
			DESCRIPTION "授权域名监测清除"
			::= { traps 35 }


		-- .1.3.6.1.4.1.47032.1.3.36
		ddiRecordialFailAlarmedNotification NOTIFICATION-TYPE
		OBJECTS{
			    ddiDeviceName,
			    ddiDeviceIp,
			    ddiDName,
			    ddiIp
			}
			STATUS current
			DESCRIPTION "授权域名监测产生"
			::= { traps 36 }


		-- .1.3.6.1.4.1.47032.1.3.37
		ddiRedirectFailClearedNotification NOTIFICATION-TYPE
		OBJECTS{
			    ddiDeviceName,
			    ddiDeviceIp,
			    ddiIp
			}
			STATUS current
			DESCRIPTION "重定向服务器清除"
			::= { traps 37 }


		-- .1.3.6.1.4.1.47032.1.3.38
		ddiRedirectFailAlarmedNotification NOTIFICATION-TYPE
		OBJECTS{
			    ddiDeviceName,
			    ddiDeviceIp,
			    ddiIp
			}
			STATUS current
			DESCRIPTION "重定向服务器产生"
			::= { traps 38 }


		-- .1.3.6.1.4.1.47032.1.3.39
		ddiNginxServerFailClearedNotification NOTIFICATION-TYPE
		OBJECTS{
			    ddiDeviceName,
			    ddiDeviceIp,
			    ddiServerName,
			    ddiServerTarget
			}
			STATUS current
			DESCRIPTION "URL转发监控清除"
			::= { traps 39 }


		-- .1.3.6.1.4.1.47032.1.3.40
		ddiNginxServerFailAlarmedNotification NOTIFICATION-TYPE
		OBJECTS{
			    ddiDeviceName,
			    ddiDeviceIp,
			    ddiServerName,
			    ddiServerTarget
			}
			STATUS current
			DESCRIPTION "URL转发监控产生"
			::= { traps 40 }


		-- .1.3.6.1.4.1.47032.1.3.41
		ddiDhcpPoolClearedNotification NOTIFICATION-TYPE
		OBJECTS{
			    ddiDeviceName,
			    ddiDeviceIp,
			    ddiDhcpIpPool,
			    ddiDhcpIpUseage
			}
			STATUS current
			DESCRIPTION "DHCP使用率告警清除"
			::= { traps 41 }


		-- .1.3.6.1.4.1.47032.1.3.42
		ddiDhcpPoolAlarmedNotification NOTIFICATION-TYPE
		OBJECTS{
			    ddiDeviceName,
			    ddiDeviceIp,
			    ddiDhcpIpPool,
			    ddiDhcpIpUseage
			}
			STATUS current
			DESCRIPTION "DHCP使用率告警产生"
			::= { traps 42 }


		-- .1.3.6.1.4.1.47032.1.3.43
		ddiDhcpIpAddressConflictsClearedNotification NOTIFICATION-TYPE
		OBJECTS{
			    ddiDeviceName,
			    ddiDeviceIp,
			    ddiDhcpIpConflict
			}
			STATUS current
			DESCRIPTION "地址冲突告警清除"
			::= { traps 43 }


		-- .1.3.6.1.4.1.47032.1.3.44
		ddiDhcpIpAddressConflictsAlarmedNotification NOTIFICATION-TYPE
		OBJECTS{
			    ddiDeviceName,
			    ddiDeviceIp,
			    ddiDhcpIpConflict
			}
			STATUS current
			DESCRIPTION "地址冲突告警产生"
			::= { traps 44 }


		-- .1.3.6.1.4.1.47032.1.3.45
		ddiDhcpQpsClearedNotification NOTIFICATION-TYPE
		OBJECTS{
			    ddiDeviceName,
			    ddiDeviceIp,
			    ddiDhcpQps
			}
			STATUS current
			DESCRIPTION "DHCP访问量告警清除"
			::= { traps 45 }


		-- .1.3.6.1.4.1.47032.1.3.46
		ddiDhcpQpsAlarmedNotification NOTIFICATION-TYPE
		OBJECTS{
			    ddiDeviceName,
			    ddiDeviceIp,
			    ddiDhcpQps
			}
			STATUS current
			DESCRIPTION "DHCP访问量告警产生"
			::= { traps 46 }


		-- .1.3.6.1.4.1.47032.1.3.47
		ddiDhcpIlegalServerClearedNotification NOTIFICATION-TYPE
		OBJECTS{
			    ddiDeviceName,
			    ddiDeviceIp,
			    ddiDhcpIllegalServer
			}
			STATUS current
			DESCRIPTION "非法DHCP服务器清除"
			::= { traps 47 }


		-- .1.3.6.1.4.1.47032.1.3.48
		ddiDhcpIlegalServerAlarmedNotification NOTIFICATION-TYPE
		OBJECTS{
			    ddiDeviceName,
			    ddiDeviceIp,
			    ddiDhcpIllegalServer
			}
			STATUS current
			DESCRIPTION "非法DHCP服务器产生"
			::= { traps 48 }


		-- .1.3.6.1.4.1.47032.1.3.49
		ddiDDNSClearedNotification NOTIFICATION-TYPE
		OBJECTS{
			    ddiDeviceName,
			    ddiDeviceIp,
			    ddiDdnsName
			}
			STATUS current
			DESCRIPTION "DDNS配置告警清除"
			::= { traps 49 }


		-- .1.3.6.1.4.1.47032.1.3.50
		ddiDDNSAlarmedNotification NOTIFICATION-TYPE
		OBJECTS{
			    ddiDeviceName,
			    ddiDeviceIp,
			    ddiDdnsName
			}
			STATUS current
			DESCRIPTION "DDNS配置告警产生"
			::= { traps 50 }


		-- .1.3.6.1.4.1.47032.1.3.51
		ddiHostHaClearedNotification NOTIFICATION-TYPE
		OBJECTS{
			    ddiDeviceName,
			    ddiDeviceIp
			}
			STATUS current
			DESCRIPTION "业务口通信清除"
			::= { traps 51 }


		-- .1.3.6.1.4.1.47032.1.3.52
		ddiHostHaAlarmedNotification NOTIFICATION-TYPE
		OBJECTS{
			    ddiDeviceName,
			    ddiDeviceIp
			}
			STATUS current
			DESCRIPTION "业务口通信产生"
			::= { traps 52 }


		-- .1.3.6.1.4.1.47032.1.3.54
		ddiDnSConfigAlarmedNotification NOTIFICATION-TYPE
		OBJECTS{
			    ddiDeviceName,
			    ddiDeviceIp,
			    ddiMessage
			}
			STATUS current
			DESCRIPTION "DNS配置下发产生"
			::= { traps 54 }


		-- .1.3.6.1.4.1.47032.1.3.56
		ddiDhcpConfigAlarmedNotification NOTIFICATION-TYPE
		OBJECTS{
			    ddiDeviceName,
			    ddiDeviceIp,
			    ddiMessage
			}
			STATUS current
			DESCRIPTION "DHCP配置下发产生"
			::= { traps 56 }


		-- .1.3.6.1.4.1.47032.1.3.58
		ddiDialConfigAlarmedNotification NOTIFICATION-TYPE
		OBJECTS{
			    ddiDeviceName,
			    ddiDeviceIp,
			    ddiMessage
			}
			STATUS current
			DESCRIPTION "健康检查配置下发产生"
			::= { traps 58 }


		-- .1.3.6.1.4.1.47032.1.3.60
		ddiFlowexportAlarmedNotification NOTIFICATION-TYPE
		OBJECTS{
			    ddiDeviceName,
			    ddiDeviceIp,
			    ddiMessage
			}
			STATUS current
			DESCRIPTION "授权统计配置下发产生"
			::= { traps 60 }


		-- .1.3.6.1.4.1.47032.1.3.61
		ddiDnsRecordExpiredClearedNotification NOTIFICATION-TYPE
		OBJECTS{
			    ddiDeviceName,
			    ddiDeviceIp,
			    ddiDName,
			    ddiIp
			}
			STATUS current
			DESCRIPTION "授权记录老化告警清除"
			::= { traps 61 }


		-- .1.3.6.1.4.1.47032.1.3.62
		ddiDnsRecordExpiredAlarmedNotification NOTIFICATION-TYPE
		OBJECTS{
			    ddiDeviceName,
			    ddiDeviceIp,
			    ddiDName,
			    ddiIp
			}
			STATUS current
			DESCRIPTION "授权记录老化告警产生"
			::= { traps 62 }


		-- .1.3.6.1.4.1.47032.1.3.64
		ddiYrDnsConfigAlarmedNotification NOTIFICATION-TYPE
		OBJECTS{
			    ddiDeviceName,
			    ddiDeviceIp,
			    ddiMessage
			}
			STATUS current
			DESCRIPTION "YRDNS配置下发产生"
			::= { traps 64 }


		-- .1.3.6.1.4.1.47032.1.3.65
		ddiDDOSClearedNotification NOTIFICATION-TYPE
		OBJECTS{
			    ddiDeviceName,
			    ddiDeviceIp,
			    ddiMessage
			}
			STATUS current
			DESCRIPTION "设备DDOS告警清除"
			::= { traps 65 }


		-- .1.3.6.1.4.1.47032.1.3.66
		ddiDDOSAlarmedNotification NOTIFICATION-TYPE
		OBJECTS{
			    ddiDeviceName,
			    ddiDeviceIp,
			    ddiMessage
			}
			STATUS current
			DESCRIPTION "设备DDOS告警产生"
			::= { traps 66 }


		-- .1.3.6.1.4.1.47032.1.3.69
		ddiZoneSyncClearedNotification NOTIFICATION-TYPE
		OBJECTS{
			    ddiDeviceName,
			    ddiDeviceIp
			}
			STATUS current
			DESCRIPTION "授权域同步清除"
			::= { traps 69 }


		-- .1.3.6.1.4.1.47032.1.3.75
		ddiDDOSATTACKDNSClearedNotification NOTIFICATION-TYPE
		OBJECTS{
			    ddiDeviceName,
			    ddiDeviceIp,
			    ddiMessage
			}
			STATUS current
			DESCRIPTION "DNS DDOS攻击告警清除"
			::= { traps 75 }


		-- .1.3.6.1.4.1.47032.1.3.76
		ddiDDOSATTACKDNSAlarmedNotification NOTIFICATION-TYPE
		OBJECTS{
			    ddiDeviceName,
			    ddiDeviceIp,
			    ddiMessage
			}
			STATUS current
			DESCRIPTION "DNS DDOS攻击告警产生"
			::= { traps 76 }


		-- .1.3.6.1.4.1.47032.1.3.73
		ddiDDOSATTACKUDPClearedNotification NOTIFICATION-TYPE
		OBJECTS{
			    ddiDeviceName,
			    ddiDeviceIp,
			    ddiMessage
			}
			STATUS current
			DESCRIPTION "UDP DDOS攻击告警清除"
			::= { traps 73 }


		-- .1.3.6.1.4.1.47032.1.3.74
		ddiDDOSATTACKUDPAlarmedNotification NOTIFICATION-TYPE
		OBJECTS{
			    ddiDeviceName,
			    ddiDeviceIp,
			    ddiMessage
			}
			STATUS current
			DESCRIPTION "UDP DDOS攻击告警产生"
			::= { traps 74 }


		-- .1.3.6.1.4.1.47032.1.3.71
		ddiDDOSATTACKTCPClearedNotification NOTIFICATION-TYPE
		OBJECTS{
			    ddiDeviceName,
			    ddiDeviceIp,
			    ddiMessage
			}
			STATUS current
			DESCRIPTION "TCP DDOS攻击告警清除"
			::= { traps 71 }


		-- .1.3.6.1.4.1.47032.1.3.72
		ddiDDOSATTACKTCPAlarmedNotification NOTIFICATION-TYPE
		OBJECTS{
			    ddiDeviceName,
			    ddiDeviceIp,
			    ddiMessage
			}
			STATUS current
			DESCRIPTION "TCP DDOS攻击告警产生"
			::= { traps 72 }


		-- .1.3.6.1.4.1.47032.1.3.77
		ddiDataCenterDialFailClearedNotification NOTIFICATION-TYPE
		OBJECTS{
			    ddiDeviceName,
			    ddiDeviceIp,
			    ddiDataCenter
			}
			STATUS current
			DESCRIPTION "数据中心链路清除"
			::= { traps 77 }


		-- .1.3.6.1.4.1.47032.1.3.78
		ddiDataCenterDialFailAlarmedNotification NOTIFICATION-TYPE
		OBJECTS{
			    ddiDeviceName,
			    ddiDeviceIp,
			    ddiDataCenter
			}
			STATUS current
			DESCRIPTION "数据中心链路产生"
			::= { traps 78 }


		-- .1.3.6.1.4.1.47032.1.3.80
		ddiFocusDomainChangeAlarmedNotification NOTIFICATION-TYPE
		OBJECTS{
			    ddiDeviceName,
			    ddiDeviceIp
			}
			STATUS current
			DESCRIPTION "重点域名变更产生"
			::= { traps 80 }


		-- .1.3.6.1.4.1.47032.1.3.82
		ddiIpRecycleAlarmedNotification NOTIFICATION-TYPE
		OBJECTS{
			    ddiDeviceName,
			    ddiDeviceIp,
			    ddiMessage
			}
			STATUS current
			DESCRIPTION "IP地址回收提醒产生"
			::= { traps 82 }

		-- .1.3.6.1.4.1.47032.1.3.99
		ddiNotificationGroup NOTIFICATION-GROUP
			NOTIFICATIONS {
			    ddiDNSysDeviceQpsOverClearedNotification,
			    ddiDNSysDeviceQpsOverAlarmedNotification,
			    ddiDNSysDeviceRequestIpOverClearedNotification,
			    ddiDNSysDeviceRequestIpOverAlarmedNotification,
			    ddiDNSysDeviceDomainQpsOverClearedNotification,
			    ddiDNSysDeviceDomainQpsOverAlarmedNotification,
			    ddiDNSysDeviceDnameQpsOverClearedNotification,
			    ddiDNSysDeviceDnameQpsOverAlarmedNotification,
			    ddiDNSysDeviceFocusDomainClearedNotification,
			    ddiDNSysDeviceFocusDomainAlarmedNotification,
			    ddiDeviceCpuUsageClearedNotification,
			    ddiDeviceCpuUsageAlarmedNotification,
			    ddiDeviceMemoryUsageClearedNotification,
			    ddiDeviceMemoryUsageAlarmedNotification,
			    ddiDevicePartitionUsageClearedNotification,
			    ddiDevicePartitionUsageAlarmedNotification,
			    ddiDeviceNicFlowOverClearedNotification,
			    ddiDeviceNicFlowOverAlarmedNotification,
			    ddiNoneDeviceConnectionClearedNotification,
			    ddiNoneDeviceConnectionAlarmedNotification,
			    ddiDeviceProcessClearedNotification,
			    ddiDeviceProcessAlarmedNotification,
			    ddiDNSysDeviceServfailOverClearedNotification,
			    ddiDNSysDeviceServfailOverAlarmedNotification,
			    ddiForwardFailClearedNotification,
			    ddiForwardFailAlarmedNotification,
			    ddiProxyFailClearedNotification,
			    ddiProxyFailAlarmedNotification,
			    ddiServiceFailClearedNotification,
			    ddiServiceFailAlarmedNotification,
			    ddiDiskFailClearedNotification,
			    ddiDiskFailAlarmedNotification,
			    ddiLogAlarmedNotification,
			    ddiLogClearedNotification,
			    ddiRecordialFailClearedNotification,
			    ddiRecordialFailAlarmedNotification,
			    ddiRedirectFailClearedNotification,
			    ddiRedirectFailAlarmedNotification,
			    ddiNginxServerFailClearedNotification,
			    ddiNginxServerFailAlarmedNotification,
			    ddiDhcpPoolClearedNotification,
			    ddiDhcpPoolAlarmedNotification,
			    ddiDhcpIpAddressConflictsClearedNotification,
			    ddiDhcpIpAddressConflictsAlarmedNotification,
			    ddiDhcpQpsClearedNotification,
			    ddiDhcpQpsAlarmedNotification,
			    ddiDhcpIlegalServerClearedNotification,
			    ddiDhcpIlegalServerAlarmedNotification,
			    ddiDDNSClearedNotification,
			    ddiDDNSAlarmedNotification,
			    ddiHostHaClearedNotification,
			    ddiHostHaAlarmedNotification,
			    ddiDnSConfigAlarmedNotification,
			    ddiDhcpConfigAlarmedNotification,
			    ddiDialConfigAlarmedNotification,
			    ddiFlowexportAlarmedNotification,
			    ddiDnsRecordExpiredClearedNotification,
			    ddiDnsRecordExpiredAlarmedNotification,
			    ddiYrDnsConfigAlarmedNotification,
			    ddiDDOSClearedNotification,
			    ddiDDOSAlarmedNotification,
			    ddiZoneSyncClearedNotification,
			    ddiDDOSATTACKDNSClearedNotification,
			    ddiDDOSATTACKDNSAlarmedNotification,
			    ddiDDOSATTACKUDPClearedNotification,
			    ddiDDOSATTACKUDPAlarmedNotification,
			    ddiDDOSATTACKTCPClearedNotification,
			    ddiDDOSATTACKTCPAlarmedNotification,
			    ddiDataCenterDialFailClearedNotification,
			    ddiDataCenterDialFailAlarmedNotification,
			    ddiFocusDomainChangeAlarmedNotification,
			    ddiIpRecycleAlarmedNotification
			}
			STATUS current
			DESCRIPTION "Description."
			::= { traps 99 }



	END

--
-- YAMU-DDI-2.2.1.mib
--
