CAPABILITY-ZXR10-MSTP-MIB DEFINITIONS ::= BEGIN
        IMPORTS
            ifIndex            
                FROM RFC1213-MIB            
            Unsigned32, OBJECT-TYPE, MODULE-IDENTITY            
                FROM SNMPv2-SMI            
            TEXTUAL-CONVENTION, RowStatus            
                FROM SNMPv2-TC            
            MODULE-COMPLIANCE, OBJECT-GROUP, NOTIFICATION-GROUP, AGENT-CAPABILITIES
                FROM SNMPv2-CONF
            zxr10,zxr10RosngMIB,zxr10RosngAgentCapability
                FROM ZXR10-SMI;
    
        -- 1.3.6.1.4.1.3902.3.6000.1000.127
        zxr10mstpMIBCapability MODULE-IDENTITY 
            LAST-UPDATED "201807051600Z"        
            ORGANIZATION 
                "ZTE Corporation"
            CONTACT-INFO 
                "ZTE Corporation
                
                Nanjing Institute of ZTE Corporation
                
                No.68 ZiJinghua Rd. YuHuatai District, Nanjing, China
                
                Tel: +86-25-52870000"
            DESCRIPTION 
                "ZXROSNG 30R2 MSTP MIB"
            REVISION "201807051600Z"        
            DESCRIPTION 
                "Add capability of ZXR10-MSTP-MIB."
            ::= { zxr10RosngAgentCapability 127 } 

    -- =============================
    -- 1. zxr10mstpMIBCapabilityCommon 
    -- =============================
    -- 1.3.6.1.4.1.3902.3.6000.1000.127.1
    -- capabilities for old MIB
    zxr10mstpMIBCapabilityCommon AGENT-CAPABILITIES  
    PRODUCT-RELEASE "ASR,ZSRV2,6100,6500,6700,59,5960,89,99,7000,8700,9700,NR8000,15K,MCG-5000,vRouter,vBRAS-C,VDC"          
    STATUS          current
    DESCRIPTION
                    "ZXR10-MSTP-MIB capabilities for common products"
    SUPPORTS        ZXR10-MSTP-MIB
    INCLUDES        {zxr10MstpGlobalParaGrp,
                     zxr10MstpInstanceGrp,
                     zxr10MstpPortGrp,
                     zxr10MstpPortInstanceGrp}
    ::= { zxr10mstpMIBCapability 1 }

    -- =============================
    -- 2. zxr10mstpMIBCapabilityFNC600 
    -- =============================
    -- 1.3.6.1.4.1.3902.3.6000.1000.127.2
    -- capabilities for C600
    zxr10mstpMIBCapabilityC600 AGENT-CAPABILITIES  
    PRODUCT-RELEASE "C600"          
    STATUS          current
    DESCRIPTION
                    "ZXR10-MSTP-MIB capabilities for C600"
    SUPPORTS        ZXR10-MSTP-MIB
    INCLUDES        {zxr10MstpTransparentStateGrp,
                     zxr10MstpGlobalCfgGrp,
                     zxr10MstpGlblCiscoDigestAdaptGrp,
                     zxr10MstpMstCfgGrp,
                     zxr10MstpMstHMD5Grp,
                     zxr10MstpInstCfgGrp,
                     zxr10MstpMacFlushFastGrp,
                     zxr10MstpPortCfgGrp,
                     zxr10MstpPortBpduGuardGrp,
                     zxr10MstpPortCiscoDigestAdaptGrp,
                     zxr10MstpPortVplsSubIfNotifyGrp,
                     zxr10MstpPortBpduGrp,
                     zxr10MstpPortInstCfgGrp,
                     zxr10MstpPortMcheckGrp,
                     zxr10MstpInstanceStateGrp,
                     zxr10MstpPortInstanceStateGrp,
                     zxr10MstpGlobalParaGrp,
                     zxr10MstpInstanceGrp,
                     zxr10MstpPortGrp,
                     zxr10MstpPortInstanceGrp}
    ::= { zxr10mstpMIBCapability 2 }



END
