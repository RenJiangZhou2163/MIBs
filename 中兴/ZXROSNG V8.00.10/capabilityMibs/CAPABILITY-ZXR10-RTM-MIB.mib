CAPABILITY-ZXR10-RTM-MIB DEFINITIONS ::= BEGIN

    IMPORTS
        MODULE-IDENTITY, OBJECT-TYPE,
        Integer32, Unsigned32, Integer32, enterprises, IpAddress
                FROM SNMPv2-SMI
        Ipv6Address
                FROM IPV6-TC
        RowStatus,DisplayString                           
                FROM SNMPv2-TC
        MODULE-COMPLIANCE, OBJECT-GROUP, NOTIFICATION-GROUP, AGENT-CAPABILITIES
                FROM SNMPv2-CONF
        zxr10,zxr10RosngMIB,zxr10RosngAgentCapability
                FROM ZXR10-SMI;

    zxr10RtmMIBCapability MODULE-IDENTITY
        LAST-UPDATED    "201707012000Z"
        ORGANIZATION    "ZTE Corp."
        CONTACT-INFO
                        "luo.lei1@zte.com.cn"
        DESCRIPTION 
                        "This MIB module provides commonly used textual 
                        conventions for RTM. "
                            
        REVISION     "201707012000Z"    --2017/07/01 20:00
        DESCRIPTION  "Add forward route table." 

        REVISION        "201701052000Z"
        DESCRIPTION     "Add capability of ZXR10-RTM-MIB."
        ::= { zxr10RosngAgentCapability 608 }

    -- =============================
    -- 1. zxr10RtmMIBCapabilityT8000 
    -- =============================
    -- 1.3.6.1.4.1.3902.3.6000.1000.608.1
    zxr10RtmMIBCapabilityT8000 AGENT-CAPABILITIES  
    PRODUCT-RELEASE "T8000"          
    STATUS          current
    DESCRIPTION
                    "ZXR10-RTM-MIB capabilities for T8000"
    SUPPORTS        ZXR10-RTM-MIB
    INCLUDES        {
                        zxr10RtmLdshWtrGroup, 
                        zxr10RtmLdshHashScrambleGroup, 
                        zxr10RtmLdshBandUnawareGroup,
                        zxr10RtmFibResGroup,
                        zxr10RtmLdshFieldGroup,
                        zxr10RtmLdshKeyGroup,
                        zxr10RtmLdshHashAlgorithmGroup,
                        zxr10RtmMplsLdshHashFieldGroup,
                        zxr10RtmIpFrrGroup,
                        zxr10RtmMplsIfGroup,
                        zxr10RtmIPv4RouteGroup,
                        zxr10RtmIPv6RouteGroup
                    }

    VARIATION       zxr10RtmLdshHashFieldL3Src
    ACCESS          not-implemented
    DESCRIPTION     "Not support to config L3Src of LDSH hash fields."
    ::= { zxr10RtmMIBCapability 1 }
END
