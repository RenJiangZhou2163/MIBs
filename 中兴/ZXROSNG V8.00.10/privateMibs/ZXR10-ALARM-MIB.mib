-- *****************************************************************
-- ALARM-MIB.mib 
-- zhongyan
-- 2008-3-15 9:35
-- 
--
-- Copyright (c) 1985-2008 by ZTE Corp.
-- All rights reserved.
-- *****************************************************************
--
ZXR10-ALARM-MIB DEFINITIONS ::= BEGIN
    
IMPORTS
        MODULE-IDENTITY, OBJECT-TYPE,
        Integer32, NOTIFICATION-TYPE,enterprises, Unsigned32
                FROM SNMPv2-SMI
        DisplayString,TEXTUAL-CONVENTION,RowStatus
                FROM SNMPv2-TC
        OBJECT-GROUP, NOTIFICATION-GROUP
                FROM SNMPv2-CONF;
  
    zxr10AlarmMIB MODULE-IDENTITY
        LAST-UPDATED "201812120000Z"
        ORGANIZATION "ZTE Corp."
        CONTACT-INFO
               "ZTE"
        DESCRIPTION 
                "The MIB module to describe the Alarm."

        REVISION "201812120000Z"
        DESCRIPTION
                "Add enum value fiveMinutes to AlarmThAlmPeriod."

        REVISION "201809170000Z"
        DESCRIPTION
                "Add curAlarmNeedConfirm to curAlarmTable.
                Add notificationNeedConfirm to notificationTable.
                 Add zxr10AlmTrapConfirmCfg.
                 Add zxr10AlmTrapConfirmOpt."

        REVISION "201809050000Z"
        DESCRIPTION
               "add curAlarmOccuredMs, curAlarmUpdatedMs and curAlarmDisappearedMs to CurAlarmEntry,
                add hisAlarmOccuredMs, hisAlarmUpdatedMs and hisAlarmDisappearedMs to HisAlarmEntry,
                add notificationAlmOccuredMs to NotificationEntry,
                add globalAlarmOccuredMs, globalAlarmUpdatedMs and globalAlarmDisappearedMs to GlobalAlarmTrapEntry,
                add curAlarmOccuredMs, curAlarmUpdatedMs and curAlarmDisappearedMs to curAlarmTrap,
                add notificationAlmOccuredMs to notificationTrap."        
        REVISION "201808020000Z"
        DESCRIPTION
                "Modify length of curAlarmParaValue, hisAlarmParaValue, notificationAlmParaType and globalAlarmParaValue from 769 to 1537,
                 Modify length of curAlarmDescription, hisAlarmDescription, notificationAlmParaValue and globalAlarmDescription from 256 to 512."
        REVISION "201802080000Z"
        DESCRIPTION
                "Add zxr10AlmShdProfTable, zxr10AlmShdProfCodeTable and zxr10AlmShdProfApplyTable."
        REVISION "201709050000Z"
        DESCRIPTION
                "Add alarmLevelChangeRowStatus to AlarmLevelChangeEntry."
        REVISION "201705270000Z"
        DESCRIPTION
                "Add alarmHeartBeatGlobalObjects and alarmHeartBeatNotification."
        REVISION "201512310000Z"
        DESCRIPTION
                "Modify length of Tpid to 'from 62 to 128',
                add curAlarmTPIDLen, curAlarmTPIDLenSwitchFrom and curAlarmTPIDLenSwitchTo to CurAlarmEntry,
                add hisAlarmTPIDLen, hisAlarmTPIDLenSwitchFrom and hisAlarmTPIDLenSwitchTo to HisAlarmEntry,
                add notificationTPIDLen to NotificationEntry,
                add globalAlarmTPIDLen, globalAlarmTPIDLenSwitchFrom and globalAlarmTPIDLenSwitchTo to GlobalAlarmTrapEntry,
                add curAlarmTPIDLen, curAlarmTPIDLenSwitchFrom and curAlarmTPIDLenSwitchTo to curAlarmTrap,
                add notificationTPIDLen to notificationTrap,
                obsolete alarmMaskTable,
                add zxr10AlarmMaskTable,
                modify description of all node, capital first letter and add punctuation at end."
        REVISION "201511130000Z"
        DESCRIPTION
                "Modify length of curAlarmNetID, hisAlarmNetID and notificationAlmNetID from 32 to 64."
        REVISION "201510201033Z"
        DESCRIPTION
                "Add enum value of AlarmThAlmType."
        REVISION "201502270000Z"
        DESCRIPTION
                "Modify description of notificationAlmLevel, 
                globalAlarmOccuredTime, globalAlarmDisappearedTime
                and globalAlarmUpdatedTime."
        REVISION "201409040000Z"
        DESCRIPTION
                "Modify description of curAlarmTrap and notificationTrap."
        REVISION "201404150000Z"
        DESCRIPTION
                "Add alarmShieldTable."
        REVISION "201311260000Z"
        DESCRIPTION
                "Obsolete alarmLevelTable,
                add alarmLevelChangeTable." 
        REVISION "201307260000Z"
        DESCRIPTION
                "Add preload trap." 
        REVISION "201307100000Z"
        DESCRIPTION
                "Add alarm mask table and timestamp node, 
                modify alarmClearStatus node attribute."        
        REVISION "201304100000Z"
        DESCRIPTION
                "Add alarm node."
        REVISION "200905200000Z"
        DESCRIPTION
                "zxr10AlarmMIB."
        ::= { zxr10 302 }

    zte OBJECT IDENTIFIER ::= { enterprises 3902 }
    zxr10 OBJECT IDENTIFIER ::= { zte 3}
    
    
AlarmClass ::= TEXTUAL-CONVENTION
       STATUS       current
       DESCRIPTION "Enum for alarm class."
       SYNTAX       INTEGER
                     { 
                       commonAlarm(1),                       
                       digitalThresholdCrossingAlarm(2),
                       analogThresholdCrossingAlarm(3),
                       switchEvent(4),
                       commonEvent(5)
                     }
                     
AlarmLevel ::= TEXTUAL-CONVENTION
       STATUS       current
       DESCRIPTION "Enum for alarm level."
       SYNTAX       INTEGER
                     {
                        emergency(1),
                        alert(2),
                        critical(3),
                        error(4),
                        warning(5),
                        notification(6),
                        information(7),
                        debugging(8),
                        all(255)
                      }
                      
                      
AlarmMaskStatus ::= TEXTUAL-CONVENTION
       STATUS       current
       DESCRIPTION "Enum for alarm mask status."
       SYNTAX       INTEGER
                     { 
                         mask(1),
                         unmask(2)
                     }                      

                    
Tpid ::= TEXTUAL-CONVENTION
       STATUS       current
       DESCRIPTION "An octet string containing TPID information."
       SYNTAX       OCTET STRING (SIZE (62..128)) 
       
AlarmType ::= TEXTUAL-CONVENTION
       STATUS       current
       DESCRIPTION "Enum for alarm type."
       SYNTAX       INTEGER
                     {
                        atCommunicationsalarm(0),
                        atQosalarm(1),
                        atEquipmentalarm(2),
                        atProcessingerroralarm(3),
                        atEnvironmentalalarm(4),
                        atAll(255)
                      }
                      
AlarmStatus ::= TEXTUAL-CONVENTION
       STATUS       current
       DESCRIPTION "Enum for alarm status."
       SYNTAX       INTEGER
                     { 
                         disappeared(0),
                         occured(1),
                         updated(2)
                     } 
 
AlarmParaValue ::= TEXTUAL-CONVENTION
       STATUS       current
       DESCRIPTION "An octet string containing Alarm ParaValue information."
       SYNTAX       OCTET STRING (SIZE (1537))


AlarmDescription ::= TEXTUAL-CONVENTION
       STATUS       current
       DESCRIPTION "An octet string containing Alarm Description information."
       SYNTAX       OCTET STRING (SIZE (512))
       
TPIDMemberType ::= TEXTUAL-CONVENTION
       STATUS       current
       DESCRIPTION "An octet string containing TPID member type information."
       SYNTAX       OCTET STRING (SIZE (0..10)) 
       
TPIDMemberName ::= TEXTUAL-CONVENTION
       STATUS       current
       DESCRIPTION "An octet string containing TPID member name information."
       SYNTAX       OCTET STRING (SIZE (0..512))      
              
AlarmComment ::= TEXTUAL-CONVENTION
       STATUS       current
       DESCRIPTION "An octet string containing Alarm Comment information."
       SYNTAX       OCTET STRING (SIZE (256))  

AlarmNetID ::= TEXTUAL-CONVENTION
       STATUS       current
       DESCRIPTION "An octet string containing Alarm NetID."
       SYNTAX       OCTET STRING (SIZE (64)) 
       
AlarmInterface ::= TEXTUAL-CONVENTION
       STATUS       current
       DESCRIPTION "An octet string containing Alarm Interface information."
       SYNTAX       OCTET STRING (SIZE (32)) 
       
       
AlarmThAlmPeriod ::= TEXTUAL-CONVENTION
       STATUS       current
       DESCRIPTION "Enum for alarm period."
       SYNTAX       INTEGER
                      {
                        fiveMinutes(5),
                        fifteenMinutes(15),
                        twentyFourHours(24),
                        invalid(254)
                      }
                      
                      
AlarmThAlmType ::= TEXTUAL-CONVENTION
       STATUS       current
       DESCRIPTION "Enum for alarm threshold crossing type."
       SYNTAX       INTEGER
                      {
                        highCrossing(1),
                        preHighCrossing(2),
                        preLowCrossing(3),
                        lowCrossing(4),
                        maxReferenceValueCrossing(5),
                        minReferenceValueCrossing(6),
                        invalid(254)
                      }
                      
PerfValue ::= TEXTUAL-CONVENTION
       STATUS       current
       DESCRIPTION "An octet string containing performance value information."
       SYNTAX       OCTET STRING (SIZE (10))
       
       
AlarmRevertType ::= TEXTUAL-CONVENTION
       STATUS       current
       DESCRIPTION "Enum for alarm revert type."
       SYNTAX       INTEGER
                      { 
                        return(1),
                        unreturn(2),
                        invalid(254)
                      }
                      
                      
AlarmProtectedType ::= TEXTUAL-CONVENTION
       STATUS       current
       DESCRIPTION "Enum for alarm protected type."
       SYNTAX       INTEGER
                      {
                                onePlusOneBidir(1), 
                                fourFBidirOneForOneExtra(2),
                                fourFBidirOneForOneNoextrA(3),
                                twoFBlsrExtra(4),
                                twoFBlsrNoextra(5),
                                fourFBlsrNoextra(6),
                                fourFBlsrExtra(7),
                                oneForNMslinear(8),
                                twoFUnidirMsringNoextra(9),
                                onePlusoneUnidir(10),
                                fourFUnidirOneForOneExtra(11),
                                fourFUnidirOneForOneNoextra(12),
                                oneForNUnidirExtra(13),
                                oneForNUnidirNoextra(14),
                                nFOneForNExtra(15),
                                sncpOnePlusOneProtect(16),
                                sncpOneForOneProtect(17),
                                oneByoneBidir(22),
                                oneByoneUnidir(23),
                                sncpOnePlusOneProtectBidir(24),
                                sncpOnePlusOneProtectUnidi(25),
                                sncpOneByOneProtectBidir(26),
                                sncpOneByOneProtectUnidi(27),
                                ringWrappingProtect(28),
                                ringSteeringProtect(29),
                                pwonePlusone2Send2RcvProtect(30),
                                pwonePlusone2Send1RcvProtect(31),
                                pwoneByone1Send2RcvProtect(32),
                                pwoneByone1Send1RcvProtect(33),
                                onePlusone2Send2RcvProtectBi(40),
                                onePlusone2Send1RcvProtectBi(41),
                                onePlusone2Send2RcvProtectUni(42),
                                onePlusone2Send1RcvProtectUni(43),
                                oneByone1Send2RcvProtectBi(44),
                                oneByone1Send1RcvProtectBi(45),
                                oneByone1Send2RcvProtectUni(46),
                                oneByone1Send1RcvProtectUni(47),
                                wdmMSLinearOnePlusOne(129),
                                wdmMSLinearOneForOne(130),
                                wdmCHLinearOnePlusOne(131),
                                wdmCHLinearOneForOne(132),
                                wdmMSTwosharering(133),
                                wdmCHTworingOneForOne(134),
                                wdmCHTworingOnePlusOne(135),
                                wdmCHTwosharering(136),
                                wdmCHOneForN(137),
                                wdmCHMForN(138),
                                boardOnePlusOne(204),
                                boardOneForN(205),
                                atmUnidirOnePlusOne(300),
                                atmBidirOnePlusOne(301),
                                atmOneForN(302),
                                mplsOnePlusOne(400),
                                mplsOneForN(401),
                                sncpRelated(402),
                                invalid(65534)
                        }
                    

AlarmSwitchReason ::= TEXTUAL-CONVENTION
       STATUS       current
       DESCRIPTION "Enum for alarm switch reason."
       SYNTAX       INTEGER
                      {
                                na(1),
                                restored(2),
                                signalfailofw(3),
                                signalmismatch(4),
                                signaldegrade(5),
                                automaticswitch(6),
                                forceswitch(7),
                                exerciseswitch(8),
                                lockout(9),
                                manualswitch(10),
                                signalfailofp(11),
                                low(12),
                                dnr(13),
                                signaldegradeofp(14),
                                wtrTimerExpires(15),
                                mappingSwitchtoW(18),
                                mappingSwitchtoP(19),
                                invalid(65534)
                       }
                       
AlarmUlPrtGroupWrkStat ::= TEXTUAL-CONVENTION
       STATUS       current
       DESCRIPTION "Enum for alarm protected group work status."
       SYNTAX       INTEGER
                      { 
                                switchToWork(1),
                                switchToProtect(2),
                                switchPointDelete(3),
                                sswitchToWork(4),
                                sswitchToProrect(5),
                                turnswitchToProtect(6),
                                retraceswitchToProtect(7),
                                switchToEclock(30),
                                switchToLclock(31),
                                switchToIclock(32),
                                switchToHoldclock(33),
                                switchToClock(34),
                                clockToLockstat(35),
                                clockToUnlockstat(36),
                                clockToCatchstat(37),
                                clockToTrackstat(38),
                                invalid(65534)
                        }                      

AlarmTPIDClass ::= TEXTUAL-CONVENTION
       STATUS       current
       DESCRIPTION "Enum for alarm TPID class."
       SYNTAX       INTEGER
                     {
                        classBoard(1),
                        classCPU(2),
                        classSystem(3),
                        classAll(255)
                      }

ProfileName ::= TEXTUAL-CONVENTION
       STATUS       current
       DESCRIPTION "An octet string containing Alarm profile name."
       SYNTAX       OCTET STRING (SIZE (0..32)) 
       
ProfileStatus ::= TEXTUAL-CONVENTION
       STATUS       current
       DESCRIPTION "Enum for alarm shield profile status."
       SYNTAX       INTEGER
                      {
                        forever(1),
                        once(2)
                      }
                      
ProfileApplyFlag ::= TEXTUAL-CONVENTION
       STATUS       current
       DESCRIPTION "Enum for alarm shield profile apply flag."
       SYNTAX       INTEGER
                      {
                        system(1),
                        board(2),
                        interface(3)
                      }

AlarmConfirmNeed ::= TEXTUAL-CONVENTION
       STATUS       current
       DESCRIPTION "Enum for if alarm need confirm."
       SYNTAX       INTEGER
                     {
                        need(1),
                        noNeed(2)
                      }
curAlarmTable OBJECT-TYPE
        SYNTAX  SEQUENCE OF CurAlarmEntry
        MAX-ACCESS  not-accessible
        STATUS  current
        DESCRIPTION
            "A list of current Alarm entries."  
        ::= { zxr10AlarmMIB 1 } 

curAlarmEntry OBJECT-TYPE
        SYNTAX  CurAlarmEntry
        MAX-ACCESS  not-accessible
        STATUS  current
        DESCRIPTION
            "An entry containing management information 
            applicable to a particular alarm."
        INDEX  { curAlarmFlowID }
        ::= { curAlarmTable 1 } 
        
CurAlarmEntry ::=
     SEQUENCE {      
         curAlarmFlowID
             Unsigned32,
         curAlarmCode      
             Integer32, 
         curAlarmClass
             AlarmClass,
         curAlarmType 
             AlarmType,
         curAlarmLevel    
             AlarmLevel, 
         curAlarmStatus
             AlarmStatus,
         curAlarmOccuredTime 
             Unsigned32,
         curAlarmDisappearedTime 
             Unsigned32,  
         curAlarmTPIDType 
             Integer32, 
         curAlarmTPID  
             Tpid, 
         curAlarmParaType
             Integer32,
         curAlarmParaValue 
             AlarmParaValue,
         curAlarmDescription 
             AlarmDescription,
         curAlarmStdCode      
             Integer32,         
         curAlarmComment 
             AlarmComment,
         curAlarmNetID 
             AlarmNetID,
         curAlarmGlobalFlowID
             Unsigned32,
         curAlarmUpdatedTime 
             Unsigned32,
         curAlarmThAlmPeriod
             AlarmThAlmPeriod,
         curAlarmThAlmType
             AlarmThAlmType,
         curAlarmThPerfValue
             PerfValue,
         curAlarmReturnMode
             AlarmRevertType,
         curAlarmProtectType
             AlarmProtectedType,
         curAlarmSwitchReason
             AlarmSwitchReason,
         curAlarmUlPrtGroupWrkStat
             AlarmUlPrtGroupWrkStat,
         curAlarmTPIDTypeSwitchFrom
             Integer32,
         curAlarmTPIDSwitchFrom 
             Tpid,
         curAlarmTPIDTypeSwitchTo
             Integer32,
         curAlarmTPIDSwitchTo 
             Tpid,
         curAlarmTimestamp
             Unsigned32,
         curAlarmTPIDLen 
             Unsigned32,
         curAlarmTPIDLenSwitchFrom 
             Unsigned32,
         curAlarmTPIDLenSwitchTo 
             Unsigned32,
         curAlarmOccuredMs 
             Unsigned32,
         curAlarmUpdatedMs
             Unsigned32,
         curAlarmDisappearedMs 
             Unsigned32,
         curAlarmNeedConfirm 
             AlarmConfirmNeed
             }

curAlarmFlowID OBJECT-TYPE
        SYNTAX   Unsigned32
        MAX-ACCESS  read-only
        STATUS  current
        DESCRIPTION "Current alarm Index."
        ::= { curAlarmEntry 1 }

curAlarmCode OBJECT-TYPE
        SYNTAX   Integer32
        MAX-ACCESS  read-only
        STATUS  current
        DESCRIPTION "Current alarm code."
        ::= { curAlarmEntry 2 }
        
curAlarmClass OBJECT-TYPE    
        SYNTAX        AlarmClass        
        MAX-ACCESS    read-only
        STATUS        current
        DESCRIPTION "Current alarm class."
        ::= { curAlarmEntry 3 }
curAlarmType OBJECT-TYPE    
        SYNTAX        AlarmType        
        MAX-ACCESS    read-only
        STATUS        current
        DESCRIPTION   "Current alarm type."
        ::= { curAlarmEntry 4 }   

curAlarmLevel OBJECT-TYPE
        SYNTAX      AlarmLevel
        MAX-ACCESS  read-only
        STATUS  current
        DESCRIPTION "Current alarm level."
        ::= { curAlarmEntry 5 }  
        

curAlarmStatus OBJECT-TYPE
        SYNTAX      AlarmStatus
        MAX-ACCESS  read-only
        STATUS  current
        DESCRIPTION "Current alarm status."
        ::= { curAlarmEntry 6 }
        
curAlarmOccuredTime OBJECT-TYPE    
        SYNTAX        Unsigned32        
        MAX-ACCESS    read-only
        STATUS        current
        DESCRIPTION   "Current alarm occured time, 
                       the time is relative to 1970-01-01 00:00:00."
        ::= { curAlarmEntry 7 }

curAlarmDisappearedTime OBJECT-TYPE    
        SYNTAX        Unsigned32        
        MAX-ACCESS    read-only
        STATUS        current
        DESCRIPTION   "Current alarm disappeared time, 
                       the time is relative to 1970-01-01 00:00:00."
        ::= { curAlarmEntry 8 }
        
curAlarmTPIDType OBJECT-TYPE    
        SYNTAX        Integer32        
        MAX-ACCESS    read-only
        STATUS        current
        DESCRIPTION   "Current alarm check point type."
        ::= { curAlarmEntry 9 }

curAlarmTPID OBJECT-TYPE    
        SYNTAX        Tpid        
        MAX-ACCESS    read-only
        STATUS        current
        DESCRIPTION   "Current alarm check point."
        ::= { curAlarmEntry 10 }

curAlarmParaType OBJECT-TYPE    
        SYNTAX        Integer32        
        MAX-ACCESS    read-only
        STATUS        current
        DESCRIPTION   "Current alarm paratype,
                      the alarm is sent by."
        ::= { curAlarmEntry 11 }
        
curAlarmParaValue OBJECT-TYPE    
        SYNTAX        AlarmParaValue        
        MAX-ACCESS    read-only
        STATUS        current
        DESCRIPTION   "Current alarm paravalue,
                      the alarm is sent by."
        ::= { curAlarmEntry 12 } 

curAlarmDescription OBJECT-TYPE    
        SYNTAX        AlarmDescription        
        MAX-ACCESS    read-only
        STATUS        current
        DESCRIPTION   "Current alarm description."
        ::= { curAlarmEntry 13 }  
curAlarmStdCode OBJECT-TYPE
        SYNTAX   Integer32
        MAX-ACCESS  read-only
        STATUS  current
        DESCRIPTION "Current alarm standard code."
        ::= { curAlarmEntry 14 }
        
curAlarmComment OBJECT-TYPE    
        SYNTAX        AlarmComment        
        MAX-ACCESS    read-only
        STATUS        current
        DESCRIPTION   "Current alarm comment."
        ::= { curAlarmEntry 15 }    
        
curAlarmNetID OBJECT-TYPE    
        SYNTAX        AlarmNetID        
        MAX-ACCESS    read-only
        STATUS        current
        DESCRIPTION   "Current alarm NetID."
        ::= { curAlarmEntry 16} 

curAlarmGlobalFlowID OBJECT-TYPE
        SYNTAX   Unsigned32
        MAX-ACCESS  read-only
        STATUS  current
        DESCRIPTION "Current alarm global index."
        ::= { curAlarmEntry 17 }
        
curAlarmUpdatedTime OBJECT-TYPE    
        SYNTAX        Unsigned32        
        MAX-ACCESS    read-only
        STATUS        current
        DESCRIPTION   "Current alarm Updated time, 
                       the time is relative to 1970-01-01 00:00:00."
        ::= { curAlarmEntry 18 }
        
curAlarmThAlmPeriod OBJECT-TYPE
        SYNTAX   AlarmThAlmPeriod
        MAX-ACCESS  read-only
        STATUS  current
        DESCRIPTION "Current alarm period."
        ::= { curAlarmEntry 19 }
        
curAlarmThAlmType OBJECT-TYPE
        SYNTAX   AlarmThAlmType
        MAX-ACCESS  read-only
        STATUS  current
        DESCRIPTION "Current alarm threshold crossing type."
        ::= { curAlarmEntry 20 }
        
curAlarmThPerfValue OBJECT-TYPE
        SYNTAX   PerfValue
        MAX-ACCESS  read-only
        STATUS  current
        DESCRIPTION "Current alarm performance value."
        ::= { curAlarmEntry 21 }
        
curAlarmReturnMode OBJECT-TYPE
        SYNTAX   AlarmRevertType
        MAX-ACCESS  read-only
        STATUS  current
        DESCRIPTION "Current alarm revert type."
        ::= { curAlarmEntry 22 }
        
curAlarmProtectType OBJECT-TYPE
        SYNTAX   AlarmProtectedType
        MAX-ACCESS  read-only
        STATUS  current
        DESCRIPTION "Current alarm protected type."
        ::= { curAlarmEntry 23 }
        
curAlarmSwitchReason OBJECT-TYPE
        SYNTAX   AlarmSwitchReason
        MAX-ACCESS  read-only
        STATUS  current
        DESCRIPTION "Current alarm switch reason."
        ::= { curAlarmEntry 24 }
        
curAlarmUlPrtGroupWrkStat OBJECT-TYPE
        SYNTAX   AlarmUlPrtGroupWrkStat
        MAX-ACCESS  read-only
        STATUS  current
        DESCRIPTION "Current alarm protected group work status."
        ::= { curAlarmEntry 25 }
        
curAlarmTPIDTypeSwitchFrom OBJECT-TYPE
        SYNTAX   Integer32
        MAX-ACCESS  read-only
        STATUS  current
        DESCRIPTION "Which check point type switch from."
        ::= { curAlarmEntry 26 }
        
curAlarmTPIDSwitchFrom OBJECT-TYPE
        SYNTAX   Tpid
        MAX-ACCESS  read-only
        STATUS  current
        DESCRIPTION "Which check point switch from."
        ::= { curAlarmEntry 27 }
        
curAlarmTPIDTypeSwitchTo OBJECT-TYPE
        SYNTAX   Integer32
        MAX-ACCESS  read-only
        STATUS  current
        DESCRIPTION "Which check point type switch to."
        ::= { curAlarmEntry 28 }
        
curAlarmTPIDSwitchTo OBJECT-TYPE
        SYNTAX   Tpid
        MAX-ACCESS  read-only
        STATUS  current
        DESCRIPTION "Which check point switch to."
        ::= { curAlarmEntry 29 }
        
curAlarmTimestamp OBJECT-TYPE
        SYNTAX   Unsigned32
        MAX-ACCESS  read-only
        STATUS  current
        DESCRIPTION "Current alarm timestamp, corresponding to time, 
                     can fix an alarm with serial number 
                     when the device restarts."
        ::= { curAlarmEntry 30 }

curAlarmTPIDLen OBJECT-TYPE    
        SYNTAX        Unsigned32
        MAX-ACCESS    read-only
        STATUS        current
        DESCRIPTION   "The length of current alarm check point."
        ::= { curAlarmEntry 31 }

curAlarmTPIDLenSwitchFrom OBJECT-TYPE
        SYNTAX      Unsigned32
        MAX-ACCESS  read-only
        STATUS      current
        DESCRIPTION "The length of check point which switch from."
        ::= { curAlarmEntry 32 }

curAlarmTPIDLenSwitchTo OBJECT-TYPE
        SYNTAX      Unsigned32
        MAX-ACCESS  read-only
        STATUS      current
        DESCRIPTION "The length of check point which switch to."
        ::= { curAlarmEntry 33 }

curAlarmOccuredMs OBJECT-TYPE
        SYNTAX        Unsigned32
        MAX-ACCESS    read-only
        STATUS        current
        DESCRIPTION   "Current alarm occured millisecond."
        ::= { curAlarmEntry 34 }

curAlarmUpdatedMs OBJECT-TYPE
        SYNTAX        Unsigned32
        MAX-ACCESS    read-only
        STATUS        current
        DESCRIPTION   "Current alarm Updated millisecond."
        ::= { curAlarmEntry 35 }

curAlarmDisappearedMs OBJECT-TYPE
        SYNTAX        Unsigned32
        MAX-ACCESS    read-only
        STATUS        current
        DESCRIPTION   "Current alarm disappeared millisecond."
        ::= { curAlarmEntry 36 }
        
curAlarmNeedConfirm OBJECT-TYPE
        SYNTAX      AlarmConfirmNeed 
        MAX-ACCESS  read-only
        STATUS      current
        DESCRIPTION "If the alarm need confirm."
        ::= { curAlarmEntry 37 }


hisAlarmTable OBJECT-TYPE
        SYNTAX  SEQUENCE OF HisAlarmEntry
        MAX-ACCESS  not-accessible
        STATUS  current
        DESCRIPTION
            "A list of history alarm entries."  
        ::= { zxr10AlarmMIB 2 } 

hisAlarmEntry OBJECT-TYPE
        SYNTAX  HisAlarmEntry
        MAX-ACCESS  not-accessible
        STATUS  current
        DESCRIPTION
            "An entry containing management information applicable 
             to a particular history alarm."
        INDEX  { hisAlarmFlowID }
        ::= { hisAlarmTable 1 } 
        
HisAlarmEntry ::=
     SEQUENCE {      
         hisAlarmFlowID
             Unsigned32,
         hisAlarmCode      
             Integer32, 
         hisAlarmClass
             AlarmClass,
         hisAlarmType 
             AlarmType,
         hisAlarmLevel    
             AlarmLevel, 
         hisAlarmStatus
             AlarmStatus,
         hisAlarmOccuredTime 
             Unsigned32,
         hisAlarmDisappearedTime 
             Unsigned32,    
         hisAlarmTPIDType 
             Integer32,
         hisAlarmTPID  
             Tpid,
         hisAlarmParaType
             Integer32,
         hisAlarmParaValue 
             AlarmParaValue,
         hisAlarmDescription 
             AlarmDescription,
         hisAlarmStdCode      
             Integer32,
         hisAlarmComment
             AlarmComment,
         hisAlarmNetID
             AlarmNetID,
         hisAlarmGlobalFlowID
             Unsigned32,
         hisAlarmUpdatedTime
             Unsigned32,
         hisAlarmThAlmPeriod
             AlarmThAlmPeriod,
         hisAlarmThAlmType
             AlarmThAlmType,
         hisAlarmThPerfValue
             PerfValue,
         hisAlarmReturnMode
             AlarmRevertType,
         hisAlarmProtectType
             AlarmProtectedType,
         hisAlarmSwitchReason
             AlarmSwitchReason,
         hisAlarmUlPrtGroupWrkStat
             AlarmUlPrtGroupWrkStat,
         hisAlarmTPIDTypeSwitchFrom
             Integer32,
         hisAlarmTPIDSwitchFrom 
             Tpid,
         hisAlarmTPIDTypeSwitchTo
             Integer32,
         hisAlarmTPIDSwitchTo
             Tpid,
         hisAlarmTimestamp
             Unsigned32,
         hisAlarmTPIDLen
             Unsigned32,
         hisAlarmTPIDLenSwitchFrom
             Unsigned32,
         hisAlarmTPIDLenSwitchTo
             Unsigned32,
         hisAlarmOccuredMs
             Unsigned32,
         hisAlarmUpdatedMs
             Unsigned32,
         hisAlarmDisappearedMs
             Unsigned32
             }


hisAlarmFlowID OBJECT-TYPE
        SYNTAX   Unsigned32
        MAX-ACCESS  read-only
        STATUS  current
        DESCRIPTION "History alarm Index."
        ::= { hisAlarmEntry 1 }

hisAlarmCode OBJECT-TYPE
        SYNTAX   Integer32
        MAX-ACCESS  read-only
        STATUS  current
        DESCRIPTION "History alarm code."
        ::= { hisAlarmEntry 2 }  

hisAlarmClass OBJECT-TYPE    
        SYNTAX        AlarmClass        
        MAX-ACCESS    read-only
        STATUS        current
        DESCRIPTION "History alarm class."
        ::= { hisAlarmEntry 3 }
        
hisAlarmType OBJECT-TYPE    
        SYNTAX        AlarmType       
        MAX-ACCESS    read-only
        STATUS        current
        DESCRIPTION   "History alarm type,
                       0:at-Communicationsalarm,
                       1:at-Qosalarm,
                       2:at-Equipmentalarm,
                       3:at-Processingerroralarm,
                       4:at-Environmentalalarm."
        ::= { hisAlarmEntry 4 }           

hisAlarmLevel OBJECT-TYPE
        SYNTAX   AlarmLevel
        MAX-ACCESS  read-only
        STATUS  current
        DESCRIPTION
            "History alarm level."
        ::= { hisAlarmEntry 5 }   
        
hisAlarmStatus OBJECT-TYPE
        SYNTAX      AlarmStatus
        MAX-ACCESS  read-only
        STATUS  current
        DESCRIPTION "History alarm status."
        ::= { hisAlarmEntry 6 }     
        
hisAlarmOccuredTime OBJECT-TYPE    
        SYNTAX        Unsigned32        
        MAX-ACCESS    read-only
        STATUS        current
        DESCRIPTION   "History alarm occured time, 
                       the time is relative to 1970-01-01 00:00:00."
        ::= { hisAlarmEntry 7 }

hisAlarmDisappearedTime OBJECT-TYPE    
        SYNTAX        Unsigned32        
        MAX-ACCESS    read-only
        STATUS        current
        DESCRIPTION   "History alarm disappeared time, 
                       the time is relative to 1970-01-01 00:00:00."
        ::= { hisAlarmEntry 8 }  
        
hisAlarmTPIDType OBJECT-TYPE    
        SYNTAX        Integer32        
        MAX-ACCESS    read-only
        STATUS        current
        DESCRIPTION   "History alarm check point type."
        ::= { hisAlarmEntry 9 }

hisAlarmTPID OBJECT-TYPE    
        SYNTAX        Tpid        
        MAX-ACCESS    read-only
        STATUS        current
        DESCRIPTION   "History alarm check point."
        ::= { hisAlarmEntry 10 }

hisAlarmParaType OBJECT-TYPE    
        SYNTAX        Integer32        
        MAX-ACCESS    read-only
        STATUS        current
        DESCRIPTION   "History alarm paratype,
                      the alarm is sent by."
        ::= { hisAlarmEntry 11 }
 
hisAlarmParaValue OBJECT-TYPE    
        SYNTAX        AlarmParaValue        
        MAX-ACCESS    read-only
        STATUS        current
        DESCRIPTION   "History alarm paravalue,
                      the alarm is sent by."
        ::= { hisAlarmEntry 12 } 

hisAlarmDescription OBJECT-TYPE    
        SYNTAX        AlarmDescription        
        MAX-ACCESS    read-only
        STATUS        current
        DESCRIPTION   "History alarm description."
        ::= { hisAlarmEntry 13 }       
hisAlarmStdCode OBJECT-TYPE
        SYNTAX   Integer32
        MAX-ACCESS  read-only
        STATUS  current
        DESCRIPTION "History alarm standard code."
        ::= { hisAlarmEntry 14 }  
hisAlarmComment OBJECT-TYPE    
        SYNTAX        AlarmComment       
        MAX-ACCESS    read-only
        STATUS        current
        DESCRIPTION   "History alarm comment."
        ::= { hisAlarmEntry 15 }  
hisAlarmNetID OBJECT-TYPE    
        SYNTAX        AlarmNetID       
        MAX-ACCESS    read-only
        STATUS        current
        DESCRIPTION   "History alarm NetID."
        ::= { hisAlarmEntry 16 }         

hisAlarmGlobalFlowID OBJECT-TYPE
        SYNTAX   Unsigned32
        MAX-ACCESS  read-only
        STATUS  current
        DESCRIPTION "History alarm global index."
        ::= { hisAlarmEntry 17 }
        
hisAlarmUpdatedTime OBJECT-TYPE    
        SYNTAX        Unsigned32        
        MAX-ACCESS    read-only
        STATUS        current
        DESCRIPTION   "History alarm Updated time, 
                       the time is relative to 1970-01-01 00:00:00."
        ::= { hisAlarmEntry 18 }
        
hisAlarmThAlmPeriod OBJECT-TYPE
        SYNTAX   AlarmThAlmPeriod
        MAX-ACCESS  read-only
        STATUS  current
        DESCRIPTION "History alarm period."
        ::= { hisAlarmEntry 19 }
        
hisAlarmThAlmType OBJECT-TYPE
        SYNTAX   AlarmThAlmType
        MAX-ACCESS  read-only
        STATUS  current
        DESCRIPTION "History alarm threshold crossing type."
        ::= { hisAlarmEntry 20 }
        
hisAlarmThPerfValue OBJECT-TYPE
        SYNTAX   PerfValue
        MAX-ACCESS  read-only
        STATUS  current
        DESCRIPTION "History alarm performance value."
        ::= { hisAlarmEntry 21 }
        
hisAlarmReturnMode OBJECT-TYPE
        SYNTAX   AlarmRevertType
        MAX-ACCESS  read-only
        STATUS  current
        DESCRIPTION "History alarm revert type."
        ::= { hisAlarmEntry 22 }
        
hisAlarmProtectType OBJECT-TYPE
        SYNTAX   AlarmProtectedType
        MAX-ACCESS  read-only
        STATUS  current
        DESCRIPTION "History alarm protected type."
        ::= { hisAlarmEntry 23 }
        
hisAlarmSwitchReason OBJECT-TYPE
        SYNTAX   AlarmSwitchReason
        MAX-ACCESS  read-only
        STATUS  current
        DESCRIPTION "History alarm switch reason."
        ::= { hisAlarmEntry 24 }
        
hisAlarmUlPrtGroupWrkStat OBJECT-TYPE
        SYNTAX   AlarmUlPrtGroupWrkStat
        MAX-ACCESS  read-only
        STATUS  current
        DESCRIPTION "History alarm protected group work status."
        ::= { hisAlarmEntry 25 }
        
hisAlarmTPIDTypeSwitchFrom OBJECT-TYPE
        SYNTAX   Integer32
        MAX-ACCESS  read-only
        STATUS  current
        DESCRIPTION "Which check point type switch from."
        ::= { hisAlarmEntry 26 }
        
hisAlarmTPIDSwitchFrom OBJECT-TYPE
        SYNTAX   Tpid
        MAX-ACCESS  read-only
        STATUS  current
        DESCRIPTION "Which check point switch from."
        ::= { hisAlarmEntry 27 }
        
hisAlarmTPIDTypeSwitchTo OBJECT-TYPE
        SYNTAX   Integer32
        MAX-ACCESS  read-only
        STATUS  current
        DESCRIPTION "Which check point type switch to."
        ::= { hisAlarmEntry 28 }
        
hisAlarmTPIDSwitchTo OBJECT-TYPE
        SYNTAX   Tpid
        MAX-ACCESS  read-only
        STATUS  current
        DESCRIPTION "Which check point switch to."
        ::= { hisAlarmEntry 29 }
        
hisAlarmTimestamp OBJECT-TYPE
        SYNTAX   Unsigned32
        MAX-ACCESS  read-only
        STATUS  current
        DESCRIPTION "History alarm timestamp, corresponding to time, 
                    can fix an alarm with serial number 
                    when the device restarts."
        ::= { hisAlarmEntry 30 }

hisAlarmTPIDLen OBJECT-TYPE    
        SYNTAX        Unsigned32
        MAX-ACCESS    read-only
        STATUS        current
        DESCRIPTION   "The length of history alarm check point."
        ::= { hisAlarmEntry 31 }

hisAlarmTPIDLenSwitchFrom OBJECT-TYPE
        SYNTAX      Unsigned32
        MAX-ACCESS  read-only
        STATUS      current
        DESCRIPTION "The length of check point which switch from."
        ::= { hisAlarmEntry 32 }

hisAlarmTPIDLenSwitchTo OBJECT-TYPE
        SYNTAX      Unsigned32
        MAX-ACCESS  read-only
        STATUS      current
        DESCRIPTION "The length of check point which switch to."
        ::= { hisAlarmEntry 33 }

hisAlarmOccuredMs OBJECT-TYPE
        SYNTAX        Unsigned32
        MAX-ACCESS    read-only
        STATUS        current
        DESCRIPTION   "History alarm occured millisecond."
        ::= { hisAlarmEntry 34 }

hisAlarmUpdatedMs OBJECT-TYPE
        SYNTAX        Unsigned32
        MAX-ACCESS    read-only
        STATUS        current
        DESCRIPTION   "History alarm Updated millisecond."
        ::= { hisAlarmEntry 35 }

hisAlarmDisappearedMs OBJECT-TYPE
        SYNTAX        Unsigned32
        MAX-ACCESS    read-only
        STATUS        current
        DESCRIPTION   "History alarm disappeared millisecond."
        ::= { hisAlarmEntry 36 }

notificationTable OBJECT-TYPE
        SYNTAX  SEQUENCE OF NotificationEntry
        MAX-ACCESS  not-accessible
        STATUS  current
        DESCRIPTION
            "A list of notification entries."  
        ::= { zxr10AlarmMIB 6 } 

notificationEntry OBJECT-TYPE
        SYNTAX  NotificationEntry
        MAX-ACCESS  not-accessible
        STATUS  current
        DESCRIPTION
            "An entry containing management information 
            applicable to a notification."
        INDEX  { notificationFlowID }
        ::= { notificationTable 1 } 
        
NotificationEntry ::=
     SEQUENCE {      
         notificationFlowID
             Unsigned32,
         notificationAlmCode      
             Integer32, 
         notificationAlmType
             AlarmType,
         notificationAlmLevel    
             AlarmLevel,  
         notificationAlmOccuredTime 
             Unsigned32,  
         notificationTPIDType 
             Integer32,
         notificationTPID  
             Tpid,
         notificationAlmParaType
             Integer32,
         notificationAlmParaValue 
             AlarmParaValue,
         notificationAlmDescription 
             AlarmDescription,
         notificationAlmStdCode      
             Integer32,
         notificationAlmComment
             AlarmComment,
         notificationAlmNetID
             AlarmNetID,
         notificationTimestamp
             Unsigned32,
         notificationTPIDLen
             Unsigned32,
         notificationAlmOccuredMs
             Unsigned32,
         notificationNeedConfirm
             AlarmConfirmNeed
         }
             
notificationFlowID OBJECT-TYPE
        SYNTAX   Unsigned32
        MAX-ACCESS  read-only
        STATUS  current
        DESCRIPTION
            "Notification Index."
        ::= { notificationEntry 1 }
        
notificationAlmCode OBJECT-TYPE
        SYNTAX   Integer32
        MAX-ACCESS  read-only
        STATUS  current
        DESCRIPTION
            "Notification alarm code."
        ::= { notificationEntry 2 }

notificationAlmType OBJECT-TYPE
        SYNTAX   AlarmType
        MAX-ACCESS  read-only
        STATUS  current
        DESCRIPTION
            "Notification alarm type."
        ::= { notificationEntry 3 }
             
notificationAlmLevel OBJECT-TYPE
        SYNTAX   AlarmLevel
        MAX-ACCESS  read-only
        STATUS  current
        DESCRIPTION
            "Notification alarm level."
        ::= { notificationEntry 4 }  
        
notificationAlmOccuredTime OBJECT-TYPE
        SYNTAX   Unsigned32
        MAX-ACCESS  read-only
        STATUS  current
        DESCRIPTION
            "Notification occured time,
            the time is relative to 1970-01-01 00:00:00."
        ::= { notificationEntry 5 } 
             
notificationTPIDType OBJECT-TYPE
        SYNTAX   Integer32
        MAX-ACCESS  read-only
        STATUS  current
        DESCRIPTION
            "Notification check point type."
        ::= { notificationEntry 6 }

notificationTPID OBJECT-TYPE
        SYNTAX   Tpid
        MAX-ACCESS  read-only
        STATUS  current
        DESCRIPTION
            "Notification check point."
        ::= { notificationEntry 7 }        

notificationAlmParaType OBJECT-TYPE    
        SYNTAX        Integer32        
        MAX-ACCESS    read-only
        STATUS        current
        DESCRIPTION   "Notification alarm paratype,
                      the alarm is sent by."
        ::= { notificationEntry 8 } 

notificationAlmParaValue OBJECT-TYPE    
        SYNTAX        AlarmParaValue        
        MAX-ACCESS    read-only
        STATUS        current
        DESCRIPTION   "Notification alarm paravalue,
                      the alarm is sent by."
        ::= { notificationEntry 9 } 

notificationAlmDescription OBJECT-TYPE    
        SYNTAX        AlarmDescription        
        MAX-ACCESS    read-only
        STATUS        current
        DESCRIPTION   "Notification alarm description."
        ::= { notificationEntry 10 }
        
notificationAlmStdCode OBJECT-TYPE
        SYNTAX   Integer32
        MAX-ACCESS  read-only
        STATUS  current
        DESCRIPTION
            "Notification alarm standard code."
        ::= { notificationEntry 11 }      
        
notificationAlmComment OBJECT-TYPE
        SYNTAX   AlarmComment
        MAX-ACCESS  read-only
        STATUS  current
        DESCRIPTION
            "Notification alarm comment."
        ::= { notificationEntry 12 }

notificationAlmNetID OBJECT-TYPE
        SYNTAX   AlarmNetID
        MAX-ACCESS  read-only
        STATUS  current
        DESCRIPTION
            "Notification alarm netID."
        ::= { notificationEntry 13 }
        
notificationTimestamp OBJECT-TYPE
        SYNTAX   Unsigned32
        MAX-ACCESS  read-only
        STATUS  current
        DESCRIPTION "Notification timestamp, corresponding to time, 
                     can fix an alarm with serial number 
                     when the device restarts."
        ::= { notificationEntry 14 }

notificationTPIDLen OBJECT-TYPE
        SYNTAX      Unsigned32
        MAX-ACCESS  read-only
        STATUS      current
        DESCRIPTION "The length of notification check point."
        ::= { notificationEntry 15 }

notificationAlmOccuredMs OBJECT-TYPE
        SYNTAX   Unsigned32
        MAX-ACCESS  read-only
        STATUS  current
        DESCRIPTION
            "Notification occured millisecond."
        ::= { notificationEntry 16 }
        
notificationNeedConfirm OBJECT-TYPE
        SYNTAX      AlarmConfirmNeed 
        MAX-ACCESS  read-only
        STATUS      current
        DESCRIPTION "If the notification need confirm."
        ::= { notificationEntry 17 }


globalAlarmTrapTable OBJECT-TYPE
        SYNTAX  SEQUENCE OF GlobalAlarmTrapEntry
        MAX-ACCESS  not-accessible
        STATUS  current
        DESCRIPTION
            "A list of global Alarm entries."  
        ::= { zxr10AlarmMIB 12 } 

globalAlarmTrapEntry OBJECT-TYPE
        SYNTAX  GlobalAlarmTrapEntry
        MAX-ACCESS  not-accessible
        STATUS  current
        DESCRIPTION
            "An entry containing management information applicable 
            to a particular alarm."
        INDEX  { globalAlarmGlobalFlowID }
        ::= { globalAlarmTrapTable 1 } 
        
GlobalAlarmTrapEntry ::=
     SEQUENCE {      
         globalAlarmFlowID
             Unsigned32,
         globalAlarmCode      
             Integer32, 
         globalAlarmClass
             AlarmClass,
         globalAlarmType 
             AlarmType,
         globalAlarmLevel    
             AlarmLevel, 
         globalAlarmStatus
             AlarmStatus,
         globalAlarmOccuredTime 
             Unsigned32,
         globalAlarmDisappearedTime 
             Unsigned32,  
         globalAlarmTPIDType 
             Integer32, 
         globalAlarmTPID  
             Tpid, 
         globalAlarmParaType
             Integer32,
         globalAlarmParaValue 
             AlarmParaValue,
         globalAlarmDescription 
             AlarmDescription,
         globalAlarmStdCode      
             Integer32,
         globalAlarmGlobalFlowID
             Unsigned32,
         globalAlarmUpdatedTime 
             Unsigned32,
         globalAlarmThAlmPeriod
             AlarmThAlmPeriod,
         globalAlarmThAlmType
             AlarmThAlmType,
         globalAlarmThPerfValue
             PerfValue,
         globalAlarmReturnMode
             AlarmRevertType,
         globalAlarmProtectType
             AlarmProtectedType,
         globalAlarmSwitchReason
             AlarmSwitchReason,
         globalAlarmUlPrtGroupWrkStat
             AlarmUlPrtGroupWrkStat,
         globalAlarmTPIDTypeSwitchFrom
             Integer32,
         globalAlarmTPIDSwitchFrom 
             Tpid,
         globalAlarmTPIDTypeSwitchTo
             Integer32,
         globalAlarmTPIDSwitchTo 
             Tpid,
         globalAlarmTimestamp
             Unsigned32,
         globalAlarmTPIDLen
             Unsigned32, 
         globalAlarmTPIDLenSwitchFrom
             Unsigned32, 
         globalAlarmTPIDLenSwitchTo
             Unsigned32,
         globalAlarmOccuredMs
             Unsigned32,
         globalAlarmUpdatedMs
             Unsigned32,
         globalAlarmDisappearedMs
             Unsigned32
             }

globalAlarmFlowID OBJECT-TYPE
        SYNTAX   Unsigned32
        MAX-ACCESS  read-only
        STATUS  current
        DESCRIPTION "Global alarm Index."
        ::= { globalAlarmTrapEntry 1 }

globalAlarmCode OBJECT-TYPE
        SYNTAX   Integer32
        MAX-ACCESS  read-only
        STATUS  current
        DESCRIPTION "Global alarm code."
        ::= { globalAlarmTrapEntry 2 }
        
globalAlarmClass OBJECT-TYPE    
        SYNTAX        AlarmClass        
        MAX-ACCESS    read-only
        STATUS        current
        DESCRIPTION "Global alarm class."
        ::= { globalAlarmTrapEntry 3 }
        
globalAlarmType OBJECT-TYPE    
        SYNTAX        AlarmType        
        MAX-ACCESS    read-only
        STATUS        current
        DESCRIPTION   "Global alarm type."
        ::= { globalAlarmTrapEntry 4 }   

globalAlarmLevel OBJECT-TYPE
        SYNTAX      AlarmLevel
        MAX-ACCESS  read-only
        STATUS  current
        DESCRIPTION "Global alarm level."
        ::= { globalAlarmTrapEntry 5 }          

globalAlarmStatus OBJECT-TYPE
        SYNTAX      AlarmStatus
        MAX-ACCESS  read-only
        STATUS  current
        DESCRIPTION "Global alarm status."
        ::= { globalAlarmTrapEntry 6 }
        
globalAlarmOccuredTime OBJECT-TYPE    
        SYNTAX        Unsigned32        
        MAX-ACCESS    read-only
        STATUS        current
        DESCRIPTION   "Global alarm occured time, 
                       the time is relative to 1970-01-01 00:00:00."
        ::= { globalAlarmTrapEntry 7 }

globalAlarmDisappearedTime OBJECT-TYPE    
        SYNTAX        Unsigned32        
        MAX-ACCESS    read-only
        STATUS        current
        DESCRIPTION   "Global alarm disappeared time, 
                       the time is relative to 1970-01-01 00:00:00."
        ::= { globalAlarmTrapEntry 8 }
        
globalAlarmTPIDType OBJECT-TYPE    
        SYNTAX        Integer32        
        MAX-ACCESS    read-only
        STATUS        current
        DESCRIPTION   "Global alarm check point type."
        ::= { globalAlarmTrapEntry 9 }

globalAlarmTPID OBJECT-TYPE    
        SYNTAX        Tpid        
        MAX-ACCESS    read-only
        STATUS        current
        DESCRIPTION   "Global alarm check point."
        ::= { globalAlarmTrapEntry 10 }

globalAlarmParaType OBJECT-TYPE    
        SYNTAX        Integer32        
        MAX-ACCESS    read-only
        STATUS        current
        DESCRIPTION   "Global alarm paratype,
                      the alarm is sent by."
        ::= { globalAlarmTrapEntry 11 }     
        
globalAlarmParaValue OBJECT-TYPE    
        SYNTAX        AlarmParaValue        
        MAX-ACCESS    read-only
        STATUS        current
        DESCRIPTION   "Global alarm paravalue,
                      the alarm is sent by."
        ::= { globalAlarmTrapEntry 12 } 

globalAlarmDescription OBJECT-TYPE    
        SYNTAX        AlarmDescription        
        MAX-ACCESS    read-only
        STATUS        current
        DESCRIPTION   "Global alarm description."
        ::= { globalAlarmTrapEntry 13 }  
        
globalAlarmStdCode OBJECT-TYPE
        SYNTAX   Integer32
        MAX-ACCESS  read-only
        STATUS  current
        DESCRIPTION "Global alarm standard code."
        ::= { globalAlarmTrapEntry 14 }

globalAlarmGlobalFlowID OBJECT-TYPE
        SYNTAX   Unsigned32
        MAX-ACCESS  read-only
        STATUS  current
        DESCRIPTION "Global alarm global index."
        ::= { globalAlarmTrapEntry 17 }
        
globalAlarmUpdatedTime OBJECT-TYPE    
        SYNTAX        Unsigned32        
        MAX-ACCESS    read-only
        STATUS        current
        DESCRIPTION   "Global alarm updated time, 
                       the time is relative to 1970-01-01 00:00:00."
        ::= { globalAlarmTrapEntry 18 }
        
globalAlarmThAlmPeriod OBJECT-TYPE
        SYNTAX   AlarmThAlmPeriod
        MAX-ACCESS  read-only
        STATUS  current
        DESCRIPTION "Global alarm period."
        ::= { globalAlarmTrapEntry 19 }
        
globalAlarmThAlmType OBJECT-TYPE
        SYNTAX   AlarmThAlmType
        MAX-ACCESS  read-only
        STATUS  current
        DESCRIPTION "Global alarm threshold crossing type."
        ::= { globalAlarmTrapEntry 20 }
        
globalAlarmThPerfValue OBJECT-TYPE
        SYNTAX   PerfValue
        MAX-ACCESS  read-only
        STATUS  current
        DESCRIPTION "Global alarm performance value."
        ::= { globalAlarmTrapEntry 21 }
        
globalAlarmReturnMode OBJECT-TYPE
        SYNTAX   AlarmRevertType
        MAX-ACCESS  read-only
        STATUS  current
        DESCRIPTION "Global alarm revert type."
        ::= { globalAlarmTrapEntry 22 }
        
globalAlarmProtectType OBJECT-TYPE
        SYNTAX   AlarmProtectedType
        MAX-ACCESS  read-only
        STATUS  current
        DESCRIPTION "Global alarm protected type."
        ::= { globalAlarmTrapEntry 23 }
        
globalAlarmSwitchReason OBJECT-TYPE
        SYNTAX   AlarmSwitchReason
        MAX-ACCESS  read-only
        STATUS  current
        DESCRIPTION "Global alarm switch reason."
        ::= { globalAlarmTrapEntry 24 }
        
globalAlarmUlPrtGroupWrkStat OBJECT-TYPE
        SYNTAX   AlarmUlPrtGroupWrkStat
        MAX-ACCESS  read-only
        STATUS  current
        DESCRIPTION "Global alarm protected group work status."
        ::= { globalAlarmTrapEntry 25 }
        
globalAlarmTPIDTypeSwitchFrom OBJECT-TYPE
        SYNTAX   Integer32
        MAX-ACCESS  read-only
        STATUS  current
        DESCRIPTION "Which check point type switch from."
        ::= { globalAlarmTrapEntry 26 }
        
globalAlarmTPIDSwitchFrom OBJECT-TYPE
        SYNTAX   Tpid
        MAX-ACCESS  read-only
        STATUS  current
        DESCRIPTION "Which check point switch from."
        ::= { globalAlarmTrapEntry 27 }
        
globalAlarmTPIDTypeSwitchTo OBJECT-TYPE
        SYNTAX   Integer32
        MAX-ACCESS  read-only
        STATUS  current
        DESCRIPTION "Which check point type switch to."
        ::= { globalAlarmTrapEntry 28 }
        
globalAlarmTPIDSwitchTo OBJECT-TYPE
        SYNTAX   Tpid
        MAX-ACCESS  read-only
        STATUS  current
        DESCRIPTION "Which check point switch to."
        ::= { globalAlarmTrapEntry 29 }
        
globalAlarmTimestamp OBJECT-TYPE
        SYNTAX   Unsigned32
        MAX-ACCESS  read-only
        STATUS  current
        DESCRIPTION "Global alarm timestamp, corresponding to time, 
        can fix an alarm with serial number when the device restarts."
        ::= { globalAlarmTrapEntry 30 }

globalAlarmTPIDLen OBJECT-TYPE
        SYNTAX        Unsigned32
        MAX-ACCESS    read-only
        STATUS        current
        DESCRIPTION   "The length of global alarm check point."
        ::= { globalAlarmTrapEntry 31 }

globalAlarmTPIDLenSwitchFrom OBJECT-TYPE
        SYNTAX      Unsigned32
        MAX-ACCESS  read-only
        STATUS      current
        DESCRIPTION "The length of check point which switch from."
        ::= { globalAlarmTrapEntry 32 }

globalAlarmTPIDLenSwitchTo OBJECT-TYPE
        SYNTAX      Unsigned32
        MAX-ACCESS  read-only
        STATUS      current
        DESCRIPTION "The length of check point which switch to."
        ::= { globalAlarmTrapEntry 33 }

globalAlarmOccuredMs OBJECT-TYPE    
        SYNTAX        Unsigned32        
        MAX-ACCESS    read-only
        STATUS        current
        DESCRIPTION   "Global alarm occured millisecond."
        ::= { globalAlarmTrapEntry 34 }

globalAlarmUpdatedMs OBJECT-TYPE    
        SYNTAX        Unsigned32        
        MAX-ACCESS    read-only
        STATUS        current
        DESCRIPTION   "Global alarm updated millisecond."
        ::= { globalAlarmTrapEntry 35 }

globalAlarmDisappearedMs OBJECT-TYPE    
        SYNTAX        Unsigned32        
        MAX-ACCESS    read-only
        STATUS        current
        DESCRIPTION   "Global alarm disappeared millisecond."
        ::= { globalAlarmTrapEntry 36 }

alarmTrap OBJECT IDENTIFIER ::= { zxr10AlarmMIB 8 }

curAlarmTrap NOTIFICATION-TYPE
        OBJECTS {
                 curAlarmFlowID,
                 curAlarmCode,
                 curAlarmClass,
                 curAlarmType,
                 curAlarmLevel, 
                 curAlarmStatus,
                 curAlarmOccuredTime,
                 curAlarmDisappearedTime,
                 curAlarmTPIDType,
                 curAlarmTPID,
                 curAlarmParaType,
                 curAlarmParaValue,
                 curAlarmDescription,
                 curAlarmStdCode,
                 curAlarmComment,
                 curAlarmNetID,
                 curAlarmGlobalFlowID,
                 curAlarmUpdatedTime,
                 curAlarmThAlmPeriod,
                 curAlarmThAlmType,
                 curAlarmThPerfValue,
                 curAlarmReturnMode,
                 curAlarmProtectType,
                 curAlarmSwitchReason,
                 curAlarmUlPrtGroupWrkStat,
                 curAlarmTPIDTypeSwitchFrom,
                 curAlarmTPIDSwitchFrom,
                 curAlarmTPIDTypeSwitchTo,
                 curAlarmTPIDSwitchTo,
                 curAlarmTimestamp,
                 curAlarmTPIDLen,
                 curAlarmTPIDLenSwitchFrom,
                 curAlarmTPIDLenSwitchTo,
                 curAlarmOccuredMs,
                 curAlarmUpdatedMs,
                 curAlarmDisappearedMs,
                 curAlarmNeedConfirm
            }
        STATUS             current
        DESCRIPTION
           "When an alarm occurred, 
           send the trap PDU to uniform network manager.
           Through the configuration command alarm trap-oid-expand, 
           the trap OID can be expanded, adding alarm status and code."
   ::= { alarmTrap 1 }

                 
notificationTrap NOTIFICATION-TYPE
        OBJECTS {
                 notificationFlowID,
                 notificationAlmCode, 
                 notificationAlmType,
                 notificationAlmLevel, 
                 notificationAlmOccuredTime,
                 notificationTPIDType,
                 notificationTPID,
                 notificationAlmParaType,
                 notificationAlmParaValue,
                 notificationAlmDescription,
                 notificationAlmStdCode,
                 notificationAlmComment,
                 notificationAlmNetID,
                 notificationTimestamp,
                 notificationTPIDLen,
                 notificationAlmOccuredMs,
                 notificationNeedConfirm
            }
        STATUS             current
        DESCRIPTION
           "When a notification occurred, 
           send the trap PDU to uniform network manager.
           Through the configuration command alarm trap-oid-expand, 
           the trap OID can be expanded, adding notification status and code."
   ::= { alarmTrap 3 }  
   
heartbeatNotification NOTIFICATION-TYPE
        STATUS      current
        DESCRIPTION 
                "Send a heart-beat trap when required."
        ::= { alarmTrap 4 }

zxr10AlarmPreloadCancelTrap NOTIFICATION-TYPE
        OBJECTS {
                 zxr10AlarmPreloadInterface
            }
        STATUS             current
        DESCRIPTION
           "When an alarm preload canceled, 
           send the trap PDU to uniform network manager."
   ::= { alarmTrap 5 }

alarmHeartBeatGlobalObjects OBJECT IDENTIFIER ::= { zxr10AlarmMIB 20 }

alarmHeartBeatNotification OBJECT-TYPE
    SYNTAX Unsigned32(1..2)
    MAX-ACCESS read-write
    STATUS  current
    DESCRIPTION
    "Alarm heart-beat notification report. 1:enable, 2:disable."
    ::= { alarmHeartBeatGlobalObjects 1 }
    
alarmHeartBeatTable OBJECT-TYPE
        SYNTAX  SEQUENCE OF AlarmHeartBeatEntry
        MAX-ACCESS  not-accessible
        STATUS  current
        DESCRIPTION
            "A list of heart-beat entries."  
        ::= { zxr10AlarmMIB 9 } 

alarmHeartBeatEntry OBJECT-TYPE
        SYNTAX  AlarmHeartBeatEntry
        MAX-ACCESS  not-accessible
        STATUS  current
        DESCRIPTION
            "An entry containing management information 
            applicable to heart-beat."
        INDEX  { alarmHeartBeatType }
        ::= { alarmHeartBeatTable 1 } 
        
AlarmHeartBeatEntry ::=
     SEQUENCE {      
         alarmHeartBeatType
             Unsigned32,
         alarmHeartBeatStart      
             Unsigned32, 
         alarmHeartBeatPeriod
             Unsigned32
             }

alarmHeartBeatType OBJECT-TYPE
        SYNTAX   Unsigned32(0..4)
        MAX-ACCESS  read-only
        STATUS  current
        DESCRIPTION "Alarm heart-beat type. 
                    0:snmp, 1:syslog, 2:ftp, 3:console, 4:all."
        ::= { alarmHeartBeatEntry 1 }
        
alarmHeartBeatStart OBJECT-TYPE
        SYNTAX   Unsigned32(0..1)
        MAX-ACCESS  read-write
        STATUS  current
        DESCRIPTION "Alarm heart-beat start. 0:not send, 1:send."
        ::= { alarmHeartBeatEntry 2 }
        
alarmHeartBeatPeriod OBJECT-TYPE
        SYNTAX   Unsigned32(0..30000)
        MAX-ACCESS  read-write
        STATUS  current
        DESCRIPTION "Alarm heart-beat period."
        ::= { alarmHeartBeatEntry 3 }

        
alarmLevelTable OBJECT-TYPE
        SYNTAX  SEQUENCE OF AlarmLevelEntry
        MAX-ACCESS  not-accessible
        STATUS  obsolete
        DESCRIPTION "A list of alarm level entries."
        ::= { zxr10AlarmMIB 11 }

alarmLevelEntry OBJECT-TYPE
        SYNTAX  AlarmLevelEntry
        MAX-ACCESS  not-accessible
        STATUS  obsolete
        DESCRIPTION "An alarm check point entry."
        INDEX  { alarmLevelAlarmCode }
        ::= { alarmLevelTable 1 }
                                                                    
AlarmLevelEntry ::=
     SEQUENCE {
         alarmLevelAlarmCode
             Unsigned32,
         alarmLevel
             AlarmLevel                                                   
}               
        
alarmLevelAlarmCode OBJECT-TYPE
        SYNTAX      Unsigned32
        MAX-ACCESS  read-only
        STATUS  obsolete
        DESCRIPTION "Alarm code."
        ::= { alarmLevelEntry 1 } 

alarmLevel OBJECT-TYPE
        SYNTAX      AlarmLevel
        MAX-ACCESS  read-write
        STATUS  obsolete
        DESCRIPTION "Alarm level."
        ::= { alarmLevelEntry 2 }        

        
alarmClearTable OBJECT-TYPE
        SYNTAX  SEQUENCE OF AlarmClearEntry
        MAX-ACCESS  not-accessible
        STATUS  current
        DESCRIPTION "A list of alarm clear entries."
        ::= {  zxr10AlarmMIB 13 }

alarmClearEntry OBJECT-TYPE
        SYNTAX  AlarmClearEntry
        MAX-ACCESS  not-accessible
        STATUS  current
        DESCRIPTION "An alarm clear entry."
        INDEX  { alarmClearGlobalFlowID }
        ::= { alarmClearTable 1 }
                                                                    
AlarmClearEntry ::=
     SEQUENCE {
         alarmClearGlobalFlowID
             Unsigned32,
         alarmClearStatus
             Integer32 
}               
        
alarmClearGlobalFlowID OBJECT-TYPE
        SYNTAX      Unsigned32
        MAX-ACCESS  read-only
        STATUS  current
        DESCRIPTION "Alarm flowid."
        ::= { alarmClearEntry 1 }      

alarmClearStatus OBJECT-TYPE
        SYNTAX      Integer32(0..1) 
        MAX-ACCESS  read-write
        STATUS  current
        DESCRIPTION "Alarm clear status. 0: the only value you can get, 
                     1:set the value means to delete the instance."
        DEFVAL{0}
        ::= { alarmClearEntry 2 }
        
        
alarmMaskTable OBJECT-TYPE
        SYNTAX  SEQUENCE OF AlarmMaskEntry
        MAX-ACCESS  not-accessible
        STATUS  obsolete
        DESCRIPTION "A list of alarm mask entries."
        ::= { zxr10AlarmMIB 15 }

alarmMaskEntry OBJECT-TYPE
        SYNTAX  AlarmMaskEntry
        MAX-ACCESS  not-accessible
        STATUS  obsolete
        DESCRIPTION "An alarm mask entry."
        INDEX  { alarmMaskTPIDType, alarmMaskTPID, 
                 alarmMaskTPIDMask, alarmMaskAlarmCode}
        ::= { alarmMaskTable 1 }
                                                                    
AlarmMaskEntry ::=
     SEQUENCE {
         alarmMaskTPIDType 
             Integer32,
         alarmMaskTPID 
             Tpid,
         alarmMaskTPIDMask 
             OCTET STRING,
         alarmMaskAlarmCode 
             Integer32,         
         alarmMaskRowStatus
             RowStatus
}               

alarmMaskTPIDType OBJECT-TYPE
        SYNTAX  Integer32(1..65535)
        MAX-ACCESS  not-accessible
        STATUS  obsolete
        DESCRIPTION
            "Alarm mask TPID type. Valid values range from 1 to 65534; 
             65535 is an invalid value."
        ::= { alarmMaskEntry 1 } 
         
alarmMaskTPID OBJECT-TYPE
        SYNTAX      Tpid
        MAX-ACCESS  not-accessible
        STATUS  obsolete
        DESCRIPTION
            "Alarm mask TPID. Length is 62 bytes. Valid and invalid values 
            are filled in according to the check point specification."
        ::= { alarmMaskEntry 2 }

alarmMaskTPIDMask OBJECT-TYPE
        SYNTAX   OCTET STRING (SIZE (8)) 
        MAX-ACCESS  not-accessible
        STATUS  obsolete
        DESCRIPTION
            "Each bit indicates whether the corresponding byte 
            in alarmMaskTPID is valid. 1 is valid, 0 is invalid."
        ::= { alarmMaskEntry 3 }
         
alarmMaskAlarmCode OBJECT-TYPE
        SYNTAX   Integer32
        MAX-ACCESS  not-accessible
        STATUS  obsolete
        DESCRIPTION
            "Alarm code."
        ::= { alarmMaskEntry 4 }
        
alarmMaskRowStatus OBJECT-TYPE
        SYNTAX       RowStatus
        MAX-ACCESS    read-create
        STATUS        obsolete
        DESCRIPTION   "Row status."
        ::= { alarmMaskEntry 100 }        
        
zxr10AlarmGlobalObjects OBJECT IDENTIFIER ::= { zxr10AlarmMIB 16 }   

zxr10AlarmPreloadInterface OBJECT-TYPE
        SYNTAX     AlarmInterface
        MAX-ACCESS accessible-for-notify
        STATUS     current
        DESCRIPTION
                "The interface which canceled proload function."
        ::= { zxr10AlarmGlobalObjects 1 }         
alarmLevelChangeTable OBJECT-TYPE
        SYNTAX  SEQUENCE OF AlarmLevelChangeEntry
        MAX-ACCESS  not-accessible
        STATUS  current
        DESCRIPTION "A list of alarm level entries."
        ::= { zxr10AlarmMIB 17 }

alarmLevelChangeEntry OBJECT-TYPE
        SYNTAX  AlarmLevelChangeEntry
        MAX-ACCESS  not-accessible
        STATUS  current
        DESCRIPTION "An alarm level entry."
        INDEX  { alarmLevelChangeCode, alarmLevelChangeTPIDType }
        ::= { alarmLevelChangeTable 1 }

AlarmLevelChangeEntry ::=
     SEQUENCE {
         alarmLevelChangeCode
             Unsigned32,
         alarmLevelChangeTPIDType
             Unsigned32,
         alarmLevelChangeLevel
             AlarmLevel,
         alarmLevelChangeRowStatus
             RowStatus
}               

alarmLevelChangeCode OBJECT-TYPE
        SYNTAX      Unsigned32
        MAX-ACCESS  not-accessible
        STATUS  current
        DESCRIPTION "Alarm code."
        ::= { alarmLevelChangeEntry 1 } 

alarmLevelChangeTPIDType OBJECT-TYPE
        SYNTAX      Unsigned32
        MAX-ACCESS  not-accessible
        STATUS  current
        DESCRIPTION "TPID Type."
        ::= { alarmLevelChangeEntry 2 } 

alarmLevelChangeLevel OBJECT-TYPE
        SYNTAX      AlarmLevel
        MAX-ACCESS  read-create
        STATUS  current
        DESCRIPTION 
           "Alarm level support 'emergency','alert','critical','error',
           'warning','notification','information','debugging'.Alarm level 
            not support 'all'."
        ::= { alarmLevelChangeEntry 3 }

alarmLevelChangeRowStatus OBJECT-TYPE
        SYNTAX       RowStatus
        MAX-ACCESS    read-create
        STATUS        current
        DESCRIPTION   "Row status."
        ::= { alarmLevelChangeEntry 100 }

alarmShieldTable OBJECT-TYPE
        SYNTAX  SEQUENCE OF AlarmShieldEntry
        MAX-ACCESS  not-accessible
        STATUS  current
        DESCRIPTION "A list of alarm shield entries."
        ::= { zxr10AlarmMIB 18 }

alarmShieldEntry OBJECT-TYPE
        SYNTAX  AlarmShieldEntry
        MAX-ACCESS  not-accessible
        STATUS  current
        DESCRIPTION "An alarm shield entry."
        INDEX  { alarmShieldAlarmCode, alarmShieldBegintime, 
                 alarmShieldEndtime, alarmShieldType,alarmShieldLevel}
        ::= { alarmShieldTable 1 }
AlarmShieldEntry ::=
     SEQUENCE {
         alarmShieldAlarmCode 
             Unsigned32,
         alarmShieldBegintime 
             Unsigned32,
         alarmShieldEndtime 
             Unsigned32,
         alarmShieldType 
             AlarmType,
         alarmShieldLevel 
             AlarmLevel, 
         alarmShieldRowStatus
             RowStatus} 

alarmShieldAlarmCode OBJECT-TYPE
        SYNTAX   Unsigned32
        MAX-ACCESS  not-accessible
        STATUS  current
        DESCRIPTION
            "Alarm code."
        ::= { alarmShieldEntry 1 }

alarmShieldBegintime OBJECT-TYPE
        SYNTAX   Unsigned32
        MAX-ACCESS  not-accessible
        STATUS  current
        DESCRIPTION
            "Alarm begin time."
        ::= { alarmShieldEntry 2 }
alarmShieldEndtime OBJECT-TYPE
        SYNTAX   Unsigned32
        MAX-ACCESS  not-accessible
        STATUS  current
        DESCRIPTION
            "Alarm end time."
        ::= { alarmShieldEntry 3 }

alarmShieldType OBJECT-TYPE
        SYNTAX   AlarmType 
        MAX-ACCESS  not-accessible
        STATUS  current
        DESCRIPTION
            "Alarm type."
        ::= { alarmShieldEntry 4 }

alarmShieldLevel OBJECT-TYPE
        SYNTAX   AlarmLevel 
        MAX-ACCESS  not-accessible
        STATUS  current
        DESCRIPTION
            "Alarm level."
        ::= { alarmShieldEntry 5 }

alarmShieldRowStatus OBJECT-TYPE
        SYNTAX       RowStatus
        MAX-ACCESS    read-create
        STATUS        current
        DESCRIPTION   "Row status."
        ::= { alarmShieldEntry 100 }

zxr10AlarmMaskTable OBJECT-TYPE
        SYNTAX      SEQUENCE OF Zxr10AlarmMaskEntry
        MAX-ACCESS  not-accessible
        STATUS      current
        DESCRIPTION "A list of alarm mask entries."
        ::= { zxr10AlarmMIB 19 }

zxr10AlarmMaskEntry OBJECT-TYPE
        SYNTAX      Zxr10AlarmMaskEntry
        MAX-ACCESS  not-accessible
        STATUS      current
        DESCRIPTION "An alarm mask entry."
        INDEX  { zxr10AlarmMaskTPIDType, zxr10AlarmMaskTPID,
                 zxr10AlarmMaskTPIDMask, zxr10AlarmMaskAlarmCode,
                 zxr10AlarmMaskTPIDClass}
        ::= { zxr10AlarmMaskTable 1 }

Zxr10AlarmMaskEntry ::=
     SEQUENCE {
         zxr10AlarmMaskTPIDType 
             Integer32,
         zxr10AlarmMaskTPID 
             Tpid,
         zxr10AlarmMaskTPIDMask 
             OCTET STRING,
         zxr10AlarmMaskAlarmCode 
             Integer32,
         zxr10AlarmMaskTPIDClass 
             AlarmTPIDClass,
         zxr10AlarmMaskTPIDLen 
             Integer32,
         zxr10AlarmMaskRowStatus
             RowStatus
}

zxr10AlarmMaskTPIDType OBJECT-TYPE
        SYNTAX      Integer32(1..65535)
        MAX-ACCESS  not-accessible
        STATUS      current
        DESCRIPTION
            "Alarm mask TPID type."
        ::= { zxr10AlarmMaskEntry 1 } 

zxr10AlarmMaskTPID OBJECT-TYPE
        SYNTAX      Tpid
        MAX-ACCESS  not-accessible
        STATUS      current
        DESCRIPTION
            "Alarm mask TPID. Length is from 62 to 128 bytes. 
             Valid and invalid values are filled 
             in according to the check point specification."
        ::= { zxr10AlarmMaskEntry 2 }

zxr10AlarmMaskTPIDMask OBJECT-TYPE
        SYNTAX      OCTET STRING (SIZE (8..16)) 
        MAX-ACCESS  not-accessible
        STATUS      current
        DESCRIPTION
            "Each bit indicates whether the corresponding byte 
             in alarmMaskTPID is valid. 1 is valid, 0 is invalid."
        ::= { zxr10AlarmMaskEntry 3 }

zxr10AlarmMaskAlarmCode OBJECT-TYPE
        SYNTAX      Integer32
        MAX-ACCESS  not-accessible
        STATUS      current
        DESCRIPTION
            "Alarm code."
        ::= { zxr10AlarmMaskEntry 4 }

zxr10AlarmMaskTPIDClass OBJECT-TYPE
        SYNTAX      AlarmTPIDClass
        MAX-ACCESS  not-accessible
        STATUS      current
        DESCRIPTION
            "Alarm TPID class."
        ::= { zxr10AlarmMaskEntry 5 }

zxr10AlarmMaskTPIDLen OBJECT-TYPE
        SYNTAX      Integer32
        MAX-ACCESS  not-accessible
        STATUS      current
        DESCRIPTION
            "Alarm TPID length. Valid value range is from 62 to 128."
        ::= { zxr10AlarmMaskEntry 6 }

zxr10AlarmMaskRowStatus OBJECT-TYPE
        SYNTAX      RowStatus
        MAX-ACCESS  read-create
        STATUS      current
        DESCRIPTION   "Row status."
        ::= { zxr10AlarmMaskEntry 100 } 

zxr10AlmShdProfTable OBJECT-TYPE
        SYNTAX      SEQUENCE OF Zxr10AlmShdProfEntry
        MAX-ACCESS  not-accessible
        STATUS      current
        DESCRIPTION "A list of alarm shield profile entries."
        ::= { zxr10AlarmMIB 21 }

zxr10AlmShdProfEntry OBJECT-TYPE
        SYNTAX      Zxr10AlmShdProfEntry
        MAX-ACCESS  not-accessible
        STATUS      current
        DESCRIPTION "An alarm shield profile entry."
        INDEX  { zxr10AlmShdProfName }
        ::= { zxr10AlmShdProfTable 1 }

Zxr10AlmShdProfEntry ::=
     SEQUENCE {
         zxr10AlmShdProfName 
             ProfileName,
         zxr10AlmShdProfRowStatus
             RowStatus
}

zxr10AlmShdProfName OBJECT-TYPE
        SYNTAX      ProfileName 
        MAX-ACCESS  not-accessible
        STATUS      current
        DESCRIPTION
            "Alarm shield profile name."
        ::= { zxr10AlmShdProfEntry 1 }

zxr10AlmShdProfRowStatus OBJECT-TYPE
        SYNTAX      RowStatus
        MAX-ACCESS  read-create
        STATUS      current
        DESCRIPTION "Row status."
        ::= { zxr10AlmShdProfEntry 100 }
        
zxr10AlmShdProfCodeTable OBJECT-TYPE
        SYNTAX      SEQUENCE OF Zxr10AlmShdProfCodeEntry
        MAX-ACCESS  not-accessible
        STATUS      current
        DESCRIPTION "A list of alarm shield profile alarm code entries."
        ::= { zxr10AlarmMIB 22 }
        
zxr10AlmShdProfCodeEntry OBJECT-TYPE
        SYNTAX      Zxr10AlmShdProfCodeEntry
        MAX-ACCESS  not-accessible
        STATUS      current
        DESCRIPTION "An alarm shield profile alarm code entry."
        INDEX  { zxr10AlmShdProfName, zxr10AlmShdProfCodeAlmCode }
        ::= { zxr10AlmShdProfCodeTable 1 }

Zxr10AlmShdProfCodeEntry ::=
     SEQUENCE {
         zxr10AlmShdProfCodeAlmCode
             Unsigned32,
         zxr10AlmShdProfCodeStatus
             ProfileStatus,
         zxr10AlmShdProfCodeRowStatus
             RowStatus
}
        
zxr10AlmShdProfCodeAlmCode OBJECT-TYPE
        SYNTAX      Unsigned32
        MAX-ACCESS  not-accessible
        STATUS      current
        DESCRIPTION "Alarm code."
        ::= { zxr10AlmShdProfCodeEntry 1 }

zxr10AlmShdProfCodeStatus OBJECT-TYPE
        SYNTAX      ProfileStatus 
        MAX-ACCESS  read-create
        STATUS      current
        DESCRIPTION
            "Alarm shield profile status. 1:forever 2:once"
        ::= { zxr10AlmShdProfCodeEntry 2 }
        
zxr10AlmShdProfCodeRowStatus OBJECT-TYPE
        SYNTAX      RowStatus
        MAX-ACCESS  read-create
        STATUS      current
        DESCRIPTION "Row status."
        ::= { zxr10AlmShdProfCodeEntry 100 }
        
zxr10AlmShdProfApplyTable OBJECT-TYPE
        SYNTAX      SEQUENCE OF Zxr10AlmShdProfApplyEntry
        MAX-ACCESS  not-accessible
        STATUS      current
        DESCRIPTION "A list of alarm shield profile apply entries."
        ::= { zxr10AlarmMIB 23 }
        
zxr10AlmShdProfApplyEntry OBJECT-TYPE
        SYNTAX      Zxr10AlmShdProfApplyEntry
        MAX-ACCESS  not-accessible
        STATUS      current
        DESCRIPTION "An alarm shield profile apply entry."
        INDEX  { zxr10AlmShdProfName, zxr10AlmShdProfApplyFlag,
                 zxr10AlmShdProfApplyBrdName, zxr10AlmShdProfApplyIfName }
        ::= { zxr10AlmShdProfApplyTable 1 }

Zxr10AlmShdProfApplyEntry ::=
     SEQUENCE {
         zxr10AlmShdProfApplyFlag
             ProfileApplyFlag,
         zxr10AlmShdProfApplyBrdName
             OCTET STRING,
         zxr10AlmShdProfApplyIfName
             OCTET STRING,
         zxr10AlmShdProfApplyRowStatus
             RowStatus
}
        
zxr10AlmShdProfApplyFlag OBJECT-TYPE
        SYNTAX      ProfileApplyFlag 
        MAX-ACCESS  not-accessible
        STATUS      current
        DESCRIPTION
            "Alarm shield profile apply flag. 1:system 2:board 3:interface"
        ::= { zxr10AlmShdProfApplyEntry 1 }
        
zxr10AlmShdProfApplyBrdName OBJECT-TYPE
        SYNTAX      OCTET STRING (SIZE (0..31))
        MAX-ACCESS  not-accessible
        STATUS      current
        DESCRIPTION
            "Alarm shield profile apply board name."
        ::= { zxr10AlmShdProfApplyEntry 2 }
        
zxr10AlmShdProfApplyIfName OBJECT-TYPE
        SYNTAX      OCTET STRING (SIZE (0..31))
        MAX-ACCESS  not-accessible
        STATUS      current
        DESCRIPTION
            "Alarm shield profile apply interface name."
        ::= { zxr10AlmShdProfApplyEntry 3 }
        
zxr10AlmShdProfApplyRowStatus OBJECT-TYPE
        SYNTAX      RowStatus
        MAX-ACCESS  read-create
        STATUS      current
        DESCRIPTION "Row status."
        ::= { zxr10AlmShdProfApplyEntry 100 }

zxr10AlmTrapConfirmCfg OBJECT IDENTIFIER ::= { zxr10AlarmMIB 24  }

    zxr10AlmConfirmEnable OBJECT-TYPE
        SYNTAX INTEGER
            {
                enable(1),
                disable(2)
            }                
        MAX-ACCESS  read-write
        STATUS      current
        DESCRIPTION
            "Enable or disable the alarm confirm."
        ::= { zxr10AlmTrapConfirmCfg 1 }
        
    zxr10AlmConfirmTimeout    OBJECT-TYPE 
        SYNTAX INTEGER
            {
                interval10(10),
                interval20(20),
                interval60(60),
                interval120(120),
                interval180(180)
            }

        UNITS        "seconds"
        MAX-ACCESS   read-write
        STATUS       current
        DESCRIPTION       
            "Specifies the time-out value, in seconds, for an event to be
             confirmed.It must be set with zxr10AlmResendingTimes together."
        DEFVAL { interval20 }
        ::= { zxr10AlmTrapConfirmCfg 2 }
    
    zxr10AlmResendingTimes OBJECT-TYPE 
        SYNTAX       Integer32(1..3)
        MAX-ACCESS   read-write
        STATUS       current
        DESCRIPTION       
            "The resending event times when device does not receive 
            the event confirm message from the snmp manager.
            It must be set with zxr10AlmConfirmTimeout together."
        DEFVAL { 1 }
        ::= { zxr10AlmTrapConfirmCfg 3 }

zxr10AlmTrapConfirmOpt OBJECT IDENTIFIER ::= { zxr10AlarmMIB 25  }

    zxr10AlmConfirmFlowId OBJECT-TYPE
        SYNTAX      Integer32
        MAX-ACCESS   read-write
        STATUS      current
        DESCRIPTION
            "The cleard Flow Id to be confirmed by a snmp manager.
            When a manager receive a trap with confirmation information,
            then the manager should set this mib object to inform the agent
            that this manager has got this event.And then the agent should
            remove this event from a unconfirmed event queue. It must be 
            set with zxr10AlmConfirmAlarmStatus together."
        ::= { zxr10AlmTrapConfirmOpt 1 }
        
    zxr10AlmConfirmAlarmStatus OBJECT-TYPE
        SYNTAX INTEGER
            {
                appear(1),
                disappear(2),
                update(3),
                notify(4)
            }                
        MAX-ACCESS  read-write
        STATUS  current
        DESCRIPTION "The alarm status of the event to be confirmed."
        ::= { zxr10AlmTrapConfirmOpt 2 }


END
