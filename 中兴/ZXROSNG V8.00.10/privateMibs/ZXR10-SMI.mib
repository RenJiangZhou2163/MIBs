-- *****************************************************************
-- $Id: ZXR10-SMI.mib 27 2005-04-13 08:47:59Z taowq $
--
-- ZXR10-SMI.mib: ZTE Corporation Enterprise Structure of Management Information
--
-- April 2005, Tao wenqiang
--
-- Copyright (c) 2005 by ZTE Corporation
-- All rights reserved.
-- 
-- *****************************************************************
--

ZXR10-SMI DEFINITIONS ::= BEGIN

IMPORTS
    MODULE-IDENTITY,
    OBJECT-IDENTITY,
    enterprises
        FROM SNMPv2-SMI;

zte MODULE-IDENTITY
    LAST-UPDATED "201810080000Z"  
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS SMI MIB"
        
    REVISION "201810080000Z"
    DESCRIPTION
        "Add new node zxr10RosngAgentCapability." 
            
    REVISION "201504140000Z"
       DESCRIPTION
            "Delete the TAB char.
            " 
    REVISION "200504120000Z"  -- April 12, 2005
    DESCRIPTION
       ""
            
    ::= { enterprises 3902 }    -- assigned by IANA


zxr10 OBJECT-IDENTITY
    STATUS    current
    DESCRIPTION
        "zxr10 is the root OBJECT IDENTIFIER for ZTE
         routers and switches pruducts"
    ::= { zte 3 }
    
--XGW TCP
zxr10TCP OBJECT-IDENTITY
    STATUS current
    DESCRIPTION
        "ZXR10-TCP Project Object."
  ::= { zxr10 68 } 
    
zxr10protocol OBJECT-IDENTITY
    STATUS    current
    DESCRIPTION
        "Subtree beneath which protocol MIBS were built."
    ::= { zxr10 101 }
    
zxr10interfaces OBJECT-IDENTITY
    STATUS    current
    DESCRIPTION
        "Subtree beneath which switches MIBS were built."
    ::= { zxr10 103 }
 
zxr10L2vpn OBJECT-IDENTITY
    STATUS    current
    DESCRIPTION
        "Subtree beneath which switches MIBS were built."
    ::= { zxr10 104 }

zxr10L3vpn OBJECT-IDENTITY
    STATUS    current
    DESCRIPTION
        "Subtree beneath which switches MIBS were built."
    ::= { zxr10 105 }

zxr10AlarmMIB OBJECT-IDENTITY
    STATUS    current
    DESCRIPTION
        "Subtree beneath which switches MIBS were built."
    ::= { zxr10 302 }

--MPLS TE
zxr10MplsTe OBJECT-IDENTITY
    STATUS    current
    DESCRIPTION
        "Mpls Te Project Objects."
    ::= { zxr10 315 } 
         
--MPLS TE FRR         
zxr10MplsTeFrr OBJECT-IDENTITY
    STATUS current
    DESCRIPTION
        "MPLS-TE FRR Project Object."
  ::= { zxr10 316 }    
  
--MPLS OAM         
zxr10MplsOam OBJECT-IDENTITY
    STATUS current
    DESCRIPTION
        "MPLS OAM Project Object."
  ::= { zxr10 317 }   
  

--MPLSTE STATIC LSP         
mplsTeStaticLsp OBJECT-IDENTITY
    STATUS current
    DESCRIPTION
        "MPLSTE STATIC LSP Project Object."
  ::= { zxr10 320 }   
   
--rosng     
zxr10RosngMIB OBJECT-IDENTITY
       STATUS current
    DESCRIPTION
        "Subtree beneath which ROSNG MIBS were built."
  ::= { zxr10 6000 }    
  
--agent capability 
zxr10RosngAgentCapability  OBJECT-IDENTITY
    STATUS current
    DESCRIPTION
        "agent capability."
  ::= { zxr10RosngMIB 1000 }
  
  
END
