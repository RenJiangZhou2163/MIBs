ZXR10-PORT-GROUP-MIB DEFINITIONS ::= BEGIN

    IMPORTS
       MODULE-IDENTITY,
       OBJECT-TYPE,
       Unsigned32,
       Integer32,
       enterprises     
           FROM SNMPv2-SMI
       DisplayString 
           FROM SNMPv2-TC;
                                               
    zxr10PortGroupMIB MODULE-IDENTITY
        LAST-UPDATED "201804211000Z"  --2018-04-21 10:00
        ORGANIZATION "ZTE Corporation"
        CONTACT-INFO
            "       Yu tongquan 
            Tel:    +86-25-52870379
            E-Mail: yu.tongquan@zte.com.cn"

        DESCRIPTION
            "The MIB module to describe the port group"
        REVISION "201804211000Z"  --2018-04-21 10:00
        DESCRIPTION
            "Modify the description and syntax clause of zxr10PortGroupType."
        
        REVISION "201406251000Z"  --2014-06-25 10:00
        DESCRIPTION
            "Modify the description and syntax clause of zxr10PortGroupID and zxr10PortGroupStatusPGID"
        
        REVISION "201403211000Z"  --2014-03-21 10:00
        DESCRIPTION
            "Modify the description and syntax clause of zxr10PortGroupType."

        REVISION "201304221000Z"  --2013-04-22 10:00
        DESCRIPTION
            "modify: zxr10PortGroupCommunicateUnit"

        REVISION "201303191000Z"  --2013-03-19 10:00
        DESCRIPTION
            "Initial version of this MIB module."
        ::= { zxr10RosngMIB 520}  
        
    zte OBJECT IDENTIFIER ::={enterprises 3902}
    zxr10 OBJECT IDENTIFIER ::={zte 3}
 
    zxr10RosngMIB OBJECT IDENTIFIER ::= { zxr10 6000}

 -- Port group interface configuration table
 
    zxr10PortGroupConfigTable  OBJECT-TYPE
        SYNTAX  SEQUENCE OF Zxr10PortGroupConfigEntry
        MAX-ACCESS  not-accessible
        STATUS  current
        DESCRIPTION
            "Port protection group configuration table"
        ::= { zxr10PortGroupMIB 1 }
        
    zxr10PortGroupConfigEntry  OBJECT-TYPE
        SYNTAX  Zxr10PortGroupConfigEntry
        MAX-ACCESS  not-accessible
        STATUS  current
        DESCRIPTION
            "Port protection group configuration information"
        INDEX  { zxr10PortGroupID }
        ::= { zxr10PortGroupConfigTable 1 }
        
    Zxr10PortGroupConfigEntry ::=
        SEQUENCE {
            zxr10PortGroupID                    Integer32, 
            zxr10PortGroupType                  INTEGER,
            zxr10PortGroupProtectType           INTEGER,
            zxr10PortGroupProtectDirection      INTEGER,
            zxr10PortGroupProtectReceiver       INTEGER,
            zxr10PortGroupWorkPort              DisplayString,
            zxr10PortGroupBackupPort            DisplayString,
            zxr10PortGroupSwitchStrategy        INTEGER,
            zxr10PortGroupCommunicateUnit       Unsigned32
    }
    
    zxr10PortGroupID  OBJECT-TYPE
        SYNTAX      Integer32(1..65536) 
        MAX-ACCESS  not-accessible
        STATUS      current
        DESCRIPTION
            "Port protection group ID,
             it's maximum value depends on the performance parameter"
        ::= { zxr10PortGroupConfigEntry 1 } 
        
     zxr10PortGroupType  OBJECT-TYPE
        SYNTAX      INTEGER
                    {
                        unknown(1),
                        msp(2),
                        mcaps(3),
                        multicast(4),
                        otn(5),
                        etherService(6),
                        flexeCross(7),
                        flexeTerminal(8)
                    }  
        MAX-ACCESS  read-only
        STATUS      current
        DESCRIPTION
            "Group type(1:unknown, 2:msp, 3:mcaps, 4:multicast, 5:otn,6:ether-service,7:flexe-cross,8:flexe-terminal)"
        ::= { zxr10PortGroupConfigEntry 2 }   
        
     zxr10PortGroupProtectType  OBJECT-TYPE
        SYNTAX      INTEGER
                    {
                        unknown(1),
                        oneByOne(2),
                        onePlusOne(3)
                    }  
        MAX-ACCESS  read-only
        STATUS      current
        DESCRIPTION
            "Protection type(OneByOne:1:1, OnePlusOne:1+1)"
        ::= { zxr10PortGroupConfigEntry 3 }   
        
     zxr10PortGroupProtectDirection  OBJECT-TYPE
        SYNTAX      INTEGER
                    {
                        unknown(1),
                        unidirectional(2),
                        bidirectional(3)
                    }  
        MAX-ACCESS  read-only
        STATUS      current
        DESCRIPTION
            "Protection direction(1:unknown, 2:unidirectional, 3:bidirectional)"
        ::= { zxr10PortGroupConfigEntry 4 }   
        
     zxr10PortGroupProtectReceiver  OBJECT-TYPE
        SYNTAX      INTEGER
                    {
                        unknown(1),
                        selective(2)
                    } 
        MAX-ACCESS  read-only
        STATUS      current
        DESCRIPTION
            "Protection receiver(1:unknown, 2:selective)"
        ::= { zxr10PortGroupConfigEntry 5 } 
        
     zxr10PortGroupWorkPort  OBJECT-TYPE
        SYNTAX      DisplayString(SIZE(1..32))
        MAX-ACCESS  read-only
        STATUS      current
        DESCRIPTION
            "Working port name"
        ::= { zxr10PortGroupConfigEntry 6 } 
        
     zxr10PortGroupBackupPort  OBJECT-TYPE
        SYNTAX      DisplayString(SIZE(1..32))
        MAX-ACCESS  read-only
        STATUS      current
        DESCRIPTION
            "Protection port name"
        ::= { zxr10PortGroupConfigEntry 7 } 

     zxr10PortGroupSwitchStrategy  OBJECT-TYPE
        SYNTAX      INTEGER
                    {
                        unknown(1),
                        aps(2)
                    }   
        MAX-ACCESS  read-only
        STATUS      current
        DESCRIPTION
            "Protection switch strategy, port protection group can only config APS"
        ::= { zxr10PortGroupConfigEntry 8 } 

     zxr10PortGroupCommunicateUnit  OBJECT-TYPE
        SYNTAX      Unsigned32(1..4294967295)  
        MAX-ACCESS  read-only
        STATUS      current
        DESCRIPTION
            "Communication unit of MCAPS port group.
             The maximum can be configured is dynamically defined."
        ::= { zxr10PortGroupConfigEntry 9 }

 -- define port group status table 
    zxr10PortGroupStatusTable  OBJECT-TYPE
        SYNTAX  SEQUENCE OF Zxr10PortGroupStatusEntry
        MAX-ACCESS  not-accessible
        STATUS  current
        DESCRIPTION
            "Port protection group status table"
        ::= { zxr10PortGroupMIB 2}
        
    zxr10PortGroupStatusEntry  OBJECT-TYPE
        SYNTAX  Zxr10PortGroupStatusEntry
        MAX-ACCESS  not-accessible
        STATUS  current
        DESCRIPTION
            "Port protection group status information"
        INDEX  { zxr10PortGroupStatusPGID }
        ::= { zxr10PortGroupStatusTable 1 }
        
    Zxr10PortGroupStatusEntry ::=
        SEQUENCE {
            zxr10PortGroupStatusPGID                  Integer32, 
            zxr10PortGroupStatusWPortState            INTEGER,
            zxr10PortGroupStatusBPortState            INTEGER,
            zxr10PortGroupStatusSwitchFlag            INTEGER
    }
    
    zxr10PortGroupStatusPGID  OBJECT-TYPE
        SYNTAX      Integer32(1..65536)
        MAX-ACCESS  not-accessible
        STATUS      current
        DESCRIPTION
            "Port protection group ID,
             it's maximum value depends on the performance parameter"
        ::= { zxr10PortGroupStatusEntry 1 } 
        
     zxr10PortGroupStatusWPortState  OBJECT-TYPE
        SYNTAX      INTEGER
                    {
                        ok(1),
                        sf(2),
                        sd(3)
                    }  
        MAX-ACCESS  read-only 
        STATUS      current
        DESCRIPTION
            "The state of working port(1:OK, 2:SF, 3:SD)"
        ::= { zxr10PortGroupStatusEntry 2 }   
        
     zxr10PortGroupStatusBPortState  OBJECT-TYPE
        SYNTAX      INTEGER
                    {
                        ok(1),
                        sf(2),
                        sd(3)
                    }  
        MAX-ACCESS  read-only 
        STATUS      current
        DESCRIPTION
            "The state of protection port(1:OK, 2:SF, 3:SD)"
        ::= { zxr10PortGroupStatusEntry 3 }   
        
     zxr10PortGroupStatusSwitchFlag  OBJECT-TYPE
        SYNTAX      INTEGER
                    {
                        unknown(1),
                        switch(2),
                        unSwitch(3),
                        switchWork(4),
                        switchProtect(5)
                    }  
        MAX-ACCESS  read-only 
        STATUS      current
        DESCRIPTION
            "The switch flag of port protection group(2:switch, 3:no switch)"
        ::= { zxr10PortGroupStatusEntry 4 } 
        
 END
