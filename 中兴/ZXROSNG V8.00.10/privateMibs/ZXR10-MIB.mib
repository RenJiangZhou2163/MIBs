ZXR10-MIB DEFINITIONS ::= BEGIN

   IMPORTS
       MODULE-IDENTITY, OBJECT-TYPE, OBJECT-IDENTITY, Counter32, Gauge32,
       Integer32, TimeTicks, Counter64,
       NOTIFICATION-TYPE,
       enterprises                      FROM SNMPv2-SMI
       MacAddress
                FROM SNMPv2-TC
                  mgmt, NetworkAddress, IpAddress, Counter, Gauge
                         FROM RFC1155-SMI
      --         Counter, TimeTicks     FROM RFC1155-SMI
      -- IpAddress,DisplayString, mib-2   FROM RFC1213-MIB
      --            OBJECT-TYPE            FROM RFC-1212
                  TRAP-TYPE              FROM RFC-1215;

   zte OBJECT IDENTIFIER ::= { enterprises 3902 }
   zxr10 OBJECT IDENTIFIER ::= { zte 3}

       -- LAST-UPDATED "0108230840Z"
       -- ORGANIZATION "ZTE"
       -- CONTACT-INFO

       -- Nanjing Institute of Telecom,ZTE Corporation
       -- Postal: 9F. No.54 Building, 301# East ZhongShan Rd.
       -- Nan Jing, China
       -- Tel:    86-25-4826606-3821
       -- E-Mail: li.xinshuang@mail.zte.com.cn
       -- DESCRIPTION
       -- The MIB module which descript the zxr10rack mib
       -- object which defined in enterprise's ZTE(3902)
      
END
