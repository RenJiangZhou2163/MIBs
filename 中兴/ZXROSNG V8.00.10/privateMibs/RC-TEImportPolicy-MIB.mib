RC-TEImportPolicy-MIB DEFINITIONS ::= BEGIN

IMPORTS
    OBJECT-TYPE, MODULE-IDENTITY, Unsigned32, IpAddress  
            FROM SNMPv2-SMI
    MacAddress, DisplayString, RowStatus
            FROM SNMPv2-TC   
    rc 
            FROM RC-SMI;  

rcTEImportPolicy MODULE-IDENTITY
                 LAST-UPDATED
                "201212110000Z"
                ORGANIZATION
                ""
                CONTACT-INFO
                " "
                DESCRIPTION
                ""
                REVISION
                "201212110000Z" 
                DESCRIPTION
                ""
                ::= { rc 2}                      

--------------------------------------------------------------
--  rcRouteMapTable
--------------------------------------------------------------   
    rcRouteMapTable OBJECT-TYPE
        SYNTAX  SEQUENCE OF RcRouteMapEntry
        MAX-ACCESS  not-accessible
        STATUS  current
        DESCRIPTION
                ""
        ::= { rcTEImportPolicy 1  }

    rcRouteMapEntry OBJECT-TYPE
        SYNTAX   RcRouteMapEntry
        MAX-ACCESS  not-accessible
        STATUS  current
        DESCRIPTION
                ""
        INDEX {rcRouteMapname,rcRouteMapIndex,rcRouteMapIntanceIndex}
        ::= { rcRouteMapTable 1 }

    RcRouteMapEntry ::=SEQUENCE {
                rcRouteMapname                                      DisplayString,
                rcRouteMapIndex                                     Unsigned32,
                rcRouteMapIntanceIndex                              Unsigned32,
                rcRouteMapMatchAcl                                  DisplayString,
                rcRouteMapSetIntfTunnelID                           Unsigned32,
                rcRouteMapRowSta                                    RowStatus
        }

    rcRouteMapname OBJECT-TYPE
        SYNTAX   DisplayString(SIZE(1..31))
        MAX-ACCESS  not-accessible
        STATUS  current
        DESCRIPTION
                "RouteMap name"
        ::= { rcRouteMapEntry  1  }
        
    rcRouteMapIndex OBJECT-TYPE
        SYNTAX   Unsigned32(1..1000)
        MAX-ACCESS  not-accessible
        STATUS  current
        DESCRIPTION
                "The index of RouteMap"
        ::= { rcRouteMapEntry  2  }

    rcRouteMapIntanceIndex OBJECT-TYPE
        SYNTAX   Unsigned32(1..100)
        MAX-ACCESS  not-accessible
        STATUS  current
        DESCRIPTION
                ""
        ::= { rcRouteMapEntry  3  }

    rcRouteMapMatchAcl OBJECT-TYPE
        SYNTAX   DisplayString(SIZE(1..31))
        MAX-ACCESS  read-create
        STATUS  current
        DESCRIPTION
                "ACL name"
        ::= { rcRouteMapEntry  4  }
                                                           
    rcRouteMapSetIntfTunnelID OBJECT-TYPE
        SYNTAX   Unsigned32(1..4000)
        MAX-ACCESS  read-create
        STATUS  current
        DESCRIPTION
                "TE Tunnel ID"
        ::= { rcRouteMapEntry  5  } 

    rcRouteMapRowSta OBJECT-TYPE
      SYNTAX       RowStatus
      MAX-ACCESS   read-create
      STATUS        current
      DESCRIPTION
           "This variable is used to create, modify, and/or
            delete a row in this table. "
      ::= { rcRouteMapEntry 6 }    
     
--------------------------------------------------------------
--------------------------------------------------------------
--rcPolicyRouteTable  
--------------------------------------------------------------
rcPolicyRouteTable OBJECT-TYPE
        SYNTAX  SEQUENCE OF RcPolicyRouteEntry
        MAX-ACCESS  not-accessible
        STATUS  current
        DESCRIPTION
                "ROUTE_MAP"
        ::= { rcTEImportPolicy 2  }

rcPolicyRouteEntry OBJECT-TYPE
        SYNTAX   RcPolicyRouteEntry
        MAX-ACCESS  not-accessible
        STATUS  current
        DESCRIPTION
                "IP POLICY"
        INDEX {rcInterfacename,rcRefRouteMapname,rcRefRouteMapIndex}
        ::= { rcPolicyRouteTable 1 }

RcPolicyRouteEntry ::=
        SEQUENCE {
                rcInterfacename                                DisplayString,
                rcRefRouteMapname                              DisplayString,
                rcRefRouteMapIndex                             Unsigned32,
                rcPolicyRouteRowSta                            RowStatus
        }

rcInterfacename OBJECT-TYPE
        SYNTAX   DisplayString(SIZE(1..31))
        MAX-ACCESS  not-accessible
        STATUS  current
        DESCRIPTION
                "The name of Interface"
        ::= { rcPolicyRouteEntry  1  }

rcRefRouteMapname OBJECT-TYPE
        SYNTAX   DisplayString(SIZE(1..31))
        MAX-ACCESS  not-accessible
        STATUS  current
        DESCRIPTION
                "The name of RouteMap"
        ::= { rcPolicyRouteEntry  2  }   
        
rcRefRouteMapIndex OBJECT-TYPE
        SYNTAX   Unsigned32(1..1000)
        MAX-ACCESS  not-accessible
        STATUS  current
        DESCRIPTION
                "The index of RouteMap"
        ::= { rcPolicyRouteEntry  3  } 
        
rcPolicyRouteRowSta OBJECT-TYPE
      SYNTAX       RowStatus
      MAX-ACCESS   read-create
      STATUS        current
      DESCRIPTION
           "This variable is used to create, modify, and/or
            delete a row in this table. "
      ::= { rcPolicyRouteEntry 4 }    
        
        
--------------------------------------------------------------
--------------------------------------------------------------
--rcACLTable  
--------------------------------------------------------------
rcACLTable OBJECT-TYPE
        SYNTAX  SEQUENCE OF RcACLEntry
        MAX-ACCESS  not-accessible
        STATUS  current
        DESCRIPTION
                ""
        ::= { rcTEImportPolicy 3  }

rcACLEntry OBJECT-TYPE
        SYNTAX   RcACLEntry
        MAX-ACCESS  not-accessible
        STATUS  current
        DESCRIPTION
                ""
        INDEX {rcIPv4ACLName,rcIPv4ACLRuleID}
        ::= { rcACLTable 1 }

RcACLEntry ::=
        SEQUENCE {
                rcIPv4ACLName                                DisplayString,
                rcIPv4ACLRuleID                              Unsigned32,
                rcIPv4ACLSrcAddr                             IpAddress,
                rcIPv4ACLSrcWildcard                         IpAddress,
                rcIPv4ACLDestAddr                            IpAddress,
                rcIPv4ACLDestWildcard                        IpAddress,
                rcIPv4ACLProtocol                            Unsigned32,
                rcIPv4ACLSrcPortBegin                        Unsigned32,                
                rcIPv4ACLSrcPortEnd                          Unsigned32,
                rcIPv4ACLDestPortBegin                       Unsigned32,
                rcIPv4ACLDestPortEnd                         Unsigned32,
                rcIPv4ACLDSCP                                Unsigned32,
                rcIPV4ACLRowsta                              RowStatus
        }

rcIPv4ACLName OBJECT-TYPE
        SYNTAX   DisplayString(SIZE(1..31))
        MAX-ACCESS  not-accessible
        STATUS  current
        DESCRIPTION
                "WORD  Name of an IPv4 access-list "
        ::= { rcACLEntry  1  }

rcIPv4ACLRuleID OBJECT-TYPE
        SYNTAX   Unsigned32(1..65535)
        MAX-ACCESS  not-accessible
        STATUS  current
        DESCRIPTION
                ""
        ::= { rcACLEntry  2  }  
        
rcIPv4ACLSrcAddr OBJECT-TYPE
        SYNTAX   IpAddress
        MAX-ACCESS  read-create
        STATUS  current
        DESCRIPTION
                "A.B.C.D  Source address"
        ::= { rcACLEntry  3  }  
        
rcIPv4ACLSrcWildcard OBJECT-TYPE
        SYNTAX   IpAddress
        MAX-ACCESS  read-create
        STATUS  current
        DESCRIPTION
                "The mask of the source IP address"
        ::= { rcACLEntry  4  } 
        
rcIPv4ACLDestAddr OBJECT-TYPE
        SYNTAX   IpAddress
        MAX-ACCESS  read-create
        STATUS  current
        DESCRIPTION
                "Destination IP address"
        ::= { rcACLEntry  5  } 
        
rcIPv4ACLDestWildcard OBJECT-TYPE
        SYNTAX   IpAddress
        MAX-ACCESS  read-create
        STATUS  current
        DESCRIPTION
                "The mask of the source IP address"
        ::= { rcACLEntry  6  } 
        
rcIPv4ACLProtocol OBJECT-TYPE
        SYNTAX   Unsigned32(0..255)
        MAX-ACCESS  read-create
        STATUS  current
        DESCRIPTION
                "IP protocol"
        ::= { rcACLEntry  7  }
        
rcIPv4ACLSrcPortBegin OBJECT-TYPE
        SYNTAX   Unsigned32(0..65535)
        MAX-ACCESS  read-create
        STATUS  current
        DESCRIPTION
                "The begin of the source port range"
        ::= { rcACLEntry  8  }
        
rcIPv4ACLSrcPortEnd OBJECT-TYPE
        SYNTAX   Unsigned32(0..65535)
        MAX-ACCESS  read-create
        STATUS  current
        DESCRIPTION
                "The end of the source port range"
        ::= { rcACLEntry  9  }
        
rcIPv4ACLDestPortBegin OBJECT-TYPE
        SYNTAX   Unsigned32(0..65535)
        MAX-ACCESS  read-create
        STATUS  current
        DESCRIPTION
                "The begin of the destination port range"
        ::= { rcACLEntry  10  }
        
rcIPv4ACLDestPortEnd OBJECT-TYPE
        SYNTAX   Unsigned32(0..65535)
        MAX-ACCESS  read-create
        STATUS  current
        DESCRIPTION
                "The end of the destination port range"
        ::= { rcACLEntry  11  }
    
rcIPv4ACLDSCP OBJECT-TYPE
        SYNTAX   Unsigned32(0..63|255)
        MAX-ACCESS  read-create
        STATUS  current
        DESCRIPTION
                "DSCP value"
        ::= { rcACLEntry  12  }
        
rcIPV4ACLRowsta OBJECT-TYPE
      SYNTAX       RowStatus
      MAX-ACCESS   read-create
      STATUS        current
      DESCRIPTION
           "This variable is used to create, modify, and/or
            delete a row in this table. "
      ::= { rcACLEntry 13 }            
    
END
