-- *****************************************************************
-- $Id: rosngmplsVpnPrivateMIB.mib  $
--
-- rosngmplsVpnPrivate.mib: ZTE Corporation Enterprise Structure of Management Information
--
-- Dec 2009, zhouzheng
--
-- Copyright (c) 2009-2010 by ZTE Corporation
-- All rights reserved.
-- 
-- *****************************************************************
--
ROSNG-VPN-PRIVATE-MIB DEFINITIONS ::= BEGIN

IMPORTS
	MODULE-IDENTITY,OBJECT-IDENTITY,
	OBJECT-TYPE,
	enterprises,TimeTicks,Unsigned32
		FROM SNMPv2-SMI
	mplsL3VpnVrfName
	    FROM MPLS-L3VPN-STD-MIB
	DisplayString
        FROM SNMPv2-TC;
zte MODULE-IDENTITY
    LAST-UPDATED "200504120000Z"  -- April 12, 2005
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS SMI MIB"

    REVISION "200504120000Z"  -- April 12, 2005
    DESCRIPTION
       ""
	::= { enterprises 3902 }	-- assigned by IANA
		
zxr10      OBJECT IDENTIFIER ::= { zte 3}
zxr10RosngMIB      OBJECT IDENTIFIER ::= { zxr10 6000 }	

rosngmplsVpnPrivateMIB OBJECT-IDENTITY
			STATUS current
			--DESCRIPTION
			-- "This mib is created for China Mobile test"
			--LAST-UPDATED "20091214"
			--ORGANIZATION "ZTE Corporation Enterprise Structure of Management Information"
			--CONTACT-INFO
			--	"ZTE Corporation Enterprise Structure of Management Information"
	
			DESCRIPTION
				"ZTE Corporation Enterprise Structure of Management Information"

    ::= { zxr10RosngMIB 105 }	
	
-- tables
            rosngmplsVpnPrivateObjects OBJECT IDENTIFIER ::= { rosngmplsVpnPrivateMIB 1 }
			
		-- mplsVpn private table.
		rosngmplsVpnPrivateTable OBJECT-TYPE
			SYNTAX SEQUENCE OF RosngmplsVpnPrivateEntry
			MAX-ACCESS not-accessible
			STATUS current
			DESCRIPTION
				   	"This rosngmplsVpnPrivateTable is ."
			::= { rosngmplsVpnPrivateObjects 1 }  
			
	    rosngmplsVpnPrivateEntry OBJECT-TYPE
			SYNTAX RosngmplsVpnPrivateEntry
			MAX-ACCESS not-accessible
			STATUS current
			DESCRIPTION	  
			      "Entry containing information about a particular VPN."
			REFERENCE
				"RFC 2547 VPNs (see draft-ietf-ppvpn-rfc2547bis)"
			INDEX { mplsL3VpnVrfName 
				  }
			::= { rosngmplsVpnPrivateTable 1 }
			
			
			RosngmplsVpnPrivateEntry ::= SEQUENCE {
        		rosngmplsVpnPrivateVpnType INTEGER,
        		rosngmplsVpnPrivateVpnIdType INTEGER,
        		rosngmplsVpnPrivateL2VpnConnectStatus INTEGER,
        		rosngmplsVpnPrivateL3VpnConnectStatus INTEGER,
				rosngmplsVpnPrivateVpnAge TimeTicks,
				rosngmplsVpnPrivateVrfConfRouteWarningPercent   Unsigned32
        	}		      
			
			rosngmplsVpnPrivateVpnType OBJECT-TYPE
			SYNTAX      INTEGER {
            other(1),
            bgpIpVpn(2),
            bgpL2Vpn(3),
            bgpVpls(4),
            l2Circuit(5),
            ldpVpls(6),
            opticalVpn(7),
            vpOxc(8),
            ccc(9),
	        bgpAtmVpn(10)
            }
			MAX-ACCESS read-only
			STATUS current
			DESCRIPTION
			"Type of the VPN.  The following types have been defined:
            bgpIpVpn:   RFC 2547 VPNs (see draft-ietf-ppvpn-rfc2547bis);
            bgpL2Vpn:   BGP-based Layer 2 VPNs (see
                        draft-kompella-ppvpn-l2vpn);
            bgpVpls:    BGP-based VPLS (see draft-kompella-ppvnp-vpls);
            l2Circuit:  LDP-based point-to-point Layer 2 circuits (see
                        draft-martini-l2circuit-trans-mpls);
            ldpVpls:    LDP-based VPLS (see
                        draft-lasserre-vkompella-ppvpn-vpls);
            opticalVpn: BGP-based Optical (port based) VPNs (see
                        draft-ouldbrahim-bgpgmpls-ovpn);
            vpOxc:         Virtual Private Optical Cross-Connect (see
                        draft-ouldbrahim-ppvpn-vpoxc);
            ccc:        proprietary Layer 2 circuit;
            bgpAtmVpn:  ATM over MPLS (draft to be published)."
			::= { rosngmplsVpnPrivateEntry 1 }
			
			rosngmplsVpnPrivateVpnIdType OBJECT-TYPE
			SYNTAX  INTEGER {
            none(0),
            other(1),
            routeDistinguisher(2),
            routeDistinguisher0(3),
            routeDistinguisher1(4),
            routeDistinguisher2(5),
            routeTarget(6),
            routeTarget0(7),
            routeTarget1(8),
            routeTarget2(9),
            vcId(10),
            localSwitch(11)
            }
			MAX-ACCESS read-only
			STATUS current
			DESCRIPTION
			"Type of the VPN Identifier.  This includes Route
             Distinguishers, Route Targets, and VC IDs."
			::= { rosngmplsVpnPrivateEntry 2 }
			
			rosngmplsVpnPrivateL2VpnConnectStatus OBJECT-TYPE
			SYNTAX  INTEGER {
            active(1),
            limbo(2)
            }
			MAX-ACCESS read-only
			STATUS current
			DESCRIPTION
			"The connect status of Layer 2 VPNs."
			::= { rosngmplsVpnPrivateEntry 3 }
			
			rosngmplsVpnPrivateL3VpnConnectStatus OBJECT-TYPE
			SYNTAX  INTEGER {
            active(1),
            limbo(2)
            }
			MAX-ACCESS read-only
			STATUS current
			DESCRIPTION
			"The connect status of Layer 3 VPNs."
			::= { rosngmplsVpnPrivateEntry 4 }
			
			rosngmplsVpnPrivateVpnAge OBJECT-TYPE
            SYNTAX     TimeTicks
            MAX-ACCESS read-only
            STATUS     current
            DESCRIPTION
            "The age (i.e., time from creation till now) of this
             VPN in hundredths of a second."
            ::= { rosngmplsVpnPrivateEntry 5 }
            rosngmplsVpnPrivateVrfConfRouteWarningPercent     OBJECT-TYPE
            SYNTAX        Unsigned32
            MAX-ACCESS    read-only
            STATUS        current
            DESCRIPTION
            "The threshol value (%) at which to give a warning."
            ::= { rosngmplsVpnPrivateEntry 6 }
   
            zxr10MplsVpnGlobalPara OBJECT IDENTIFIER ::= { rosngmplsVpnPrivateMIB 2 }
            
			zxr10MplsVpnGlobalVrfCapacity OBJECT-TYPE
			SYNTAX      Unsigned32
			MAX-ACCESS read-only
			STATUS current
			DESCRIPTION
			"The number of VRFs that are configured in the global."
			::= { zxr10MplsVpnGlobalPara 1 }
            			
	END
