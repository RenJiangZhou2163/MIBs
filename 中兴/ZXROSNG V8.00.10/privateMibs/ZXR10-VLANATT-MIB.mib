--  ********************************************************
--  $Id: ZXR10-VLAN.mib 2010-03-01 01:34:21Z Jiashurui $
--
--  ZXR10-VlanAtt-MIB: ZXR10 VLAN MIB file
--
--  Mar. 2010, Jia Shurui
--  modify by yuly 187517
--  Copyright(c) 2010 by ZTE Corporation
--  All rights reserved
--
--  ********************************************************

ZXR10-VLANATT-MIB DEFINITIONS ::= BEGIN

IMPORTS
    MODULE-IDENTITY, 
    OBJECT-TYPE, 
    Unsigned32,
    Counter64
        FROM SNMPv2-SMI
    enterprises                      
        FROM SNMPv2-SMI    
    TEXTUAL-CONVENTION,  
    RowStatus,
    DisplayString
        FROM SNMPv2-TC;

        
zte MODULE-IDENTITY
    LAST-UPDATED "201404041000Z"  --2014-04-04 10:00
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS SMI MIB"

    REVISION "201404041000Z"  --2014-04-04 10:00 
    DESCRIPTION
        "modify:    
                    zxr10VlanIfConfigEntry DESCRIPTION
        "
        
    REVISION "201308061000Z"  --2013-06-04 10:00 
    DESCRIPTION
        "modify:    
                    PidtagType
        "
        
    REVISION "201306041400Z"  --2013-06-04 14:00 
    DESCRIPTION
        "modify:    zxr10VlanAttExterPid
                    zxr10VlanAttInterPid
                    zxr10VlanAttRangeFlag
                    zxr10VlanAttSingleLayer
        "

    REVISION "201303261400Z"  --2013-03-26 14:00 
    DESCRIPTION
        "add:       zxr10VlanTpidTable
                    zxr10VlanRangeFlagTable
                    PidtagType
                    EnabledStatus
         modify:    EncapsulationType
        "


    REVISION "201101190000Z"  -- Nov 19, 2011
    DESCRIPTION
       ""
    ::= { enterprises 3902 }    -- assigned by IANA

    zxr10 OBJECT IDENTIFIER ::= { zte 3}
    zxr10switch OBJECT IDENTIFIER ::= { zxr10 102}
    zxr10VlanAtt OBJECT IDENTIFIER ::= {  zxr10switch 52}
    
    

    EncapsulationType ::= TEXTUAL-CONVENTION
          STATUS        current
          DESCRIPTION   "Enc Type"
          SYNTAX        INTEGER
                        {       
                           none(1),
                           dot1q(2),
                           qinq(3),    
                           dot1q_range(4),
                           qinq_range(5)
                        }

    PidtagType ::= TEXTUAL-CONVENTION
          STATUS        current
          DESCRIPTION   "Pidtag Type"
          SYNTAX        INTEGER
                        {       
                           pidtag88a8(1),
                           pidtag8100(2),
                           pidtag9100(3),
                           pidtag9200(4),
                           pidtag9300(5),
                           pidtag88e8(6)
                        }

    EnabledStatus ::= TEXTUAL-CONVENTION
          STATUS current
          DESCRIPTION   "A simple status value for the object."
          SYNTAX        INTEGER 
                        {  enabled(1),
                           disabled(2)
                        }

---vlanIntfAtt      




    zxr10VlanAttTable   OBJECT-TYPE
        SYNTAX          SEQUENCE OF Zxr10VlanAttEntry
        MAX-ACCESS      not-accessible
        STATUS          current
        DESCRIPTION   "Configure VLAN Intf Att parameters."
        ::=  { zxr10VlanAtt  1 }

    zxr10VlanAttEntry   OBJECT-TYPE
        SYNTAX          Zxr10VlanAttEntry
        MAX-ACCESS      not-accessible
        STATUS          current
        DESCRIPTION   "Each row index by ifIndex and AttNo
                     And contain imformation of VLAN."
        INDEX            {  zxr10VlanAttIntfIndex , zxr10VlanAttAttNo  }
        ::=  { zxr10VlanAttTable 1 }

    Zxr10VlanAttEntry
        ::=  SEQUENCE
        {
            zxr10VlanAttIntfIndex                         Unsigned32,      
            zxr10VlanAttIntfName                          DisplayString,   
            zxr10VlanAttParentIfIndex                     Unsigned32,
            zxr10VlanAttParentIfName                      DisplayString,
            zxr10VlanAttEncType                           EncapsulationType,
            zxr10VlanAttAttNo                             Unsigned32,
            zxr10VlanAttInterVlan                         DisplayString,
            zxr10VlanAttExterVlan                         DisplayString
        }

    zxr10VlanAttIntfIndex   OBJECT-TYPE
        SYNTAX          Unsigned32
        MAX-ACCESS      read-only
        STATUS          current
        DESCRIPTION   "Interface Index."
        ::=  { zxr10VlanAttEntry  1 }

    zxr10VlanAttIntfName   OBJECT-TYPE
        SYNTAX          DisplayString
        MAX-ACCESS      read-only
        STATUS          current
        DESCRIPTION   "Interface Name."
        ::=  { zxr10VlanAttEntry  2 }    

    zxr10VlanAttParentIfIndex   OBJECT-TYPE
        SYNTAX          Unsigned32
        MAX-ACCESS      read-only
        STATUS          current
        DESCRIPTION     "Parent Interface Index."
        ::=  { zxr10VlanAttEntry  3 }

    zxr10VlanAttParentIfName   OBJECT-TYPE
        SYNTAX          DisplayString
        MAX-ACCESS      read-only
        STATUS          current
        DESCRIPTION   "Parent Interface Name."
        ::=  { zxr10VlanAttEntry  4 }

    zxr10VlanAttEncType   OBJECT-TYPE
        SYNTAX          EncapsulationType
        MAX-ACCESS      read-only
        STATUS          current
        DESCRIPTION   "Encapsulation Type."
        ::=  { zxr10VlanAttEntry  5 }              

    zxr10VlanAttAttNo   OBJECT-TYPE
        SYNTAX          Unsigned32
        MAX-ACCESS      read-only
        STATUS          current
        DESCRIPTION   "Att No"
        ::=  { zxr10VlanAttEntry  6 }

    zxr10VlanAttInterVlan   OBJECT-TYPE
        SYNTAX          DisplayString
        MAX-ACCESS      read-only
        STATUS          current
        DESCRIPTION   "Internal Vlan."
        ::=  { zxr10VlanAttEntry  7 }

    zxr10VlanAttExterVlan   OBJECT-TYPE
        SYNTAX          DisplayString
        MAX-ACCESS      read-only
        STATUS          current
        DESCRIPTION   "External Vlan."
        ::=  { zxr10VlanAttEntry  8 }






---zxr10IfVlanTrafficStatTable      

    zxr10IfVlanTrafficStatTable  OBJECT-TYPE
        SYNTAX        SEQUENCE OF Zxr10IfVlanTrafficStatEntry
        MAX-ACCESS    not-accessible
        STATUS        current
        DESCRIPTION   "Traffic Statistic for qinq vlan."
        ::=  { zxr10VlanAtt  2 }

    zxr10IfVlanTrafficStatEntry  OBJECT-TYPE
        SYNTAX        Zxr10IfVlanTrafficStatEntry
        MAX-ACCESS    not-accessible
        STATUS        current
        DESCRIPTION   "Each row index by ifIndex and internal vlan id or 
                 external vlan id And contain imformation of VLAN."
        INDEX   {  zxr10IfVlanTrafficStatIfIndex,
                   zxr10IfVlanTrafficStatInterVlanID,
                   zxr10IfVlanTrafficStatExterVlanID }
        ::=  { zxr10IfVlanTrafficStatTable 1 }

    Zxr10IfVlanTrafficStatEntry
        ::=  SEQUENCE
        {
            zxr10IfVlanTrafficStatIfIndex                 Unsigned32,
            zxr10IfVlanTrafficStatIfName                  DisplayString,
            zxr10IfVlanTrafficStatInterVlanID             Unsigned32,
            zxr10IfVlanTrafficStatExterVlanID             Unsigned32,
            zxr10IfVlanTrafficStatInPkts                  Counter64,
            zxr10IfVlanTrafficStatInBytes                 Counter64,
            zxr10IfVlanTrafficStatOutPkts                 Counter64,
            zxr10IfVlanTrafficStatOutBytes                Counter64,
            zxr10IfVlanTrafficStatInDiscards              Counter64,
            zxr10IfVlanTrafficStatOutDiscards             Counter64
        }

    zxr10IfVlanTrafficStatIfIndex   OBJECT-TYPE
        SYNTAX          Unsigned32
        MAX-ACCESS      read-only
        STATUS          current
        DESCRIPTION   "Interface Index."
        ::=  { zxr10IfVlanTrafficStatEntry  1 }

    zxr10IfVlanTrafficStatIfName   OBJECT-TYPE
        SYNTAX          DisplayString
        MAX-ACCESS      read-only
        STATUS          current
        DESCRIPTION   "Interface Name."
        ::=  { zxr10IfVlanTrafficStatEntry  2 }

    zxr10IfVlanTrafficStatInterVlanID   OBJECT-TYPE
        SYNTAX          Unsigned32
        MAX-ACCESS      read-only
        STATUS          current
        DESCRIPTION   "Inter vlan id."
        ::=  { zxr10IfVlanTrafficStatEntry  3 }

    zxr10IfVlanTrafficStatExterVlanID   OBJECT-TYPE
        SYNTAX          Unsigned32
        MAX-ACCESS      read-only
        STATUS          current
        DESCRIPTION   "Exter vlan id."
        ::=  { zxr10IfVlanTrafficStatEntry  4 }

    zxr10IfVlanTrafficStatInPkts   OBJECT-TYPE
        SYNTAX          Counter64
        MAX-ACCESS      read-only
        STATUS          current
        DESCRIPTION   " In Packets."
        ::=  { zxr10IfVlanTrafficStatEntry  5 }

    zxr10IfVlanTrafficStatInBytes   OBJECT-TYPE
        SYNTAX          Counter64
        MAX-ACCESS      read-only
        STATUS          current
        DESCRIPTION   " In Bytes."
        ::=  { zxr10IfVlanTrafficStatEntry  6 }  

    zxr10IfVlanTrafficStatOutPkts   OBJECT-TYPE
        SYNTAX          Counter64
        MAX-ACCESS      read-only
        STATUS          current
        DESCRIPTION   " Out Packets."
        ::=  { zxr10IfVlanTrafficStatEntry  7 }

    zxr10IfVlanTrafficStatOutBytes   OBJECT-TYPE
        SYNTAX          Counter64
        MAX-ACCESS      read-only
        STATUS          current
        DESCRIPTION   " Out Bytes."
        ::=  { zxr10IfVlanTrafficStatEntry  8 }  

    zxr10IfVlanTrafficStatInDiscards   OBJECT-TYPE
        SYNTAX          Counter64
        MAX-ACCESS      read-only
        STATUS          current
        DESCRIPTION   " In Discards."
        ::=  { zxr10IfVlanTrafficStatEntry  9 }      

    zxr10IfVlanTrafficStatOutDiscards   OBJECT-TYPE
        SYNTAX          Counter64
        MAX-ACCESS      read-only
        STATUS          current
        DESCRIPTION   " Out Discards."
        ::=  { zxr10IfVlanTrafficStatEntry  10 }  






---zxr10VlanIfConfigTable

    zxr10VlanIfConfigTable  OBJECT-TYPE
        SYNTAX        SEQUENCE OF Zxr10VlanIfConfigEntry
        MAX-ACCESS    not-accessible
        STATUS        current
        DESCRIPTION   "Configuration infomation of vlan sub-interface."
        ::=  { zxr10VlanAtt  3}

    zxr10VlanIfConfigEntry  OBJECT-TYPE
        SYNTAX        Zxr10VlanIfConfigEntry
        MAX-ACCESS    not-accessible
        STATUS        current
        DESCRIPTION   "Each row index by ifName and internal vlan id and 
                 external vlan id And contain imformation of VLAN.
                 In project 5900 and 9900,user can set dot1q type
                 vlan only,and vlanid 1 is not allowed to configurate."
        INDEX   {  zxr10VlanIfConfigIfName,
                   zxr10VlanIfConfigInterVlan,
                   zxr10VlanIfConfigExterVlan }
        ::=  { zxr10VlanIfConfigTable 1 } 

    Zxr10VlanIfConfigEntry
        ::=  SEQUENCE
        {     
            zxr10VlanIfConfigIfName                       DisplayString,
            zxr10VlanIfConfigInterVlan                    DisplayString,
            zxr10VlanIfConfigExterVlan                    DisplayString,
            zxr10VlanIfConfigRowStatus                    RowStatus
        }

    zxr10VlanIfConfigIfName   OBJECT-TYPE
        SYNTAX          DisplayString
        MAX-ACCESS      not-accessible
        STATUS          current
        DESCRIPTION   "Interface Name."
        ::=  { zxr10VlanIfConfigEntry  1 }

    zxr10VlanIfConfigInterVlan   OBJECT-TYPE
        SYNTAX          DisplayString
        MAX-ACCESS      not-accessible
        STATUS          current
        DESCRIPTION   "InnerVlan infomation."
        ::=  { zxr10VlanIfConfigEntry  2 }

    zxr10VlanIfConfigExterVlan   OBJECT-TYPE
        SYNTAX          DisplayString
        MAX-ACCESS      not-accessible
        STATUS          current
        DESCRIPTION   "OuterVlan infomation."
        ::=  { zxr10VlanIfConfigEntry  3 }

    zxr10VlanIfConfigRowStatus   OBJECT-TYPE
        SYNTAX          RowStatus
        MAX-ACCESS      read-create
        STATUS          current
        DESCRIPTION   "Row Status infomation."
        ::=  { zxr10VlanIfConfigEntry  4 }



---zxr10VlanTpidTable

    zxr10VlanTpidTable  OBJECT-TYPE
        SYNTAX        SEQUENCE OF Zxr10VlanTpidEntry
        MAX-ACCESS    not-accessible
        STATUS        current
        DESCRIPTION   "TPID infomation of vlan sub-interface."
        ::=  { zxr10VlanAtt  4}

    zxr10VlanTpidEntry  OBJECT-TYPE
        SYNTAX        Zxr10VlanTpidEntry
        MAX-ACCESS    not-accessible
        STATUS        current
        DESCRIPTION   "Each row index by ifName 
                 And contain imformation of VLAN."
        INDEX   {  zxr10VlanPidAttIntfName }
        ::=  { zxr10VlanTpidTable 1 } 

    Zxr10VlanTpidEntry
        ::=  SEQUENCE
        {     
            zxr10VlanPidAttIntfName                 DisplayString,
            zxr10VlanAttExterPid                    PidtagType,
            zxr10VlanAttInterPid                    PidtagType
        }

    zxr10VlanPidAttIntfName   OBJECT-TYPE
        SYNTAX          DisplayString
        MAX-ACCESS      not-accessible
        STATUS          current
        DESCRIPTION   "Interface Name."
        ::=  { zxr10VlanTpidEntry  1 }

    zxr10VlanAttExterPid   OBJECT-TYPE
        SYNTAX          PidtagType
        MAX-ACCESS      read-only
        STATUS          current
        DESCRIPTION   "Value of External Pid,valid value is 1-6,they 
                       separately mean 88a8 8100 9100 9200 9300 88e8,
                       default value can be set by different project."
        ::=  { zxr10VlanTpidEntry  2 }

    zxr10VlanAttInterPid   OBJECT-TYPE
        SYNTAX          PidtagType
        MAX-ACCESS      read-only
        STATUS          current
        DESCRIPTION   "Value of Internal Pid,valid value is 1-6,they 
                       separately mean 88a8 8100 9100 9200 9300 88e8,
                       default value can be set by different project."
        ::=  { zxr10VlanTpidEntry  3 }


---zxr10VlanRangeBrdcstFlagTable

    zxr10VlanRangeBrdcstFlagTable OBJECT-TYPE
        SYNTAX        SEQUENCE OF Zxr10VlanRangeBrdcstFlagEntry
        MAX-ACCESS    not-accessible
        STATUS        current
        DESCRIPTION   "Range Flag infomation of vlan sub-interface."
        ::=  { zxr10VlanAtt  5}

    zxr10VlanRangeBrdcstFlagEntry OBJECT-TYPE
        SYNTAX        Zxr10VlanRangeBrdcstFlagEntry
        MAX-ACCESS    not-accessible
        STATUS        current
        DESCRIPTION   "Each row index by ifName ."
        INDEX   {  zxr10VlanRangeAttIntfName }
        ::=  { zxr10VlanRangeBrdcstFlagTable 1 } 

    Zxr10VlanRangeBrdcstFlagEntry
        ::=  SEQUENCE
        {     
            zxr10VlanRangeAttIntfName               DisplayString,
            zxr10VlanAttRangeFlag                   EnabledStatus,
            zxr10VlanAttSingleLayer                 EnabledStatus
        }

    zxr10VlanRangeAttIntfName   OBJECT-TYPE
        SYNTAX          DisplayString
        MAX-ACCESS      not-accessible
        STATUS          current
        DESCRIPTION   "Interface Name."
        ::=  { zxr10VlanRangeBrdcstFlagEntry  1 }

    zxr10VlanAttRangeFlag   OBJECT-TYPE
        SYNTAX          EnabledStatus
        MAX-ACCESS      read-only
        STATUS          current
        DESCRIPTION   "Vlan range broadcast flag,1 mean enable,2 mean
                       disable,default value is 2."
        DEFVAL  { disabled }
        ::=  { zxr10VlanRangeBrdcstFlagEntry  2 }

    zxr10VlanAttSingleLayer   OBJECT-TYPE
        SYNTAX          EnabledStatus
        MAX-ACCESS      read-only
        STATUS          current
        DESCRIPTION   "Vlan range broadcast singlelayer flag,1 mean 
                       enable,2 mean disable,default value is 2."
        DEFVAL  { disabled }
        ::=  { zxr10VlanRangeBrdcstFlagEntry  3 }


END
