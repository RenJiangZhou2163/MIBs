--*****************************************************************
-- ZXR10-AAA-MIB
-- OAM
-- 2013-10-24 16:30  zhuhuaxing
-- Copyright (c) 1985-2013 by ZTE Corp.
-- All rights reserved. 
--*****************************************************************

ZXR10-AAA-MIB DEFINITIONS ::= BEGIN

IMPORTS
    MODULE-IDENTITY,OBJECT-TYPE,Unsigned32
        FROM SNMPv2-SMI
    DisplayString,TEXTUAL-CONVENTION
        FROM SNMPv2-TC
    zxr10
        FROM ZXR10-SMI;

zxr10AAA MODULE-IDENTITY
        LAST-UPDATED "201510081000Z"
        ORGANIZATION "ZTE Corporation"
        CONTACT-INFO
            "       Zang Liang
            Tel:    +86-25-52870000
            E-Mail: zang.liang@zte.com.cn "

        DESCRIPTION
            "M6000 60 AAA config MIB"
            
        REVISION "201510081000Z"
        DESCRIPTION
             "1.add new type for zxr10AAAauthenType.
             2.add new type for zxr10AAAauthorType.
             3.add new type for zxr10AAAacctType"
        
        REVISION "201408071000Z"  
        DESCRIPTION
            "1.Change STATUS of leaf zxr10AAAauthenDiameterGroup to obsolete.
             2.Add leaf zxr10AAAauthenDimGroup."

        REVISION "201401061000Z"  
        DESCRIPTION
            "1.modify zxr10AAAauthenTable description.
             2.modify zxr10AAAauthenEntry description.
             3.modify zxr10AAAauthorEntry description."

        REVISION "201310241000Z"  
        DESCRIPTION
            "1.leaf zxr10AAAauthenRadiusGroup obsolete
             2.leaf zxr10AAAauthenRadGroup add
             3.leaf zxr10AAAauthorRadiusGroup obsolete
             4.leaf zxr10AAAauthorRadGroup add
             5.leaf zxr10AAAacctFirstRadiusGroup obsolete
             6.leaf zxr10AAAacctFirstRadGroup add
             7.leaf zxr10AAAacctSecondRadiusGroup obsolete
             8.leaf zxr10AAAacctSecondRadGroup add"

        REVISION "201012250000Z"
        DESCRIPTION
            "This mib defines management information objects for AAA" 
        ::= { zxr10 1010 } 

--******************************************************
--    he follow part defined some data types which will 
--    be used in this mib file later  
--****************************************************** 
AuthenType ::= TEXTUAL-CONVENTION
    STATUS       current
    DESCRIPTION
            "The true value of AAA authentication type."
    SYNTAX   INTEGER {none(1),local(2),radius(3),localRadius(4),
                     radiusLocal(5),radiusNone(6),tacacs(7),
                     localTacacs(8),tacacsLocal(9),tacacsNone(10),
                     diameter(11),tacacsRadius(12),radiusTacacs(13)}

AuthorType ::= TEXTUAL-CONVENTION
    STATUS       current
    DESCRIPTION
            "The true value of AAA authoritarian type."
    SYNTAX   INTEGER {local(1),radius(2),tacacs(3),radiusLocal(4),
                     localTacacs(5),none(6),localRadius(7),
                     tacacsLocal(8),tacacsRadius(9),radiusTacacs(10)}

AcctType ::= TEXTUAL-CONVENTION
    STATUS       current
    DESCRIPTION
            "The true value of AAA accounting type."
    SYNTAX   INTEGER {none(1),radius(2),tacacs(3),tacacsRadius(4),radiusTacacs(5)}

--******************************************************
-- the AAA authen table
--******************************************************
    zxr10AAAauthenTable OBJECT-TYPE
              SYNTAX  SEQUENCE OF Zxr10AAAauthenEntry
              MAX-ACCESS  not-accessible
              STATUS  current
              DESCRIPTION
                      "A table containing aaa authen temp information."
              ::= { zxr10AAA 1 }

    zxr10AAAauthenEntry OBJECT-TYPE
              SYNTAX  Zxr10AAAauthenEntry
              MAX-ACCESS  not-accessible
              STATUS  current
              DESCRIPTION
                      "Information about aaa authen temp."
              INDEX   { 
                          zxr10AAAauthenTempNo
                      }
              ::= { zxr10AAAauthenTable 1 }

    Zxr10AAAauthenEntry ::=
              SEQUENCE {
                  zxr10AAAauthenTempNo
                      Unsigned32,
                  zxr10AAAauthenDescription
                      DisplayString,
                  zxr10AAAauthenType
                      AuthenType,
                  zxr10AAAauthenRadiusGroup
                      Unsigned32,
                  zxr10AAAauthenTacacsGroup
                      DisplayString,
                  zxr10AAAauthenDiameterGroup
                      Unsigned32,
                  zxr10AAAauthenRadGroup
                      DisplayString,
                  zxr10AAAauthenDimGroup
                      DisplayString
              }

    zxr10AAAauthenTempNo OBJECT-TYPE
              SYNTAX  Unsigned32
              MAX-ACCESS  read-only
              STATUS  current
              DESCRIPTION
                      "The AAA authen temp number."
              ::= { zxr10AAAauthenEntry 1 }
              
    zxr10AAAauthenDescription OBJECT-TYPE
              SYNTAX  DisplayString
              MAX-ACCESS  read-only
              STATUS  current
              DESCRIPTION
                      "The AAA authen temp description."
              ::= { zxr10AAAauthenEntry 2 }
              
    zxr10AAAauthenType OBJECT-TYPE
              SYNTAX  AuthenType
              MAX-ACCESS  read-write
              STATUS  current
              DESCRIPTION
                      "The AAA authen type."
              ::= { zxr10AAAauthenEntry 3 }

    zxr10AAAauthenRadiusGroup OBJECT-TYPE
              SYNTAX  Unsigned32
              MAX-ACCESS  read-only
              STATUS  obsolete
              DESCRIPTION
                      "The AAA authen radius Group."
              ::= { zxr10AAAauthenEntry 4 }

    zxr10AAAauthenTacacsGroup OBJECT-TYPE
              SYNTAX  DisplayString
              MAX-ACCESS  read-only
              STATUS  current
              DESCRIPTION
                      "The AAA authen tacacs Group."
              ::= { zxr10AAAauthenEntry 5 }

    zxr10AAAauthenDiameterGroup OBJECT-TYPE
              SYNTAX  Unsigned32
              MAX-ACCESS  read-only
              STATUS  obsolete
              DESCRIPTION
                      "The AAA authen diameter Group."
              ::= { zxr10AAAauthenEntry 6 }

    zxr10AAAauthenRadGroup OBJECT-TYPE
              SYNTAX  DisplayString
              MAX-ACCESS  read-only
              STATUS  current
              DESCRIPTION
                      "The AAA authen radius Group."
              ::= { zxr10AAAauthenEntry 7 }

    zxr10AAAauthenDimGroup OBJECT-TYPE
              SYNTAX  DisplayString(SIZE(1..32))
              MAX-ACCESS  read-only
              STATUS  current
              DESCRIPTION
                      "The AAA authen diameter Group."
              ::= { zxr10AAAauthenEntry 8 }

--******************************************************
-- the AAA author table
--******************************************************
    zxr10AAAauthorTable OBJECT-TYPE
              SYNTAX  SEQUENCE OF Zxr10AAAauthorEntry
              MAX-ACCESS  not-accessible
              STATUS  current
              DESCRIPTION
                      "A table containing aaa author temp information."
              ::= { zxr10AAA 2 }

    zxr10AAAauthorEntry OBJECT-TYPE
              SYNTAX  Zxr10AAAauthorEntry
              MAX-ACCESS  not-accessible
              STATUS  current
              DESCRIPTION
                      "Information about aaa author temp."
              INDEX   { 
                          zxr10AAAauthorTempNo
                      }
              ::= { zxr10AAAauthorTable 1 }

    Zxr10AAAauthorEntry ::=
              SEQUENCE {
                  zxr10AAAauthorTempNo
                      Unsigned32,
                  zxr10AAAauthorDescription
                      DisplayString,
                  zxr10AAAauthorType
                      AuthorType,
                  zxr10AAAauthorTacacsGroup
                      DisplayString,
                  zxr10AAAauthorRadiusGroup
                      Unsigned32,
                  zxr10AAAauthorRadGroup
                      DisplayString
              }

    zxr10AAAauthorTempNo OBJECT-TYPE
              SYNTAX  Unsigned32
              MAX-ACCESS  read-only
              STATUS  current
              DESCRIPTION
                      "The AAA author temp number."
              ::= { zxr10AAAauthorEntry 1 }
              
    zxr10AAAauthorDescription OBJECT-TYPE
              SYNTAX  DisplayString
              MAX-ACCESS  read-only
              STATUS  current
              DESCRIPTION
                      "The AAA author temp description."
              ::= { zxr10AAAauthorEntry 2 }
              
    zxr10AAAauthorType OBJECT-TYPE
              SYNTAX  AuthorType
              MAX-ACCESS  read-only
              STATUS  current
              DESCRIPTION
                      "The AAA author type."
              ::= { zxr10AAAauthorEntry 3 }

    zxr10AAAauthorTacacsGroup OBJECT-TYPE
              SYNTAX  DisplayString
              MAX-ACCESS  read-only
              STATUS  current
              DESCRIPTION
                      "The AAA author tacacs Group."
              ::= { zxr10AAAauthorEntry 4 }

    zxr10AAAauthorRadiusGroup OBJECT-TYPE
              SYNTAX  Unsigned32
              MAX-ACCESS  read-only
              STATUS  obsolete
              DESCRIPTION
                      "The AAA author radius Group."
              ::= { zxr10AAAauthorEntry 5 }

    zxr10AAAauthorRadGroup OBJECT-TYPE
              SYNTAX  DisplayString
              MAX-ACCESS  read-only
              STATUS  current
              DESCRIPTION
                      "The AAA author radius Group."
              ::= { zxr10AAAauthorEntry 6 }

--******************************************************
-- the AAA acct table
--******************************************************
    zxr10AAAacctTable OBJECT-TYPE
              SYNTAX  SEQUENCE OF Zxr10AAAacctEntry
              MAX-ACCESS  not-accessible
              STATUS  current
              DESCRIPTION
                      "A table containing aaa acct temp information."
              ::= { zxr10AAA 3 }

    zxr10AAAacctEntry OBJECT-TYPE
              SYNTAX  Zxr10AAAacctEntry
              MAX-ACCESS  not-accessible
              STATUS  current
              DESCRIPTION
                      "Information about aaa acct temp."
              INDEX   { 
                          zxr10AAAacctTempNo
                      }
              ::= { zxr10AAAacctTable 1 }

    Zxr10AAAacctEntry ::=
              SEQUENCE {
                  zxr10AAAacctTempNo
                      Unsigned32,
                  zxr10AAAacctDescription
                      DisplayString,
                  zxr10AAAacctType
                      AcctType,
                  zxr10AAAacctFirstRadiusGroup
                      Unsigned32,
                  zxr10AAAacctSecondRadiusGroup
                      Unsigned32, 
                  zxr10AAAacctTacacsGroup
                      DisplayString,
                  zxr10AAAacctFirstRadGroup
                      DisplayString,
                  zxr10AAAacctSecondRadGroup
                      DisplayString
                  
              }

    zxr10AAAacctTempNo OBJECT-TYPE
              SYNTAX  Unsigned32
              MAX-ACCESS  read-only
              STATUS  current
              DESCRIPTION
                      "The AAA acct temp number."
              ::= { zxr10AAAacctEntry 1 }
              
    zxr10AAAacctDescription OBJECT-TYPE
              SYNTAX  DisplayString
              MAX-ACCESS  read-only
              STATUS  current
              DESCRIPTION
                      "The AAA acct temp description."
              ::= { zxr10AAAacctEntry 2 }
              
    zxr10AAAacctType OBJECT-TYPE
              SYNTAX  AcctType
              MAX-ACCESS  read-write
              STATUS  current
              DESCRIPTION
                      "The AAA acct type."
              ::= { zxr10AAAacctEntry 3 }

    zxr10AAAacctFirstRadiusGroup OBJECT-TYPE
              SYNTAX  Unsigned32
              MAX-ACCESS  read-only
              STATUS  obsolete
              DESCRIPTION
                      "The AAA acct first radius Group."
              ::= { zxr10AAAacctEntry 4 }

    zxr10AAAacctSecondRadiusGroup OBJECT-TYPE
              SYNTAX  Unsigned32
              MAX-ACCESS  read-only
              STATUS  obsolete
              DESCRIPTION
                      "The AAA acct second radius Group."
              ::= { zxr10AAAacctEntry 5 }
  
    zxr10AAAacctTacacsGroup OBJECT-TYPE
              SYNTAX  DisplayString
              MAX-ACCESS  read-only
              STATUS  current
              DESCRIPTION
                      "The AAA acct tacacs Group."
              ::= { zxr10AAAacctEntry 6 }

    zxr10AAAacctFirstRadGroup OBJECT-TYPE
              SYNTAX  DisplayString
              MAX-ACCESS  read-only
              STATUS  current
              DESCRIPTION
                      "The AAA acct first radius Group."
              ::= { zxr10AAAacctEntry 7 }

    zxr10AAAacctSecondRadGroup OBJECT-TYPE
              SYNTAX  DisplayString
              MAX-ACCESS  read-only
              STATUS  current
              DESCRIPTION
                      "The AAA acct second radius Group."
              ::= { zxr10AAAacctEntry 8 }
     END
