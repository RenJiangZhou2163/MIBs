--  ************************************************
--  $Id: zxr10ping.mib 8 2005-07-28 12:17:08Z zhanglh $
--
--  zxr10lspping.mib: ZXR10 LSP Ping MIB file
--
--  JUL. 2005, Zhang lihui
--
--  Copyright(c) 2005 by ZTE Corporaton
--  All rights reservered
--
--  ************************************************

ZXR10-LSP-PING-MIB DEFINITIONS ::= BEGIN

IMPORTS
    MODULE-IDENTITY,
    OBJECT-TYPE,
    NOTIFICATION-TYPE,
    Integer32, Unsigned32, IpAddress
        FROM SNMPv2-SMI
    TruthValue, DisplayString
        FROM SNMPv2-TC
    zxr10L2vpn
        FROM ZXR10-SMI
    Ipv6Address
        FROM IPV6-TC;

zxr10LspPingMIB MODULE-IDENTITY
    LAST-UPDATED    "201309041830Z"
    ORGANIZATION    "ZTE Corporation."
    CONTACT-INFO
        "       Zhao yanhua
        Tel:    +86-25-52870000
        E-Mail: zhao.yanhua3@zte.com.cn
        "
    DESCRIPTION
        "ZTE LSP-PING MIB
        "
    REVISION        "201309041830Z"
    DESCRIPTION
        "add:       zxr10LspPingReplyMode
                    zxr10lspPingPwPeerAddr
                    zxr10lspPingPwPeerVcId
        
         update:    zxr10LspPingTtl delete default            
         "
    REVISION        "201305310930Z"
    DESCRIPTION
        "update:    lspPingType add v6ldp(3)
                    lspPingDataLen default value from 100 to 120
                    zxr10LspPingLspType add tunnel(3)                    
         modify compiling warnings for some nodes
         update desciptions for nodes with problem.
        "
    REVISION        "201303191130Z"
    DESCRIPTION
        "add:       zxr10LspPingPwMultiSegment
                    zxr10LspPingLspType
                    zxr10LspPingV6LdpPrefix
                    zxr10LspPingV6LdpPrefixlen
                    zxr10LspPingSrcIpAddr
                    zxr10LspPingV6SrcIpAddr
                    zxr10LspPingOutInterface
                    zxr10LspPingTtl                    
         modify compiling warnings for some nodes
         update desciptions for nodes with problem.
        "
    REVISION        "200901070000Z"
    DESCRIPTION
        "Initial version of this MIB module.
        "
    ::= { zxr10L2vpn 5 }

   lspPingTable  OBJECT-TYPE
        SYNTAX      SEQUENCE OF LspPingEntry
        MAX-ACCESS  not-accessible
        STATUS      current
        DESCRIPTION
            "lsp ping information table."
        ::= { zxr10LspPingMIB 1 }

   lspPingEntry  OBJECT-TYPE
        SYNTAX      LspPingEntry
        MAX-ACCESS  not-accessible
        STATUS      current
        DESCRIPTION
            "lsp ping entry."
        INDEX       { lspPingSerial }
        ::= { lspPingTable 1 }

    LspPingEntry ::=
        SEQUENCE {
            lspPingSerial
                Integer32,
            lspPingType
                INTEGER,
            lspPingLdpPrefix
                IpAddress,
            lspPingLdpPrefixlen
                Integer32,
            lspPingMplsTeTunnelIfName
                DisplayString,
      --    lspPingPwNextAddr   
      --        IpAddress,
      --    lspPingPwNextVcId 
      --        Counter32,
            lspPingPwDestAddr   
                IpAddress,
            lspPingPwDestVcId 
                Unsigned32,
      --    lspPingPwTtl 
      --        Integer32,
            lspPingIfOption
                INTEGER,
            lspPingPacketCount
                Integer32,
            lspPingTimeOut
                Integer32,
            lspPingDataLen
                Integer32,
            lspPingTrapOncompletion
                TruthValue,
            lspPingRosStatus
                INTEGER,
            lspPingEntryOwner
                DisplayString ,
            lspPingPwType 
                INTEGER,
            lspPingPwName
                DisplayString,
            zxr10LspPingPwMultiSegment
                TruthValue,
            zxr10LspPingLspType
                INTEGER,
            zxr10LspPingV6LdpPrefix
                Ipv6Address,
            zxr10LspPingV6LdpPrefixlen
                Integer32,
            zxr10LspPingSrcIpAddr
                IpAddress,
            zxr10LspPingV6SrcIpAddr
                Ipv6Address,
            zxr10LspPingOutInterface
                DisplayString,
            zxr10LspPingTtl
                Integer32,
            zxr10LspPingReplyMode
                INTEGER,
            zxr10lspPingPwPeerAddr   
                IpAddress,
            zxr10lspPingPwPeerVcId 
                Unsigned32
    }

    lspPingSerial  OBJECT-TYPE
        SYNTAX      Integer32
        MAX-ACCESS  read-only 
        STATUS  current
        DESCRIPTION
            "lsp ping serial number"
        ::= { lspPingEntry 1 }

    lspPingType  OBJECT-TYPE
        SYNTAX      INTEGER  {
                        ldp(0),
                        rsvpTe(1),
                        vccv(2),
                        v6ldp(3)
                    }
        MAX-ACCESS  read-write
        STATUS  current
        DESCRIPTION
            "lsp ping type (0:ldp,1:rsvpTe,2:vccv,3:v6ldp)"
        ::= { lspPingEntry 2 }

    lspPingLdpPrefix  OBJECT-TYPE
        SYNTAX      IpAddress
        MAX-ACCESS  read-write
        STATUS      current
        DESCRIPTION
            "ldp prefix"
        ::= { lspPingEntry 3 }

    lspPingLdpPrefixlen  OBJECT-TYPE
        SYNTAX      Integer32 (0..32)
        MAX-ACCESS  read-write
        STATUS      current
        DESCRIPTION
            "ldp prefix length"
        ::= { lspPingEntry 4 }

    lspPingMplsTeTunnelIfName  OBJECT-TYPE
        SYNTAX      DisplayString(SIZE(0..32))
        MAX-ACCESS  read-write
        STATUS      current
        DESCRIPTION
            "tunnel name"
        ::= { lspPingEntry 5 }

--    lspPingPwNextAddr  OBJECT-TYPE
--        SYNTAX  IpAddress 
--        MAX-ACCESS  read-write 
--        STATUS  current
--        DESCRIPTION
--            "vccv next address"
--        ::= { lspPingEntry 6 }
   
--    lspPingPwNextVcId  OBJECT-TYPE
--        SYNTAX  Counter32 
--        MAX-ACCESS  read-write 
--        STATUS  current
--        DESCRIPTION
--            "next vc id  "
--       ::= { lspPingEntry 7 }
   
    lspPingPwDestAddr  OBJECT-TYPE
        SYNTAX  IpAddress 
        MAX-ACCESS  read-write 
        STATUS  obsolete
        DESCRIPTION
            "vccv target address"
        ::= { lspPingEntry 8 }
   
    lspPingPwDestVcId  OBJECT-TYPE
        SYNTAX  Unsigned32
        MAX-ACCESS  read-write 
        STATUS  obsolete
        DESCRIPTION
            "target vc id  "
        ::= { lspPingEntry 9 }
                
--    lspPingPwTtl  OBJECT-TYPE
--        SYNTAX  Integer32 (1..255) 
--        MAX-ACCESS  read-write 
--        STATUS  current
--        DESCRIPTION
--            "pw label ttl "   
--        DEFVAL       { 1 }
--        ::= { lspPingEntry 10 }

   
    lspPingIfOption  OBJECT-TYPE
        SYNTAX      INTEGER { none(0),option(1) }
        MAX-ACCESS  read-write
        STATUS      current
        DESCRIPTION
            "if select option, default:none"
        DEFVAL      { 0 }
        ::= { lspPingEntry 11 }

    lspPingPacketCount  OBJECT-TYPE
        SYNTAX      Integer32 (1..65535)
        MAX-ACCESS  read-write
        STATUS      current
        DESCRIPTION
            "send packets count, default:5"
        DEFVAL      { 5 }
        ::= { lspPingEntry 12 }

    lspPingTimeOut  OBJECT-TYPE
        SYNTAX      Integer32 (1..20)
        MAX-ACCESS  read-write
        STATUS      current
        DESCRIPTION
            "timeout, default:2"
        DEFVAL      { 2 }
        ::= { lspPingEntry 13 }

    lspPingDataLen  OBJECT-TYPE
        SYNTAX      Integer32 (100..1500)
        MAX-ACCESS  read-write
        STATUS      current
        DESCRIPTION
            "data length, default:120"
        DEFVAL      { 120 }
        ::= { lspPingEntry 14 }

    lspPingTrapOncompletion  OBJECT-TYPE
        SYNTAX      TruthValue
        MAX-ACCESS  read-write
        STATUS      current
        DESCRIPTION
            "if trap"
        DEFVAL      { true }
        ::= { lspPingEntry 15 }

    lspPingRosStatus  OBJECT-TYPE
        SYNTAX      INTEGER {
                        notActive(1),
                        startPing(2),
                        pingProcessing(3),
                        pingCompleted(4)
                    }
        MAX-ACCESS  read-write
        STATUS      current
        DESCRIPTION
            "Controls to start lsp ping"
        DEFVAL      { 1 }
        ::= { lspPingEntry 16 }

    lspPingEntryOwner  OBJECT-TYPE
        SYNTAX      DisplayString
        MAX-ACCESS  read-write
        STATUS      current
        DESCRIPTION
            "lsp ping entry owner"
        ::= { lspPingEntry 17 }

    lspPingPwType  OBJECT-TYPE
        SYNTAX  INTEGER{etherVlan(0),ether(1)}
        MAX-ACCESS  read-write 
        STATUS  obsolete
        DESCRIPTION
            "pw type:ehter-vlan(0),ether(1),default (0)"
        DEFVAL       { 0 }        
        ::= { lspPingEntry 18 }    

    lspPingPwName  OBJECT-TYPE
        SYNTAX      DisplayString
        MAX-ACCESS  read-write
        STATUS      current
        DESCRIPTION
            "pw name"
        ::= { lspPingEntry 19 }

    zxr10LspPingPwMultiSegment  OBJECT-TYPE
        SYNTAX      TruthValue
        MAX-ACCESS  read-write
        STATUS      current
        DESCRIPTION
            "Indicate if the pw is multi-segment or not."
        ::= { lspPingEntry 20 }

    zxr10LspPingLspType  OBJECT-TYPE
        SYNTAX      INTEGER { master(1), slave(2), tunnel(3) }
        MAX-ACCESS  read-write
        STATUS      current
        DESCRIPTION
            "te-tunnel lsp type"
        ::= { lspPingEntry 21 }

    zxr10LspPingV6LdpPrefix  OBJECT-TYPE
        SYNTAX      Ipv6Address
        MAX-ACCESS  read-write
        STATUS      current
        DESCRIPTION
            "ldp IPv6 prefix"
        ::= { lspPingEntry 22 }

    zxr10LspPingV6LdpPrefixlen  OBJECT-TYPE
        SYNTAX      Integer32 (0..128)
        MAX-ACCESS  read-write
        STATUS      current
        DESCRIPTION
            "ldp IPv6 prefix length"
        ::= { lspPingEntry 23 }

    zxr10LspPingSrcIpAddr  OBJECT-TYPE
        SYNTAX      IpAddress
        MAX-ACCESS  read-write
        STATUS      current
        DESCRIPTION
            "source IP address"
        ::= { lspPingEntry 24 }

    zxr10LspPingV6SrcIpAddr  OBJECT-TYPE
        SYNTAX      Ipv6Address
        MAX-ACCESS  read-write
        STATUS      current
        DESCRIPTION
            "IPv6 source IP address"
        ::= { lspPingEntry 25 }

    zxr10LspPingOutInterface  OBJECT-TYPE
        SYNTAX      DisplayString
        MAX-ACCESS  read-write
        STATUS      current
        DESCRIPTION
            "out interface for tracing packets"
        ::= { lspPingEntry 26 }

    zxr10LspPingTtl  OBJECT-TYPE
        SYNTAX      Integer32 (1..255)
        MAX-ACCESS  read-write
        STATUS      current
        DESCRIPTION
            "ttl"
        ::= { lspPingEntry 27 }

      zxr10LspPingReplyMode  OBJECT-TYPE
        SYNTAX      INTEGER  {
                        notReply(1),
                        ip(2),
                        routerAlert(3),
                        applicationChannel(4)
                    }
        MAX-ACCESS  read-write
        STATUS      current
        DESCRIPTION
            "ReplyMode"
         DEFVAL      { 2 }
         ::= { lspPingEntry 28 }

    zxr10lspPingPwPeerAddr  OBJECT-TYPE
        SYNTAX  IpAddress 
        MAX-ACCESS  read-write 
        STATUS  current
        DESCRIPTION
            "vccv target address"
        ::= { lspPingEntry 29 }
   
    zxr10lspPingPwPeerVcId  OBJECT-TYPE
        SYNTAX  Unsigned32
        MAX-ACCESS  read-write 
        STATUS  current
        DESCRIPTION
            "target vc id  "
        ::= { lspPingEntry 30 }

--- lsp ping result

   lspPingResultTable  OBJECT-TYPE
        SYNTAX      SEQUENCE OF LspPingResultEntry
        MAX-ACCESS  not-accessible
        STATUS      current
        DESCRIPTION
            "lsp ping result table."
        ::= { zxr10LspPingMIB 2 }

    lspPingResultEntry  OBJECT-TYPE
        SYNTAX      LspPingResultEntry
        MAX-ACCESS  not-accessible
        STATUS      current
        DESCRIPTION
            "lsp ping result entry."
        INDEX       {
                        lspPingResultSerial
                    }
        ::= { lspPingResultTable 1 }

    LspPingResultEntry ::=
        SEQUENCE {
            lspPingResultSerial
                Integer32,
            lspPingResultSentPkts
                Integer32,
            lspPingResultRcvPkts
                Integer32,
            lspPingResultRoundTripMinTime
                Integer32,
            lspPingResultRoundTripMaxTime
                Integer32,
            lspPingResultRoundTripAvgTime
                Integer32,
            lspPingResultEntryOwner
                DisplayString,
            lspPingResultRoundWobbleMinTime
                Integer32,
            lspPingResultRoundWobbleMaxTime
                Integer32,
            lspPingResultRoundWobbleAvgTime
                Integer32
    }

     lspPingResultSerial  OBJECT-TYPE
        SYNTAX      Integer32
        MAX-ACCESS  read-only
        STATUS      current
        DESCRIPTION
            "lsp ping result serial number"
        ::= { lspPingResultEntry 1 }

     lspPingResultSentPkts  OBJECT-TYPE
        SYNTAX      Integer32
        MAX-ACCESS  read-only
        STATUS      current
        DESCRIPTION
            "send packet"
        ::= { lspPingResultEntry 2 }

     lspPingResultRcvPkts  OBJECT-TYPE
        SYNTAX      Integer32
        MAX-ACCESS  read-only
        STATUS      current
        DESCRIPTION
            "receive packet"
        ::= { lspPingResultEntry 3 }

     lspPingResultRoundTripMinTime  OBJECT-TYPE
        SYNTAX      Integer32
        MAX-ACCESS  read-only
        STATUS      current
        DESCRIPTION
            "min RTT"
        ::= { lspPingResultEntry 4 }

     lspPingResultRoundTripMaxTime  OBJECT-TYPE
        SYNTAX      Integer32
        MAX-ACCESS  read-only
        STATUS      current
        DESCRIPTION
            "max RTT"
        ::= { lspPingResultEntry 5 }

     lspPingResultRoundTripAvgTime  OBJECT-TYPE
        SYNTAX      Integer32
        MAX-ACCESS  read-only
        STATUS      current
        DESCRIPTION
            "average RTT"
        ::= { lspPingResultEntry 6 }

     lspPingResultEntryOwner  OBJECT-TYPE
        SYNTAX      DisplayString
        MAX-ACCESS  read-only
        STATUS      current
        DESCRIPTION
            "entry owner"
        ::= { lspPingResultEntry 9 }

     lspPingResultRoundWobbleMinTime  OBJECT-TYPE
        SYNTAX      Integer32
        MAX-ACCESS  read-only
        STATUS      current
        DESCRIPTION
            "max RWT"
        ::= { lspPingResultEntry 10 }

     lspPingResultRoundWobbleMaxTime  OBJECT-TYPE
        SYNTAX      Integer32
        MAX-ACCESS  read-only
        STATUS      current
        DESCRIPTION
            "max RWT"
        ::= { lspPingResultEntry 11 }

     lspPingResultRoundWobbleAvgTime  OBJECT-TYPE
        SYNTAX      Integer32
        MAX-ACCESS  read-only
        STATUS      current
        DESCRIPTION
            "average RWT"
        ::= { lspPingResultEntry 12 }


-- *******************************************************************
--   Trap Definitions
-- *******************************************************************

    lsppingNotifications   OBJECT IDENTIFIER ::= { zxr10LspPingMIB 3 }

    lsppingTrapResult NOTIFICATION-TYPE
        OBJECTS
            {
                lspPingResultSerial,
                lspPingResultSentPkts,
                lspPingResultRcvPkts,
                lspPingResultRoundTripMinTime,
                lspPingResultRoundTripMaxTime,
                lspPingResultRoundTripAvgTime,
                lspPingResultRoundWobbleMinTime,
                lspPingResultRoundWobbleMaxTime,
                lspPingResultRoundWobbleAvgTime
            }
     STATUS     current
     DESCRIPTION
         "The newMaster trap indicates that the sending agent
         has transitioned to 'Master' state."
     ::= { lsppingNotifications 1 }

 END
