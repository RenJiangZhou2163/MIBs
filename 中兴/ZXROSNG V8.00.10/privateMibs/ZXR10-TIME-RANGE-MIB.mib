--  ******************************************************
--  $Id: zxr10TimeRange.mib 12 2009-02-18 10:38:49Z  $
--
--  zxr10TimeRange.mib: ZXR10 time range MIB file
--  
--  Jan. 2009, Meng Jian
--   
--  Copyright(c) 2005 by ZTE Corporaton
--  All rights reservered
--  UR-ZXROS-090116-01/UR-ZXROS-090213-03
--
--  modified list:
--  V1.6  zxr10TimeRangeIsActive is added by mengj 2009.03.02

--  ******************************************************

ZXR10-TIME-RANGE-MIB DEFINITIONS ::= BEGIN

IMPORTS
        MODULE-IDENTITY, OBJECT-TYPE,
        Integer32, enterprises
                FROM SNMPv2-SMI
        DisplayString,TEXTUAL-CONVENTION
                FROM SNMPv2-TC;
        

    zxr10TimeRange MODULE-IDENTITY
        LAST-UPDATED "201503200000Z"
        ORGANIZATION "ZTE Corporation."
        CONTACT-INFO
               "ZTE"
        DESCRIPTION 
                ""
    
        REVISION "201503200000Z"
        DESCRIPTION
            "Delete the Chinese char and TAB char,
             modify invalid TC definition: WEEKDAY, TimeRangeStatus,
             EentryType and TrStatus,
             rename WEEKDAY for WeekDay."
    
        REVISION "200405140000Z"
        DESCRIPTION
                "TIMERANGE"
        ::= { zxr10 332 }

    zte OBJECT IDENTIFIER ::= { enterprises 3902 }
    zxr10 OBJECT IDENTIFIER ::= { zte 3}


--The follow part defined some data types which will be used in this file later

    WeekDay ::= TEXTUAL-CONVENTION
        STATUS current
        DESCRIPTION
            "For periodic time range, 
             weekdays: form monday to friday,
             weekend: saturday and sunday, 
             daily: everyday"
        SYNTAX INTEGER
            {
                null(-1),
                weekdays(0),
                monday(1),
                tuesday(2),
                wednesday(3),
                thursday(4),
                friday(5),
                saturday(6),
                sunday(7),
                weekend(8),
                daily(9)
            }

    EentryType ::= TEXTUAL-CONVENTION
        STATUS current
        DESCRIPTION
            "The type of timerange rule."
        SYNTAX INTEGER
            {
                null(-1),
                absolute(0),
                periodic(1)
            }

    TimeRangeStatus ::= TEXTUAL-CONVENTION
        STATUS current
        DESCRIPTION
            ""
        SYNTAX INTEGER
            {
                disable(0),
                enable(1)
            }
                        
    TrStatus ::= TEXTUAL-CONVENTION
        STATUS current
        DESCRIPTION
            ""
        SYNTAX INTEGER
            {
                inactive(0),
                active(1)
            }

-- end for data type definition

-- The follow part defined some objects which will be used in this file later

-- TIMERANGE mib define

    timeRangeStatus OBJECT-TYPE
        SYNTAX   TimeRangeStatus
        MAX-ACCESS  read-only
        STATUS  current
        DESCRIPTION
            "Time range is enable or disable."
        ::= { zxr10TimeRange  1 }

    zxr10TimeRangeTable  OBJECT-TYPE
        SYNTAX  SEQUENCE OF Zxr10TimeRangeEntry
        MAX-ACCESS  not-accessible
        STATUS  current
        DESCRIPTION
            "It displays the configuration of time range."
        ::= { zxr10TimeRange  2 }

    zxr10TimeRangeEntry  OBJECT-TYPE
        SYNTAX  Zxr10TimeRangeEntry
        MAX-ACCESS  not-accessible
        STATUS  current
        DESCRIPTION
            "It displays the content of time range."
        INDEX  {zxr10TimeRangeName, zxr10TimeRangeEntrySeq }
        ::= { zxr10TimeRangeTable 1 }

    Zxr10TimeRangeEntry ::=
        SEQUENCE {
            zxr10TimeRangeName               DisplayString, 
            zxr10TimeRangeIsActive           TrStatus,
            zxr10TimeRangeEntrySeq           Integer32,
            zxr10TimeRangeEentryType         EentryType,
            zxr10TimeRangeAbsStart           DisplayString,
            zxr10TimeRangeAbsEnd             DisplayString,
            zxr10TimeRangeDaysofWeekStart    WeekDay,
            zxr10TimeRangeTimeofDayStart     DisplayString,
            zxr10TimeRangeDaysofWeekEnd      WeekDay,
            zxr10TimeRangeTimeofDayEnd       DisplayString
            }

    zxr10TimeRangeName  OBJECT-TYPE
        SYNTAX  DisplayString
        MAX-ACCESS  read-only
        STATUS  current
        DESCRIPTION
            "The name of the time range list."
        ::= { zxr10TimeRangeEntry 1 }    
        
    zxr10TimeRangeIsActive  OBJECT-TYPE
        SYNTAX  TrStatus
        MAX-ACCESS  read-only 
        STATUS  current
        DESCRIPTION
            "Whether the time range list is active."
        ::= { zxr10TimeRangeEntry 2 }          
        
    zxr10TimeRangeEntrySeq  OBJECT-TYPE
        SYNTAX  Integer32
        MAX-ACCESS  read-only
        STATUS  current
        DESCRIPTION
            "The sequence of the entry in time range list."
        ::= { zxr10TimeRangeEntry 3 }    
        
    zxr10TimeRangeEentryType  OBJECT-TYPE
        SYNTAX  EentryType
        MAX-ACCESS  read-only 
        STATUS  current
        DESCRIPTION
            "The type of the entry in time range list,
             it is absolute or periodic."
        ::= { zxr10TimeRangeEntry 4 }    
        
    zxr10TimeRangeAbsStart  OBJECT-TYPE
        SYNTAX  DisplayString
        MAX-ACCESS  read-only 
        STATUS  current
        DESCRIPTION
            "The start time of the absolute time range."
        ::= { zxr10TimeRangeEntry 5 }  
        
    zxr10TimeRangeAbsEnd  OBJECT-TYPE
        SYNTAX  DisplayString
        MAX-ACCESS  read-only 
        STATUS  current
        DESCRIPTION
            "The end time of the absolute time range."
        ::= { zxr10TimeRangeEntry 6 }  
        
    zxr10TimeRangeDaysofWeekStart  OBJECT-TYPE
        SYNTAX  WeekDay
        MAX-ACCESS  read-only 
        STATUS  current
        DESCRIPTION
            "The start day of the periodic time range."
        ::= { zxr10TimeRangeEntry 7 }  
        
    zxr10TimeRangeTimeofDayStart  OBJECT-TYPE
        SYNTAX  DisplayString
        MAX-ACCESS  read-only 
        STATUS  current
        DESCRIPTION
            "The time of the day at start periodic time range."
        ::= { zxr10TimeRangeEntry 8 }  
        
    zxr10TimeRangeDaysofWeekEnd  OBJECT-TYPE
        SYNTAX  WeekDay
        MAX-ACCESS  read-only 
        STATUS  current
        DESCRIPTION
            "The end day of the periodic time range."
        ::= { zxr10TimeRangeEntry 9 } 
         
    zxr10TimeRangeTimeofDayEnd  OBJECT-TYPE
        SYNTAX  DisplayString
        MAX-ACCESS  read-only 
        STATUS  current
        DESCRIPTION
            "The time of the day at end periodic time range."
        ::= { zxr10TimeRangeEntry 10 }  
        
-- TIMERANGE mib finished to define

    END
