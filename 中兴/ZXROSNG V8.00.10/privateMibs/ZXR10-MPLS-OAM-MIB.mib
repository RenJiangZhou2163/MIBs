--  ************************************************
--  $Id: ZXR10-MPLS-OAM.mib   2008-11-12 19:20:22Z zhitaoFu $
--
--  ZXR10-MPLS-MPLSOAM.mib: ZXR10 MPLS MPLSOAM query  MIB file
--
--  Nov. 2008, Fu zhitao
--
--  Copyright(c) 2008 by ZTE Corporaton
--  All rights reservered
--
--  ************************************************

ZXR10-MPLS-OAM-MIB DEFINITIONS ::= BEGIN

IMPORTS
    MODULE-IDENTITY,
    OBJECT-TYPE, 
    Unsigned32,
    IpAddress,
    NOTIFICATION-TYPE
        FROM SNMPv2-SMI 
       
    zxr10MplsOam
        FROM ZXR10-SMI;




    zxr10MplsOamMIB MODULE-IDENTITY
    LAST-UPDATED "200507260000Z"  -- Mar 12, 2010
    ORGANIZATION "ZTE Corporation"
    CONTACT-INFO
        "ZTE Corporation
         NanJing Institute of ZTE Corporation

         No.68 Zijinghua Rd. Yuhuatai District, Nanjing, China

         Tel: +86-25-52870000"

    DESCRIPTION
        "Rosng T8000_V1.00.11 MPLS OAM query and configuration MIB"

    REVISION "200507260000Z"  -- Mar 12, 2010
    DESCRIPTION
       ""

    ::= { zxr10MplsOam 1 }   
    
    zxr10MplsOamNotifications               OBJECT IDENTIFIER ::= { zxr10MplsOamMIB 0 }
    zxr10MplsOamScalarsObjects              OBJECT IDENTIFIER ::= { zxr10MplsOamMIB 1 }
    zxr10MplsOamLocalTunnelObjects          OBJECT IDENTIFIER ::= { zxr10MplsOamMIB 2 }
    zxr10MplsOamRemoteTunnelObjects         OBJECT IDENTIFIER ::= { zxr10MplsOamMIB 3 }

--- Mpls oam instance object  
--- ******************************************************************************************                         
       
    zxr10MplsOamEnable OBJECT-TYPE
            SYNTAX     INTEGER {enable(1),
                                disable(0)
                               }
            MAX-ACCESS read-only
            STATUS     current
            DESCRIPTION
                    "If this object is enable(1), then it enables the zxr10MplsOam;or it disables the zxr10MplsOam"
            ::= { zxr10MplsOamScalarsObjects 1 }
                       
--- *******************************************************************************************
 
 
--- Mpls oam local tunnel table
--- *******************************************************************************************
    zxr10MplsOamLocalTunnelTable  OBJECT-TYPE
        SYNTAX  SEQUENCE OF Zxr10MplsOamLocalTunnelEntry
        MAX-ACCESS  not-accessible
        STATUS  current
        DESCRIPTION
            "Mpls oam local tunnel information query table"
        ::= { zxr10MplsOamLocalTunnelObjects 1 }

    zxr10MplsOamLocalTunnelEntry  OBJECT-TYPE
        SYNTAX  Zxr10MplsOamLocalTunnelEntry
        MAX-ACCESS  not-accessible
        STATUS  current
        DESCRIPTION
            "Local tunnel information of Mpls oam instance"
        INDEX  {zxr10MplsOamLocalTunnelId,   
                zxr10MplsOamLocalTunnelLsplId,
		        zxr10MplsOamLocalTunnelIngressId
               }
        ::= { zxr10MplsOamLocalTunnelTable 1 }

    Zxr10MplsOamLocalTunnelEntry ::=
        SEQUENCE {
            zxr10MplsOamLocalTunnelId               Unsigned32,    
            zxr10MplsOamLocalTunnelLsplId           Unsigned32, 
            zxr10MplsOamLocalTunnelIngressId        IpAddress, 
            zxr10MplsOamLocalTunnelEgressId         IpAddress,
            zxr10MplsOamLocalTunnelRouterId         IpAddress,  
            zxr10MplsOamLocalTunnelNexthop          IpAddress,
            zxr10MplsOamLocalTunnelOutIfIndex       Unsigned32,
            zxr10MplsOamLocalTunnelNodeRole         INTEGER,
            zxr10MplsOamLocalTunnelFrequency        INTEGER,  
            zxr10MplsOamLocalTunnelPktType          INTEGER,
            zxr10MplsOamLocalTunnelPriority         Unsigned32,
            zxr10MplsOamLocalTunnelStatus           INTEGER,          
 --         zxr10MplsOamLocalTunnelAttribute        INTEGER,
            zxr10MplsOamLocalTunnelMplsoamEnable    INTEGER,            
            zxr10MplsOamLocalTunnelStartCountCv      INTEGER,
            zxr10MplsOamLocalTunnelStartCountFfd     INTEGER,
            zxr10MplsOamLocalTunnelStartCountBdi     INTEGER,
            zxr10MplsOamLocalTunnelStartCountFdi     INTEGER,
            zxr10MplsOamLocalTunnelCvCount           Unsigned32, 
            zxr10MplsOamLocalTunnelFfdCount          Unsigned32,
            zxr10MplsOamLocalTunnelBdiCount          Unsigned32,
            zxr10MplsOamLocalTunnelFdiCount          Unsigned32
     }

    zxr10MplsOamLocalTunnelId  OBJECT-TYPE
        SYNTAX  Unsigned32 (1..64511)
        MAX-ACCESS  read-only
        STATUS  current
        DESCRIPTION
            "Uniquely identifies a set of Mpls Oam Local tunnel instances
            between a pair of ingress and egress LSRs. 
            The range of this parameter depend on the device."
        ::= { zxr10MplsOamLocalTunnelEntry 1 }

    zxr10MplsOamLocalTunnelLsplId  OBJECT-TYPE
        SYNTAX  Unsigned32 
        MAX-ACCESS  read-only
        STATUS  current
        DESCRIPTION
            "Uniquely identifies a particular instance of a
		     Mpls Oam Local tunnel between a pair of ingress and egress LSRs."
        ::= { zxr10MplsOamLocalTunnelEntry 2 }

    zxr10MplsOamLocalTunnelIngressId  OBJECT-TYPE
        SYNTAX  IpAddress
        MAX-ACCESS  read-only
        STATUS  current
        DESCRIPTION
            "Identity of the ingress LSR associated with this tunnel instance."
        ::= { zxr10MplsOamLocalTunnelEntry 3 }

    zxr10MplsOamLocalTunnelEgressId  OBJECT-TYPE
        SYNTAX  IpAddress
        MAX-ACCESS  read-only
        STATUS  obsolete   --Modify by inger 10117247 for MPLSOAM Key change. Change the value from current to obsolete @ 2011.11.21:
        DESCRIPTION
            "Identity of the egress LSR associated with this tunnel instance. "
        ::= { zxr10MplsOamLocalTunnelEntry 4 }

    zxr10MplsOamLocalTunnelRouterId  OBJECT-TYPE
        SYNTAX  IpAddress
        MAX-ACCESS  read-only
        STATUS  current
        DESCRIPTION
            "A unique identifier for an MPLS LSR."
        ::= { zxr10MplsOamLocalTunnelEntry 5 }

    zxr10MplsOamLocalTunnelNexthop OBJECT-TYPE
        SYNTAX  IpAddress
        MAX-ACCESS  read-only
        STATUS  current
        DESCRIPTION
            "This value identifies the next hop of this LSR. "
        ::= { zxr10MplsOamLocalTunnelEntry 6 } 
  
    zxr10MplsOamLocalTunnelOutIfIndex  OBJECT-TYPE
        SYNTAX  Unsigned32
        MAX-ACCESS  read-only
        STATUS  current
        DESCRIPTION
            "This value identifies the index of the outgoing interface."
        ::= { zxr10MplsOamLocalTunnelEntry 7 }
 
        
    zxr10MplsOamLocalTunnelNodeRole  OBJECT-TYPE
        SYNTAX  INTEGER{head     (1),
                        transit  (2),
                        tail     (3)
                       }
        MAX-ACCESS  read-only
        STATUS  current
        DESCRIPTION
            "This value signifies the role that this tunnel	entry/instance represents. "
        ::= { zxr10MplsOamLocalTunnelEntry 8 }
        
    zxr10MplsOamLocalTunnelFrequency  OBJECT-TYPE
        SYNTAX  INTEGER{tenms   (1),
                        twentyms   (2),
                        fiftyms   (3),
                        onehundredms  (4),
                        twohundredms  (5),
                        fivehundredms  (6),
                        threepointthreems  (7),
                        onethousandms (8),
                        zeroms    (0)  
                       }
        MAX-ACCESS  read-only
        STATUS  current
        DESCRIPTION
            "This value identifies the frequency of packet-sending."
        ::= { zxr10MplsOamLocalTunnelEntry 9 }

    zxr10MplsOamLocalTunnelPktType  OBJECT-TYPE
        SYNTAX  INTEGER{cv(1),
                        ffd(7),
                        null(0)
                        }
        MAX-ACCESS  read-only
        STATUS  current
        DESCRIPTION
            "This value identifies the message type.
             cv(1):Connectivity Verification;
             ffd(7):Fast Failure Detection."
        ::= { zxr10MplsOamLocalTunnelEntry 10 }     
     
    
    zxr10MplsOamLocalTunnelPriority OBJECT-TYPE
        SYNTAX  Unsigned32
        MAX-ACCESS  read-only
        STATUS  current
        DESCRIPTION
            "This value identifies the message's priority."
        ::= { zxr10MplsOamLocalTunnelEntry 11 }
        
      
        
    zxr10MplsOamLocalTunnelStatus  OBJECT-TYPE
        SYNTAX  INTEGER{default(0),
                        down(1),
                        up(2)
                        }
        MAX-ACCESS  read-only
        STATUS  current
        DESCRIPTION
            "This value identifies actual operational status of this tunnel."
        ::= { zxr10MplsOamLocalTunnelEntry 12 }   
        
 --   zxr10MplsOamLocalTunnelAttribute  OBJECT-TYPE
 --       SYNTAX  INTEGER{static(0),
 --                       dynamic(1)
 --                       }
 --       MAX-ACCESS  read-only
 --       STATUS  current
 --       DESCRIPTION
 --           " "
 --       ::= { zxr10MplsOamLocalTunnelEntry 13 }   

    zxr10MplsOamLocalTunnelMplsoamEnable  OBJECT-TYPE
        SYNTAX  INTEGER{disable(0),
                        enable(1)
                        }
        MAX-ACCESS  read-only
        STATUS  current
        DESCRIPTION
            "Tunnel mpls oam enables or not. "
        ::= { zxr10MplsOamLocalTunnelEntry 14 }   
               


    zxr10MplsOamLocalTunnelStartCountCv  OBJECT-TYPE
        SYNTAX  INTEGER{true(1),
                        false(0)                        
                        }
        MAX-ACCESS  read-only
        STATUS  current
        DESCRIPTION
            "Statistics of CV message enables or not."
        ::= { zxr10MplsOamLocalTunnelEntry 15 } 


    zxr10MplsOamLocalTunnelStartCountFfd  OBJECT-TYPE
        SYNTAX  INTEGER{true(1),
                        false(0)                        
                        }
        MAX-ACCESS  read-only
        STATUS  current
        DESCRIPTION
            "Statistics of FFD message enables or not."
        ::= { zxr10MplsOamLocalTunnelEntry 16 } 

    zxr10MplsOamLocalTunnelStartCountBdi  OBJECT-TYPE
        SYNTAX  INTEGER{true(1),
                        false(0)                        
                        }
        MAX-ACCESS  read-only
        STATUS  current
        DESCRIPTION
            "Statistics of BDI message enables or not."
        ::= { zxr10MplsOamLocalTunnelEntry 17 } 

    zxr10MplsOamLocalTunnelStartCountFdi  OBJECT-TYPE
        SYNTAX  INTEGER{true(1),
                        false(0)                        
                        }
        MAX-ACCESS  read-only
        STATUS  current
        DESCRIPTION
            "Statistics of FDI message enables or not."
        ::= { zxr10MplsOamLocalTunnelEntry 18 } 


    zxr10MplsOamLocalTunnelCvCount  OBJECT-TYPE
        SYNTAX  Unsigned32
        MAX-ACCESS  read-only
        STATUS  current
        DESCRIPTION
            "The number of CV messages."
        ::= { zxr10MplsOamLocalTunnelEntry 19 }  
        
        
    zxr10MplsOamLocalTunnelFfdCount  OBJECT-TYPE
        SYNTAX  Unsigned32
        MAX-ACCESS  read-only
        STATUS  current
        DESCRIPTION
            "The number of FFD messages. "
        ::= { zxr10MplsOamLocalTunnelEntry 20 } 


    zxr10MplsOamLocalTunnelBdiCount  OBJECT-TYPE
        SYNTAX  Unsigned32
        MAX-ACCESS  read-only
        STATUS  current
        DESCRIPTION
            "The number of BDI messages. "
        ::= { zxr10MplsOamLocalTunnelEntry 21 } 


    zxr10MplsOamLocalTunnelFdiCount  OBJECT-TYPE
        SYNTAX  Unsigned32
        MAX-ACCESS  read-only
        STATUS  current
        DESCRIPTION
            "The number of  FDI messages. "
        ::= { zxr10MplsOamLocalTunnelEntry 22 } 
        
--- *******************************************************************************************        


--- Mpls Oam Remote tunnel table
--- *******************************************************************************************
    zxr10MplsOamRemoteTunnelTable  OBJECT-TYPE
        SYNTAX  SEQUENCE OF Zxr10MplsOamRemoteTunnelEntry
        MAX-ACCESS  not-accessible
        STATUS  current
        DESCRIPTION
            "Mpls oam remote tunnel information query table."
        ::= { zxr10MplsOamRemoteTunnelObjects 1 }

    zxr10MplsOamRemoteTunnelEntry  OBJECT-TYPE
        SYNTAX  Zxr10MplsOamRemoteTunnelEntry
        MAX-ACCESS  not-accessible
        STATUS  current
        DESCRIPTION
            "Remote tunnel onformation of Mpls oam instance."
        INDEX  {zxr10MplsOamRemoteTunnelId,
                zxr10MplsOamRemoteTunnelLsplId,
                zxr10MplsOamRemoteTunnelIngressId              
               }
        ::= { zxr10MplsOamRemoteTunnelTable 1 }

    Zxr10MplsOamRemoteTunnelEntry ::=
        SEQUENCE {
            zxr10MplsOamRemoteTunnelId                Unsigned32,    
            zxr10MplsOamRemoteTunnelLsplId            Unsigned32, 
            zxr10MplsOamRemoteTunnelIngressId         IpAddress, 
            zxr10MplsOamRemoteTunnelEgressId          IpAddress,
            zxr10MplsOamRemoteTunnelRouterId          IpAddress,  
            zxr10MplsOamRemoteTunnelBackFwdTunnelId   Unsigned32, 
            zxr10MplsOamRemoteTunnelBackFwdOutIfIndex Unsigned32,  
            zxr10MplsOamRemoteTunnelBackFwdNexthop    IpAddress,
            zxr10MplsOamRemoteTunnelNodeRole          INTEGER,
            zxr10MplsOamRemoteTunnelShareMode         INTEGER, 
            zxr10MplsOamRemoteTunnelFrequency         INTEGER,  
            zxr10MplsOamRemoteTunnelPktType           INTEGER,
            zxr10MplsOamRemoteTunnelPriority          Unsigned32,
            zxr10MplsOamRemoteTunnelStatus            INTEGER,          
--          zxr10MplsOamRemoteTunnelAttribute         INTEGER,
            zxr10MplsOamRemoteTunnelMplsoamEnable     INTEGER,            
            zxr10MplsOamRemoteTunnelStartCountCv      INTEGER,
            zxr10MplsOamRemoteTunnelStartCountFfd     INTEGER,
            zxr10MplsOamRemoteTunnelStartCountBdi     INTEGER,
            zxr10MplsOamRemoteTunnelStartCountFdi     INTEGER,
            zxr10MplsOamRemoteTunnelCvCount           Unsigned32, 
            zxr10MplsOamRemoteTunnelFfdCount          Unsigned32,
            zxr10MplsOamRemoteTunnelBdiCount          Unsigned32,
            zxr10MplsOamRemoteTunnelFdiCount          Unsigned32
     }

    zxr10MplsOamRemoteTunnelId  OBJECT-TYPE
        SYNTAX  Unsigned32  (1..64511)
        MAX-ACCESS  read-only
        STATUS  current
        DESCRIPTION
            "Uniquely identifies a set of Mpls Oam remote tunnel instances
            between a pair of ingress and egress LSRs.
            The range of this parameter depend on the device."
        ::= { zxr10MplsOamRemoteTunnelEntry 1 }

    zxr10MplsOamRemoteTunnelLsplId  OBJECT-TYPE
        SYNTAX  Unsigned32 
        MAX-ACCESS  read-only
        STATUS  current
        DESCRIPTION
            "Uniquely identifies a particular instance of an Mpls Oam remote tunnel between a pair of ingress and egress LSRs."
        ::= { zxr10MplsOamRemoteTunnelEntry 2 }

    zxr10MplsOamRemoteTunnelIngressId  OBJECT-TYPE
        SYNTAX  IpAddress
        MAX-ACCESS  read-only
        STATUS  current
        DESCRIPTION
            "Identity of the ingress LSR associated with this tunnel instance. "
        ::= { zxr10MplsOamRemoteTunnelEntry 3 }

    zxr10MplsOamRemoteTunnelEgressId  OBJECT-TYPE
        SYNTAX  IpAddress
        MAX-ACCESS  read-only
        STATUS   obsolete   --Modify by inger 10117247 for MPLSOAM Key change. Change the value from current to obsolete @ 2011.11.21:
        DESCRIPTION
            "Identity of the egress LSR associated with this tunnel instance.  "
        ::= { zxr10MplsOamRemoteTunnelEntry 4 }

    zxr10MplsOamRemoteTunnelRouterId  OBJECT-TYPE
        SYNTAX  IpAddress
        MAX-ACCESS  read-only
        STATUS  current
        DESCRIPTION
            "A unique identifier for an MPLS LSR."
        ::= { zxr10MplsOamRemoteTunnelEntry 5 }

    zxr10MplsOamRemoteTunnelBackFwdTunnelId OBJECT-TYPE
        SYNTAX  Unsigned32  (1..64511)
        MAX-ACCESS  read-only
        STATUS  current
        DESCRIPTION
            "This value identifies the index of backward tunnel.
            The range of this parameter depend on the device."
        ::= { zxr10MplsOamRemoteTunnelEntry 6 }

    zxr10MplsOamRemoteTunnelBackFwdOutIfIndex  OBJECT-TYPE
        SYNTAX  Unsigned32
        MAX-ACCESS  read-only
        STATUS  current
        DESCRIPTION
            "This value identifies the index of the outgoing interface for backward tunnel."
        ::= { zxr10MplsOamRemoteTunnelEntry 7 }
 
    zxr10MplsOamRemoteTunnelBackFwdNexthop OBJECT-TYPE
        SYNTAX  IpAddress
        MAX-ACCESS  read-only
        STATUS  current
        DESCRIPTION
            "This value identifies the next hop of backward tunnel LSR."
        ::= { zxr10MplsOamRemoteTunnelEntry 8 } 
  
        
    zxr10MplsOamRemoteTunnelNodeRole  OBJECT-TYPE
        SYNTAX  INTEGER{head     (1),
                        transit  (2),
                        tail     (3)
                       }
        MAX-ACCESS  read-only
        STATUS  current
        DESCRIPTION
            "This value signifies the role that this tunnel	entry/instance represents. "
        ::= { zxr10MplsOamRemoteTunnelEntry 9 }
     
    zxr10MplsOamRemoteTunnelShareMode  OBJECT-TYPE
        SYNTAX  INTEGER{monopolize (0),
                        share      (1)
                       }
        MAX-ACCESS  read-only
        STATUS  current
        DESCRIPTION
            "This value identifies backward tunnel sharing mode. "
        ::= { zxr10MplsOamRemoteTunnelEntry 10 }
        
    zxr10MplsOamRemoteTunnelFrequency  OBJECT-TYPE
        SYNTAX  INTEGER{tenms   (1),
                        twentyms   (2),
                        fiftyms   (3),
                        onehundredms  (4),
                        twohundredms  (5),
                        fivehundredms  (6),
                        threepointthreems  (7),
                        onethousandms (8),
                        zeroms    (0) 
                       }
        MAX-ACCESS  read-only
        STATUS  current
        DESCRIPTION
            "This value identifies the frequency of packet-sending."
        ::= { zxr10MplsOamRemoteTunnelEntry 11 }

    zxr10MplsOamRemoteTunnelPktType  OBJECT-TYPE
        SYNTAX  INTEGER{cv(1),
                        ffd(7),
                        null(0)
                        }
        MAX-ACCESS  read-only
        STATUS  current
        DESCRIPTION
            "This value identifies the message type.
             cv(1):Connectivity Verification;
             ffd(7):Fast Failure Detection. "
        ::= { zxr10MplsOamRemoteTunnelEntry 12 }     
     
    
    zxr10MplsOamRemoteTunnelPriority OBJECT-TYPE
        SYNTAX  Unsigned32
        MAX-ACCESS  read-only
        STATUS  current
        DESCRIPTION
            "This value identifies the message's priority. "
        ::= { zxr10MplsOamRemoteTunnelEntry 13 }
        
      
        
    zxr10MplsOamRemoteTunnelStatus  OBJECT-TYPE
        SYNTAX  INTEGER{default(0),
                        down(1),
                        up(2)
                        }
        MAX-ACCESS  read-only
        STATUS  current
        DESCRIPTION
            "This value identifies actual operational status of this tunnel. "
        ::= { zxr10MplsOamRemoteTunnelEntry 14 }   
        
 --   zxr10MplsOamRemoteTunnelAttribute  OBJECT-TYPE
 --       SYNTAX  INTEGER{static(0),
 --                       dynamic(1)
 --                       }
 --       MAX-ACCESS  read-only
 --       STATUS  current
 --       DESCRIPTION
 --           " "
 --       ::= { zxr10MplsOamRemoteTunnelEntry 15 }   

    zxr10MplsOamRemoteTunnelMplsoamEnable  OBJECT-TYPE
        SYNTAX  INTEGER{disable(0),
                        enable(1)
                        }
        MAX-ACCESS  read-only
        STATUS  current
        DESCRIPTION
            "Tunnel mpls oam enables or not. "
        ::= { zxr10MplsOamRemoteTunnelEntry 16 }   
               


    zxr10MplsOamRemoteTunnelStartCountCv  OBJECT-TYPE
        SYNTAX  INTEGER{true(1),
                        false(0)                        
                        }
        MAX-ACCESS  read-only
        STATUS  current
        DESCRIPTION
            "Statistics of CV message enables or not. "
        ::= { zxr10MplsOamRemoteTunnelEntry 17 } 


    zxr10MplsOamRemoteTunnelStartCountFfd  OBJECT-TYPE
        SYNTAX  INTEGER{true(1),
                        false(0)                        
                        }
        MAX-ACCESS  read-only
        STATUS  current
        DESCRIPTION
            "Statistics of FFD message enables or not.  "
        ::= { zxr10MplsOamRemoteTunnelEntry 18 } 

    zxr10MplsOamRemoteTunnelStartCountBdi  OBJECT-TYPE
        SYNTAX  INTEGER{true(1),
                        false(0)                        
                        }
        MAX-ACCESS  read-only
        STATUS  current
        DESCRIPTION
            "Statistics of BDI message enables or not. "
        ::= { zxr10MplsOamRemoteTunnelEntry 19 } 

    zxr10MplsOamRemoteTunnelStartCountFdi  OBJECT-TYPE
        SYNTAX  INTEGER{true(1),
                        false(0)                        
                        }
        MAX-ACCESS  read-only
        STATUS  current
        DESCRIPTION
            "Statistics of FDI message enables or not. "
        ::= { zxr10MplsOamRemoteTunnelEntry 20 } 


    zxr10MplsOamRemoteTunnelCvCount  OBJECT-TYPE
        SYNTAX  Unsigned32
        MAX-ACCESS  read-only
        STATUS  current
        DESCRIPTION
            "The number of CV messages."
        ::= { zxr10MplsOamRemoteTunnelEntry 21 }  
        
        
    zxr10MplsOamRemoteTunnelFfdCount  OBJECT-TYPE
        SYNTAX  Unsigned32
        MAX-ACCESS  read-only
        STATUS  current
        DESCRIPTION
            "The number of FFD messages."
        ::= { zxr10MplsOamRemoteTunnelEntry 22 } 


    zxr10MplsOamRemoteTunnelBdiCount  OBJECT-TYPE
        SYNTAX  Unsigned32
        MAX-ACCESS  read-only
        STATUS  current
        DESCRIPTION
            "The number of BDI messages."
        ::= { zxr10MplsOamRemoteTunnelEntry 23 } 


    zxr10MplsOamRemoteTunnelFdiCount  OBJECT-TYPE
        SYNTAX  Unsigned32
        MAX-ACCESS  read-only
        STATUS  current
        DESCRIPTION
            "The number of FDI messages."
        ::= { zxr10MplsOamRemoteTunnelEntry 24 } 
                
        
END
