ZXR10-MC-MONITOR-MIB DEFINITIONS ::= BEGIN
           
   IMPORTS
       MODULE-IDENTITY, OBJECT-TYPE, 
       Unsigned32,  
       IpAddress           
          FROM SNMPv2-SMI         -- [RFC2578]
       DisplayString, RowStatus        
          FROM SNMPv2-TC          -- [RFC2579]   
      enterprises                      
          FROM SNMPv2-SMI;

zxr10McastMonitorMIB MODULE-IDENTITY
    LAST-UPDATED "201008020000Z" -- 02 Auguest 2010
    ORGANIZATION "ZTE Corporation"
    CONTACT-INFO "ZTE Corporation 
         Nanjing Institute of ZTE Corporation  
         No.68 Zijinghua Rd. Yuhuatai District, Nanjing, China
         Tel: +86-25-52870000" 
         
    DESCRIPTION
            "The MIB module for management of Mcast Mroute monitor.
            This MIB module is a private MIB."    
    REVISION "201507271500Z"
    DESCRIPTION
            "modify: the description of zxr10McastMonitorMrouteTable, 
             delete: the punctuation of zxr10McastMonitorMrouteEntry."        
    REVISION     "201008020000Z" -- 02 Auguest 2010
    DESCRIPTION  " This MIB module is a private MIB,the object defined as 
                  follows:
                  
                 o  This MIB module includes objects that are specifies monitor interface.                    
                 o  This MIB module includes a table of monitor mroute
                    Table. "      
                 
                    
  ::= { zxr10 882 }
                    
    zte OBJECT IDENTIFIER ::= { enterprises 3902 }
    zxr10 OBJECT IDENTIFIER ::= { zte 3}
--
-- Top-level structure of the MIB
--
zxr10McastMonitor      OBJECT IDENTIFIER ::= { zxr10McastMonitorMIB 1 }

zxr10McastMonitorInterface OBJECT-TYPE
    SYNTAX     DisplayString
    MAX-ACCESS read-only
    STATUS     current
    DESCRIPTION
            "Monitor interface."
    ::= { zxr10McastMonitor 1 }    
--
--
--  The IP Mstatic Routing Table
--  
-- 
zxr10McastMonitorMrouteTable OBJECT-TYPE
    SYNTAX     SEQUENCE OF zxr10McastMonitorMrouteEntry
    MAX-ACCESS not-accessible
    STATUS     current          
    DESCRIPTION
            "The (conceptual) table containing monitor mroute
            information for source and destination address."
    ::= { zxr10McastMonitor 2 }   
    
zxr10McastMonitorMrouteEntry OBJECT-TYPE
    SYNTAX     zxr10McastMonitorMrouteEntry
    MAX-ACCESS not-accessible
    STATUS     current
    DESCRIPTION
            "An entry (conceptual row) containing the monitor mroute
            information for IP datagrams from a particular source and
            addressed to a particular IP multicast group address.

            OIDs are limited to 128 sub-identifiers, but this limit
            is not enforced by the syntax of this entry."
    INDEX      { 
                  zxr10McastMonitorMrouteSourceIPAddr,
                  zxr10McastMonitorMrouteDestIPAddr}
    ::= { zxr10McastMonitorMrouteTable 1 }

zxr10McastMonitorMrouteEntry ::= SEQUENCE {    
    zxr10McastMonitorMrouteSourceIPAddr        IpAddress,
    zxr10McastMonitorMrouteDestIPAddr         IpAddress,
    zxr10McastMonitorMrouteDestState         RowStatus,
    zxr10McastMonitorMrouteInterface        DisplayString
} 

zxr10McastMonitorMrouteSourceIPAddr  OBJECT-TYPE
    SYNTAX     IpAddress
    MAX-ACCESS read-only
    STATUS     current
    DESCRIPTION
            "The IP multicast source address."
            
    ::= { zxr10McastMonitorMrouteEntry 1 }       

zxr10McastMonitorMrouteDestIPAddr  OBJECT-TYPE
    SYNTAX     IpAddress
    MAX-ACCESS read-only
    STATUS     current
    DESCRIPTION
            "The IP multicast group address." 
                      
    ::= { zxr10McastMonitorMrouteEntry 2 }   

zxr10McastMonitorMrouteDestState  OBJECT-TYPE
    SYNTAX     RowStatus
    MAX-ACCESS read-only
    STATUS     current
    DESCRIPTION
            "The activation of a row enables Multicast Monitor." 
                      
    ::= { zxr10McastMonitorMrouteEntry 3 } 

zxr10McastMonitorMrouteInterface  OBJECT-TYPE
    SYNTAX     DisplayString
    MAX-ACCESS read-only
    STATUS     current
    DESCRIPTION
            "The forwarding interface of a row enables Multicast Monitor." 
                      
    ::= { zxr10McastMonitorMrouteEntry 4 } 
    
     END
