ZXR10-MPLS-TE-MIB DEFINITIONS ::= BEGIN


        IMPORTS
            MODULE-IDENTITY, OBJECT-TYPE,NOTIFICATION-TYPE,IpAddress,Integer32, Unsigned32, TimeTicks,Counter32,Counter64
                    FROM SNMPv2-SMI
            DisplayString, RowStatus,  StorageType, TimeStamp
                    FROM SNMPv2-TC
            zxr10MplsTe
                    FROM ZXR10-SMI;



         zxr10MplsTeMIB MODULE-IDENTITY
                LAST-UPDATED
                "201504201330Z"
                ORGANIZATION
                "Multiprotocol Label Switching (MPLS) Working Group"
                CONTACT-INFO
                " Cheenu SrinivasanBloomberg L.P.
                Email: cheenu@bloomberg.net
                Arun Viswanathan
                Force10 Networks, Inc.
                Email: arunv@force10networks.com
                Thomas D. Nadeau
                Cisco Systems, Inc.
                Email: tnadeau@cisco.com
                Comments about this document should be emailed
                directly to the MPLS working group mailing list at
                mpls@uu.net."
                DESCRIPTION
                "Copyright (C) The Internet Society (2004). The
                initial version of this MIB module was published
                in RFC 3812. For full legal notices see the RFC
                itself or see: http://www.ietf.org/copyrights/ianamib.html
                This MIB module contains managed object definitions
                for MPLS Traffic Engineering (TE) as defined in:
                1. Extensions to RSVP for LSP Tunnels, Awduche et
                al, RFC 3209, December 20012.
                 Constraint-Based LSP Setup using LDP, Jamoussi
                 (Editor), RFC 3212, January 2002
                 3. Requirements for Traffic Engineering Over MPLS,
                 Awduche, D., Malcolm, J., Agogbua, J., O'Dell, M.,
                 and J. McManus, [RFC2702], September 1999"
                 -- Revision history.
                REVISION
                "201504201330Z"
                DESCRIPTION
                "Add new fields zxr10MplsRemoteTunnelLspInOctets
                 in zxr10MplsRemoteTunnelTable.
                 Add new fields zxr10MplsRemoteTunnelLspInPackets
                 in zxr10MplsRemoteTunnelTable."
                REVISION
                "201412231714Z"
                DESCRIPTION
                "Add the syntax of zxr10MplsTunnelUpcallNetmng
                in zxr10MplsTeNotifications."
                REVISION
                "201401281330Z"
                DESCRIPTION
                "Modify the syntax of zxr10MplsTunnelPathInUse
                in zxr10MplsTunnelTable."
                REVISION
                "201306201130Z"
                DESCRIPTION
                "Add new fields zxr10MplsTunnelAssociateStatus
                                 in zxr10MplsTunnelTable."
                REVISION
                "200406030000Z" -- June 3, 2004
                DESCRIPTION
                        "Initial version issued as part of RFC 3812."
                ::= { zxr10MplsTe 1 }


         -- trap
            zxr10MplsTeNotifications OBJECT IDENTIFIER ::= { zxr10MplsTeMIB 0 }
         -- tables, scalars
            zxr10MplsTeScalars OBJECT IDENTIFIER ::= { zxr10MplsTeMIB 1 }
            zxr10MplsTeTunnelObjects OBJECT IDENTIFIER ::= { zxr10MplsTeMIB 2 }
            zxr10MplsTeRemoteTunnelObjects OBJECT IDENTIFIER ::= { zxr10MplsTeMIB 3 }

            zxr10MplsTeHopObjects OBJECT IDENTIFIER ::= { zxr10MplsTeMIB 4 }
            zxr10MplsTeResourceObjects OBJECT IDENTIFIER ::= { zxr10MplsTeMIB 5 }
            zxr10MplsTeCHopObjects OBJECT IDENTIFIER ::= { zxr10MplsTeMIB 6  }
            zxr10MplsTeARHopObjects OBJECT IDENTIFIER ::= { zxr10MplsTeMIB 7  }


            zxr10MplsTeInterfaceObjects OBJECT IDENTIFIER ::= { zxr10MplsTeMIB 8  }
            zxr10MplsIpExplicitObjects OBJECT IDENTIFIER ::= { zxr10MplsTeMIB 9  }
            zxr10MplsPathOptObjects OBJECT IDENTIFIER ::= { zxr10MplsTeMIB 10 }
            zxr10MplsAdminGroupListObjects OBJECT IDENTIFIER ::= { zxr10MplsTeMIB 11 }
            zxr10MplsHotStandbyLspObjects  OBJECT IDENTIFIER ::= { zxr10MplsTeMIB 12 }


        -- MPLS Tunnel scalars.
         zxr10MplsTunnelEnable OBJECT-TYPE
            SYNTAX INTEGER { false(0), true(1) }
            MAX-ACCESS read-only
            STATUS obsolete
            DESCRIPTION
                "If this object is true, then it enables the zxr10MplsTunnel."
            ::= { zxr10MplsTeScalars 1 }


         zxr10MplsTunnelConfiguredNum OBJECT-TYPE
            SYNTAX Unsigned32
            MAX-ACCESS read-only
            STATUS current
            DESCRIPTION
                "The number of tunnels configured on this device. A
                tunnel is considered configured if the
                zxr10MplsTunnelRowStatus is active(1)."
            ::= { zxr10MplsTeScalars 2 }


         zxr10MplsTunnelTEDistProto OBJECT-TYPE
            SYNTAX INTEGER {
                other (0),
                ospf (1),
                isis (2),
                both (3)
                }
            MAX-ACCESS read-only
            STATUS current
            DESCRIPTION
                "The traffic engineering distribution protocol(s)
                used by this LSR. Note that an LSR may support more
                than one distribution protocol simultaneously."
            ::= { zxr10MplsTeScalars 3 }

         zxr10MplsTunnelImplicitNullEnable  OBJECT-TYPE
            SYNTAX INTEGER { false(0), true(1) }
            MAX-ACCESS read-only
            STATUS obsolete
            DESCRIPTION
                "If this object is true, then it enables the ImplicitNull."
            ::= { zxr10MplsTeScalars 4 }

         zxr10MplsTunnelGrEnable   OBJECT-TYPE
            SYNTAX INTEGER { false(0), true(1) }
            MAX-ACCESS read-only
            STATUS obsolete
            DESCRIPTION
                "If this object is true, then it enables the GR."
            ::= { zxr10MplsTeScalars 5 }

         zxr10MplsTunnelGrRefreshInterval OBJECT-TYPE
            SYNTAX Unsigned32
            MAX-ACCESS read-only
            STATUS obsolete
            DESCRIPTION
                "Graceful-restart interval time 10~30000."
            ::= { zxr10MplsTeScalars 6 }

         zxr10MplsTunnelGrRefreshMisses OBJECT-TYPE
            SYNTAX Unsigned32
            MAX-ACCESS read-only
            STATUS obsolete
            DESCRIPTION
                "Graceful-restart miss number 4~10."
            ::= { zxr10MplsTeScalars 7 }

         zxr10MplsTunnelGrRecoveryTime OBJECT-TYPE
            SYNTAX Unsigned32
            MAX-ACCESS read-only
            STATUS obsolete
            DESCRIPTION
                "Graceful-restart RecoveryTime 0~300000."
            ::= { zxr10MplsTeScalars 8 }

         zxr10MplsTunnelGrRestartTime OBJECT-TYPE
            SYNTAX Unsigned32
            MAX-ACCESS read-only
            STATUS obsolete
            DESCRIPTION
                "Graceful-restart time 0~300000."
            ::= { zxr10MplsTeScalars 9 }

         zxr10MplsTunnelSignallingRefreshInterval OBJECT-TYPE
            SYNTAX Unsigned32
            MAX-ACCESS read-only
            STATUS obsolete
            DESCRIPTION
                "RefreshInterval 5000~65535000"
            ::= { zxr10MplsTeScalars 10 }

         zxr10MplsTunnelSignallingRefreshMisses OBJECT-TYPE
            SYNTAX Unsigned32
            MAX-ACCESS read-only
            STATUS obsolete
            DESCRIPTION
                "SignallingRefreshMisses 2~10"
            ::= { zxr10MplsTeScalars 11 }

       --added
         zxr10MplsVersion OBJECT-TYPE
            SYNTAX     Integer32
            MAX-ACCESS read-only
            STATUS     current
            DESCRIPTION
                "MPLS version number."
            ::= { zxr10MplsTeScalars 12 }

         zxr10MplsActiveLsps OBJECT-TYPE
            SYNTAX     Integer32
            MAX-ACCESS read-only
            STATUS     current
            DESCRIPTION
                 "Number of active LSPs."
            ::= { zxr10MplsTeScalars 13 }


         -- mpls atuobak tunnel
         zxr10MplsAutobakTunnelMinID OBJECT-TYPE
            SYNTAX Unsigned32
            MAX-ACCESS read-only
            STATUS obsolete
            DESCRIPTION
                "The Min tunnelID can be used by Auto baktunnel."
            ::= { zxr10MplsTeScalars 16 }

         zxr10MplsAutobakTunnelMaxID OBJECT-TYPE
            SYNTAX Unsigned32
            MAX-ACCESS read-only
            STATUS obsolete
            DESCRIPTION
                "The Max tunnelID can be used by Auto baktunnel."
            ::= { zxr10MplsTeScalars 17 }

        zxr10MplsRouterID OBJECT-TYPE
            SYNTAX DisplayString
            MAX-ACCESS read-only
            STATUS obsolete
            DESCRIPTION
                "TE_Routerid with interface name."
            ::= { zxr10MplsTeScalars 18 }
       --end added

       -- End of MPLS Tunnel scalars.


      -- MPLS tunnel table.
        zxr10MplsTunnelTable OBJECT-TYPE
            SYNTAX SEQUENCE OF Zxr10MplsTunnelEntry
            MAX-ACCESS not-accessible
            STATUS current
            DESCRIPTION
                    "The mplsTunnelTable allows new MPLS tunnels to be
                    created between an LSR and a remote endpoint, and
                    existing tunnels to be reconfigured or removed.
                    Note that only point-to-point tunnel segments are
                    supported, although multipoint-to-point and pointto-
                    multipoint connections are supported by an LSR
                    acting as a cross-connect. Each MPLS tunnel can
                    thus have one out-segment originating at this LSR
                    and/or one in-segment terminating at this LSR."
            ::= { zxr10MplsTeTunnelObjects 1 }

        zxr10MplsTunnelEntry OBJECT-TYPE
            SYNTAX Zxr10MplsTunnelEntry
            MAX-ACCESS not-accessible
            STATUS current
            DESCRIPTION
                  "An entry in this table represents an MPLS tunnel.
                  An entry can be created by a network administrator
                  or by an SNMP agent as instructed by an MPLS
                  signalling protocol. Whenever a new entry is
                  created with zxr10MplsTunnelIsIf set to true(1), then a
                  corresponding entry is created in ifTable as well
                  (see RFC 2863). The ifType of this entry is
                  zxr10MplsTunnel(150).
                  A tunnel entry needs to be uniquely identified across
                  a MPLS network. Indices zxr10MplsTunnelIndex and
                  zxr10MplsTunnelInstance uniquely identify a tunnel on
                  the LSR originating the tunnel. To uniquely
                  identify a tunnel across an MPLS network requires
                  index zxr10MplsTunnelIngressLSRId. The last index
                  zxr10MplsTunnelEgressLSRId is useful in identifying all
                  instances of a tunnel that terminate on the same
                  egress LSR."
            REFERENCE
                "1. RFC 2863 - The Interfaces Group MIB, McCloghrie,
                K., and F. Kastenholtz, June 2000 "
            INDEX { zxr10MplsTunnelIndex,
                    zxr10MplsTunnelInstance
                  }
            ::= { zxr10MplsTunnelTable 1 }


            Zxr10MplsTunnelEntry ::= SEQUENCE {
                zxr10MplsTunnelIndex Unsigned32,
                zxr10MplsTunnelInstance Unsigned32,
                zxr10MplsTunnelIngressLSRId IpAddress,
                zxr10MplsTunnelEgressLSRId IpAddress,
                zxr10MplsTunnelOutLabel Unsigned32,
                zxr10MplsTunnelOutIntf DisplayString,
                zxr10MplsTunnelName DisplayString,
                zxr10MplsTunnelDescr DisplayString,
                zxr10MplsTunnelIsIf INTEGER,
                zxr10MplsTunnelIfIndex Unsigned32,
                zxr10MplsTunnelIfType INTEGER,
                zxr10MplsTunnelIfAddrOrName DisplayString,
                zxr10MplsTunnelIfMaskOrIndex DisplayString,
                zxr10MplsTunnelOwner INTEGER,
                zxr10MplsTunnelRole INTEGER,
                zxr10MplsTunnelSignallingProto INTEGER,
                zxr10MplsTunnelSetupPrio Integer32,
                zxr10MplsTunnelHoldingPrio Integer32,
                zxr10MplsTunnelSessionAttributes DisplayString,
                zxr10MplsTunnelFrrEnable INTEGER,
                zxr10MplsTunnelResourcePointer Unsigned32,
                zxr10MplsTunnelPrimaryInstance Unsigned32,
                zxr10MplsTunnelInstancePriority Unsigned32,
                zxr10MplsTunnelHopTableIndex Unsigned32,
                zxr10MplsTunnelPathInUse Unsigned32,
                zxr10MplsTunnelARHopTableIndex Unsigned32,
                zxr10MplsTunnelCHopTableIndex Unsigned32,
                zxr10MplsTunnelTotalUpTime TimeTicks,
                zxr10MplsTunnelInstanceUpTime TimeTicks,
                zxr10MplsTunnelPrimaryUpTime TimeTicks,
                zxr10MplsTunnelPathChanges Counter32,
                zxr10MplsTunnelLastPathChange TimeTicks,
                zxr10MplsTunnelCreationTime TimeStamp,
                zxr10MplsTunnelStateTransitions Counter32,
                zxr10MplsTunnelAdminStatus INTEGER,
                zxr10MplsTunnelOperStatus INTEGER,
                zxr10MplsTunnelRowStatus RowStatus,
                zxr10MplsTunnelStorageType StorageType,
                zxr10MplsTunnelAutorouteEnable INTEGER,
                zxr10MplsTunnelAutorouteMetricType  INTEGER,
                zxr10MplsTunnelAutorouteMetricRelativeValue Integer32,
                zxr10MplsTunnelAutorouteMetricAbsoluteValue Unsigned32,
                zxr10MplsTunnelRecordRouteEnable INTEGER,
                zxr10MplsTunnelCACStatus INTEGER,
                zxr10MplsTunnelLspOctets Counter64,
                zxr10MplsTunnelLspPackets Counter64,
                zxr10MplsTunnelLspLastTransition TimeStamp,
                zxr10MplsTunnelLspConfiguredPaths  Integer32,
                zxr10MplsTunnelPathType     INTEGER,
                zxr10MplsTunnelPathExplicitRoute   OCTET STRING,
                zxr10MplsTunnelPathRecordRoute     OCTET STRING,
                zxr10MplsTunnelPathCOS             INTEGER,
                zxr10MplsTunnelPathInclude         Integer32,
                zxr10MplsTunnelPathExclude         Integer32,

                zxr10MplsTunnelHotStandbyEnable                INTEGER,
                zxr10MplsTunnelHotStandbyPrimaryPathOption     Unsigned32,
                zxr10MplsTunnelHotStandbySecondaryPathOption   Unsigned32,
                zxr10MplsTunnelHotStandbyInstance              Integer32,
                zxr10MplsTunnelHotStandbyState                 INTEGER ,

                        zxr10MplsTunnelBfdEnable   INTEGER,
                        zxr10MplsTunnelBFDmult             Unsigned32,
                zxr10MplsTunnelBFDminTxInterval    Unsigned32,
                zxr10MplsTunnelBFDminRxInterval    Unsigned32,
                zxr10MplsTunnelBFDstatus           INTEGER,

                zxr10MplsTunnelFrrProtectionMethod INTEGER,
                zxr10MplsTunnelBandwidth    Unsigned32,
                zxr10MplsTunnelSubPoolBandwidth    Unsigned32 ,
                        zxr10MplsTunnelIgpMetric           Unsigned32,
                zxr10MplsTunnelTeMetric            Unsigned32,
                zxr10MplsTunnelBFDSlaveStatus      INTEGER,
                zxr10MplsTunnelAssociateStatus      INTEGER
            }



            zxr10MplsTunnelIndex OBJECT-TYPE
            SYNTAX Unsigned32
            MAX-ACCESS read-only
            STATUS current
            DESCRIPTION
            "Uniquely identifies a set of tunnel instances
            between a pair of ingress and egress LSRs.
            Managers should obtain new values for row
            creation in this table by reading
            zxr10MplsTunnelIndexNext. When
            the MPLS signalling protocol is rsvp(2) this value
            SHOULD be equal to the value signaled in the
            Tunnel Id of the Session object. When the MPLS
            signalling protocol is crldp(3) this value
            SHOULD be equal to the value signaled in the
            LSP ID."
            ::= { zxr10MplsTunnelEntry 1 }

            zxr10MplsTunnelInstance OBJECT-TYPE
            SYNTAX Unsigned32
            MAX-ACCESS read-only
            STATUS current
            DESCRIPTION
                "Uniquely identifies a particular instance of a
                tunnel between a pair of ingress and egress LSRs.
                It is useful to identify multiple instances of
                tunnels for the purposes of backup and parallel
                tunnels. When the MPLS signaling protocol is
                rsvp(2) this value SHOULD be equal to the LSP Id
                of the Sender Template object. When the signaling
                protocol is crldp(3) there is no equivalent
                signaling object."
                ::= { zxr10MplsTunnelEntry 2 }

            zxr10MplsTunnelIngressLSRId OBJECT-TYPE
            SYNTAX IpAddress
            MAX-ACCESS read-only
            STATUS current
            DESCRIPTION
                "Identity of the ingress LSR associated with this
                tunnel instance. When the MPLS signalling protocol
                is rsvp(2) this value SHOULD be equal to the Tunnel
                Sender Address in the Sender Template object and MAY
                be equal to the Extended Tunnel Id field in the
                SESSION object. When the MPLS signalling protocol is

                rldp(3) this value SHOULD be equal to the Ingress
                LSR Router ID field in the LSPID TLV object."
                REFERENCE
                "1. RSVP-TE: Extensions to RSVP for LSP Tunnels,
                Awduche et al, RFC 3209, December 2001
                2. Constraint-Based LSP Setup using LDP, Jamoussi
                (Editor), RFC 3212, January 2002"
            ::= { zxr10MplsTunnelEntry 3 }

            zxr10MplsTunnelEgressLSRId OBJECT-TYPE
            SYNTAX IpAddress
            MAX-ACCESS read-only
            STATUS current
            DESCRIPTION
                "Identity of the egress LSR associated with this
                tunnel instance."
            ::= { zxr10MplsTunnelEntry 4 }


         zxr10MplsTunnelOutLabel OBJECT-TYPE
            SYNTAX Unsigned32
            MAX-ACCESS read-only
            STATUS current
            DESCRIPTION
                "Out label of local tunnel."
            ::= { zxr10MplsTunnelEntry 5 }


         zxr10MplsTunnelOutIntf OBJECT-TYPE
            SYNTAX DisplayString
            MAX-ACCESS read-only
            STATUS current
            DESCRIPTION
                "The name of out interface that local tunnel transits."
            ::= { zxr10MplsTunnelEntry 6 }

            zxr10MplsTunnelName OBJECT-TYPE
            SYNTAX DisplayString
            MAX-ACCESS read-only
            STATUS current
            DESCRIPTION
                "The canonical name assigned to the tunnel. This name
                can be used to refer to the tunnel on the LSR's
                console port. If zxr10MplsTunnelIsIf is set to true
                then the ifName of the interface corresponding to
                this tunnel should have a value equal to
                zxr10MplsTunnelName. Also see the description of ifName
                in RFC 2863."
            ::= { zxr10MplsTunnelEntry 7 }

            zxr10MplsTunnelDescr OBJECT-TYPE
            SYNTAX DisplayString
            MAX-ACCESS read-only
            STATUS current
            DESCRIPTION
            "A textual string containing information about the
            tunnel. If there is no description this object
            contains a zero length string. This object is may
            not be signaled by MPLS signaling protocols,
            consequentally the value of this object at transit
            and egress LSRs MAY be automatically generated or
            absent."
            ::= { zxr10MplsTunnelEntry 8 }

            zxr10MplsTunnelIsIf OBJECT-TYPE
            SYNTAX INTEGER { false(0), true(1) }
            MAX-ACCESS read-only
            STATUS obsolete
            DESCRIPTION
            "Denotes whether or not this tunnel corresponds to an
            interface represented in the interfaces group
            table. Note that if this variable is set to true
            then the ifName of the interface corresponding to
            this tunnel should have a value equal to
            zxr10MplsTunnelName. Also see the description of ifName
            in RFC 2863. This object is meaningful only at the
            ingress and egress LSRs."
            ::= { zxr10MplsTunnelEntry 9 }

            zxr10MplsTunnelIfIndex OBJECT-TYPE
            SYNTAX Unsigned32(0..2147483647)
            MAX-ACCESS read-only
            STATUS current
            DESCRIPTION
            "If zxr10MplsTunnelIsIf is set to true, then this value
            contains the LSR-assigned ifIndex which corresponds
            to an entry in the interfaces table. Otherwise
            this variable should contain the value of zero
            indicating that a valid ifIndex was not assigned to
            his tunnel interface."
            REFERENCE
            "RFC 2863 - The Interfaces Group MIB, McCloghrie, K.,
            and F. Kastenholtz, June 2000"
            DEFVAL { 0 }
            ::= { zxr10MplsTunnelEntry 10 }

            zxr10MplsTunnelIfType OBJECT-TYPE
            SYNTAX INTEGER {
                    unassigned(0),
                    ipAddress(1),
                    unnumbered(2)
                    }
            MAX-ACCESS read-only
            STATUS current
            DESCRIPTION
                 "Type of tunnel interface."
            ::= { zxr10MplsTunnelEntry 11 }


            zxr10MplsTunnelIfAddrOrName OBJECT-TYPE
            SYNTAX DisplayString
            MAX-ACCESS read-only
            STATUS current
            DESCRIPTION
                 "Ip address or loopback name of tunnel interface."
            ::= { zxr10MplsTunnelEntry 12 }

            zxr10MplsTunnelIfMaskOrIndex OBJECT-TYPE
            SYNTAX DisplayString
            MAX-ACCESS read-only
            STATUS current
            DESCRIPTION
                 "Subnet mask or loopback interface index of tunnel interface"
            ::= { zxr10MplsTunnelEntry 13 }

            zxr10MplsTunnelOwner OBJECT-TYPE
            SYNTAX  INTEGER {
                    unknown(1),
                    other(2),
                    snmp(3),
                    ldp(4),
                    crldp(5),
                    rsvpTe(6),
                    policyAgent(7)
                }
            MAX-ACCESS read-only
            STATUS current
            DESCRIPTION
            "Denotes the entity that created and is responsible
             for managing this tunnel. This column isau
             tomatically filled by the agent on creation of a
             ow."
             ::= { zxr10MplsTunnelEntry 14 }

             zxr10MplsTunnelRole OBJECT-TYPE
             SYNTAX INTEGER { head(1),
                            transit(2),
                            tail(3),
                            headTail(4) }
             MAX-ACCESS read-only
             STATUS current
             DESCRIPTION
             "This value signifies the role that this tunnel
             entry/instance represents. This value MUST be set
             to head(1) at the originating point of the tunnel.
             This value MUST be set to transit(2) at transit
             points along the tunnel, if transit points are
             supported. This value MUST be set to tail(3) at the
             terminating point of the tunnel if tunnel tails are
             supported.
             The value headTail(4) is provided for tunnels that
             begin and end on the same LSR."
             ::= { zxr10MplsTunnelEntry 15 }

             zxr10MplsTunnelSignallingProto OBJECT-TYPE
             SYNTAX INTEGER {none(1),
                            rsvp(2),
                            crldp(3),
                            other(4)
                            }
             MAX-ACCESS read-only
             STATUS current
             DESCRIPTION
             "The signalling protocol, if any, used to setup this
             tunnel."
             DEFVAL { none }
             ::= { zxr10MplsTunnelEntry 16 }

             zxr10MplsTunnelSetupPrio OBJECT-TYPE
             SYNTAX Integer32 (0..7)
             MAX-ACCESS read-only
             STATUS current
             DESCRIPTION
             "Indicates the setup priority of this tunnel."
             REFERENCE
             "1. RSVP-TE: Extensions to RSVP for LSP Tunnels,
             Awduche et al, RFC 3209, December 2001
             2. Constraint-Based LSP Setup using LDP, Jamoussi
             (Editor), RFC 3212, January 2002"
             DEFVAL { 7 }
             ::= { zxr10MplsTunnelEntry 17 }

             zxr10MplsTunnelHoldingPrio OBJECT-TYPE
             SYNTAX Integer32 (0..7)
             MAX-ACCESS read-only
             STATUS current
             DESCRIPTION
             "Indicates the holding priority for this tunnel."
             REFERENCE
             "1. RSVP-TE: Extensions to RSVP for LSP Tunnels,
             Awduche et al, RFC 3209, December 2001
             2. Constraint-Based LSP Setup using LDP, Jamoussi
             (Editor), RFC 3212, January 2002"
             DEFVAL { 7 }
             ::= { zxr10MplsTunnelEntry 18 }

            zxr10MplsTunnelSessionAttributes OBJECT-TYPE
             SYNTAX DisplayString
             MAX-ACCESS read-only
             STATUS current
             DESCRIPTION
             "This bit mask indicates optional session values for
             this tunnel. "
             REFERENCE
             "1. RSVP-TE: Extensions to RSVP for LSP Tunnels,
             Awduche et al, RFC 3209, December 2001."
             ::= { zxr10MplsTunnelEntry 19 }

            zxr10MplsTunnelFrrEnable OBJECT-TYPE
             SYNTAX INTEGER { false(0), true(1) }
             MAX-ACCESS read-only
             STATUS obsolete
             DESCRIPTION
             "If this tunnel enables FRR,this value is true,otherwise it is false."
             DEFVAL { false }
             ::= { zxr10MplsTunnelEntry 20 }

             zxr10MplsTunnelResourcePointer OBJECT-TYPE
             SYNTAX Unsigned32
             MAX-ACCESS read-only
             STATUS current
             DESCRIPTION
             "This variable represents a pointer to the traffic
             parameter specification for this tunnel. This
             value may point at an entry in the
             zxr10MplsTunnelResourceEntry to indicate which
             zxr10MplsTunnelResourceEntry is to be assigned to this
             LSP instance. This value may optionally point at
             an externally defined traffic parameter
             specification table. A value of zeroDotZero
             indicates best-effort treatment. By having the
             same value of this object, two or more LSPs can
             indicate resource sharing."
             ::= { zxr10MplsTunnelEntry 21 }

             zxr10MplsTunnelPrimaryInstance OBJECT-TYPE
             SYNTAX Unsigned32
             MAX-ACCESS read-only
             STATUS current
             DESCRIPTION
             "Specifies the instance index of the primary instance
             of this tunnel. More details of the definition of
             tunnel instances and the primary tunnel instance
             can be found in the description of the TEXTUAL-CONVENTION
             MplsTunnelInstanceIndex."
             DEFVAL { 0 }
             ::= { zxr10MplsTunnelEntry 22 }

             zxr10MplsTunnelInstancePriority OBJECT-TYPE
             SYNTAX Unsigned32
             MAX-ACCESS read-only
             STATUS current
             DESCRIPTION
             "This value indicates which priority, in descending
             order, with 0 indicating the lowest priority,
             within a group of tunnel instances. A group of
             tunnel instances is defined as a set of LSPs with
             the same zxr10MplsTunnelIndex in this table, but with a
             different zxr10MplsTunnelInstance. Tunnel instance
             priorities are used to denote the priority at which
             a particular tunnel instance will supercede
             another. Instances of tunnels containing the same
             zxr10MplsTunnelInstancePriority will be used for load
             sharing."
             DEFVAL { 0 }
             ::= { zxr10MplsTunnelEntry 23 }

             zxr10MplsTunnelHopTableIndex OBJECT-TYPE
             SYNTAX Unsigned32
             MAX-ACCESS read-only
             STATUS current
             DESCRIPTION
             "Index into the zxr10MplsTunnelHopTable entry that
             specifies the explicit route hops for this tunnel.
             This object is meaningful only at the head-end of
             the tunnel."
             DEFVAL { 0 }
             ::= { zxr10MplsTunnelEntry 24 }

             zxr10MplsTunnelPathInUse OBJECT-TYPE
             SYNTAX Unsigned32(0..16)
             MAX-ACCESS read-only
             STATUS current
             DESCRIPTION
             "This value denotes the configured path that was
             chosen for this tunnel. This value reflects the
             secondary index into zxr10MplsTunnelHopTable. This path
             may not exactly match the one in
             zxr10MplsTunnelARHopTable due to the fact that some CSPF
             modification may have taken place. See
             zxr10MplsTunnelARHopTable for the actual path being
             taken by the tunnel. A value of zero denotes that
             no path is currently in use or available."
             DEFVAL { 0 }
             ::= { zxr10MplsTunnelEntry 25 }

             zxr10MplsTunnelARHopTableIndex OBJECT-TYPE
             SYNTAX Unsigned32
             MAX-ACCESS read-only
             STATUS current
             DESCRIPTION
             "Index into the zxr10MplsTunnelARHopTable entry that
             specifies the actual hops traversed by the tunnel.
             This is automatically updated by the agent when the
             actual hops becomes available."
             DEFVAL { 0 }
             ::= { zxr10MplsTunnelEntry 26 }

             zxr10MplsTunnelCHopTableIndex OBJECT-TYPE
             SYNTAX Unsigned32
             MAX-ACCESS read-only
             STATUS current
             DESCRIPTION
             "Index into the zxr10MplsTunnelCHopTable entry that
             specifies the computed hops traversed by the
             tunnel. This is automatically updated by the agent
             when computed hops become available or when
             computed hops get modified."
             DEFVAL { 0 }
             ::= { zxr10MplsTunnelEntry 27 }

             zxr10MplsTunnelTotalUpTime OBJECT-TYPE
             SYNTAX TimeTicks
             MAX-ACCESS read-only
             STATUS current
             DESCRIPTION
             "This value represents the aggregate up time for all
             instances of this tunnel, if available. If this
             value is unavailable, it MUST return a value of 0."
             ::= { zxr10MplsTunnelEntry 28 }

             zxr10MplsTunnelInstanceUpTime OBJECT-TYPE
             SYNTAX TimeTicks
             MAX-ACCESS read-only
             STATUS current
             DESCRIPTION
             "This value identifies the total time that this
             tunnel instance's operStatus has been Up(1)."
             ::= { zxr10MplsTunnelEntry 29 }

             zxr10MplsTunnelPrimaryUpTime OBJECT-TYPE
             SYNTAX TimeTicks
             MAX-ACCESS read-only
             STATUS current
             DESCRIPTION
             "Specifies the total time the primary instance of
             this tunnel has been active. The primary instance
             of this tunnel is defined in
             zxr10MplsTunnelPrimaryInstance."
             ::= { zxr10MplsTunnelEntry 30 }

             zxr10MplsTunnelPathChanges OBJECT-TYPE
             SYNTAX Counter32
             MAX-ACCESS read-only
             STATUS current
             DESCRIPTION
             "Specifies the number of times the actual path for
             this tunnel instance has changed."
             ::= { zxr10MplsTunnelEntry 31 }

             zxr10MplsTunnelLastPathChange OBJECT-TYPE
             SYNTAX TimeTicks
             MAX-ACCESS read-only
             STATUS current
             DESCRIPTION
             "Specifies the time since the last change to the
             actual path for this tunnel instance."
             ::= { zxr10MplsTunnelEntry 32 }

             zxr10MplsTunnelCreationTime OBJECT-TYPE
             SYNTAX TimeStamp
             MAX-ACCESS read-only
             STATUS current
             DESCRIPTION
             "Specifies the value of SysUpTime when the first
             instance of this tunnel came into existence.
             That is, when the value of zxr10MplsTunnelOperStatus
             was first set to up(1)."
             ::= { zxr10MplsTunnelEntry 33 }

             zxr10MplsTunnelStateTransitions OBJECT-TYPE
             SYNTAX Counter32
             MAX-ACCESS read-only
             STATUS current
             DESCRIPTION
             "Specifies the number of times the state
             (zxr10MplsTunnelOperStatus) of this tunnel instance has
             changed."
             ::= { zxr10MplsTunnelEntry 34 }

             zxr10MplsTunnelAdminStatus OBJECT-TYPE
             SYNTAX INTEGER {
             -- ready to pass packets
                         up(1),
                         down(2)
                         }
             MAX-ACCESS read-only
             STATUS current
             DESCRIPTION
             "Indicates the desired operational status of this
             tunnel."
             ::= { zxr10MplsTunnelEntry 35 }

             zxr10MplsTunnelOperStatus OBJECT-TYPE
             SYNTAX INTEGER {
             -- ready to pass packets
                         up(1),
                         down(2)
                         }
             MAX-ACCESS read-only
             STATUS current
             DESCRIPTION
             "Indicates the actual operational status of this
             tunnel, which is typically but not limited to, a
             function of the state of individual segments of
             this tunnel."
             ::= { zxr10MplsTunnelEntry 36 }

             zxr10MplsTunnelRowStatus OBJECT-TYPE
             SYNTAX RowStatus
             MAX-ACCESS read-only
             STATUS current
             DESCRIPTION
             "This variable is used to create, modify, and/or
             delete a row in this table. When a row in this
             table is in active(1) state, no objects in that row
             can be modified by the agent except
             zxr10MplsTunnelAdminStatus, zxr10MplsTunnelRowStatus and
             zxr10MplsTunnelStorageType."
             ::= { zxr10MplsTunnelEntry 37 }

             zxr10MplsTunnelStorageType OBJECT-TYPE
             SYNTAX StorageType
             MAX-ACCESS read-only
             STATUS current
             DESCRIPTION "The storage type for this tunnel entry.
             Conceptual rows having the value 'permanent'
             need not allow write-access to any columnar
             objects in the row."
             DEFVAL { volatile }
             ::= { zxr10MplsTunnelEntry 38 }

             zxr10MplsTunnelAutorouteEnable OBJECT-TYPE
             SYNTAX INTEGER { false(0), true(1) }
             MAX-ACCESS read-only
             STATUS obsolete
             DESCRIPTION
                "If this object is true, then it enables the Autoroute."
             ::= { zxr10MplsTunnelEntry 39 }

             zxr10MplsTunnelAutorouteMetricType OBJECT-TYPE
             SYNTAX INTEGER {
                         igp(0),
                         defaultAbsolute(1),
                         absolute(2),
                         relative(3)
                        }
             MAX-ACCESS read-only
             STATUS obsolete
             DESCRIPTION
                "Indicates the autoroute metric type over this tunnel."
             ::= { zxr10MplsTunnelEntry 40 }


             zxr10MplsTunnelAutorouteMetricRelativeValue OBJECT-TYPE
             SYNTAX  Integer32
             MAX-ACCESS read-only
             STATUS obsolete
             DESCRIPTION
                "Indicates the value that adjust metric for autoroutes relative to IGP."
             ::= { zxr10MplsTunnelEntry 41 }

             zxr10MplsTunnelAutorouteMetricAbsoluteValue OBJECT-TYPE
             SYNTAX  Unsigned32
             MAX-ACCESS read-only
             STATUS obsolete
             DESCRIPTION
                "Indicates the value for all autoroutes over tunnel. "
             ::= { zxr10MplsTunnelEntry 42 }

             zxr10MplsTunnelRecordRouteEnable OBJECT-TYPE
             SYNTAX INTEGER { false(0), true(1) }
             MAX-ACCESS read-only
             STATUS obsolete
             DESCRIPTION
                "If this object is true, then it enables the RecordRoute"
             ::= { zxr10MplsTunnelEntry 43 }


             zxr10MplsTunnelCACStatus OBJECT-TYPE
                         SYNTAX INTEGER { disable(0), enable(1) }
             MAX-ACCESS read-only
             STATUS current
             DESCRIPTION
                "CAC switch status"
            ::= { zxr10MplsTunnelEntry 44 }

             --added
            zxr10MplsTunnelLspOctets OBJECT-TYPE
            SYNTAX     Counter64
            MAX-ACCESS read-only
            STATUS     current
            DESCRIPTION
                "The number of octets that have been forwarded
                 over current LSP active path. The number reported
                 is not realtime, may subject to several minutes
                 delay.  The delay is controllable by mpls statistics
                 gathering interval, which by default is once every
                 5 minutes.  If mpls statistics gathering is not
                 enabled, this number will not increment."
            ::= { zxr10MplsTunnelEntry 45 }

            zxr10MplsTunnelLspPackets OBJECT-TYPE
            SYNTAX     Counter64
            MAX-ACCESS read-only
            STATUS     current
            DESCRIPTION
                "The number of packets that have been forwarded
                 over current LSP active path. The number reported
                 is not realtime, may subject to several minutes
                 delay.  The delay is controllable by mpls statistics
                 gathering interval, which by default is once every
                 5 minutes.  If mpls statistics gathering is not
                 enabled, this number will not increment."
            ::= { zxr10MplsTunnelEntry 46 }

            zxr10MplsTunnelLspLastTransition OBJECT-TYPE
            SYNTAX     TimeStamp
            MAX-ACCESS read-only
            STATUS     current
            DESCRIPTION
                "The time in 10-millisecond units since the last
                 transition occurred on this LSP."
            ::= { zxr10MplsTunnelEntry  47}


            zxr10MplsTunnelLspConfiguredPaths OBJECT-TYPE
            SYNTAX     Integer32
            MAX-ACCESS read-only
            STATUS     current
            DESCRIPTION
                "The number of paths configured for this LSP."
            ::= { zxr10MplsTunnelEntry 48 }

            zxr10MplsTunnelPathType OBJECT-TYPE
            SYNTAX     INTEGER {
                other(1),
                primary(2)
            }
            MAX-ACCESS read-only
            STATUS     current
            DESCRIPTION
                "The type of path that is active, i.e., a
                 primary path, a standby path, or a generic
                 secondary path. This field is meaningless
             unless mplsPathName is not empty"
            ::= { zxr10MplsTunnelEntry 49 }



            zxr10MplsTunnelPathExplicitRoute OBJECT-TYPE
            SYNTAX     OCTET STRING (SIZE (0..1024))
            MAX-ACCESS read-only
            STATUS     current
            DESCRIPTION
                "The explicit route used to set up this LSP.
                 This may either be the route configured by
                 the user, or a route automatically computed
                 to satisfy constraints set by the user.
             This field is a displayable string in the
             format of XXX.XXX.XXX.XXX <space> S/L <newline>
             repeated for each explicit address. The S/L character
             stands for Strict/Loose route.
             This field is meaningless unless mplsPathName
             is not empty"
            ::= { zxr10MplsTunnelEntry 50 }



            zxr10MplsTunnelPathRecordRoute OBJECT-TYPE
            SYNTAX     OCTET STRING (SIZE (0..1024))
            MAX-ACCESS read-only
            STATUS     current
            DESCRIPTION
                "The route actually used for this path, as
                 recorded by the signaling protocol.
             This field is a displayable string in the
             format of XXX.XXX.XXX.XXX <space>
             repeated for each address.
             This field is meaningless unless mplsPathName is
             not empty"
            ::= { zxr10MplsTunnelEntry 51 }

            zxr10MplsTunnelPathCOS OBJECT-TYPE
            SYNTAX     INTEGER (0..7 | 255)
            MAX-ACCESS read-only
            STATUS     current
            DESCRIPTION
                "The configured Class Of Service on this path.  If
                 the value is between 0 and 7 inclusive, this value
                 will be inserted in the 3 bit COS field in the
                 label.  If the value is 255, the value in the COS
                 field of the label will depend on other factors.
             This field is meaningless unless mplsPathName is not empty"
            ::= { zxr10MplsTunnelEntry 52 }


            zxr10MplsTunnelPathInclude OBJECT-TYPE
            SYNTAX     Integer32
            MAX-ACCESS read-only
            STATUS     current
            DESCRIPTION
                "This is a configured set of colors (administrative
                groups) specified as a bit vector (i.e., bit n is 1
                if color n is in the set, where n = 0 is the LSB).
                For each link that this path goes through, the
                link MUST have colors associated with it, and
                the intersection of the link's colors and the
                'include' set MUST be non-null. This field is meaningless
                unless mplsPathName is not empty"
            ::= { zxr10MplsTunnelEntry 53 }

            zxr10MplsTunnelPathExclude OBJECT-TYPE
            SYNTAX     Integer32
            MAX-ACCESS read-only
            STATUS     current
            DESCRIPTION
                "This is a configured set of colors (administrative
                groups) specified as a bit vector (i.e., bit n is 1
                if color n is in the set, where n = 0 is the LSB).
                For each link that this path goes through, the
                link MUST have colors associated with it, and
                the intersection of the link's colors and the
                'exclude' set MUST be null. This field is meaningless
                unless mplsPathName is not empty"
            ::= { zxr10MplsTunnelEntry 54 }

             --end added

         --hsb added
                    zxr10MplsTunnelHotStandbyEnable  OBJECT-TYPE
            SYNTAX                         INTEGER { false(0), true(1) }
            MAX-ACCESS                     read-only
            STATUS                         obsolete
            DESCRIPTION
                "If this object is true, then it enables hotstandby."
            ::= { zxr10MplsTunnelEntry 55}

            zxr10MplsTunnelHotStandbyPrimaryPathOption  OBJECT-TYPE
            SYNTAX                         Unsigned32
            MAX-ACCESS                     read-only
            STATUS                         obsolete
            DESCRIPTION
                "Specifies the pathOption of protected LSP."
            ::= { zxr10MplsTunnelEntry 56}

            zxr10MplsTunnelHotStandbySecondaryPathOption  OBJECT-TYPE
            SYNTAX                         Unsigned32
            MAX-ACCESS                     read-only
            STATUS                         obsolete
            DESCRIPTION
                "Specifies the pathOption of hotstandby LSP."
            ::= { zxr10MplsTunnelEntry 57}

          zxr10MplsTunnelHotStandbyInstance  OBJECT-TYPE
            SYNTAX                         Integer32
            MAX-ACCESS                     read-only
            STATUS                         current
            DESCRIPTION
                "Uniquely identifies the tunnel instance of hotstandby lsp."
            ::= { zxr10MplsTunnelEntry 58}

            zxr10MplsTunnelHotStandbyState  OBJECT-TYPE
            SYNTAX                         INTEGER { active(2), ready(1), unready(0)}
            MAX-ACCESS                     read-only
            STATUS                         current
            DESCRIPTION
                "Specifies the hotstandby state of the tunnel."
            ::= { zxr10MplsTunnelEntry 59}
         --hsb ended
         --bfd added
         zxr10MplsTunnelBfdEnable  OBJECT-TYPE
            SYNTAX                         INTEGER { false(0), true(1) }
            MAX-ACCESS                     read-only
            STATUS                         obsolete
            DESCRIPTION
                "If this object is true, then it enables bfd on the tunnel."
            ::= { zxr10MplsTunnelEntry 60}

            zxr10MplsTunnelBFDmult  OBJECT-TYPE
            SYNTAX Unsigned32
            MAX-ACCESS read-only
            STATUS obsolete
            DESCRIPTION
            "The detecting multiple of receive/send CONTROL
            message."
            ::= { zxr10MplsTunnelEntry 61 }

        zxr10MplsTunnelBFDminTxInterval  OBJECT-TYPE
            SYNTAX Unsigned32
            MAX-ACCESS read-only
            STATUS obsolete
            DESCRIPTION
            "The minimal time to send CONTROL message."
            ::= { zxr10MplsTunnelEntry 62 }

        zxr10MplsTunnelBFDminRxInterval  OBJECT-TYPE
            SYNTAX Unsigned32
            MAX-ACCESS read-only
            STATUS obsolete
            DESCRIPTION
            "The minimal time to receive CONTROL message."
            ::= { zxr10MplsTunnelEntry 63 }

         zxr10MplsTunnelBFDstatus OBJECT-TYPE
            SYNTAX INTEGER { bfddisconnect(0),bfddown(1),bfdup(2) }
            MAX-ACCESS read-only
            STATUS current
            DESCRIPTION
                "The status of bfd."
            ::= { zxr10MplsTunnelEntry 64 }
         --bfd ended


         zxr10MplsTunnelFrrProtectionMethod OBJECT-TYPE
            SYNTAX        INTEGER {
                                   unknown(0),
                                   facilityBackup(1),
                                   oneToOneBackup(2)
                                   }
            MAX-ACCESS    read-only
            STATUS        obsolete
            DESCRIPTION
             "Indicates which protection method is used for fast
              reroute on this device.
              unknown(0)        indicates no FRR protection exists.
              facilityBackup(1) indicates bypass protection exists.
              oneToOneBackup(2) indicates detour protection exists. "
            ::= {  zxr10MplsTunnelEntry 65 }

         --cisco non-ietf added
         zxr10MplsTunnelBandwidth OBJECT-TYPE
            SYNTAX Unsigned32
            UNITS "kilobits per second"
            MAX-ACCESS read-only
            STATUS current
            DESCRIPTION
            "Specifies the bandwidth of the tunnel."
            ::= { zxr10MplsTunnelEntry 66 }

         zxr10MplsTunnelSubPoolBandwidth OBJECT-TYPE
            SYNTAX Unsigned32
            UNITS "kilobits per second"
            MAX-ACCESS read-only
            STATUS current
            DESCRIPTION
            "Specifies the sub pool bandwidth of the tunnel."
            ::= { zxr10MplsTunnelEntry 67 }
         --cisco non-ietf ended

             zxr10MplsTunnelIgpMetric  OBJECT-TYPE
          SYNTAX Unsigned32
              MAX-ACCESS read-only
              STATUS current
              DESCRIPTION
                "The value of igp metric is used for build tunnel."
          ::= { zxr10MplsTunnelEntry 68}

          zxr10MplsTunnelTeMetric    OBJECT-TYPE
          SYNTAX Unsigned32
              MAX-ACCESS read-only
              STATUS current
              DESCRIPTION
                "The value of te metric is used for build tunnel."
          ::= { zxr10MplsTunnelEntry 69}

          zxr10MplsTunnelBFDSlaveStatus OBJECT-TYPE
            SYNTAX INTEGER { bfddisconnect(0),bfddown(1),bfdup(2) }
            MAX-ACCESS read-only
            STATUS current
            DESCRIPTION
                "The status of slave lsp bfd."
            ::= { zxr10MplsTunnelEntry 70 }

          zxr10MplsTunnelAssociateStatus OBJECT-TYPE
            SYNTAX INTEGER { disabled(1),unbound(2),bound(3) }
            MAX-ACCESS read-only
            STATUS current
            DESCRIPTION
                "The associate bidirect status of this tunnel."
            ::= { zxr10MplsTunnelEntry 71 }


             -- End of zxr10MplsTunnelTable


      -- MPLS remote tunnel table.
        zxr10MplsRemoteTunnelTable OBJECT-TYPE
            SYNTAX SEQUENCE OF Zxr10MplsRemoteTunnelEntry
            MAX-ACCESS not-accessible
            STATUS current
            DESCRIPTION
                    "The Mpls Remote Tunnel Table "
            ::= { zxr10MplsTeRemoteTunnelObjects 1 }

        zxr10MplsRemoteTunnelEntry OBJECT-TYPE
            SYNTAX Zxr10MplsRemoteTunnelEntry
            MAX-ACCESS not-accessible
            STATUS current
            DESCRIPTION
                  "An entry in this table represents an MPLS remote tunnel."
            INDEX { zxr10MplsRemoteTunnelIndex,
                    zxr10MplsRemoteTunnelInstance,
                    zxr10MplsRemoteTunnelIngressLSRId,
                    zxr10MplsRemoteTunnelEgressLSRId
                  }
            ::= { zxr10MplsRemoteTunnelTable 1 }


            Zxr10MplsRemoteTunnelEntry ::= SEQUENCE {
                zxr10MplsRemoteTunnelIndex Unsigned32,
                zxr10MplsRemoteTunnelInstance Unsigned32,
                zxr10MplsRemoteTunnelIngressLSRId IpAddress,
                zxr10MplsRemoteTunnelEgressLSRId IpAddress,
                zxr10MplsRemoteTunnelInLabel Unsigned32,
                zxr10MplsRemoteTunnelOutLabel Unsigned32,
                zxr10MplsRemoteTunnelInIntf DisplayString,
                zxr10MplsRemoteTunnelOutIntf DisplayString,
                zxr10MplsRemoteTunnelName DisplayString,
                zxr10MplsRemoteTunnelIsIf INTEGER,
                zxr10MplsRemoteTunnelOwner INTEGER,
                zxr10MplsRemoteTunnelRole INTEGER,
                zxr10MplsRemoteTunnelSignallingProto INTEGER,
                zxr10MplsRemoteTunnelSetupPrio Integer32,
                zxr10MplsRemoteTunnelHoldingPrio Integer32,
                zxr10MplsRemoteTunnelSessionAttributes DisplayString,
                zxr10MplsRemoteTunnelLocalProtectInUse INTEGER,
                zxr10MplsRemoteTunnelPrimaryInstance Unsigned32,
                zxr10MplsRemoteTunnelInstancePriority Unsigned32,
                zxr10MplsRemoteTunnelTotalUpTime TimeTicks,
                zxr10MplsRemoteTunnelInstanceUpTime TimeTicks,
                zxr10MplsRemoteTunnelPrimaryUpTime TimeTicks,
                zxr10MplsRemoteTunnelCreationTime TimeStamp,
                zxr10MplsRemoteTunnelAdminStatus INTEGER,
                zxr10MplsRemoteTunnelOperStatus INTEGER,
                zxr10MplsRemoteTunnelRowStatus RowStatus,
                zxr10MplsRemoteTunnelStorageType StorageType,
                        zxr10MplsRemoteTunnelPathExplicitRoute   OCTET STRING,
                zxr10MplsRemoteTunnelPathRecordRoute     OCTET STRING,
                zxr10MplsRemoteTunnelFrrProtectionMethod INTEGER,
                zxr10MplsRemoteTunnelARHopTableIndex    Unsigned32,
                zxr10MplsRemoteTunnelLspInOctets Counter64,
                zxr10MplsRemoteTunnelLspInPackets Counter64
                }

            zxr10MplsRemoteTunnelIndex OBJECT-TYPE
            SYNTAX Unsigned32
            MAX-ACCESS read-only
            STATUS current
            DESCRIPTION
                "Uniquely identifies a set of tunnel instances
            between a pair of ingress and egress LSRs."
            ::= { zxr10MplsRemoteTunnelEntry 1 }

            zxr10MplsRemoteTunnelInstance OBJECT-TYPE
            SYNTAX Unsigned32
            MAX-ACCESS read-only
            STATUS current
            DESCRIPTION
                "Uniquely identifies a particular instance of a
                tunnel between a pair of ingress and egress LSRs.
                It is useful to identify multiple instances of
                tunnels for the purposes of backup and parallel
                tunnels. "
            ::= { zxr10MplsRemoteTunnelEntry 2 }

            zxr10MplsRemoteTunnelIngressLSRId OBJECT-TYPE
            SYNTAX IpAddress
            MAX-ACCESS read-only
            STATUS current
            DESCRIPTION
                "Identity of the ingress LSR associated with this
                tunnel instance. "
            ::= { zxr10MplsRemoteTunnelEntry 3 }

            zxr10MplsRemoteTunnelEgressLSRId OBJECT-TYPE
            SYNTAX IpAddress
            MAX-ACCESS read-only
            STATUS current
            DESCRIPTION
                "Identity of the egress LSR associated with this
                tunnel instance."
            ::= { zxr10MplsRemoteTunnelEntry 4 }

         zxr10MplsRemoteTunnelInLabel OBJECT-TYPE
            SYNTAX Unsigned32
            MAX-ACCESS read-only
            STATUS current
            DESCRIPTION
                "In label of Remote tunnel."
            ::= { zxr10MplsRemoteTunnelEntry 5 }

         zxr10MplsRemoteTunnelOutLabel OBJECT-TYPE
            SYNTAX Unsigned32
            MAX-ACCESS read-only
            STATUS current
            DESCRIPTION
                "Out label of Remote tunnel."
            ::= { zxr10MplsRemoteTunnelEntry 6 }

         zxr10MplsRemoteTunnelInIntf OBJECT-TYPE
            SYNTAX DisplayString
            MAX-ACCESS read-only
            STATUS current
            DESCRIPTION
                "The name of in interface that remote tunnel transits."
            ::= { zxr10MplsRemoteTunnelEntry 7 }

         zxr10MplsRemoteTunnelOutIntf OBJECT-TYPE
            SYNTAX DisplayString
            MAX-ACCESS read-only
            STATUS current
            DESCRIPTION
                "The name of out interface that remote tunnel transits."
            ::= { zxr10MplsRemoteTunnelEntry 8 }

            zxr10MplsRemoteTunnelName OBJECT-TYPE
            SYNTAX DisplayString
            MAX-ACCESS read-only
            STATUS current
            DESCRIPTION
                "The canonical name assigned to the tunnel. This name
                can be used to refer to the tunnel on the LSR's
                console port. If zxr10MplsRemoteTunnelIsIf is set to true
                then the ifName of the interface corresponding to
                this tunnel should have a value equal to
                zxr10MplsRemoteTunnelName. Also see the description of ifName
                in RFC 2863."
            ::= { zxr10MplsRemoteTunnelEntry 9 }

            zxr10MplsRemoteTunnelIsIf OBJECT-TYPE
            SYNTAX INTEGER { false(0), true(1) }
            MAX-ACCESS read-only
            STATUS current
            DESCRIPTION
            "Denotes whether or not this tunnel corresponds to an
            interface represented in the interfaces group
            table. Note that if this variable is set to true
            then the ifName of the interface corresponding to
            this tunnel should have a value equal to
            zxr10MplsRemoteTunnelName. Also see the description of ifName
            in RFC 2863. This object is meaningful only at the
            ingress and egress LSRs."
            ::= { zxr10MplsRemoteTunnelEntry 11 }

            zxr10MplsRemoteTunnelOwner OBJECT-TYPE
            SYNTAX  INTEGER {
                    unknown(1),
                    other(2),
                    snmp(3),
                    ldp(4),
                    crldp(5),
                    rsvpTe(6),
                    policyAgent(7)
                }
            MAX-ACCESS read-only
            STATUS current
            DESCRIPTION
            "Denotes the entity that created and is responsible
             for managing this tunnel. This column isau
             tomatically filled by the agent on creation of a
             ow."
             ::= { zxr10MplsRemoteTunnelEntry 12 }

             zxr10MplsRemoteTunnelRole OBJECT-TYPE
             SYNTAX INTEGER { head(1),
                            transit(2),
                            tail(3),
                            headTail(4) }
             MAX-ACCESS read-only
             STATUS current
             DESCRIPTION
             "This value signifies the role that this tunnel
             entry/instance represents. This value MUST be set
             to head(1) at the originating point of the tunnel.
             This value MUST be set to transit(2) at transit
             points along the tunnel, if transit points are
             supported. This value MUST be set to tail(3) at the
             terminating point of the tunnel if tunnel tails are
             supported.
             The value headTail(4) is provided for tunnels that
             begin and end on the same LSR."
             ::= { zxr10MplsRemoteTunnelEntry 13 }

             zxr10MplsRemoteTunnelSignallingProto OBJECT-TYPE
             SYNTAX INTEGER {none(1),
                            rsvp(2),
                            crldp(3),
                            other(4)
                            }
             MAX-ACCESS read-only
             STATUS current
             DESCRIPTION
             "The signalling protocol, if any, used to setup this
             tunnel."
             DEFVAL { none }
             ::= { zxr10MplsRemoteTunnelEntry 14 }

             zxr10MplsRemoteTunnelSetupPrio OBJECT-TYPE
             SYNTAX Integer32 (0..7)
             MAX-ACCESS read-only
             STATUS current
             DESCRIPTION
             "Indicates the setup priority of this tunnel."
             DEFVAL { 7 }
             ::= { zxr10MplsRemoteTunnelEntry 15 }

             zxr10MplsRemoteTunnelHoldingPrio OBJECT-TYPE
             SYNTAX Integer32 (0..7)
             MAX-ACCESS read-only
             STATUS current
             DESCRIPTION
             "Indicates the holding priority for this tunnel."
             DEFVAL { 7 }
             ::= { zxr10MplsRemoteTunnelEntry 16 }

            zxr10MplsRemoteTunnelSessionAttributes OBJECT-TYPE
             SYNTAX DisplayString
             MAX-ACCESS read-only
             STATUS current
             DESCRIPTION
             "This bit mask indicates optional session values for
             this tunnel. "
             ::= { zxr10MplsRemoteTunnelEntry 17 }

            zxr10MplsRemoteTunnelLocalProtectInUse OBJECT-TYPE
             SYNTAX INTEGER { false(0), true(1) }
             MAX-ACCESS read-only
             STATUS current
             DESCRIPTION
             "Indicates that the local repair mechanism is in use
             to maintain this tunnel (usually in the face of an
             outage of the link it was previously routed over)."
             DEFVAL { false }
             ::= { zxr10MplsRemoteTunnelEntry 18 }

             zxr10MplsRemoteTunnelPrimaryInstance OBJECT-TYPE
             SYNTAX Unsigned32
             MAX-ACCESS read-only
             STATUS current
             DESCRIPTION
             "Specifies the instance index of the primary instance
             of this tunnel. More details of the definition of
             tunnel instances and the primary tunnel instance
             can be found in the description of the TEXTUAL-CONVENTION
             MplsTunnelInstanceIndex."
             DEFVAL { 0 }
             ::= { zxr10MplsRemoteTunnelEntry 19 }

             zxr10MplsRemoteTunnelInstancePriority OBJECT-TYPE
             SYNTAX Unsigned32
             MAX-ACCESS read-only
             STATUS current
             DESCRIPTION
             "This value indicates which priority, in descending
             order, with 0 indicating the lowest priority,
             within a group of tunnel instances. A group of
             tunnel instances is defined as a set of LSPs with
             the same zxr10MplsRemoteTunnelIndex in this table, but with a
             different zxr10MplsRemoteTunnelInstance. Tunnel instance
             priorities are used to denote the priority at which
             a particular tunnel instance will supercede
             another. Instances of tunnels containing the same
             zxr10MplsRemoteTunnelInstancePriority will be used for load
             sharing."
             DEFVAL { 0 }
             ::= { zxr10MplsRemoteTunnelEntry 20 }

             zxr10MplsRemoteTunnelTotalUpTime OBJECT-TYPE
             SYNTAX TimeTicks
             MAX-ACCESS read-only
             STATUS current
             DESCRIPTION
             "This value represents the aggregate up time for all
             instances of this tunnel, if available. If this
             value is unavailable, it MUST return a value of 0."
             ::= { zxr10MplsRemoteTunnelEntry 21 }

             zxr10MplsRemoteTunnelInstanceUpTime OBJECT-TYPE
             SYNTAX TimeTicks
             MAX-ACCESS read-only
             STATUS current
             DESCRIPTION
             "This value identifies the total time that this
             tunnel instance's operStatus has been Up(1)."
             ::= { zxr10MplsRemoteTunnelEntry 22 }

             zxr10MplsRemoteTunnelPrimaryUpTime OBJECT-TYPE
             SYNTAX TimeTicks
             MAX-ACCESS read-only
             STATUS current
             DESCRIPTION
             "Specifies the total time the primary instance of
             this tunnel has been active. The primary instance
             of this tunnel is defined in
             zxr10MplsRemoteTunnelPrimaryInstance."
             ::= { zxr10MplsRemoteTunnelEntry 23 }

             zxr10MplsRemoteTunnelCreationTime OBJECT-TYPE
             SYNTAX TimeStamp
             MAX-ACCESS read-only
             STATUS current
             DESCRIPTION
             "Specifies the value of SysUpTime when the first
             instance of this tunnel came into existence.
             That is, when the value of zxr10MplsRemoteTunnelOperStatus
             was first set to up(1)."
             ::= { zxr10MplsRemoteTunnelEntry 26 }

             zxr10MplsRemoteTunnelAdminStatus OBJECT-TYPE
             SYNTAX INTEGER {
             -- ready to pass packets
                         up(1),
                         down(2)
                         }
             MAX-ACCESS read-only
             STATUS current
             DESCRIPTION
             "Indicates the desired operational status of this
             tunnel."
             ::= { zxr10MplsRemoteTunnelEntry 28 }

             zxr10MplsRemoteTunnelOperStatus OBJECT-TYPE
             SYNTAX INTEGER {
             -- ready to pass packets
                         up(1),
                         down(2)
                         }
             MAX-ACCESS read-only
             STATUS current
             DESCRIPTION
             "Indicates the actual operational status of this
             tunnel, which is typically but not limited to, a
             function of the state of individual segments of
             this tunnel."
             ::= { zxr10MplsRemoteTunnelEntry 29 }

             zxr10MplsRemoteTunnelRowStatus OBJECT-TYPE
             SYNTAX RowStatus
             MAX-ACCESS read-only
             STATUS current
             DESCRIPTION
             "This variable is used to create, modify, and/or
             delete a row in this table. When a row in this
             table is in active(1) state, no objects in that row
             can be modified by the agent except
             zxr10MplsRemoteTunnelAdminStatus, zxr10MplsRemoteTunnelRowStatus and
             zxr10MplsRemoteTunnelStorageType."
             ::= { zxr10MplsRemoteTunnelEntry 30 }

             zxr10MplsRemoteTunnelStorageType OBJECT-TYPE
             SYNTAX StorageType
             MAX-ACCESS read-only
             STATUS current
             DESCRIPTION "The storage type for this tunnel entry.
             Conceptual rows having the value 'permanen'
             need not allow write-access to any columnar
             objects in the row."
             DEFVAL { volatile }
             ::= { zxr10MplsRemoteTunnelEntry 31 }

                 zxr10MplsRemoteTunnelPathExplicitRoute OBJECT-TYPE
            SYNTAX     OCTET STRING (SIZE (0..1024))
            MAX-ACCESS read-only
            STATUS     current
            DESCRIPTION
                "The explicit route used to set up this LSP.
                 This may either be the route configured by
                 the user, or a route automatically computed
                 to satisfy constraints set by the user.
             This field is a displayable string in the
             format of XXX.XXX.XXX.XXX <space> S/L <newline>
             repeated for each explicit address. The S/L character
             stands for Strict/Loose route.
             This field is meaningless unless mplsPathName
             is not empty"
            ::= { zxr10MplsRemoteTunnelEntry 32 }



            zxr10MplsRemoteTunnelPathRecordRoute OBJECT-TYPE
            SYNTAX     OCTET STRING (SIZE (0..1024))
            MAX-ACCESS read-only
            STATUS     current
            DESCRIPTION
                "The route actually used for this path, as
                 recorded by the signaling protocol.
             This field is a displayable string in the
             format of XXX.XXX.XXX.XXX <space>
             repeated for each address.
             This field is meaningless unless mplsPathName is
             not empty"
            ::= { zxr10MplsRemoteTunnelEntry 33 }

         zxr10MplsRemoteTunnelFrrProtectionMethod OBJECT-TYPE
            SYNTAX        INTEGER {
                                   unknown(0),
                                   facilityBackup(1),
                                   oneToOneBackup(2)
                                   }
            MAX-ACCESS    read-only
            STATUS        current
            DESCRIPTION
             "Indicates which protection method is used for fast
              reroute on this device.
              unknown(0)        indicates no FRR protection exists.
              facilityBackup(1) indicates bypass protection exists.
              oneToOneBackup(2) indicates detour protection exists. "
            ::= {  zxr10MplsRemoteTunnelEntry 34 }

         zxr10MplsRemoteTunnelARHopTableIndex OBJECT-TYPE
            SYNTAX        Unsigned32
            MAX-ACCESS    read-only
            STATUS        current
            DESCRIPTION
             "Index into the zxr10MplsTunnelARHopTable entry that
             specifies the actual hops traversed by the remote tunnel.
             This is automatically updated by the agent when the
             actual hops becomes available. "
            ::= {  zxr10MplsRemoteTunnelEntry 35 }

         zxr10MplsRemoteTunnelLspInOctets OBJECT-TYPE
            SYNTAX     Counter64
            MAX-ACCESS read-only
            STATUS     current
            DESCRIPTION
             "The number of octets that have been forwarded
              over current LSP active path. The number reported
              is not realtime, may subject to several minutes
              delay.  The delay is controllable by mpls statistics
              gathering interval, which by default is once every
              5 minutes.  If mpls statistics gathering is not
              enabled, this number will not increment."
            ::= { zxr10MplsRemoteTunnelEntry 36 }

         zxr10MplsRemoteTunnelLspInPackets OBJECT-TYPE
            SYNTAX     Counter64
            MAX-ACCESS read-only
            STATUS     current
            DESCRIPTION
             "The number of packets that have been forwarded
              over current LSP active path. The number reported
              is not realtime, may subject to several minutes
              delay.  The delay is controllable by mpls statistics
              gathering interval, which by default is once every
              5 minutes.  If mpls statistics gathering is not
              enabled, this number will not increment."
            ::= { zxr10MplsRemoteTunnelEntry 37 }
             -- mplsHopTable

            zxr10MplsTunnelHopTable OBJECT-TYPE
             SYNTAX SEQUENCE OF Zxr10MplsTunnelHopEntry
             MAX-ACCESS not-accessible
             STATUS current
             DESCRIPTION
             "The zxr10MplsTunnelHopTable is used to indicate the hops,
             strict or loose, for an instance of an MPLS tunnel
             defined in zxr10MplsTunnelTable, when it is established
             via signalling, for the outgoing direction of the
             tunnel."
             ::= { zxr10MplsTeHopObjects 1 }

             zxr10MplsTunnelHopEntry OBJECT-TYPE
             SYNTAX Zxr10MplsTunnelHopEntry
             MAX-ACCESS not-accessible
             STATUS current
             DESCRIPTION
             "An entry in this table represents a tunnel hop. An
             entry is created by a network administrator for
             signaled ERLSP set up by an MPLS signalling
             protocol."
             INDEX {
                   zxr10MplsTunnelHopListIndex,
                   zxr10MplsTunnelHopPathOptionIndex,
                   zxr10MplsTunnelHopIndex
                   }
             ::= { zxr10MplsTunnelHopTable 1 }

             Zxr10MplsTunnelHopEntry ::= SEQUENCE {
                    zxr10MplsTunnelHopListIndex Unsigned32,
                    zxr10MplsTunnelHopPathOptionIndex Unsigned32,
                    zxr10MplsTunnelHopIndex Unsigned32,
                    zxr10MplsTunnelHopAddrType INTEGER,
                    zxr10MplsTunnelHopIpAddr IpAddress,
                    zxr10MplsTunnelHopIpPrefixLen Unsigned32,
                    zxr10MplsTunnelHopAsNumber Unsigned32,
                    zxr10MplsTunnelHopAddrUnnum Unsigned32,
                    zxr10MplsTunnelHopLspId Unsigned32,
                    zxr10MplsTunnelHopType INTEGER,
                    zxr10MplsTunnelHopInclude INTEGER,
                    zxr10MplsTunnelHopPathOptionName DisplayString,
                    zxr10MplsTunnelHopEntryPathComp INTEGER,
                    zxr10MplsTunnelHopRowStatus RowStatus,
                    zxr10MplsTunnelHopStorageType StorageType
                    }

              zxr10MplsTunnelHopListIndex OBJECT-TYPE
              SYNTAX Unsigned32
              MAX-ACCESS read-only
              STATUS current
              DESCRIPTION
              "Primary index into this table identifying a
              particular explicit route object."
              ::= { zxr10MplsTunnelHopEntry 1 }

              zxr10MplsTunnelHopPathOptionIndex OBJECT-TYPE
              SYNTAX Unsigned32
              MAX-ACCESS read-only
              STATUS current
              DESCRIPTION
              "Secondary index into this table identifying a
              particular group of hops representing a particular
              configured path. This is otherwise known as a path
              option."
              ::= { zxr10MplsTunnelHopEntry 2 }

              zxr10MplsTunnelHopIndex OBJECT-TYPE
              SYNTAX Unsigned32
              MAX-ACCESS read-only
              STATUS current
              DESCRIPTION
              "Tertiary index into this table identifying a
              particular hop."
              ::= { zxr10MplsTunnelHopEntry 3 }

              zxr10MplsTunnelHopAddrType OBJECT-TYPE
              SYNTAX     INTEGER {
                        unknown(0),
                        ipv4(1),
                        ipv6(2),
                        asnumber(3),
                        unnum(4),
                        lspid(5)
                     }
              MAX-ACCESS read-only
              STATUS current
              DESCRIPTION
              "The Hop Address Type of this tunnel hop."
              DEFVAL { ipv4 }
              ::= { zxr10MplsTunnelHopEntry 4 }

              zxr10MplsTunnelHopIpAddr OBJECT-TYPE
              SYNTAX IpAddress
              MAX-ACCESS read-only
              STATUS current
              DESCRIPTION
              "The Tunnel Hop Address for this tunnel hop."
              ::= { zxr10MplsTunnelHopEntry 5 }

              zxr10MplsTunnelHopIpPrefixLen OBJECT-TYPE
              SYNTAX Unsigned32
              MAX-ACCESS read-only
              STATUS current
              DESCRIPTION "If zxr10MplsTunnelHopAddrType is set to ipv4(1) or
              ipv6(2), then this value will contain an
              appropriate prefix length for the IP address in
              object zxr10MplsTunnelHopIpAddr. Otherwise this value
              is irrelevant and should be ignored. "
              DEFVAL { 32 }
              ::= { zxr10MplsTunnelHopEntry 6 }

              zxr10MplsTunnelHopAsNumber OBJECT-TYPE
              SYNTAX Unsigned32
              MAX-ACCESS read-only
              STATUS current
              DESCRIPTION
              "If zxr10MplsTunnelHopAddrType is set to asnumber(3), then
              this value will contain the AS number of this hop.
              Otherwise the agent should set this object to zerolength
              string and the manager should ignore this."
              ::= { zxr10MplsTunnelHopEntry 7 }

              zxr10MplsTunnelHopAddrUnnum OBJECT-TYPE
              SYNTAX Unsigned32
              MAX-ACCESS read-only
              STATUS current
              DESCRIPTION
              "If zxr10MplsTunnelHopAddrType is set to unnum(4), then
              this value will contain the interface identifier of
              the unnumbered interface for this hop. This object
              should be used in conjunction with
              zxr10MplsTunnelHopIpAddress which would contain the LSR
              Router ID in this case. Otherwise the agent should
              set this object to zero-length string and the
              manager should ignore this."
              ::= { zxr10MplsTunnelHopEntry 8 }

              zxr10MplsTunnelHopLspId OBJECT-TYPE
              SYNTAX Unsigned32
              MAX-ACCESS read-only
              STATUS current
              DESCRIPTION
              "If zxr10MplsTunnelHopAddrType is set to lspid(5), then
              this value will contain the LSPID of a tunnel of
              this hop. The present tunnel being configured is
              tunneled through this hop (using label stacking).
              This object is otherwise insignificant and should
              contain a value of 0 to indicate this fact."
              ::= { zxr10MplsTunnelHopEntry 9 }

              zxr10MplsTunnelHopType OBJECT-TYPE
              SYNTAX INTEGER {
                            strict(1),
                            loose(2)
                            }
              MAX-ACCESS read-only
              STATUS current
              DESCRIPTION
              "Denotes whether this tunnel hop is routed in a
              strict or loose fashion. The value of this object
              has no meaning if the zxr10MplsTunnelHopInclude object
              is set to 'false'."
              ::= { zxr10MplsTunnelHopEntry 10 }

              zxr10MplsTunnelHopInclude OBJECT-TYPE
              SYNTAX INTEGER { false(0), true(1) }
              MAX-ACCESS read-only
              STATUS current
              DESCRIPTION
              "If this value is set to true, then this indicates
              that this hop must be included in the tunnel's
              path. If this value is set to 'false', then this hoph
              must be avoided when calculating the path for this
              tunnel. The default value of this object is 'true',
              so that by default all indicated hops are included
              in the CSPF path computation. If this object is set
              to 'false' the value of zxr10MplsTunnelHopType should be
              ignored."
              DEFVAL { true }
              ::= { zxr10MplsTunnelHopEntry 11 }

              zxr10MplsTunnelHopPathOptionName OBJECT-TYPE
              SYNTAX DisplayString
              MAX-ACCESS read-only
              STATUS current
              DESCRIPTION
              "The description of this series of hops as they
              relate to the specified path option. The
              value of this object SHOULD be the same for
              each hop in the series that comprises a
              path option."
              ::= { zxr10MplsTunnelHopEntry 12 }

              zxr10MplsTunnelHopEntryPathComp OBJECT-TYPE
              SYNTAX INTEGER {
                            dynamic(1), -- CSPF computed
                            explicit(2) -- strict hop
                            }
              MAX-ACCESS read-only
              STATUS current
              DESCRIPTION
              "If this value is set to dynamic, then the user
              should only specify the source and destination of
              the path and expect that the CSPF will calculate
              the remainder of the path. If this value is set to
              explicit, the user should specify the entire path
              for the tunnel to take. This path may contain
              strict or loose hops. Each hop along a specific
              path SHOULD have this object set to the same value."
              ::= { zxr10MplsTunnelHopEntry 13 }

              zxr10MplsTunnelHopRowStatus OBJECT-TYPE
              SYNTAX RowStatus
              MAX-ACCESS read-only
              STATUS current
              DESCRIPTION
              "This variable is used to create, modify, and/or
              delete a row in this table. When a row in this
              table is in active(1) state, no objects in that row
              can be modified by the agent except
              zxr10MplsTunnelHopRowStatus and
              zxr10MplsTunnelHopStorageType."
              ::= { zxr10MplsTunnelHopEntry 14 }

              zxr10MplsTunnelHopStorageType OBJECT-TYPE
              SYNTAX StorageType
              MAX-ACCESS read-only
              STATUS current
              DESCRIPTION
              "The storage type for this Hop entry. Conceptual
              rows having the value 'permanent' need not
              allow write-access to any columnar objects
              in the row."
              DEFVAL { volatile }
              ::= { zxr10MplsTunnelHopEntry 15 }

        -- End of zxr10MplsTunnelHopTable


        -- Begin of zxr10MplsTunnelResourceTablem
             zxr10MplsTunnelResourceTable OBJECT-TYPE
              SYNTAX SEQUENCE OF Zxr10MplsTunnelResourceEntry
              MAX-ACCESS not-accessible
              STATUS current
              DESCRIPTION
              "The zxr10MplsTunnelResourceTable allows a manager to
              specify which resources are desired for an MPLS
              tunnel. This table also allows several tunnels to
              point to a single entry in this table, implying
              that these tunnels should share resources."
              ::= { zxr10MplsTeResourceObjects 1 }

             zxr10MplsTunnelResourceEntry OBJECT-TYPE
              SYNTAX Zxr10MplsTunnelResourceEntry
              MAX-ACCESS not-accessible
              STATUS current
              DESCRIPTION
              "An entry in this table represents a set of resources
              for an MPLS tunnel. An entry can be created by a
              network administrator or by an SNMP agent as
              instructed by any MPLS signalling protocol.
              An entry in this table referenced by a tunnel instance

              with zero zxr10MplsTunnelInstance value indicates a
              configured set of resource parameter. An entry
              referenced by a tunnel instance with a non-zero
              zxr10MplsTunnelInstance reflects the in-use resource
              parameters for the tunnel instance which may have
              been negotiated or modified by the MPLS signaling
              protocols."
              INDEX { zxr10MplsTunnelResourceIndex }
              ::= { zxr10MplsTunnelResourceTable 1 }

              Zxr10MplsTunnelResourceEntry ::= SEQUENCE {
                      zxr10MplsTunnelResourceIndex Unsigned32,
                      zxr10MplsTunnelResourceMaxRate Unsigned32,
                      zxr10MplsTunnelResourceMeanRate Unsigned32,
                      zxr10MplsTunnelResourceMaxBurstSize Unsigned32,
                      zxr10MplsTunnelResourceMeanBurstSize Unsigned32,
                      zxr10MplsTunnelResourceRowStatus RowStatus,
                      zxr10MplsTunnelResourceStorageType StorageType
              }

              zxr10MplsTunnelResourceIndex OBJECT-TYPE
              SYNTAX Unsigned32
              MAX-ACCESS read-only
              STATUS current
              DESCRIPTION
              "Uniquely identifies this row."
              ::= { zxr10MplsTunnelResourceEntry 1 }

              zxr10MplsTunnelResourceMaxRate OBJECT-TYPE
              SYNTAX Unsigned32
              UNITS "kilobits per second"
              MAX-ACCESS read-only
              STATUS current
              DESCRIPTION
              "The maximum rate in bits/second. Note that setting
              zxr10MplsTunnelResourceMaxRate,
              zxr10MplsTunnelResourceMeanRate, and
              zxr10MplsTunnelResourceMaxBurstSize to 0 indicates besteffort
              treatment."
              ::= { zxr10MplsTunnelResourceEntry 2 }

              zxr10MplsTunnelResourceMeanRate OBJECT-TYPE
              SYNTAX Unsigned32
              UNITS "kilobits per second"
              MAX-ACCESS read-only
              STATUS current
              DESCRIPTION
              "This object is copied into an instance of
              mplsTrafficParamMeanRate in the
              mplsTrafficParamTable. The OID of this table entry
              is then copied into the corresponding
              mplsInSegmentTrafficParamPtr."
              ::= { zxr10MplsTunnelResourceEntry 3 }

              zxr10MplsTunnelResourceMaxBurstSize OBJECT-TYPE
              SYNTAX Unsigned32
              UNITS "bytes"
              MAX-ACCESS read-only
              STATUS current
              DESCRIPTION
              "The maximum burst size in bytes."
              ::= { zxr10MplsTunnelResourceEntry 4 }

              zxr10MplsTunnelResourceMeanBurstSize OBJECT-TYPE
              SYNTAX Unsigned32
              UNITS "bytes"
              MAX-ACCESS read-only
              STATUS current
              DESCRIPTION
              "The mean burst size in bytes. The implementations
              which do not implement this variable must return
              noSuchObject exception for this object and must
              not allow a user to set this object."
              ::= { zxr10MplsTunnelResourceEntry 5 }

              zxr10MplsTunnelResourceRowStatus OBJECT-TYPE
              SYNTAX RowStatus
              MAX-ACCESS read-only
              STATUS current
              DESCRIPTION
              "This variable is used to create, modify, and/or
              delete a row in this table. When a row in this
              table is in active(1) state, no objects in that row
              can be modified by the agent except
              zxr10MplsTunnelResourceRowStatus and
              zxr10MplsTunnelResourceStorageType."
              ::= { zxr10MplsTunnelResourceEntry 6 }

              zxr10MplsTunnelResourceStorageType OBJECT-TYPE
              SYNTAX StorageType
              MAX-ACCESS read-only
              STATUS current
              DESCRIPTION
              "The storage type for this Hop entry. Conceptual
              rows having the value 'permanent' need not
              allow write-access to any columnar objects
              Srinivasan, et al. Standards Track [Page 38]
              RFC 3812 MPLS-TE-STD-MIB June 2004
              in the row."
              DEFVAL { volatile }
              ::= { zxr10MplsTunnelResourceEntry 7 }
              -- End zxr10MplsTunnelResourceTable


              -- Tunnel Computed Hop table.
              zxr10MplsTunnelCHopTable OBJECT-TYPE
              SYNTAX SEQUENCE OF Zxr10MplsTunnelCHopEntry
              MAX-ACCESS not-accessible
              STATUS current
              DESCRIPTION
              "The zxr10MplsTunnelCHopTable is used to indicate the
              hops, strict or loose, for an MPLS tunnel defined
              in zxr10MplsTunnelTable, as computed by a constraintbased
              routing protocol, based on the
              zxr10MplsTunnelHopTable for the outgoing direction of
              the tunnel. Thus at a transit LSR, this table (if
              the table is supported) MAY contain the path
              computed by the CSPF engine on (or on behalf of)
              this LSR. Each row in this table is indexed by
              zxr10MplsTunnelCHopListIndex. Each row also has a
              secondary index zxr10MplsTunnelCHopIndex, corresponding
              to the next hop that this row corresponds to. In
              case we want to specify a particular interface on
              the originating LSR of an outgoing tunnel by which
              we want packets to exit the LSR, we specify this as
              the first hop for this tunnel in
              zxr10MplsTunnelCHopTable.
              lease note that since the information necessary to
              build entries within this table may not be
              supported by some LSRs, implementation of this
              table is optional. Furthermore, since the
              information in this table describes the path
              computed by the CSPF engine the entries in this
              table are read-only."
              ::= { zxr10MplsTeCHopObjects 1 }

              zxr10MplsTunnelCHopEntry OBJECT-TYPE
              SYNTAX Zxr10MplsTunnelCHopEntry
              MAX-ACCESS not-accessible
              STATUS current
              DESCRIPTION
              "An entry in this table represents a tunnel hop. An
              entry in this table is created by a path
              computation engine using CSPF techniques applied to
              he information collected by routing protocols and
              the hops specified in the corresponding
              zxr10MplsTunnelHopTable."
              INDEX { zxr10MplsTunnelCHopListIndex, zxr10MplsTunnelCHopIndex }
              ::= { zxr10MplsTunnelCHopTable 1 }

              Zxr10MplsTunnelCHopEntry ::= SEQUENCE {
                          zxr10MplsTunnelCHopListIndex Unsigned32,
                          zxr10MplsTunnelCHopIndex Unsigned32,
                          zxr10MplsTunnelCHopAddrType INTEGER,
                          zxr10MplsTunnelCHopIpAddr IpAddress,
                          zxr10MplsTunnelCHopIpPrefixLen Unsigned32,
                          zxr10MplsTunnelCHopAsNumber Unsigned32,
                          zxr10MplsTunnelCHopAddrUnnum Unsigned32,
                          zxr10MplsTunnelCHopLspId Unsigned32,
                          zxr10MplsTunnelCHopType INTEGER
                          }

              zxr10MplsTunnelCHopListIndex OBJECT-TYPE
              SYNTAX Unsigned32
              MAX-ACCESS read-only
              STATUS current
              DESCRIPTION
              "Primary index into this table identifying a
              particular computed hop list."
              ::= { zxr10MplsTunnelCHopEntry 1 }

              zxr10MplsTunnelCHopIndex OBJECT-TYPE
              SYNTAX Unsigned32
              MAX-ACCESS read-only
              STATUS current
              DESCRIPTION
              "Secondary index into this table identifying the
              particular hop."
              ::= { zxr10MplsTunnelCHopEntry 2 }

              zxr10MplsTunnelCHopAddrType OBJECT-TYPE
              SYNTAX     INTEGER {
                        unknown(0),
                        ipv4(1),
                        ipv6(2),
                        asnumber(3),
                        unnum(4),
                        lspid(5)
                     }
              MAX-ACCESS read-only
              STATUS current
              DESCRIPTION
              "The Hop Address Type of this tunnel hop.
              Note that lspid(5) is a valid option only
              for tunnels signaled via CRLDP."
              DEFVAL { ipv4 }
              ::= { zxr10MplsTunnelCHopEntry 3 }

              zxr10MplsTunnelCHopIpAddr OBJECT-TYPE
              SYNTAX IpAddress
              MAX-ACCESS read-only
              STATUS current
              DESCRIPTION
                "The Tunnel Hop Address for this tunnel hop.
                 The type of this address is determined by the
                value of the corresponding zxr10MplsTunnelCHopAddrType.
                If zxr10MplsTunnelCHopAddrType is set to unnum(4), then
                this value will contain the LSR Router ID of the
                unnumbered interface. Otherwise the agent should
                set this object to the zero-length string and the
                manager SHOULD ignore this object."
              DEFVAL { '00000000'h } -- IPv4 address 0.0.0.0
              ::= { zxr10MplsTunnelCHopEntry 4 }

              zxr10MplsTunnelCHopIpPrefixLen OBJECT-TYPE
              SYNTAX Unsigned32(0..2040)
              MAX-ACCESS read-only
              STATUS current
              DESCRIPTION
              "If zxr10MplsTunnelCHopAddrType is set to ipv4(1) or
              ipv6(2), then this value will contain an
              appropriate prefix length for the IP address in
              object zxr10MplsTunnelCHopIpAddr. Otherwise this value
              is irrelevant and should be ignored.
              "
              DEFVAL { 32 }
              ::= { zxr10MplsTunnelCHopEntry 5 }

              zxr10MplsTunnelCHopAsNumber OBJECT-TYPE
              SYNTAX Unsigned32
              MAX-ACCESS read-only
              STATUS current
              DESCRIPTION
              "If zxr10MplsTunnelCHopAddrType is set to asnumber(3),
              then this value will contain the AS number of this
              hop. Otherwise the agent should set this object to
              zero-length string and the manager should ignore
              this."
              ::= { zxr10MplsTunnelCHopEntry 6 }

              zxr10MplsTunnelCHopAddrUnnum OBJECT-TYPE
              SYNTAX Unsigned32
              MAX-ACCESS read-only
              STATUS current
              DESCRIPTION
              "If zxr10MplsTunnelCHopAddrType is set to unnum(4), then
              this value will contain the unnumbered interface
              identifier of this hop. This object should be used
              in conjunction with zxr10MplsTunnelCHopIpAddr which
              would contain the LSR Router ID in this case.
              Otherwise the agent should set this object to zerolength
              string and the manager should ignore this."
              ::= { zxr10MplsTunnelCHopEntry 7 }

              zxr10MplsTunnelCHopLspId OBJECT-TYPE
              SYNTAX Unsigned32
              MAX-ACCESS read-only
              STATUS current
              DESCRIPTION
              "If zxr10MplsTunnelCHopAddrType is set to lspid(5), then
              his value will contain the LSP ID of this hop.
              his object is otherwise insignificant and should
              contain a value of 0 to indicate this fact."
              ::= { zxr10MplsTunnelCHopEntry 8 }

              zxr10MplsTunnelCHopType OBJECT-TYPE
              SYNTAX INTEGER { strict(1),
                                loose(2)
                             }
              MAX-ACCESS read-only
              STATUS current
              DESCRIPTION
              "Denotes whether this is tunnel hop is routed in a
              strict or loose fashion."
              ::= { zxr10MplsTunnelCHopEntry 9 }
              -- End of zxr10MplsTunnelCHopTable


              -- Tunnel Actual Route Hop table.
              zxr10MplsTunnelARHopTable OBJECT-TYPE
              SYNTAX SEQUENCE OF Zxr10MplsTunnelARHopEntry
              MAX-ACCESS not-accessible
              STATUS current
              DESCRIPTION
              "The zxr10MplsTunnelARHopTable is used to indicate the
              hops for an MPLS tunnel defined in zxr10MplsTunnelTable,
              as reported by the MPLS signalling protocol. Thus at
              a transit LSR, this table (if the table is supported
              and if the signaling protocol is recording actual
              route information) contains the actual route of the
              whole tunnel. If the signaling protocol is not
              recording the actual route, this table MAY report
              the information from the zxr10MplsTunnelHopTable or the
              zxr10MplsTunnelCHopTable.
              Each row in this table is indexed by
              zxr10MplsTunnelARHopListIndex. Each row also has a
              secondary index zxr10MplsTunnelARHopIndex, corresponding
              to the next hop that this row corresponds to.
              Please note that since the information necessary to
              build entries within this table is not provided by
              some MPLS signalling protocols, implementation of
              this table is optional. Furthermore, since the
              information in this table is actually provided by
              the MPLS signalling protocol after the path has
              been set-up, the entries in this table are provided
              only for observation, and hence, all variables in
              this table are accessible exclusively as readonly.
              Note also that the contents of this table may change
              while it is being read because of re-routing
              activities. A network administrator may verify that
              the actual route read is consistent by reference to
              the zxr10MplsTunnelLastPathChange object."
              ::= { zxr10MplsTeARHopObjects 1 }

              zxr10MplsTunnelARHopEntry OBJECT-TYPE
              SYNTAX Zxr10MplsTunnelARHopEntry
              MAX-ACCESS not-accessible
              STATUS current
              DESCRIPTION
              "An entry in this table represents a tunnel hop. An
              entry is created by the agent for signaled ERLSP
              set up by an MPLS signalling protocol."
              INDEX { zxr10MplsTunnelARHopListIndex, zxr10MplsTunnelARHopIndex }
              ::= { zxr10MplsTunnelARHopTable 1 }

              Zxr10MplsTunnelARHopEntry ::= SEQUENCE {
                        zxr10MplsTunnelARHopListIndex Unsigned32,
                        zxr10MplsTunnelARHopIndex Unsigned32,
                        zxr10MplsTunnelARHopAddrType INTEGER,
                        zxr10MplsTunnelARHopIpAddr IpAddress,
                        zxr10MplsTunnelARHopAddrUnnum Unsigned32,
                        zxr10MplsTunnelARHopLspId Unsigned32
                        }

              zxr10MplsTunnelARHopListIndex OBJECT-TYPE
              SYNTAX Unsigned32
              MAX-ACCESS read-only
              STATUS current
              DESCRIPTION
              "Primary index into this table identifying a
              particular recorded hop list."
              ::= { zxr10MplsTunnelARHopEntry 1 }
              zxr10MplsTunnelARHopIndex OBJECT-TYPE
              SYNTAX Unsigned32
              MAX-ACCESS read-only
              STATUS current
              DESCRIPTION
              "Secondary index into this table identifying the
              particular hop."
              ::= { zxr10MplsTunnelARHopEntry 2 }
              zxr10MplsTunnelARHopAddrType OBJECT-TYPE
              SYNTAX     INTEGER {
                        unknown(0),
                        ipv4(1),
                        ipv6(2),
                        asnumber(3),
                        unnum(4),
                        lspid(5)
                     }
              MAX-ACCESS read-only
              STATUS current
              DESCRIPTION
              "The Hop Address Type of this tunnel hop.
              ote that lspid(5) is a valid option only
              for tunnels signaled via CRLDP."
              DEFVAL { ipv4 }
              ::= { zxr10MplsTunnelARHopEntry 3 }

              zxr10MplsTunnelARHopIpAddr OBJECT-TYPE
              SYNTAX IpAddress
              MAX-ACCESS read-only
              STATUS current
              DESCRIPTION
              "The Tunnel Hop Address for this tunnel hop.
              The type of this address is determined by the
              value of the corresponding zxr10MplsTunnelARHopAddrType.
              If zxr10MplsTunnelARHopAddrType is set to unnum(4),
              then this value contains the LSR Router ID of the
              unnumbered interface. Otherwise the agent SHOULD
              set this object to the zero-length string and the
              manager should ignore this object."
              DEFVAL { '00000000'h } -- IPv4 address 0.0.0.0
              ::= { zxr10MplsTunnelARHopEntry 4 }

              zxr10MplsTunnelARHopAddrUnnum OBJECT-TYPE
              SYNTAX Unsigned32
              MAX-ACCESS read-only
              STATUS current
              DESCRIPTION
              "If zxr10MplsTunnelARHopAddrType is set to unnum(4), then
              this value will contain the interface identifier of
              the unnumbered interface for this hop. This object
              should be used in conjunction with
              zxr10MplsTunnelARHopIpAddr which would contain the LSR
              Router ID in this case. Otherwise the agent should
              set this object to zero-length string and the
              manager should ignore this."
              ::= { zxr10MplsTunnelARHopEntry 5 }

              zxr10MplsTunnelARHopLspId OBJECT-TYPE
              SYNTAX Unsigned32(0..65535)
              MAX-ACCESS read-only
              STATUS current
              DESCRIPTION
              "If zxr10MplsTunnelARHopAddrType is set to lspid(5), then
              this value will contain the LSP ID of this hop.
              This object is otherwise insignificant and should
              contain a value of 0 to indicate this fact."
              ::= { zxr10MplsTunnelARHopEntry 6 }
              -- End of zxr10MplsTunnelARHopTable

      -- MPLS TE Interface table.
        zxr10MplsInterfaceTable OBJECT-TYPE
            SYNTAX SEQUENCE OF Zxr10MplsInterfaceEntry
            MAX-ACCESS not-accessible
            STATUS obsolete
            DESCRIPTION
                "A list of mpls traffic-eng interface entries."
            ::= { zxr10MplsTeInterfaceObjects 1 }

        zxr10MplsInterfaceEntry OBJECT-TYPE
            SYNTAX Zxr10MplsInterfaceEntry
            MAX-ACCESS not-accessible
            STATUS obsolete
            DESCRIPTION
                "An entry containing mpls traffic-eng interface."
            INDEX { zxr10MplsInterfaceIndex }
            ::= { zxr10MplsInterfaceTable 1 }


            Zxr10MplsInterfaceEntry ::= SEQUENCE {
                            zxr10MplsInterfaceIndex Unsigned32,
                            zxr10MplsInterfaceName DisplayString,
                            zxr10MplsInterfaceIpAddr IpAddress,
                            zxr10MplsInterfaceMask IpAddress,
                            zxr10MplsInterfaceBfdEnable INTEGER,
                            zxr10MplsInterfaceAuthEnable INTEGER,
                            zxr10MplsInterfaceAuthChallengeEnable INTEGER,
                            zxr10MplsInterfaceAuthChallengeImpEnable INTEGER,
                            zxr10MplsInterfaceAuthLifeTime Unsigned32,
                            zxr10MplsInterfaceAuthKey DisplayString,
                            zxr10MplsInterfaceAuthType INTEGER,
                            zxr10MplsInterfaceAuthWinSize Integer32,
                            zxr10MplsInterfaceTotalBandwidth Unsigned32,
                            zxr10MplsInterfaceAvailableBandwidth Unsigned32,
                zxr10MplsInterfaceMetric    DisplayString,
                zxr10MplsInterfaceAutobakTunnelEnable    INTEGER,
                zxr10MplsInterfaceAutobakTunnelNhoponly  INTEGER,
                zxr10MplsInterfaceSrlgs   DisplayString,
                zxr10MplsInterfaceAttributeFlags  INTEGER
                           }

         zxr10MplsInterfaceIndex OBJECT-TYPE
            SYNTAX Unsigned32
            MAX-ACCESS read-only
            STATUS obsolete
            DESCRIPTION
                "A unique value, greater than zero, for each interface whitch enables mpls traffic-eng."
            ::= { zxr10MplsInterfaceEntry 1 }

         zxr10MplsInterfaceName OBJECT-TYPE
            SYNTAX DisplayString
            MAX-ACCESS read-only
            STATUS obsolete
            DESCRIPTION
                "The name of this interface."
            ::= { zxr10MplsInterfaceEntry 2 }

         zxr10MplsInterfaceIpAddr OBJECT-TYPE
            SYNTAX IpAddress
            MAX-ACCESS read-only
            STATUS obsolete
            DESCRIPTION
                "The ip address of this interface."
            ::= { zxr10MplsInterfaceEntry 3 }

         zxr10MplsInterfaceMask OBJECT-TYPE
            SYNTAX IpAddress
            MAX-ACCESS read-only
            STATUS obsolete
            DESCRIPTION
                "The subnet mask of this interface."
            ::= { zxr10MplsInterfaceEntry 4 }

         zxr10MplsInterfaceBfdEnable OBJECT-TYPE
            SYNTAX INTEGER { false(0), true(1) }
            MAX-ACCESS read-only
            STATUS obsolete
            DESCRIPTION
                "If this interface enables bfd,this value is true,otherwise it is false."
            ::= { zxr10MplsInterfaceEntry 5 }

         zxr10MplsInterfaceAuthEnable OBJECT-TYPE
            SYNTAX INTEGER { false(0), true(1) }
            MAX-ACCESS read-only
            STATUS obsolete
            DESCRIPTION
                "If this interface enables RSVP cryptographic authentication, this value is true,otherwise it is false."
            ::= { zxr10MplsInterfaceEntry 6 }

         zxr10MplsInterfaceAuthChallengeEnable OBJECT-TYPE
            SYNTAX INTEGER { false(0), true(1) }
            MAX-ACCESS read-only
            STATUS obsolete
            DESCRIPTION
                "If this interface as a receiver enables rsvp authentication challenge,this value is true,otherwise it is false."
            ::= { zxr10MplsInterfaceEntry 7 }

         zxr10MplsInterfaceAuthChallengeImpEnable OBJECT-TYPE
            SYNTAX INTEGER { false(0), true(1) }
            MAX-ACCESS read-only
            STATUS obsolete
            DESCRIPTION
                "If this interface as a sender enables rsvp authentication challenge,this value is true,otherwise it is false."
            ::= { zxr10MplsInterfaceEntry 8 }

         zxr10MplsInterfaceAuthLifeTime OBJECT-TYPE
            SYNTAX Unsigned32
            MAX-ACCESS read-only
            STATUS obsolete
            DESCRIPTION
                "Specifies maximum lifetime of neighbor authentication state on this interface"
            ::= { zxr10MplsInterfaceEntry 9 }

         zxr10MplsInterfaceAuthKey OBJECT-TYPE
            SYNTAX DisplayString
            MAX-ACCESS read-only
            STATUS obsolete
            DESCRIPTION
                "Specifies shared secret for all neighbors on this interface."
            ::= { zxr10MplsInterfaceEntry 10 }

         zxr10MplsInterfaceAuthType OBJECT-TYPE
            SYNTAX INTEGER { md5(1),sha1(2) }
            MAX-ACCESS read-only
            STATUS obsolete
            DESCRIPTION
                "Specifies the type of authentication algorithm on this interface."
            ::= { zxr10MplsInterfaceEntry 11 }

         zxr10MplsInterfaceAuthWinSize OBJECT-TYPE
            SYNTAX Integer32
            MAX-ACCESS read-only
            STATUS obsolete
            DESCRIPTION
                "Specifies received window size for authenticated messages on this interface."
            ::= { zxr10MplsInterfaceEntry 12 }

         zxr10MplsInterfaceTotalBandwidth OBJECT-TYPE
            SYNTAX Unsigned32
            MAX-ACCESS read-only
            STATUS obsolete
            DESCRIPTION
                "Specifies reservable total bandwidth on this interface."
            ::= { zxr10MplsInterfaceEntry 13 }

         zxr10MplsInterfaceAvailableBandwidth OBJECT-TYPE
            SYNTAX Unsigned32
            MAX-ACCESS read-only
            STATUS obsolete
            DESCRIPTION
                "Specifies available bandwidth on this interface."
            ::= { zxr10MplsInterfaceEntry 14 }

             zxr10MplsInterfaceMetric OBJECT-TYPE
            SYNTAX DisplayString
            MAX-ACCESS read-only
            STATUS obsolete
            DESCRIPTION
                "The config metric of mpls te interface."
            ::= { zxr10MplsInterfaceEntry 15 }

             zxr10MplsInterfaceAutobakTunnelEnable OBJECT-TYPE
            SYNTAX INTEGER { false(0), true(1) }
            MAX-ACCESS read-only
            STATUS obsolete
            DESCRIPTION
                "If this object is true, then it prefers NODE_PROTECT to LINK_PROTECT by autobackup tunnel."
            ::= { zxr10MplsInterfaceEntry 16 }

             zxr10MplsInterfaceAutobakTunnelNhoponly OBJECT-TYPE
            SYNTAX INTEGER { false(0), true(1) }
            MAX-ACCESS read-only
            STATUS obsolete
            DESCRIPTION
                "If this object is true, then it only requires LINK_PROTECT by autobackup tunnel."
            ::= { zxr10MplsInterfaceEntry 17 }

             zxr10MplsInterfaceSrlgs OBJECT-TYPE
            SYNTAX DisplayString
            MAX-ACCESS read-only
            STATUS obsolete
            DESCRIPTION
                "Specifies srlgs on this interface."
            ::= { zxr10MplsInterfaceEntry 18 }

             zxr10MplsInterfaceAttributeFlags OBJECT-TYPE
            SYNTAX INTEGER { false(0), true(1) }
            MAX-ACCESS read-only
            STATUS obsolete
            DESCRIPTION
                "Specifies attribute flags on this interface."
            ::= { zxr10MplsInterfaceEntry 19 }
       -- end mpls interface Table

       ---MPLS explicit path Table
        zxr10MplsIpExplicitTable OBJECT-TYPE
            SYNTAX SEQUENCE OF Zxr10MplsIpExplicitEntry
            MAX-ACCESS not-accessible
            STATUS obsolete
            DESCRIPTION
                "Explicit-path table is user configured,the user should specify the
                entire path for the tunnel to take. This path may contain strict or
                loose hops. Each hop along a specific path SHOULD have this object
                set to the same value"
            ::= { zxr10MplsIpExplicitObjects 1 }

        zxr10MplsIpExplicitEntry OBJECT-TYPE
            SYNTAX Zxr10MplsIpExplicitEntry
            MAX-ACCESS not-accessible
            STATUS obsolete
            DESCRIPTION
                "Explicit-path table entry."
            INDEX { zxr10MplsIpExplicitNameType, zxr10MplsIpExplicitName }
            ::= { zxr10MplsIpExplicitTable 1 }


        Zxr10MplsIpExplicitEntry ::= SEQUENCE {
                            zxr10MplsIpExplicitNameType INTEGER,
                            zxr10MplsIpExplicitName DisplayString,
                            zxr10MplsIpExplicitType DisplayString,
                            zxr10MplsIpExplicitNextIpAddr DisplayString,
                            zxr10MplsIpExplicitIndex  DisplayString
                            }

         zxr10MplsIpExplicitNameType OBJECT-TYPE
            SYNTAX INTEGER {
                         explicitId(2),
                         explicitName(3)
                         }
            MAX-ACCESS read-only
            STATUS obsolete
            DESCRIPTION
                "First index of Explicit-path table."
            ::= { zxr10MplsIpExplicitEntry 1 }

         zxr10MplsIpExplicitName OBJECT-TYPE
            SYNTAX DisplayString
            MAX-ACCESS read-only
            STATUS obsolete
            DESCRIPTION
                "Secondary index of Explicit-path table.If the explicit name type is
                explicitId then this value is a number, or it is a string."
            ::= { zxr10MplsIpExplicitEntry 2 }

         zxr10MplsIpExplicitType OBJECT-TYPE
            SYNTAX DisplayString
            MAX-ACCESS read-only
            STATUS obsolete
            DESCRIPTION
                "router type string list 1:strict  2:loose  3:exclude intf  4:exclude router-id eg. 1.4.3.2"
            ::= { zxr10MplsIpExplicitEntry 3 }

         zxr10MplsIpExplicitNextIpAddr OBJECT-TYPE
            SYNTAX DisplayString
            MAX-ACCESS read-only
            STATUS obsolete
            DESCRIPTION
                "Identify the next hop IP address,This field is a displayable string in the
             format of 'XXX.XXX.XXX.XXX,'repeated.Example:1.1.1.1,1.1.1.2,... ..."
            ::= { zxr10MplsIpExplicitEntry 4 }

         zxr10MplsIpExplicitIndex OBJECT-TYPE
            SYNTAX DisplayString
            MAX-ACCESS read-only
            STATUS obsolete
            DESCRIPTION
                "ip addr index,This field is a displayable string in the format of '1,2,...'."
            ::= { zxr10MplsIpExplicitEntry 5 }

      -- end mpls IP explicit Table

       ---mpls path option Table
        zxr10MplsPathOptTable OBJECT-TYPE
            SYNTAX SEQUENCE OF Zxr10MplsPathOptEntry
            MAX-ACCESS not-accessible
            STATUS obsolete
            DESCRIPTION
                "Path option Table."
            ::= { zxr10MplsPathOptObjects 1 }

        zxr10MplsPathOptEntry OBJECT-TYPE
            SYNTAX Zxr10MplsPathOptEntry
            MAX-ACCESS not-accessible
            STATUS obsolete
            DESCRIPTION
                "Path option Table entry. "
            INDEX { zxr10MplsPathOptIndex,
                   zxr10MplsPathOptValue
                  }
            ::= { zxr10MplsPathOptTable 1 }


        Zxr10MplsPathOptEntry ::= SEQUENCE {
                            zxr10MplsPathOptIndex Unsigned32,
                            zxr10MplsPathOptValue Unsigned32,
                            zxr10MplsPathOptType  INTEGER,
                            zxr10MplsPathOptName DisplayString,
                            zxr10MplsPathOptHotStandbyType INTEGER,
                            zxr10MplsPathOptHotStandbyBackupPathName DisplayString
                            }

         zxr10MplsPathOptIndex OBJECT-TYPE
            SYNTAX Unsigned32 (0..65535)
            MAX-ACCESS read-only
            STATUS obsolete
            DESCRIPTION
                "The index of path option whitch equals to tunnel index."
            ::= { zxr10MplsPathOptEntry 1 }

        zxr10MplsPathOptValue OBJECT-TYPE
            SYNTAX Unsigned32(0..16)
            MAX-ACCESS read-only
            STATUS obsolete
            DESCRIPTION
                "Secondary index whitch identifies the configure value of path option ."
            ::= { zxr10MplsPathOptEntry 2 }

         zxr10MplsPathOptType OBJECT-TYPE
            SYNTAX INTEGER {
                         dynamic(1),
                         explicitId(2),
                         explicitName(3)
                         }
            MAX-ACCESS read-only
            STATUS obsolete
            DESCRIPTION
                "If this value is dynamic ,indicates that user only specify the source and destination of
              the path and the CSPF will calculate the remainder of the path. If this value is
              explicitId or explicitName, the user specify the entire path for the tunnel . This path may contain
              strict or loose hops. Each hop along a specific path SHOULD have this object set to the same value."
            ::= { zxr10MplsPathOptEntry 3 }

         zxr10MplsPathOptName OBJECT-TYPE
            SYNTAX DisplayString
            MAX-ACCESS read-only
            STATUS obsolete
            DESCRIPTION
                "This value identifier the name of the path-option,when the type of the path-option is explicitName,the other times the value is null."
            ::= { zxr10MplsPathOptEntry 4 }

         zxr10MplsPathOptHotStandbyType OBJECT-TYPE
            SYNTAX INTEGER {
                         none(0),
                         dynamic(1),
                         explicitId(2),
                         explicitName(3),
                         dynamic_prefer(4)
                         }
            MAX-ACCESS read-only
            STATUS obsolete
            DESCRIPTION
                "Specifies the hotstandby protect type of the path_option."
            ::= { zxr10MplsPathOptEntry 5 }

         zxr10MplsPathOptHotStandbyBackupPathName OBJECT-TYPE
            SYNTAX DisplayString
            MAX-ACCESS read-only
            STATUS obsolete
            DESCRIPTION
                "The name of Backup path.If the type of hotstandby protection is dynamic,then this value is '1';
                if the type is dynamic prefer,then this value is '2';
                if the type is explicitId or explicitName,then this value is a number or a string."
            ::= { zxr10MplsPathOptEntry 6 }

      -- end mpls path option Objects

      -- add admin group
        zxr10MplsAdminGroupListTable OBJECT-TYPE
            SYNTAX SEQUENCE OF Zxr10MplsAdminGroupListEntry
            MAX-ACCESS not-accessible
            STATUS obsolete
            DESCRIPTION
                "List of configured administrative groups.
         Administrative groups are used to label links in
         the Traffic Engineering topology in order to place
         constraints (include and exclude) on LSP paths."
            ::= { zxr10MplsAdminGroupListObjects 1 }

        zxr10MplsAdminGroupListEntry OBJECT-TYPE
            SYNTAX Zxr10MplsAdminGroupListEntry
            MAX-ACCESS not-accessible
            STATUS obsolete
            DESCRIPTION
                "A mapping between a configured group number and its
         human-readable name.  The group number should be
         between 0 and 31, inclusive."
            INDEX { zxr10MplsAdminGroupNumber   }
            ::= { zxr10MplsAdminGroupListTable 1 }


        Zxr10MplsAdminGroupListEntry ::=
            SEQUENCE {
                zxr10MplsAdminGroupNumber    Unsigned32,
                zxr10MplsAdminGroupName      DisplayString
            }

        zxr10MplsAdminGroupNumber OBJECT-TYPE
            SYNTAX     Unsigned32
            MAX-ACCESS read-only
            STATUS     obsolete
            DESCRIPTION
               "Index of the administrative group."
            ::= { zxr10MplsAdminGroupListEntry 1 }

        zxr10MplsAdminGroupName OBJECT-TYPE
            SYNTAX     DisplayString
            MAX-ACCESS read-only
            STATUS     obsolete
            DESCRIPTION
               "Name of the administrative group."
            ::= { zxr10MplsAdminGroupListEntry 2 }

      -- end add


        zxr10MplsHotStandbyLspTable  OBJECT-TYPE
            SYNTAX SEQUENCE OF   Zxr10MplsHotStandbyLspEntry
            MAX-ACCESS not-accessible
            STATUS current
            DESCRIPTION
                    ""
            ::= { zxr10MplsHotStandbyLspObjects 1 }

        zxr10MplsHotStandbyLspEntry OBJECT-TYPE
            SYNTAX Zxr10MplsHotStandbyLspEntry
            MAX-ACCESS not-accessible
            STATUS current
            DESCRIPTION
                  ""
            INDEX { zxr10MplsHotTunnelIndex,
                   zxr10MplsTunnelInstance
                  }
            ::= { zxr10MplsHotStandbyLspTable 1 }


        Zxr10MplsHotStandbyLspEntry ::=
     SEQUENCE {
         zxr10MplsHotTunnelIndex Unsigned32,
         zxr10MplsHotTunnelInstance Unsigned32,
         zxr10MplsHotTunnelIngressLSRId IpAddress,
         zxr10MplsHotTunnelEgressLSRId IpAddress,
         zxr10MplsHotTunnelOutLabel  Unsigned32,
         zxr10MplsHotTunnelOutIntf  DisplayString,
         zxr10MplsHotTunnelRole INTEGER,
         zxr10MplsHotTunnelSessionAttributes DisplayString,
         zxr10MplsHotTunnelResourcePointer Unsigned32,
         zxr10MplsHotTunnelInstancePriority Unsigned32,
         zxr10MplsHotTunnelHopTableIndex Unsigned32,
         zxr10MplsHotTunnelPathInUse Integer32,
         zxr10MplsHotTunnelARHopTableIndex Unsigned32,
         zxr10MplsHotTunnelCHopTableIndex Unsigned32,
         zxr10MplsHotTunnelInstanceUpTime TimeTicks,
         zxr10MplsHotTunnelOperStatus  INTEGER,
         zxr10MplsHotTunnelRowStatus  RowStatus
             }

         zxr10MplsHotTunnelIndex  OBJECT-TYPE
            SYNTAX Unsigned32
            MAX-ACCESS read-only
            STATUS current
            DESCRIPTION
            "Uniquely identifies a set of tunnel instances
            between a pair of ingress and egress LSRs.
            Managers should obtain new values for row
            creation in this table by reading
            zxr10MplsTunnelIndexNext. When
            the MPLS signalling protocol is rsvp(2) this value
            SHOULD be equal to the value signaled in the
            Tunnel Id of the Session object. When the MPLS
            signalling protocol is crldp(3) this value
            SHOULD be equal to the value signaled in the
            LSP ID."
            ::= { zxr10MplsHotStandbyLspEntry 1 }

         zxr10MplsHotTunnelInstance  OBJECT-TYPE
            SYNTAX Unsigned32
            MAX-ACCESS read-only
            STATUS current
            DESCRIPTION
                "Uniquely identifies a particular instance of a
                tunnel between a pair of ingress and egress LSRs.
                It is useful to identify multiple instances of
                tunnels for the purposes of backup and parallel
                tunnels. When the MPLS signaling protocol is
                rsvp(2) this value SHOULD be equal to the LSP Id
                of the Sender Template object. When the signaling
                protocol is crldp(3) there is no equivalent
                signaling object."
            ::= { zxr10MplsHotStandbyLspEntry 2 }

        zxr10MplsHotTunnelIngressLSRId   OBJECT-TYPE
            SYNTAX IpAddress
            MAX-ACCESS read-only
            STATUS current
            DESCRIPTION
            "Identity of the ingress LSR associated with this
            tunnel instance. When the MPLS signalling protocol
            is rsvp(2) this value SHOULD be equal to the Tunnel
            Sender Address in the Sender Template object and MAY
            be equal to the Extended Tunnel Id field in the
            SESSION object. When the MPLS signalling protocol is
            rldp(3) this value SHOULD be equal to the Ingress
            LSR Router ID field in the LSPID TLV object."
            ::= { zxr10MplsHotStandbyLspEntry 3 }

         zxr10MplsHotTunnelEgressLSRId  OBJECT-TYPE
            SYNTAX IpAddress
            MAX-ACCESS read-only
            STATUS current
            DESCRIPTION
                "Identity of the egress LSR associated with this
                tunnel instance."
            ::= { zxr10MplsHotStandbyLspEntry 4 }

         zxr10MplsHotTunnelOutLabel  OBJECT-TYPE
            SYNTAX Unsigned32
            MAX-ACCESS read-only
            STATUS current
            DESCRIPTION
                "Out label of hotstandby tunnel."
            ::= { zxr10MplsHotStandbyLspEntry 5 }

         zxr10MplsHotTunnelOutIntf   OBJECT-TYPE
            SYNTAX DisplayString
            MAX-ACCESS read-only
            STATUS current
            DESCRIPTION
                "The name of out interface that hotstandby tunnel transits."
            ::= { zxr10MplsHotStandbyLspEntry 6 }

         zxr10MplsHotTunnelRole        OBJECT-TYPE
            SYNTAX INTEGER{ head(1), transit(2), tail(3), headTail(4) }
            MAX-ACCESS read-only
            STATUS current
            DESCRIPTION
            "This value signifies the role that this tunnel
             entry/instance represents. This value MUST be set
             to head(1) at the originating point of the tunnel.
             This value MUST be set to transit(2) at transit
             points along the tunnel, if transit points are
             supported. This value MUST be set to tail(3) at the
             terminating point of the tunnel if tunnel tails are
             supported.
             The value headTail(4) is provided for tunnels that
             begin and end on the same LSR."
            ::= { zxr10MplsHotStandbyLspEntry 7 }

         zxr10MplsHotTunnelSessionAttributes        OBJECT-TYPE
            SYNTAX DisplayString
            MAX-ACCESS read-only
            STATUS current
            DESCRIPTION
            "This bit mask indicates optional session values for
             this tunnel. "

            ::= { zxr10MplsHotStandbyLspEntry 8 }

         zxr10MplsHotTunnelResourcePointer        OBJECT-TYPE
            SYNTAX Unsigned32
            MAX-ACCESS read-only
            STATUS current
            DESCRIPTION
            "This variable represents a pointer to the traffic
             parameter specification for this tunnel. This
             value may point at an entry in the
             zxr10MplsTunnelResourceEntry to indicate which
             zxr10MplsTunnelResourceEntry is to be assigned to this
             LSP instance. This value may optionally point at
             an externally defined traffic parameter
             specification table. A value of zeroDotZero
             indicates best-effort treatment. By having the
             same value of this object, two or more LSPs can
             indicate resource sharing."
            ::= { zxr10MplsHotStandbyLspEntry 9 }

         zxr10MplsHotTunnelInstancePriority        OBJECT-TYPE
            SYNTAX Unsigned32
            MAX-ACCESS read-only
            STATUS current
            DESCRIPTION
            "This value indicates which priority, in descending
             order, with 0 indicating the lowest priority,
             within a group of tunnel instances. A group of
             tunnel instances is defined as a set of LSPs with
             the same zxr10MplsTunnelIndex in this table, but with a
             different zxr10MplsTunnelInstance. Tunnel instance
             priorities are used to denote the priority at which
             a particular tunnel instance will supercede
             another. Instances of tunnels containing the same
             zxr10MplsTunnelInstancePriority will be used for load
             sharing."
            ::= { zxr10MplsHotStandbyLspEntry 10 }

         zxr10MplsHotTunnelHopTableIndex         OBJECT-TYPE
            SYNTAX Unsigned32
            MAX-ACCESS read-only
            STATUS current
            DESCRIPTION
            "Index into the zxr10MplsTunnelHopTable entry that
             specifies the explicit route hops for this tunnel.
             This object is meaningful only at the head-end of
             the tunnel."
            ::= { zxr10MplsHotStandbyLspEntry 11 }

         zxr10MplsHotTunnelPathInUse         OBJECT-TYPE
            SYNTAX Integer32
            MAX-ACCESS read-only
            STATUS current
            DESCRIPTION
             "This value denotes the configured path that was
             chosen for this tunnel. This value reflects the
             secondary index into zxr10MplsTunnelHopTable. This path
             may not exactly match the one in
             zxr10MplsTunnelARHopTable due to the fact that some CSPF
             modification may have taken place. See
             zxr10MplsTunnelARHopTable for the actual path being
             taken by the tunnel. A value of zero denotes that
             no path is currently in use or available."
            ::= { zxr10MplsHotStandbyLspEntry 12 }

         zxr10MplsHotTunnelARHopTableIndex          OBJECT-TYPE
            SYNTAX Unsigned32
            MAX-ACCESS read-only
            STATUS current
            DESCRIPTION
            "Index into the zxr10MplsTunnelARHopTable entry that
             specifies the actual hops traversed by the tunnel.
             This is automatically updated by the agent when the
             actual hops becomes available."
            ::= { zxr10MplsHotStandbyLspEntry 13 }

         zxr10MplsHotTunnelCHopTableIndex            OBJECT-TYPE
            SYNTAX Unsigned32
            MAX-ACCESS read-only
            STATUS current
            DESCRIPTION
             "Index into the zxr10MplsTunnelCHopTable entry that
             specifies the computed hops traversed by the
             tunnel. This is automatically updated by the agent
             when computed hops become available or when
             computed hops get modified."
            ::= { zxr10MplsHotStandbyLspEntry 14 }

         zxr10MplsHotTunnelInstanceUpTime              OBJECT-TYPE
            SYNTAX TimeTicks
            MAX-ACCESS read-only
            STATUS current
            DESCRIPTION
             "This value identifies the total time that this
             tunnel instance's operStatus has been Up(1)."
            ::= { zxr10MplsHotStandbyLspEntry 15 }

         zxr10MplsHotTunnelOperStatus              OBJECT-TYPE
            SYNTAX INTEGER
            {
             -- ready to pass packets
                         up(1),
                         down(2)
            }
            MAX-ACCESS read-only
            STATUS current
            DESCRIPTION
            "Indicates the actual operational status of this
             tunnel, which is typically but not limited to, a
             function of the state of individual segments of
             this tunnel."
            ::= { zxr10MplsHotStandbyLspEntry 16 }

         zxr10MplsHotTunnelRowStatus               OBJECT-TYPE
            SYNTAX RowStatus
            MAX-ACCESS read-only
            STATUS current
            DESCRIPTION
             "This variable is used to create, modify, and/or
             delete a row in this table. When a row in this
             table is in active(1) state, no objects in that row
             can be modified by the agent except
             zxr10MplsTunnelAdminStatus, zxr10MplsTunnelRowStatus and
             zxr10MplsTunnelStorageType."
            ::= { zxr10MplsHotStandbyLspEntry 17 }

           ---end mpls HotStandby Lsp Objects


      --trap

       zxr10MplsTunnelUp NOTIFICATION-TYPE
             OBJECTS     {
                zxr10MplsTunnelOperStatus
             }
             STATUS      current
             DESCRIPTION
                  "This notification is generated when a
             zxr10MplsTunnelOperStatus object for one of the
             configured tunnels is about to leave the down state
             and transition into up state."
             ::= { zxr10MplsTeNotifications 1 }

       zxr10MplsTunnelDown NOTIFICATION-TYPE
             OBJECTS     {
                zxr10MplsTunnelOperStatus
             }
             STATUS      current
             DESCRIPTION
                  "This notification is generated when a
             zxr10MplsTunnelOperStatus object for one of the
             configured tunnels is about to leave the up state
             and transition into down state."
             ::= { zxr10MplsTeNotifications 2 }


       zxr10MplsLspUp NOTIFICATION-TYPE
             OBJECTS     {
                zxr10MplsTunnelOperStatus,
                zxr10MplsRemoteTunnelOperStatus
             }
             STATUS      current
             DESCRIPTION
                  "This notification is generated when a
             zxr10MplsTunnelOperStatus object for one of the
             LSPs is about to leave the down state
             and transition into up state."
             ::= { zxr10MplsTeNotifications 3 }
       zxr10MplsLspDown NOTIFICATION-TYPE
             OBJECTS     {
                zxr10MplsTunnelOperStatus,
                zxr10MplsRemoteTunnelOperStatus
             }
             STATUS      current
             DESCRIPTION
                  "This notification is generated when a
             zxr10MplsTunnelOperStatus object for one of the
             LSPs is about to leave the up state
             and transition into down state."
             ::= { zxr10MplsTeNotifications 4 }

       zxr10MplsLspChange NOTIFICATION-TYPE
             OBJECTS     {
                zxr10MplsTunnelOutLabel,
                zxr10MplsTunnelOutIntf,
                zxr10MplsTunnelOperStatus
             }
             STATUS      current
             DESCRIPTION
                  "This notification is generated when a
             tunnel is MBB."
             ::= { zxr10MplsTeNotifications 5 }


       zxr10MplsTunnelUpcallNetmng NOTIFICATION-TYPE
             OBJECTS     {
                zxr10MplsTunnelOperStatus
             }
             STATUS      current
             DESCRIPTION
                  "This notification is generated when tunnel state changed,
                  for example tunnel hotstandby bind or delete,tunnel creat successs,
                  tunnel config success or fail..."
             ::= { zxr10MplsTeNotifications 6 }
    END
