ZXR10-OSPFV2-MIB DEFINITIONS ::= BEGIN

IMPORTS
        MODULE-IDENTITY, OBJECT-TYPE,
        enterprises, Unsigned32, Counter64, IpAddress
                FROM SNMPv2-SMI
        DisplayString, TruthValue
                FROM SNMPv2-TC;

zxr10ospf MODULE-IDENTITY
        LAST-UPDATED "201904260000Z"
        ORGANIZATION "ZTE Corp."
        CONTACT-INFO
               "ZTE"
        DESCRIPTION
               ""
        REVISION "201904260000Z"
        DESCRIPTION
                "add dyn-leasedline(22)
                 in zxr10ospfRedistributePrococol"
        REVISION "201904190000Z"
        DESCRIPTION
                "Modify the MAX-ACCESS of these nodes from not-accessible to read-only:
                 zxr10ospfv2AreaAreaId1
                 zxr10ospfv2TeAreaAreaIp
                 zxr10AreaIfBfdAreaId
                 zxr10AreaIfBfdAreaIp
                 zxr10AreaNetworkProId
                 zxr10AreaNetworkIpAddr
                 zxr10AreaNetworkIpMask
                 zxr10AreaNetworkAreaId"
        REVISION "201804120000Z"
        DESCRIPTION
                "add zenicLocal(21)
                 in zxr10ospfRedistributePrococol"
        REVISION "201712140000Z"
        DESCRIPTION
                "add natmask(20)
                 in zxr10ospfRedistributePrococol"
        REVISION "201707050000Z"
        DESCRIPTION
                "add zxr10ospfFrrPolicyType,
                     zxr10ospfFrrPolicyName
                 in zxr10ospfEntry"
        REVISION "201704050000Z"
        DESCRIPTION
                "add zxr10AreaIfdampingCostAdjustType,
                     zxr10AreaIfdampingCostIncrease,
                     zxr10AreaIfdampingTime
                 in zxr10AreaIfEntry"
        REVISION "201703280000Z"
        DESCRIPTION
                "add ipsec(19)
                 in zxr10ospfRedistributePrococol"
        REVISION "201703170000Z"
        DESCRIPTION
                "add zxr10ospfv2BgpLsTable"
        REVISION "201702090000Z"
        DESCRIPTION
                "add braspool(18)
                 in zxr10ospfRedistributePrococol"
        REVISION "201607060000Z"
        DESCRIPTION
                "add zxr10areaStubDefaultOrigin
                 in zxr10areaStubEntry"
        REVISION "201601280000Z"
        DESCRIPTION
                "add zxr10areaVirtualAuthenKeychain
                 in Zxr10areaVirtualAuthTypeEntry,
                 add zxr10ospfv2areaAuthenKeychain
                 in Zxr10ospfv2areaAuthenEntry,
                 add zxr10AreaIfAuthKeychain
                 in Zxr10AreaIfAuthTypeEntry"
        REVISION "201512170000Z"
        DESCRIPTION
                "add zxr10ospfBfdCapability,zxr10ospfBfdInterval,
                 zxr10ospfBfdMinRx and zxr10ospfBfdMultiplier
                 in zxr10ospfEntry,
                 add zxr10ospfv2AreaBfdInterval,
                 zxr10ospfv2AreaBfdMinRx and zxr10ospfv2AreaBfdMultiplier
                 in Zxr10ospfv2AreaBfdEntry"
        REVISION "201511080000Z"
        DESCRIPTION
                "modify the SYNTAX of zxr10ospfTtlSecurityAllInterfaces,
                 modify the SYNTAX of zxr10AreaIfTtlSecurity"
        REVISION "201509100000Z"
        DESCRIPTION
                "add the SYNTAX of zxr10ospfv2DynamicRlfaTable,
                add the SYNTAX of zxr10AreaDynamicRlfaTable,
                add the SYNTAX of zxr10ospfv2FrrPriorityTable"
        REVISION "201505210000Z"
        DESCRIPTION
                "add the SYNTAX of zxr10AreaIfSDCost"
        REVISION "201504230000Z"
        DESCRIPTION
                "modify the DESCRIPTION of zxr10areaRangRangNssaFlag,
        modify the STATUS from current to deprecated"
        REVISION "201503040000Z"
        DESCRIPTION
                "The range of zxr10ospfMaxMetricTimeout changed from
                5..86400 into 2|5..86400,
                The range of zxr10ospfv2NeighborCost changed from
                0..65535 into 0..65535|65536,
                The range of zxr10ospfv2NeighborPollInterval changed from
                1..65535 into 0|1..65535,
                The range of zxr10ospfv2FilterPreference changed from
                1..255 into 0|1..255,
                The range of zxr10ospfv2SummaryAddrCostValue changed from
                1..16777214 into 0|1..16777214"
        REVISION "201412050000Z"
        DESCRIPTION
                "add the SYNTAX of zxr10areaVirtualAuthEncrypted,
                add the SYNTAX of zxr10AreaIfAuthEncrypted"
        REVISION "201411100000Z"
        DESCRIPTION
                "add the ENTRY of zxr10AreaIfStaticRlfaTable,
                add the SYNTAX of zxr10AreaIfStaticRlfaProId, 
                zxr10AreaIfStaticRlfaIntfName,
                zxr10AreaIfStaticRlfaAreaId,
                zxr10AreaIfStaticRlfaAreaIp,
                zxr10AreaIfStaticRlfaPrefixList,
                zxr10AreaIfStaticRlfaNextHop"
        REVISION "201410090000Z"
        DESCRIPTION
                "obsolete the ENTRY of zxr10ospfv2InterfaceTable,
                zxr10ospfv2IntfBfdProId,zxr10ospfv2IntfAuthTypeTable,
                zxr10ospfv2IntfMdKeyTable,zxr10ospfv2IntfTypeTable,
                zxr10ospfv2IntfFastRerouteTable
                add the ENTRY of zxr10AreaIfTable,
                zxr10AreaIfBfdTable,zxr10AreaIfAuthTypeTable,
                zxr10AreaIfTypeTable,zxr10AreaIfFrrTable,
                obsolete the ENTRY of zxr10ospfNetworkTable,
                add the ENTRY of zxr10AreaNetworkTable,
                zxr10AreaIfMdKeyTable"
        REVISION "201405260000Z"
        DESCRIPTION
                "obsolete the ENTRY of zxr10ospfv2BfdTable,
                 add the ENTRY of zxr10ospfv2AreaBfdTable"
        REVISION "201404290000Z"
        DESCRIPTION
                "obsolete the ENTRY of zxr10ospfFastFldTable,
                obsolete the SYNTAX of zxr10ospfv2IfFastFlood, 
                zxr10ospfv2IfDisableFastFlood"
        REVISION "201404150000Z"
        DESCRIPTION
                "add zxr10ospfLdpIgpSyn and zxr10ospfLdpAutoConfig
                in zxr10ospfEntry;
                add zxr10ospfInterfaceLdpIgpSync and 
                zxr10ospfInterfaceLdpAutoConfig in Zxr10ospfInterfaceEntry;
                add table zxr10areaLdpIgpSyncTable, 
                zxr10areaLdpAutoConfigTable"
        REVISION "201404090000Z"
        DESCRIPTION
                "obsolete the ENTRY of zxr10ospfPassiveIntfTable,
        zxr10ospfNeighborTable,  zxr10ospfFilterTable, zxr10ospfBfdTable, 
        zxr10ospfSummaryAddrTable, zxr10ospfAreaTable, 
        zxr10ospfTeAreaTable, zxr10areaAuthenTable, zxr10ospfInterfaceTable, 
        zxr10ospfIntfBfdTable, zxr10ospfIntfAuthTypeTable,
        zxr10ospfIntfMdKeyTable, zxr10ospfIntfTypeTable, 
        zxr10ospfIntfFastRerouteTable;
        
        and increase the ENTRY of zxr10ospfPassiveIntfTable,
        zxr10ospfNeighborTable,  zxr10ospfFilterTable, zxr10ospfBfdTable, 
        zxr10ospfSummaryAddrTable, zxr10ospfAreaTable, 
        zxr10ospfTeAreaTable, zxr10areaAuthenTable, zxr10ospfInterfaceTable, 
        zxr10ospfIntfBfdTable, zxr10ospfIntfAuthTypeTable,
        zxr10ospfIntfMdKeyTable, zxr10ospfIntfTypeTable, 
        zxr10ospfIntfFastRerouteTable.

        modify the name of zxr10ospfNotifyDlrouteDelfautRoute,
        zxr10ospfFilterPrefence and zxr10ospfDistributeListGeteway"

        REVISION "201305290000Z"
        DESCRIPTION
                "modify the SYNTAX of zxr10ospfRedistributePrococol 
        from Unsigned32 to INTEGER,
        and add some new protocals(userspecial and slnat64ipv4) 
        for this node;
        modify the SYNTAX of zxr10ospfAreaFilterDirectionIn 
        from Unsigned32 to INTEGER;
        modify the SYNTAX of zxr10areaRangRangSummaryLink 
        from Unsigned32 to INTEGER,
        and add new summary types(summarylink and nssaexternallink)
        for this node;
        modify the SYNTAX of zxr10ospfIntfTypeType1 
        from Unsigned32 to INTEGER,
        and modify the pointtomultipoint type for this node"
        REVISION "201102090000Z"
        DESCRIPTION
                ""
        ::= { zxr10ospfMIBs 1 }

    zte OBJECT IDENTIFIER ::= { enterprises 3902 }

    zxr10 OBJECT IDENTIFIER ::= { zte 3}

    zxr10RosngMIB OBJECT IDENTIFIER ::= { zxr10 6000}

    zxr10ospfMIBs OBJECT IDENTIFIER ::= { zxr10RosngMIB 157}

        
zxr10ospfMIB OBJECT IDENTIFIER ::= { zxr10ospf 1 }

zxr10ospfTable OBJECT-TYPE
        SYNTAX  SEQUENCE OF Zxr10ospfEntry
        MAX-ACCESS  not-accessible
        STATUS  current
        DESCRIPTION
            "An table to ospf instance"
        ::= { zxr10ospfMIB 1 }

zxr10ospfEntry OBJECT-TYPE
        SYNTAX Zxr10ospfEntry
        MAX-ACCESS  not-accessible
        STATUS  current
        DESCRIPTION
            "An entry to ospf instance."
        INDEX  { zxr10ospfProId }
        ::= { zxr10ospfTable 1 }
            
Zxr10ospfEntry ::=
        SEQUENCE {
            zxr10ospfProId
                Unsigned32,
            zxr10ospfVrfName
                DisplayString,
            zxr10ospfTimersSpf
                Unsigned32,
            zxr10ospfTimersLsaGroupPacing
                Unsigned32,
            zxr10ospfTimersFastReroute
                Unsigned32,
            zxr10ospfMaximumPaths
                Unsigned32,
            zxr10ospfGracePeriod
                Unsigned32,
            zxr10ospfDefaultMetric
                Unsigned32,
            zxr10ospfAutoCost
                Unsigned32,
            zxr10ospfDebugFlag
                Unsigned32,
            zxr10ospfCapOpaque
                Unsigned32,
            zxr10ospfCapVrflite
                Unsigned32,
            zxr10ospfRfc1583Value
                Unsigned32,
            zxr10ospfOspfNsf
                Unsigned32,
            zxr10ospfOspfLocalMt
                Unsigned32,
            zxr10ospfTtlSecurityAllInterfaces
                INTEGER,
            zxr10ospfLdpIgpSyn
                Unsigned32,
            zxr10ospfLdpAutoConfig
                Unsigned32,
            zxr10ospfBfdCapability
                Unsigned32,
            zxr10ospfBfdInterval
                Unsigned32,
            zxr10ospfBfdMinRx
                Unsigned32,
            zxr10ospfBfdMultiplier
                Unsigned32,
            zxr10ospfFrrPolicyType
                INTEGER,
            zxr10ospfFrrPolicyName
                DisplayString    
        }

zxr10ospfProId OBJECT-TYPE
        SYNTAX Unsigned32 (1..65535)
        MAX-ACCESS  read-only
        STATUS  current
        DESCRIPTION
            "ospf instance number"
        ::= { zxr10ospfEntry 1 }

zxr10ospfVrfName OBJECT-TYPE
        SYNTAX DisplayString (SIZE (1..32))
        MAX-ACCESS  read-only
        STATUS  current
        DESCRIPTION
            "vrf name"
        ::= { zxr10ospfEntry 2 }


zxr10ospfTimersSpf OBJECT-TYPE
        SYNTAX Unsigned32
        MAX-ACCESS  read-only
        STATUS  current
        DESCRIPTION
            "spf interval"
        ::= { zxr10ospfEntry 5 }

zxr10ospfTimersLsaGroupPacing OBJECT-TYPE
        SYNTAX Unsigned32
        MAX-ACCESS  read-only
        STATUS  current
        DESCRIPTION
            "lsa group pacing time"
        ::= { zxr10ospfEntry 6 }

zxr10ospfTimersFastReroute OBJECT-TYPE
        SYNTAX Unsigned32
        MAX-ACCESS  read-only
        STATUS  current
        DESCRIPTION
            "ipfrr spf interval"
        ::= { zxr10ospfEntry 7 }

zxr10ospfMaximumPaths OBJECT-TYPE
        SYNTAX Unsigned32
        MAX-ACCESS  read-only
        STATUS  current
        DESCRIPTION
            "Maximum number of parallel routes OSPF can support"
        ::= { zxr10ospfEntry 8 }

zxr10ospfGracePeriod OBJECT-TYPE
        SYNTAX Unsigned32
        MAX-ACCESS  read-only
        STATUS  current
        DESCRIPTION
            "grace-period for graceful-restart"
        ::= { zxr10ospfEntry 9 }

zxr10ospfDefaultMetric OBJECT-TYPE
        SYNTAX Unsigned32
        MAX-ACCESS  read-only
        STATUS  current
        DESCRIPTION
            "default metric"
        ::= { zxr10ospfEntry 10 }

zxr10ospfAutoCost OBJECT-TYPE
        SYNTAX Unsigned32
        MAX-ACCESS  read-only
        STATUS  current
        DESCRIPTION
            "ospf interface cost according to bandwidth"
        ::= { zxr10ospfEntry 11 }

zxr10ospfDebugFlag OBJECT-TYPE
        SYNTAX Unsigned32 (0..256)
        MAX-ACCESS  read-only
        STATUS  current
        DESCRIPTION
            "ospf debug flag"
        ::= { zxr10ospfEntry 12 }

zxr10ospfCapOpaque OBJECT-TYPE
        SYNTAX Unsigned32 (0..256)
        MAX-ACCESS  read-only
        STATUS  current
        DESCRIPTION
            "the capability of ospf opaque lsa function"
        ::= { zxr10ospfEntry 13 }

zxr10ospfCapVrflite OBJECT-TYPE
        SYNTAX Unsigned32 (0..256)
        MAX-ACCESS  read-only
        STATUS  current
        DESCRIPTION
            "the capability of ignoring ospf vrf loop-prevention"
        ::= { zxr10ospfEntry 14 }

zxr10ospfRfc1583Value OBJECT-TYPE
        SYNTAX Unsigned32 (0..256)
        MAX-ACCESS  read-only
        STATUS  current
        DESCRIPTION
            "the capability of ospf compatible with rfc1583 when calulating 
         external route"
        ::= { zxr10ospfEntry 15 }

zxr10ospfOspfNsf OBJECT-TYPE
        SYNTAX Unsigned32 (0..256)
        MAX-ACCESS  read-only
        STATUS  current
        DESCRIPTION
            "the capability of Non-stop forwarding"
        ::= { zxr10ospfEntry 16 }

zxr10ospfOspfLocalMt OBJECT-TYPE
        SYNTAX Unsigned32 (0..256)
        MAX-ACCESS  read-only
        STATUS  current
        DESCRIPTION
            "the capability of ospf local_mt"
        ::= { zxr10ospfEntry 17 }

zxr10ospfTtlSecurityAllInterfaces OBJECT-TYPE
        SYNTAX INTEGER (1..254)
        MAX-ACCESS  read-only
        STATUS  current
        DESCRIPTION
            "ttl_security"
        ::= { zxr10ospfEntry 18 }

zxr10ospfLdpIgpSyn OBJECT-TYPE
        SYNTAX Unsigned32 (0..1)
        MAX-ACCESS  read-only
        STATUS  current
        DESCRIPTION
            "ospf ldp igp sync"
        ::= { zxr10ospfEntry 19 }

zxr10ospfLdpAutoConfig OBJECT-TYPE
        SYNTAX Unsigned32 (0..1)
        MAX-ACCESS  read-only
        STATUS  current
        DESCRIPTION
            "ospf ldp auto-config"
        ::= { zxr10ospfEntry 20 }

zxr10ospfBfdCapability OBJECT-TYPE
        SYNTAX Unsigned32 (0..1)
        MAX-ACCESS  read-only
        STATUS  current
        DESCRIPTION
            "ospf BFD capability"
        ::= { zxr10ospfEntry 21 }

zxr10ospfBfdInterval OBJECT-TYPE
        SYNTAX Unsigned32 (10..990)
        MAX-ACCESS  read-only
        STATUS  current
        DESCRIPTION
            "ospf BFD interval"
        ::= { zxr10ospfEntry 22 }

zxr10ospfBfdMinRx OBJECT-TYPE
        SYNTAX Unsigned32 (10..990)
        MAX-ACCESS  read-only
        STATUS  current
        DESCRIPTION
            "ospf BFD min_rx"
        ::= { zxr10ospfEntry 23 }

zxr10ospfBfdMultiplier OBJECT-TYPE
        SYNTAX Unsigned32 (3..50)
        MAX-ACCESS  read-only
        STATUS  current
        DESCRIPTION
            "ospf BFD multiplier"
        ::= { zxr10ospfEntry 24 }
        
zxr10ospfFrrPolicyType OBJECT-TYPE
        SYNTAX INTEGER {rpl(1),noCfg(255)} 
        MAX-ACCESS  read-only
        STATUS  current
        DESCRIPTION
            "ospf FRR policy type"
        ::= { zxr10ospfEntry 25 }

zxr10ospfFrrPolicyName OBJECT-TYPE
        SYNTAX DisplayString (SIZE (1..31))
        MAX-ACCESS  read-only
        STATUS  current
        DESCRIPTION
            "ospf FRR policy name"
        ::= { zxr10ospfEntry 26 }

zxr10ospfFrrTypeTable OBJECT-TYPE
        SYNTAX  SEQUENCE OF Zxr10ospfFrrTypeEntry
        MAX-ACCESS  not-accessible
        STATUS  current
        DESCRIPTION
            "An table to ipfrr"
        ::= { zxr10ospfMIB 2 }

zxr10ospfFrrTypeEntry OBJECT-TYPE
        SYNTAX Zxr10ospfFrrTypeEntry
        MAX-ACCESS  not-accessible
        STATUS  current
        DESCRIPTION
            "An entry to ipfrr."
        INDEX  { zxr10ospfFrrTypeProId }
        ::= { zxr10ospfFrrTypeTable 1 }
            
Zxr10ospfFrrTypeEntry ::=
        SEQUENCE {
            zxr10ospfFrrTypeProId
                Unsigned32,
            zxr10ospfFrrTypeFrrType
                Unsigned32
        }

zxr10ospfFrrTypeProId OBJECT-TYPE
        SYNTAX Unsigned32
        MAX-ACCESS  read-only
        STATUS  current
        DESCRIPTION
            "ospf instance ID"
        ::= { zxr10ospfFrrTypeEntry 1 }

zxr10ospfFrrTypeFrrType OBJECT-TYPE
        SYNTAX Unsigned32
        MAX-ACCESS  read-only
        STATUS  current
        DESCRIPTION
            "fast-reroute policy"
        ::= { zxr10ospfFrrTypeEntry 2 }




zxr10ospfPassiveIntfTable OBJECT-TYPE
        SYNTAX  SEQUENCE OF Zxr10ospfPassiveIntfEntry
        MAX-ACCESS  not-accessible
        STATUS  obsolete
        DESCRIPTION
            "An table to passive interface"
        ::= { zxr10ospfMIB 3 }

zxr10ospfPassiveIntfEntry OBJECT-TYPE
        SYNTAX Zxr10ospfPassiveIntfEntry
        MAX-ACCESS  not-accessible
        STATUS  obsolete
        DESCRIPTION
            "An entry to passive interface."
        INDEX  { zxr10ospfPassiveIntfIntfName,zxr10ospfPassiveIntfProId,
                 zxr10ospfPassiveIntfDefault }
        ::= { zxr10ospfPassiveIntfTable 1 }
            
Zxr10ospfPassiveIntfEntry ::=
        SEQUENCE {
            zxr10ospfPassiveIntfIntfName
                DisplayString,
            zxr10ospfPassiveIntfProId
                Unsigned32,
            zxr10ospfPassiveIntfDefault
                Unsigned32,
            zxr10ospfPassiveIntfDisable
                Unsigned32
        }

zxr10ospfPassiveIntfIntfName OBJECT-TYPE
        SYNTAX DisplayString (SIZE (1..31))
        MAX-ACCESS  read-only
        STATUS  obsolete
        DESCRIPTION
            "interface name"
        ::= { zxr10ospfPassiveIntfEntry 1 }

zxr10ospfPassiveIntfProId OBJECT-TYPE
        SYNTAX Unsigned32
        MAX-ACCESS  read-only
        STATUS  obsolete
        DESCRIPTION
            "ospf instance ID"
        ::= { zxr10ospfPassiveIntfEntry 2 }

zxr10ospfPassiveIntfDefault OBJECT-TYPE
        SYNTAX Unsigned32 (0..256)
        MAX-ACCESS  read-only
        STATUS  obsolete
        DESCRIPTION
            "default set"
        ::= { zxr10ospfPassiveIntfEntry 3 }

zxr10ospfPassiveIntfDisable OBJECT-TYPE
        SYNTAX Unsigned32 (0..256)
        MAX-ACCESS  read-only
        STATUS  obsolete
        DESCRIPTION
            "disable passive interface"
        ::= { zxr10ospfPassiveIntfEntry 4 }


zxr10ospfRedistributeTable OBJECT-TYPE
        SYNTAX  SEQUENCE OF Zxr10ospfRedistributeEntry
        MAX-ACCESS  not-accessible
        STATUS  current
        DESCRIPTION
            "An table to redistribute"
        ::= { zxr10ospfMIB 4 }

zxr10ospfRedistributeEntry OBJECT-TYPE
        SYNTAX Zxr10ospfRedistributeEntry
        MAX-ACCESS  not-accessible
        STATUS  current
        DESCRIPTION
            "An entry to redistribute."
        INDEX  { zxr10ospfRedistributeProId,zxr10ospfRedistributePrococol,
                 zxr10ospfRedistributeProtocalId }
        ::= { zxr10ospfRedistributeTable 1 }
            
Zxr10ospfRedistributeEntry ::=
        SEQUENCE {
            zxr10ospfRedistributeProId
                Unsigned32,
            zxr10ospfRedistributePrococol
                INTEGER,
            zxr10ospfRedistributeProtocalId
                Unsigned32,
            zxr10ospfRedistributePeerAddress
                IpAddress,
            zxr10ospfRedistributeTagValue
                Unsigned32,
            zxr10ospfRedistributeMetricValue
                Unsigned32,
            zxr10ospfRedistributeMetricType
                Unsigned32,
            zxr10ospfRedistributeRouterMap
                DisplayString,
            zxr10ospfRedistributeWithorigmetric
                Unsigned32,
            zxr10ospfRedistributeAsAsndot
                DisplayString,
            zxr10ospfRedistributeAsNoflag
                Unsigned32
        }

zxr10ospfRedistributeProId OBJECT-TYPE
        SYNTAX Unsigned32
        MAX-ACCESS  read-only
        STATUS  current
        DESCRIPTION
            "ospf instance ID"
        ::= { zxr10ospfRedistributeEntry 1 }

zxr10ospfRedistributePrococol OBJECT-TYPE
        SYNTAX INTEGER {static(1),connected(2),rip(3),ospfint(4),ospfext(5),
                        isis1(6),isis2(7),isis12(8),bgpext(9),bgpint(10),
                        nat(11),subscriberhost(12),natpt(13),psbusiaddr(14),
                        psuseraddr(15),subscriberaggregation(16),
                        userspecial(17),slnat64ipv4(27),braspool(18),
                        ipsec(19),natmask(20),zenicLocal(21),dynleasedline(22)}
        MAX-ACCESS  read-only
        STATUS  current
        DESCRIPTION
            "protocal"
        ::= { zxr10ospfRedistributeEntry 2 }

zxr10ospfRedistributeProtocalId OBJECT-TYPE
        SYNTAX Unsigned32
        MAX-ACCESS  read-only
        STATUS  current
        DESCRIPTION
            "the instance ID of redistribute"
        ::= { zxr10ospfRedistributeEntry 3 }

zxr10ospfRedistributePeerAddress OBJECT-TYPE
        SYNTAX IpAddress
        MAX-ACCESS  read-only
        STATUS  current
        DESCRIPTION
            "peer address"
        ::= { zxr10ospfRedistributeEntry 5 }

zxr10ospfRedistributeTagValue OBJECT-TYPE
        SYNTAX Unsigned32
        MAX-ACCESS  read-only
        STATUS  current
        DESCRIPTION
            "the tag value of redistribute"
        ::= { zxr10ospfRedistributeEntry 6 }

zxr10ospfRedistributeMetricValue OBJECT-TYPE
        SYNTAX Unsigned32
        MAX-ACCESS  read-only
        STATUS  current
        DESCRIPTION
            "the metric value of redistribute"
        ::= { zxr10ospfRedistributeEntry 7 }

zxr10ospfRedistributeMetricType OBJECT-TYPE
        SYNTAX Unsigned32
        MAX-ACCESS  read-only
        STATUS  current
        DESCRIPTION
            "the metric_type of redistribute"
        ::= { zxr10ospfRedistributeEntry 8 }

zxr10ospfRedistributeRouterMap OBJECT-TYPE
        SYNTAX DisplayString (SIZE (1..31))
        MAX-ACCESS  read-only
        STATUS  current
        DESCRIPTION
            "the routemap policy of redistribute"
        ::= { zxr10ospfRedistributeEntry 10 }

zxr10ospfRedistributeWithorigmetric OBJECT-TYPE
        SYNTAX Unsigned32
        MAX-ACCESS  read-only
        STATUS  current
        DESCRIPTION
            "redistribute with original metric"
        ::= { zxr10ospfRedistributeEntry 11 }

zxr10ospfRedistributeAsAsndot OBJECT-TYPE
        SYNTAX DisplayString
        MAX-ACCESS  read-only
        STATUS  current
        DESCRIPTION
            "as number"
        ::= { zxr10ospfRedistributeEntry 12 }

zxr10ospfRedistributeAsNoflag OBJECT-TYPE
        SYNTAX Unsigned32 (0..256)
        MAX-ACCESS  read-only
        STATUS  current
        DESCRIPTION
            "as number flag"
        ::= { zxr10ospfRedistributeEntry 13 }



zxr10ospfNetworkTable OBJECT-TYPE
        SYNTAX  SEQUENCE OF Zxr10ospfNetworkEntry
        MAX-ACCESS  not-accessible
        STATUS  obsolete
        DESCRIPTION
            "An table to network"
        ::= { zxr10ospfMIB 5 }

zxr10ospfNetworkEntry OBJECT-TYPE
        SYNTAX Zxr10ospfNetworkEntry
        MAX-ACCESS  not-accessible
        STATUS  obsolete
        DESCRIPTION
            "An entry to network."
        INDEX  { zxr10ospfNetworkProId,zxr10ospfNetworkIpAddr,
                 zxr10ospfNetworkIpMask }
        ::= { zxr10ospfNetworkTable 1 }
            
Zxr10ospfNetworkEntry ::=
        SEQUENCE {
            zxr10ospfNetworkProId
                Unsigned32,
            zxr10ospfNetworkIpAddr
                IpAddress,
            zxr10ospfNetworkIpMask
                IpAddress,
            zxr10ospfNetworkAreaId
                Unsigned32,
            zxr10ospfNetworkAreaId1
                IpAddress
        }

zxr10ospfNetworkProId OBJECT-TYPE
        SYNTAX Unsigned32
        MAX-ACCESS  read-only
        STATUS  obsolete
        DESCRIPTION
            "ospf instance ID"
        ::= { zxr10ospfNetworkEntry 1 }

zxr10ospfNetworkIpAddr OBJECT-TYPE
        SYNTAX IpAddress
        MAX-ACCESS  read-only
        STATUS  obsolete
        DESCRIPTION
            "ip address"
        ::= { zxr10ospfNetworkEntry 2 }

zxr10ospfNetworkIpMask OBJECT-TYPE
        SYNTAX IpAddress
        MAX-ACCESS  read-only
        STATUS  obsolete
        DESCRIPTION
            "mask"
        ::= { zxr10ospfNetworkEntry 3 }

zxr10ospfNetworkAreaId OBJECT-TYPE
        SYNTAX Unsigned32
        MAX-ACCESS  read-only
        STATUS  obsolete
        DESCRIPTION
            "area ID"
        ::= { zxr10ospfNetworkEntry 4 }

zxr10ospfNetworkAreaId1 OBJECT-TYPE
        SYNTAX IpAddress
        MAX-ACCESS  read-only
        STATUS  obsolete
        DESCRIPTION
            "area ID"
        ::= { zxr10ospfNetworkEntry 5 }



zxr10ospfNeighborTable OBJECT-TYPE
        SYNTAX  SEQUENCE OF Zxr10ospfNeighborEntry
        MAX-ACCESS  not-accessible
        STATUS  obsolete
        DESCRIPTION
            "An table to neighbor"
        ::= { zxr10ospfMIB 6 }

zxr10ospfNeighborEntry OBJECT-TYPE
        SYNTAX Zxr10ospfNeighborEntry
        MAX-ACCESS  not-accessible
        STATUS  obsolete
        DESCRIPTION
            "An entry to neighbor."
        INDEX  { zxr10ospfNeighborIpAddress,zxr10ospfNeighborProId }
        ::= { zxr10ospfNeighborTable 1 }
            
Zxr10ospfNeighborEntry ::=
        SEQUENCE {
            zxr10ospfNeighborIpAddress
                IpAddress,
            zxr10ospfNeighborProId
                Unsigned32,
            zxr10ospfNeighborCost
                Unsigned32,
            zxr10ospfNeighborPriority
                Unsigned32,
            zxr10ospfNeighborPollInterval
                Unsigned32
        }

zxr10ospfNeighborIpAddress OBJECT-TYPE
        SYNTAX IpAddress
        MAX-ACCESS  read-only
        STATUS  obsolete
        DESCRIPTION
            "ip address of neighbor"
        ::= { zxr10ospfNeighborEntry 1 }

zxr10ospfNeighborProId OBJECT-TYPE
        SYNTAX Unsigned32
        MAX-ACCESS  read-only
        STATUS  obsolete
        DESCRIPTION
            "ospf instance ID"
        ::= { zxr10ospfNeighborEntry 2 }

zxr10ospfNeighborCost OBJECT-TYPE
        SYNTAX Unsigned32
        MAX-ACCESS  read-only
        STATUS  obsolete
        DESCRIPTION
            "cost of neighbor"
        ::= { zxr10ospfNeighborEntry 3 }

zxr10ospfNeighborPriority OBJECT-TYPE
        SYNTAX Unsigned32
        MAX-ACCESS  read-only
        STATUS  obsolete
        DESCRIPTION
            "priority of neighbor"
        ::= { zxr10ospfNeighborEntry 4 }

zxr10ospfNeighborPollInterval OBJECT-TYPE
        SYNTAX Unsigned32
        MAX-ACCESS  read-only
        STATUS  obsolete
        DESCRIPTION
            "pollinterval of neighbor"
        ::= { zxr10ospfNeighborEntry 5 }


zxr10ospfNotifyDlrouteTable OBJECT-TYPE
        SYNTAX  SEQUENCE OF Zxr10ospfNotifyDlrouteEntry
        MAX-ACCESS  not-accessible
        STATUS  current
        DESCRIPTION
            "An table to notify default route"
        ::= { zxr10ospfMIB 7 }

zxr10ospfNotifyDlrouteEntry OBJECT-TYPE
        SYNTAX Zxr10ospfNotifyDlrouteEntry
        MAX-ACCESS  not-accessible
        STATUS  current
        DESCRIPTION
            "An entry to notify default route."
        INDEX  { zxr10ospfNotifyDlrouteProId,
                 zxr10ospfNotifyDlrouteDefaultRoute }
        ::= { zxr10ospfNotifyDlrouteTable 1 }
            
Zxr10ospfNotifyDlrouteEntry ::=
        SEQUENCE {
            zxr10ospfNotifyDlrouteProId
                Unsigned32,
            zxr10ospfNotifyDlrouteDefaultRoute
                Unsigned32,
            zxr10ospfNotifyDlrouteAlways
                Unsigned32,
            zxr10ospfNotifyDlrouteMetric
                Unsigned32,
            zxr10ospfNotifyDlrouteMetricType
                Unsigned32,
            zxr10ospfNotifyDlrouteRouteMap
                DisplayString
        }

zxr10ospfNotifyDlrouteProId OBJECT-TYPE
        SYNTAX Unsigned32
        MAX-ACCESS  read-only
        STATUS  current
        DESCRIPTION
            "ospf instance ID"
        ::= { zxr10ospfNotifyDlrouteEntry 1 }

zxr10ospfNotifyDlrouteDefaultRoute OBJECT-TYPE
        SYNTAX Unsigned32
        MAX-ACCESS  read-only
        STATUS  current
        DESCRIPTION
            "notify_default_route"
        ::= { zxr10ospfNotifyDlrouteEntry 2 }

zxr10ospfNotifyDlrouteAlways OBJECT-TYPE
        SYNTAX Unsigned32 (0..256)
        MAX-ACCESS  read-only
        STATUS  current
        DESCRIPTION
            "notify default route anyway"
        ::= { zxr10ospfNotifyDlrouteEntry 3 }

zxr10ospfNotifyDlrouteMetric OBJECT-TYPE
        SYNTAX Unsigned32
        MAX-ACCESS  read-only
        STATUS  current
        DESCRIPTION
            "cost of notify_default_route"
        ::= { zxr10ospfNotifyDlrouteEntry 4 }

zxr10ospfNotifyDlrouteMetricType OBJECT-TYPE
        SYNTAX Unsigned32
        MAX-ACCESS  read-only
        STATUS  current
        DESCRIPTION
            "type of notify_default_route"
        ::= { zxr10ospfNotifyDlrouteEntry 5 }

zxr10ospfNotifyDlrouteRouteMap OBJECT-TYPE
        SYNTAX DisplayString (SIZE (1..31))
        MAX-ACCESS  read-only
        STATUS  current
        DESCRIPTION
            "routemap name of notify default route"
        ::= { zxr10ospfNotifyDlrouteEntry 6 }



zxr10ospfFilterTable OBJECT-TYPE
        SYNTAX  SEQUENCE OF Zxr10ospfFilterEntry
        MAX-ACCESS  not-accessible
        STATUS  obsolete
        DESCRIPTION
            "An table to filter"
        ::= { zxr10ospfMIB 8 }

zxr10ospfFilterEntry OBJECT-TYPE
        SYNTAX Zxr10ospfFilterEntry
        MAX-ACCESS  not-accessible
        STATUS  obsolete
        DESCRIPTION
            "An entry to filter."
        INDEX  { zxr10ospfFilterIpAddr,zxr10ospfFilterProId,
                 zxr10ospfFilterNetMask }
        ::= { zxr10ospfFilterTable 1 }
            
Zxr10ospfFilterEntry ::=
        SEQUENCE {
            zxr10ospfFilterIpAddr
                IpAddress,
            zxr10ospfFilterProId
                Unsigned32,
            zxr10ospfFilterNetMask
                IpAddress,
            zxr10ospfFilterExact
                Unsigned32,
            zxr10ospfFilterPreference
                Unsigned32
        }

zxr10ospfFilterIpAddr OBJECT-TYPE
        SYNTAX IpAddress
        MAX-ACCESS  read-only
        STATUS  obsolete
        DESCRIPTION
            "the ip address of filter"
        ::= { zxr10ospfFilterEntry 1 }

zxr10ospfFilterProId OBJECT-TYPE
        SYNTAX Unsigned32
        MAX-ACCESS  read-only
        STATUS  obsolete
        DESCRIPTION
            "ospf instance ID"
        ::= { zxr10ospfFilterEntry 2 }

zxr10ospfFilterNetMask OBJECT-TYPE
        SYNTAX IpAddress
        MAX-ACCESS  read-only
        STATUS  obsolete
        DESCRIPTION
            "mask of filter"
        ::= { zxr10ospfFilterEntry 3 }

zxr10ospfFilterExact OBJECT-TYPE
        SYNTAX Unsigned32
        MAX-ACCESS  read-only
        STATUS  obsolete
        DESCRIPTION
            "exact filter"
        ::= { zxr10ospfFilterEntry 4 }

zxr10ospfFilterPreference OBJECT-TYPE
        SYNTAX Unsigned32
        MAX-ACCESS  read-only
        STATUS  obsolete
        DESCRIPTION
            "preference of filter"
        ::= { zxr10ospfFilterEntry 5 }
        

zxr10ospfDistributeListTable OBJECT-TYPE
        SYNTAX  SEQUENCE OF Zxr10ospfDistributeListEntry
        MAX-ACCESS  not-accessible
        STATUS  current
        DESCRIPTION
            "An table to distributelist"
        ::= { zxr10ospfMIB 9 }

zxr10ospfDistributeListEntry OBJECT-TYPE
        SYNTAX Zxr10ospfDistributeListEntry
        MAX-ACCESS  not-accessible
        STATUS  current
        DESCRIPTION
            "An entry to distributelist."
        INDEX  { zxr10ospfDistributeListProId,zxr10ospfDistributeListIn,
                 zxr10ospfDistributeListOut}
        ::= { zxr10ospfDistributeListTable 1 }
            
Zxr10ospfDistributeListEntry ::=
        SEQUENCE {
            zxr10ospfDistributeListProId
                Unsigned32,
            zxr10ospfDistributeListIn
                Unsigned32,
            zxr10ospfDistributeListOut
                Unsigned32,
            zxr10ospfDistributeListLocalMt
                Unsigned32,
            zxr10ospfDistributeListAccessListNum
                Unsigned32,
            zxr10ospfDistributeListAccessListName
                DisplayString,
            zxr10ospfDistributeListNameIpPrefixList
                DisplayString,
            zxr10ospfDistributeListNameRouteMap
                DisplayString,
            zxr10ospfDistributeListGateway
                DisplayString,
            zxr10ospfDistributeListPrefixListGateway
                DisplayString,
            zxr10ospfDistributeListAccessListNum1
                Unsigned32
        }

zxr10ospfDistributeListProId OBJECT-TYPE
        SYNTAX Unsigned32
        MAX-ACCESS  read-only
        STATUS  current
        DESCRIPTION
            "ospf instance ID"
        ::= { zxr10ospfDistributeListEntry 1 }

zxr10ospfDistributeListIn OBJECT-TYPE
        SYNTAX Unsigned32
        MAX-ACCESS  read-only
        STATUS  current
        DESCRIPTION
            "distributelist in"
        ::= { zxr10ospfDistributeListEntry 2 }

zxr10ospfDistributeListOut OBJECT-TYPE
        SYNTAX Unsigned32
        MAX-ACCESS  read-only
        STATUS  current
        DESCRIPTION
            "distributelist out"
        ::= { zxr10ospfDistributeListEntry 3 }

zxr10ospfDistributeListLocalMt OBJECT-TYPE
        SYNTAX Unsigned32
        MAX-ACCESS  read-only
        STATUS  current
        DESCRIPTION
            "distributelist localmt"
        ::= { zxr10ospfDistributeListEntry 4 }

zxr10ospfDistributeListAccessListNum OBJECT-TYPE
        SYNTAX Unsigned32
        MAX-ACCESS  read-only
        STATUS  current
        DESCRIPTION
            "acl number"
        ::= { zxr10ospfDistributeListEntry 5 }

zxr10ospfDistributeListAccessListName OBJECT-TYPE
        SYNTAX DisplayString (SIZE (1..31))
        MAX-ACCESS  read-only
        STATUS  current
        DESCRIPTION
            "access_list name"
        ::= { zxr10ospfDistributeListEntry 6 }

zxr10ospfDistributeListNameIpPrefixList OBJECT-TYPE
        SYNTAX DisplayString (SIZE (1..31))
        MAX-ACCESS  read-only
        STATUS  current
        DESCRIPTION
            "prefix_list name"
        ::= { zxr10ospfDistributeListEntry 7 }

zxr10ospfDistributeListNameRouteMap OBJECT-TYPE
        SYNTAX DisplayString (SIZE (1..31))
        MAX-ACCESS  read-only
        STATUS  current
        DESCRIPTION
            "route_map name"
        ::= { zxr10ospfDistributeListEntry 8 }

zxr10ospfDistributeListGateway OBJECT-TYPE
        SYNTAX DisplayString (SIZE (1..31))
        MAX-ACCESS  read-only
        STATUS  current
        DESCRIPTION
            "gateway name"
        ::= { zxr10ospfDistributeListEntry 9 }

zxr10ospfDistributeListPrefixListGateway OBJECT-TYPE
        SYNTAX DisplayString (SIZE (1..31))
        MAX-ACCESS  read-only
        STATUS  current
        DESCRIPTION
            "gateway name of prefix list"
        ::= { zxr10ospfDistributeListEntry 10 }

zxr10ospfDistributeListAccessListNum1 OBJECT-TYPE
        SYNTAX Unsigned32
        MAX-ACCESS  read-only
        STATUS  current
        DESCRIPTION
            "acl number"
        ::= { zxr10ospfDistributeListEntry 11 }



zxr10ospfBfdTable OBJECT-TYPE
        SYNTAX  SEQUENCE OF Zxr10ospfBfdEntry
        MAX-ACCESS  not-accessible
        STATUS  obsolete
        DESCRIPTION
            "An table to BFD"
        ::= { zxr10ospfMIB 10 }

zxr10ospfBfdEntry OBJECT-TYPE
        SYNTAX Zxr10ospfBfdEntry
        MAX-ACCESS  not-accessible
        STATUS  obsolete
        DESCRIPTION
            "An entry to BFD."
        INDEX  { zxr10ospfBfdAreaId,zxr10ospfBfdProId,zxr10ospfBfdAreaId1,
                 zxr10ospfBfdAreaFlag }
        ::= { zxr10ospfBfdTable 1 }
            
Zxr10ospfBfdEntry ::=
        SEQUENCE {
            zxr10ospfBfdAreaId
                Unsigned32,
            zxr10ospfBfdProId
                Unsigned32,
            zxr10ospfBfdAreaId1
                IpAddress,
            zxr10ospfBfdAreaFlag
                Unsigned32,
            zxr10ospfBfdEnable
                Unsigned32
        }

zxr10ospfBfdAreaId OBJECT-TYPE
        SYNTAX Unsigned32
        MAX-ACCESS  read-only
        STATUS  obsolete
        DESCRIPTION
            "area ID"
        ::= { zxr10ospfBfdEntry 1 }

zxr10ospfBfdProId OBJECT-TYPE
        SYNTAX Unsigned32
        MAX-ACCESS  read-only
        STATUS  obsolete
        DESCRIPTION
            "ospf instance ID"
        ::= { zxr10ospfBfdEntry 2 }

zxr10ospfBfdAreaId1 OBJECT-TYPE
        SYNTAX IpAddress
        MAX-ACCESS  read-only
        STATUS  obsolete
        DESCRIPTION
            "area ID"
        ::= { zxr10ospfBfdEntry 3 }

zxr10ospfBfdAreaFlag OBJECT-TYPE
        SYNTAX Unsigned32 (1..2)
        MAX-ACCESS  read-only
        STATUS  obsolete
        DESCRIPTION
            "area BFD"
        ::= { zxr10ospfBfdEntry 4 }

zxr10ospfBfdEnable OBJECT-TYPE
        SYNTAX Unsigned32
        MAX-ACCESS  read-only
        STATUS  obsolete
        DESCRIPTION
            "enable BFD"
        ::= { zxr10ospfBfdEntry 5 }
        
        
zxr10ospfMaxMetricTable OBJECT-TYPE
        SYNTAX  SEQUENCE OF Zxr10ospfMaxMetricEntry
        MAX-ACCESS  not-accessible
        STATUS  current
        DESCRIPTION
            "An table to maxmetric"
        ::= { zxr10ospfMIB 12 }

zxr10ospfMaxMetricEntry OBJECT-TYPE
        SYNTAX Zxr10ospfMaxMetricEntry
        MAX-ACCESS  not-accessible
        STATUS  current
        DESCRIPTION
            "An entry to maxmetric."
        INDEX  { zxr10ospfMaxMetricProId}
        ::= { zxr10ospfMaxMetricTable 1 }
            
Zxr10ospfMaxMetricEntry ::=
        SEQUENCE {
            zxr10ospfMaxMetricProId
                Unsigned32,
            zxr10ospfMaxMetricRouterLsa
                Unsigned32,
            zxr10ospfMaxMetricWaitForBgp
                Unsigned32,
            zxr10ospfMaxMetricTimeout
                Unsigned32
        }

zxr10ospfMaxMetricProId OBJECT-TYPE
        SYNTAX Unsigned32
        MAX-ACCESS  read-only
        STATUS  current
        DESCRIPTION
            "ospf instance ID"
        ::= { zxr10ospfMaxMetricEntry 1 }

zxr10ospfMaxMetricRouterLsa OBJECT-TYPE
        SYNTAX Unsigned32
        MAX-ACCESS  read-only
        STATUS  current
        DESCRIPTION
            "maxmetric in self-originated router-LSAs"
        ::= { zxr10ospfMaxMetricEntry 2 }

zxr10ospfMaxMetricWaitForBgp OBJECT-TYPE
        SYNTAX Unsigned32 (0..256)
        MAX-ACCESS  read-only
        STATUS  current
        DESCRIPTION
            "BGP decide when to originate a normal router-LSA"
        ::= { zxr10ospfMaxMetricEntry 3 }

zxr10ospfMaxMetricTimeout OBJECT-TYPE
        SYNTAX Unsigned32 (2|5..86400)
        MAX-ACCESS  read-only
        STATUS  current
        DESCRIPTION
            "maximum metric temporarily after reboot.  The value 2 is invalid."
        ::= { zxr10ospfMaxMetricEntry 4 }



zxr10ospfDomainIdTable OBJECT-TYPE
        SYNTAX  SEQUENCE OF Zxr10ospfDomainIdEntry
        MAX-ACCESS  not-accessible
        STATUS  current
        DESCRIPTION
            "An table to domain ID"
        ::= { zxr10ospfMIB 13 }

zxr10ospfDomainIdEntry OBJECT-TYPE
        SYNTAX Zxr10ospfDomainIdEntry
        MAX-ACCESS  not-accessible
        STATUS  current
        DESCRIPTION
            "An entry to domain ID."
        INDEX  { zxr10ospfDomainIdProId }
        ::= { zxr10ospfDomainIdTable 1 }
            
Zxr10ospfDomainIdEntry ::=
        SEQUENCE {
            zxr10ospfDomainIdProId
                Unsigned32,
            zxr10ospfDomainIdDomainId
                IpAddress
        }

zxr10ospfDomainIdProId OBJECT-TYPE
        SYNTAX Unsigned32
        MAX-ACCESS  read-only
        STATUS  current
        DESCRIPTION
            "ospf instance ID"
        ::= { zxr10ospfDomainIdEntry 1 }

zxr10ospfDomainIdDomainId OBJECT-TYPE
        SYNTAX IpAddress
        MAX-ACCESS  read-only
        STATUS  current
        DESCRIPTION
            "domain ID"
        ::= { zxr10ospfDomainIdEntry 2 }




zxr10ospfRouterIdTable OBJECT-TYPE
        SYNTAX  SEQUENCE OF Zxr10ospfRouterIdEntry
        MAX-ACCESS  not-accessible
        STATUS  current
        DESCRIPTION
            "An table to router_id"
        ::= { zxr10ospfMIB 14 }

zxr10ospfRouterIdEntry OBJECT-TYPE
        SYNTAX Zxr10ospfRouterIdEntry
        MAX-ACCESS  not-accessible
        STATUS  current
        DESCRIPTION
            "An entry to router_id."
        INDEX  { zxr10ospfRouterIdProId }
        ::= { zxr10ospfRouterIdTable 1 }
            
Zxr10ospfRouterIdEntry ::=
        SEQUENCE {
            zxr10ospfRouterIdProId
                Unsigned32,
            zxr10ospfRouterIdRouterId
                IpAddress
        }

zxr10ospfRouterIdProId OBJECT-TYPE
        SYNTAX Unsigned32
        MAX-ACCESS  read-only
        STATUS  current
        DESCRIPTION
            " instance ID"
        ::= { zxr10ospfRouterIdEntry 1 }


zxr10ospfRouterIdRouterId OBJECT-TYPE
        SYNTAX IpAddress
        MAX-ACCESS  read-only
        STATUS  current
        DESCRIPTION
            "router ID"
        ::= { zxr10ospfRouterIdEntry 3 }



zxr10ospfDomainTagTable OBJECT-TYPE
        SYNTAX  SEQUENCE OF Zxr10ospfDomainTagEntry
        MAX-ACCESS  not-accessible
        STATUS  current
        DESCRIPTION
            "An table to domain tag"
        ::= { zxr10ospfMIB 15 }

zxr10ospfDomainTagEntry OBJECT-TYPE
        SYNTAX Zxr10ospfDomainTagEntry
        MAX-ACCESS  not-accessible
        STATUS  current
        DESCRIPTION
            "An entry to domain tag."
        INDEX  { zxr10ospfDomainTagProId }
        ::= { zxr10ospfDomainTagTable 1 }
            
Zxr10ospfDomainTagEntry ::=
        SEQUENCE {
            zxr10ospfDomainTagProId
                Unsigned32,
            zxr10ospfDomainTagDomainTag
                Unsigned32
        }

zxr10ospfDomainTagProId OBJECT-TYPE
        SYNTAX Unsigned32
        MAX-ACCESS  read-only
        STATUS  current
        DESCRIPTION
            " instance ID"
        ::= { zxr10ospfDomainTagEntry 1 }

zxr10ospfDomainTagDomainTag OBJECT-TYPE
        SYNTAX Unsigned32
        MAX-ACCESS  read-only
        STATUS  current
        DESCRIPTION
            "domain tag"
        ::= { zxr10ospfDomainTagEntry 2 }



zxr10ospfSummaryAddrTable OBJECT-TYPE
        SYNTAX  SEQUENCE OF Zxr10ospfSummaryAddrEntry
        MAX-ACCESS  not-accessible
        STATUS  obsolete
        DESCRIPTION
            "An table to summary"
        ::= { zxr10ospfMIB 16 }

zxr10ospfSummaryAddrEntry OBJECT-TYPE
        SYNTAX Zxr10ospfSummaryAddrEntry
        MAX-ACCESS  not-accessible
        STATUS  obsolete
        DESCRIPTION
            "An entry to summary."
        INDEX  { zxr10ospfSummaryAddrIpAddr,zxr10ospfSummaryAddrProId,
                 zxr10ospfSummaryAddrNetMask }
        ::= { zxr10ospfSummaryAddrTable 1 }
            
Zxr10ospfSummaryAddrEntry ::=
        SEQUENCE {
            zxr10ospfSummaryAddrIpAddr
                IpAddress,
            zxr10ospfSummaryAddrProId
                Unsigned32,
            zxr10ospfSummaryAddrNetMask
                IpAddress,
            zxr10ospfSummaryAddrCostValue
                Unsigned32
        }

zxr10ospfSummaryAddrIpAddr OBJECT-TYPE
        SYNTAX IpAddress
        MAX-ACCESS  read-only
        STATUS  obsolete
        DESCRIPTION
            "summary address"
        ::= { zxr10ospfSummaryAddrEntry 1 }

zxr10ospfSummaryAddrProId OBJECT-TYPE
        SYNTAX Unsigned32
        MAX-ACCESS  read-only
        STATUS  obsolete
        DESCRIPTION
            "ospf instance ID"
        ::= { zxr10ospfSummaryAddrEntry 2 }

zxr10ospfSummaryAddrNetMask OBJECT-TYPE
        SYNTAX IpAddress
        MAX-ACCESS  read-only
        STATUS  obsolete
        DESCRIPTION
            "summary address net mask"
        ::= { zxr10ospfSummaryAddrEntry 3 }

zxr10ospfSummaryAddrCostValue OBJECT-TYPE
        SYNTAX Unsigned32
        MAX-ACCESS  read-only
        STATUS  obsolete
        DESCRIPTION
            "cost value of summary address"
        ::= { zxr10ospfSummaryAddrEntry 4 }

zxr10ospfTrackTable OBJECT-TYPE
        SYNTAX  SEQUENCE OF Zxr10ospfTrackEntry
        MAX-ACCESS  not-accessible
        STATUS  current
        DESCRIPTION
            "An table to track"
        ::= { zxr10ospfMIB 17 }

zxr10ospfTrackEntry OBJECT-TYPE
        SYNTAX Zxr10ospfTrackEntry
        MAX-ACCESS  not-accessible
        STATUS  current
        DESCRIPTION
            "An entry to track."
        INDEX  { zxr10ospfTrackProId,zxr10ospfTrackName }
        ::= { zxr10ospfTrackTable 1 }
            
Zxr10ospfTrackEntry ::=
        SEQUENCE {
            zxr10ospfTrackProId
                Unsigned32,
            zxr10ospfTrackName
                DisplayString
        }

zxr10ospfTrackProId OBJECT-TYPE
        SYNTAX Unsigned32
        MAX-ACCESS  read-only
        STATUS  current
        DESCRIPTION
            "ospf instance ID"
        ::= { zxr10ospfTrackEntry 1 }

zxr10ospfTrackName OBJECT-TYPE
        SYNTAX DisplayString (SIZE (1..31))
        MAX-ACCESS  read-only
        STATUS  current
        DESCRIPTION
            "track name"
        ::= { zxr10ospfTrackEntry 2 }



zxr10ospfFastFldTable OBJECT-TYPE
        SYNTAX  SEQUENCE OF Zxr10ospfFastFldEntry
        MAX-ACCESS  not-accessible
        STATUS  obsolete
        DESCRIPTION
            "An table to fast flood"
        ::= { zxr10ospfMIB 18 }

zxr10ospfFastFldEntry OBJECT-TYPE
        SYNTAX Zxr10ospfFastFldEntry
        MAX-ACCESS  not-accessible
        STATUS  obsolete
        DESCRIPTION
            "An entry to fast flood."
        INDEX  { zxr10ospfFastFldProId }
        ::= { zxr10ospfFastFldTable 1 }
            
Zxr10ospfFastFldEntry ::=
        SEQUENCE {
            zxr10ospfFastFldProId
                Unsigned32,
            zxr10ospfFastFldFastfldValue
                Unsigned32
        }

zxr10ospfFastFldProId OBJECT-TYPE
        SYNTAX Unsigned32
        MAX-ACCESS  read-only
        STATUS  obsolete
        DESCRIPTION
            ""
        ::= { zxr10ospfFastFldEntry 1 }

zxr10ospfFastFldFastfldValue OBJECT-TYPE
        SYNTAX Unsigned32
        MAX-ACCESS  read-only
        STATUS  obsolete
        DESCRIPTION
            "fast flood value"
        ::= { zxr10ospfFastFldEntry 2 }



zxr10ospfSeqBackupTable OBJECT-TYPE
        SYNTAX  SEQUENCE OF Zxr10ospfSeqBackupEntry
        MAX-ACCESS  not-accessible
        STATUS  current
        DESCRIPTION
            "An table to sequence-backup"
        ::= { zxr10ospfMIB 19 }

zxr10ospfSeqBackupEntry OBJECT-TYPE
        SYNTAX Zxr10ospfSeqBackupEntry
        MAX-ACCESS  not-accessible
        STATUS  current
        DESCRIPTION
            "An entry to sequence-backup."
        INDEX  { zxr10ospfSeqBackupProId }
        ::= { zxr10ospfSeqBackupTable 1 }
            
Zxr10ospfSeqBackupEntry ::=
        SEQUENCE {
            zxr10ospfSeqBackupProId
                Unsigned32,
            zxr10ospfSeqBackupSeqBackup
                Unsigned32
        }

zxr10ospfSeqBackupProId OBJECT-TYPE
        SYNTAX Unsigned32
        MAX-ACCESS  read-only
        STATUS  current
        DESCRIPTION
            " instance ID"
        ::= { zxr10ospfSeqBackupEntry 1 }

zxr10ospfSeqBackupSeqBackup OBJECT-TYPE
        SYNTAX Unsigned32
        MAX-ACCESS  read-only
        STATUS  current
        DESCRIPTION
            "sequence-backup"
        ::= { zxr10ospfSeqBackupEntry 2 }




zxr10ospfDistanceTable OBJECT-TYPE
        SYNTAX  SEQUENCE OF Zxr10ospfDistanceEntry
        MAX-ACCESS  not-accessible
        STATUS  current
        DESCRIPTION
            "An table to distance"
        ::= { zxr10ospfMIB 20 }

zxr10ospfDistanceEntry OBJECT-TYPE
        SYNTAX Zxr10ospfDistanceEntry
        MAX-ACCESS  not-accessible
        STATUS  current
        DESCRIPTION
            "An entry to distance."
        INDEX  { zxr10ospfDistanceProId }
        ::= { zxr10ospfDistanceTable 1 }
            
Zxr10ospfDistanceEntry ::=
        SEQUENCE {
            zxr10ospfDistanceProId
                Unsigned32,
            zxr10ospfDistanceFlag
                Unsigned32,
            zxr10ospfDistanceDistanceInter
                Unsigned32,
            zxr10ospfDistanceDistanceExt1
                Unsigned32,
            zxr10ospfDistanceDistanceExt2
                Unsigned32
        }

zxr10ospfDistanceProId OBJECT-TYPE
        SYNTAX Unsigned32
        MAX-ACCESS  read-only
        STATUS  current
        DESCRIPTION
            "ospf instance ID"
        ::= { zxr10ospfDistanceEntry 1 }

zxr10ospfDistanceFlag OBJECT-TYPE
        SYNTAX Unsigned32 (0..256)
        MAX-ACCESS  read-only
        STATUS  current
        DESCRIPTION
            "flag of distance"
        ::= { zxr10ospfDistanceEntry 2 }

zxr10ospfDistanceDistanceInter OBJECT-TYPE
        SYNTAX Unsigned32
        MAX-ACCESS  read-only
        STATUS  current
        DESCRIPTION
            "distance of inter"
        ::= { zxr10ospfDistanceEntry 3 }

zxr10ospfDistanceDistanceExt1 OBJECT-TYPE
        SYNTAX Unsigned32
        MAX-ACCESS  read-only
        STATUS  current
        DESCRIPTION
            "distance of ext1"
        ::= { zxr10ospfDistanceEntry 4 }

zxr10ospfDistanceDistanceExt2 OBJECT-TYPE
        SYNTAX Unsigned32
        MAX-ACCESS  read-only
        STATUS  current
        DESCRIPTION
            "distance of ext2"
        ::= { zxr10ospfDistanceEntry 5 }


zxr10ospfAreaMIB OBJECT IDENTIFIER ::= { zxr10ospfMIB 21 }

zxr10ospfAreaTable OBJECT-TYPE
        SYNTAX  SEQUENCE OF Zxr10ospfAreaEntry
        MAX-ACCESS  not-accessible
        STATUS  obsolete
        DESCRIPTION
            "An table to area"
        ::= { zxr10ospfAreaMIB 1 }

zxr10ospfAreaEntry OBJECT-TYPE
        SYNTAX Zxr10ospfAreaEntry
        MAX-ACCESS  not-accessible
        STATUS  obsolete
        DESCRIPTION
            "An entry to area."
        INDEX  { zxr10ospfAreaAreaId,zxr10ospfAreaProId,
                 zxr10ospfAreaAreaId1 }
        ::= { zxr10ospfAreaTable 1 }
            
Zxr10ospfAreaEntry ::=
        SEQUENCE {
            zxr10ospfAreaAreaId
                Unsigned32,
            zxr10ospfAreaProId
                Unsigned32,
            zxr10ospfAreaAreaId1
                IpAddress
        }

zxr10ospfAreaAreaId OBJECT-TYPE
        SYNTAX Unsigned32
        MAX-ACCESS  read-only
        STATUS  obsolete
        DESCRIPTION
            "area ID"
        ::= { zxr10ospfAreaEntry 1 }

zxr10ospfAreaProId OBJECT-TYPE
        SYNTAX Unsigned32
        MAX-ACCESS  read-only
        STATUS  obsolete
        DESCRIPTION
            "ospf instance ID"
        ::= { zxr10ospfAreaEntry 2 }

zxr10ospfAreaAreaId1 OBJECT-TYPE
        SYNTAX IpAddress
        MAX-ACCESS  read-only
        STATUS  obsolete
        DESCRIPTION
            "area ID"
        ::= { zxr10ospfAreaEntry 3 }
        

zxr10ospfTeAreaTable OBJECT-TYPE
        SYNTAX  SEQUENCE OF Zxr10ospfTeAreaEntry
        MAX-ACCESS  not-accessible
        STATUS  obsolete
        DESCRIPTION
            "An table to MPLS traffic engineering area"
        ::= { zxr10ospfAreaMIB 2 }

zxr10ospfTeAreaEntry OBJECT-TYPE
        SYNTAX Zxr10ospfTeAreaEntry
        MAX-ACCESS  not-accessible
        STATUS  obsolete
        DESCRIPTION
            "An entry to MPLS traffic engineering area."
        INDEX  { zxr10ospfTeAreaAreaId,zxr10ospfTeAreaProId,
                 zxr10ospfTeAreaAreaIp }
        ::= { zxr10ospfTeAreaTable 1 }
            
Zxr10ospfTeAreaEntry ::=
        SEQUENCE {
            zxr10ospfTeAreaAreaId
                Unsigned32,
            zxr10ospfTeAreaProId
                Unsigned32,
            zxr10ospfTeAreaAreaIp
                IpAddress
        }

zxr10ospfTeAreaAreaId OBJECT-TYPE
        SYNTAX Unsigned32
        MAX-ACCESS  read-only
        STATUS  obsolete
        DESCRIPTION
            "area ID"
        ::= { zxr10ospfTeAreaEntry 1 }

zxr10ospfTeAreaProId OBJECT-TYPE
        SYNTAX Unsigned32
        MAX-ACCESS  read-only
        STATUS  obsolete
        DESCRIPTION
            " instance ID"
        ::= { zxr10ospfTeAreaEntry 2 }

zxr10ospfTeAreaAreaIp OBJECT-TYPE
        SYNTAX IpAddress
        MAX-ACCESS  read-only
        STATUS  obsolete
        DESCRIPTION
            "area ID"
        ::= { zxr10ospfTeAreaEntry 3 }


zxr10ospfAreaFilterTable OBJECT-TYPE
        SYNTAX  SEQUENCE OF Zxr10ospfAreaFilterEntry
        MAX-ACCESS  not-accessible
        STATUS  current
        DESCRIPTION
            "An table to area filter"
        ::= { zxr10ospfAreaMIB 3 }

zxr10ospfAreaFilterEntry OBJECT-TYPE
        SYNTAX Zxr10ospfAreaFilterEntry
        MAX-ACCESS  not-accessible
        STATUS  current
        DESCRIPTION
            "An entry to area filter."
        INDEX  { zxr10ospfAreaFilterProId,zxr10ospfAreaFilterAreaId,
                 zxr10ospfAreaFilterAreaId1,zxr10ospfAreaFilterDirectionIn }
        ::= { zxr10ospfAreaFilterTable 1 }
            
Zxr10ospfAreaFilterEntry ::=
        SEQUENCE {
            zxr10ospfAreaFilterProId
                Unsigned32,
            zxr10ospfAreaFilterAreaId
                Unsigned32,
            zxr10ospfAreaFilterAreaId1
                IpAddress,
            zxr10ospfAreaFilterDirectionIn
                INTEGER,
            zxr10ospfAreaFilterDirectionOut
                Unsigned32,
            zxr10ospfAreaFilterPrefixName
                DisplayString
        }

zxr10ospfAreaFilterProId OBJECT-TYPE
        SYNTAX Unsigned32
        MAX-ACCESS  read-only
        STATUS  current
        DESCRIPTION
            "ospf instance ID"
        ::= { zxr10ospfAreaFilterEntry 1 }

zxr10ospfAreaFilterAreaId OBJECT-TYPE
        SYNTAX Unsigned32
        MAX-ACCESS  read-only
        STATUS  current
        DESCRIPTION
            "area ID"
        ::= { zxr10ospfAreaFilterEntry 2 }

zxr10ospfAreaFilterAreaId1 OBJECT-TYPE
        SYNTAX IpAddress
        MAX-ACCESS  read-only
        STATUS  current
        DESCRIPTION
            "area ID"
        ::= { zxr10ospfAreaFilterEntry 3 }

zxr10ospfAreaFilterDirectionIn OBJECT-TYPE
        SYNTAX INTEGER {in(1),out(2)}    
        MAX-ACCESS  read-only
        STATUS  current
        DESCRIPTION
            "filter direction in or out"
        ::= { zxr10ospfAreaFilterEntry 4 }

zxr10ospfAreaFilterDirectionOut OBJECT-TYPE
        SYNTAX Unsigned32 (0..256)
        MAX-ACCESS  read-only
        STATUS  current
        DESCRIPTION
            "filter direction out,not in use now"
        ::= { zxr10ospfAreaFilterEntry 5 }

zxr10ospfAreaFilterPrefixName OBJECT-TYPE
        SYNTAX DisplayString (SIZE (1..31))
        MAX-ACCESS  read-only
        STATUS  current
        DESCRIPTION
            "prefix name of area filter"
        ::= { zxr10ospfAreaFilterEntry 6 }



zxr10areaStubhostTable OBJECT-TYPE
        SYNTAX  SEQUENCE OF Zxr10areaStubhostEntry
        MAX-ACCESS  not-accessible
        STATUS  current
        DESCRIPTION
            "An table to stub host"
        ::= { zxr10ospfAreaMIB 4 }

zxr10areaStubhostEntry OBJECT-TYPE
        SYNTAX Zxr10areaStubhostEntry
        MAX-ACCESS  not-accessible
        STATUS  current
        DESCRIPTION
            "An entry to stub host."
        INDEX  { zxr10areaStubhostProId,zxr10areaStubhostAreaId,
                 zxr10areaStubhostAreaIp,zxr10areaStubhostStubhostIpaddr }
        ::= { zxr10areaStubhostTable 1 }
            
Zxr10areaStubhostEntry ::=
        SEQUENCE {
            zxr10areaStubhostProId
                Unsigned32,
            zxr10areaStubhostAreaId
                Unsigned32,
            zxr10areaStubhostAreaIp
                IpAddress,
            zxr10areaStubhostStubhostIpaddr
                IpAddress,
            zxr10areaStubhostStubhostCots
                Unsigned32
        }

zxr10areaStubhostProId OBJECT-TYPE
        SYNTAX Unsigned32
        MAX-ACCESS  read-only
        STATUS  current
        DESCRIPTION
            "ospf instance ID"
        ::= { zxr10areaStubhostEntry 1 }

zxr10areaStubhostAreaId OBJECT-TYPE
        SYNTAX Unsigned32
        MAX-ACCESS  read-only
        STATUS  current
        DESCRIPTION
            "area ID"
        ::= { zxr10areaStubhostEntry 2 }

zxr10areaStubhostAreaIp OBJECT-TYPE
        SYNTAX IpAddress
        MAX-ACCESS  read-only
        STATUS  current
        DESCRIPTION
            "area ID"
        ::= { zxr10areaStubhostEntry 3 }

zxr10areaStubhostStubhostIpaddr OBJECT-TYPE
        SYNTAX IpAddress
        MAX-ACCESS  read-only
        STATUS  current
        DESCRIPTION
            "ip address of stub host"
        ::= { zxr10areaStubhostEntry 4 }

zxr10areaStubhostStubhostCots OBJECT-TYPE
        SYNTAX Unsigned32
        MAX-ACCESS  read-only
        STATUS  current
        DESCRIPTION
            "cost of stub host"
        ::= { zxr10areaStubhostEntry 5 }


zxr10areaVirtualMIB OBJECT IDENTIFIER ::= { zxr10ospfAreaMIB 5 }

zxr10areaVirtualTable OBJECT-TYPE
        SYNTAX  SEQUENCE OF Zxr10areaVirtualEntry
        MAX-ACCESS  not-accessible
        STATUS  current
        DESCRIPTION
            "An table to area virtual"
        ::= { zxr10areaVirtualMIB 1 }

zxr10areaVirtualEntry OBJECT-TYPE
        SYNTAX Zxr10areaVirtualEntry
        MAX-ACCESS  not-accessible
        STATUS  current
        DESCRIPTION
            "An entry to area virtual."
        INDEX  { zxr10areaVirtualProId,zxr10areaVirtualAreaId,
                 zxr10areaVirtualAreaIp,zxr10areaVirtualVirtualIpaddr }
        ::= { zxr10areaVirtualTable 1 }
            
Zxr10areaVirtualEntry ::=
        SEQUENCE {
            zxr10areaVirtualProId
                Unsigned32,
            zxr10areaVirtualAreaId
                Unsigned32,
            zxr10areaVirtualAreaIp
                IpAddress,
            zxr10areaVirtualVirtualIpaddr
                IpAddress,
            zxr10areaVirtualVirtualHellointerval
                Unsigned32,
            zxr10areaVirtualVirtualRetrainterval
                Unsigned32,
            zxr10areaVirtualVirtualTransmitdelay
                Unsigned32,
            zxr10areaVirtualVirtualDeadinterval
                Unsigned32,
            zxr10areaVirtualVirtualDeaddelay
                Unsigned32,
            zxr10areaVirtualVirtualAuthenkey
                DisplayString,
            zxr10areaVirtualAuthEncrypted
                DisplayString
        }

zxr10areaVirtualProId OBJECT-TYPE
        SYNTAX Unsigned32
        MAX-ACCESS  read-only
        STATUS  current
        DESCRIPTION
            "ospf instance ID"
        ::= { zxr10areaVirtualEntry 1 }

zxr10areaVirtualAreaId OBJECT-TYPE
        SYNTAX Unsigned32
        MAX-ACCESS  read-only
        STATUS  current
        DESCRIPTION
            "area ID"
        ::= { zxr10areaVirtualEntry 2 }

zxr10areaVirtualAreaIp OBJECT-TYPE
        SYNTAX IpAddress
        MAX-ACCESS  read-only
        STATUS  current
        DESCRIPTION
            "area ID"
        ::= { zxr10areaVirtualEntry 3 }

zxr10areaVirtualVirtualIpaddr OBJECT-TYPE
        SYNTAX IpAddress
        MAX-ACCESS  read-only
        STATUS  current
        DESCRIPTION
            "ip address of area virtual"
        ::= { zxr10areaVirtualEntry 4 }

zxr10areaVirtualVirtualHellointerval OBJECT-TYPE
        SYNTAX Unsigned32
        MAX-ACCESS  read-only
        STATUS  current
        DESCRIPTION
            "hello interval of area virtual"
        ::= { zxr10areaVirtualEntry 5 }

zxr10areaVirtualVirtualRetrainterval OBJECT-TYPE
        SYNTAX Unsigned32
        MAX-ACCESS  read-only
        STATUS  current
        DESCRIPTION
            "retransmit-interval of area virtual"
        ::= { zxr10areaVirtualEntry 6 }

zxr10areaVirtualVirtualTransmitdelay OBJECT-TYPE
        SYNTAX Unsigned32
        MAX-ACCESS  read-only
        STATUS  current
        DESCRIPTION
            "transmit-delay of area virtual"
        ::= { zxr10areaVirtualEntry 7 }

zxr10areaVirtualVirtualDeadinterval OBJECT-TYPE
        SYNTAX Unsigned32
        MAX-ACCESS  read-only
        STATUS  current
        DESCRIPTION
            "dead-interval of area virtual"
        ::= { zxr10areaVirtualEntry 8 }

zxr10areaVirtualVirtualDeaddelay OBJECT-TYPE
        SYNTAX Unsigned32
        MAX-ACCESS  read-only
        STATUS  current
        DESCRIPTION
            "dead-delay of area virtual"
        ::= { zxr10areaVirtualEntry 9 }

zxr10areaVirtualVirtualAuthenkey OBJECT-TYPE
        SYNTAX DisplayString (SIZE (1..8))
        MAX-ACCESS  read-only
        STATUS  current
        DESCRIPTION
            "authen key of area virtual"
        ::= { zxr10areaVirtualEntry 10 }

zxr10areaVirtualAuthEncrypted OBJECT-TYPE
        SYNTAX DisplayString (SIZE (24))
        MAX-ACCESS  read-only
        STATUS  current
        DESCRIPTION
            "authen encrypted of area virtual"
        ::= { zxr10areaVirtualEntry 11 }



zxr10areaVirtualMd5Table OBJECT-TYPE
        SYNTAX  SEQUENCE OF Zxr10areaVirtualMd5Entry
        MAX-ACCESS  not-accessible
        STATUS  current
        DESCRIPTION
            "An table to area virtual md5"
        ::= { zxr10areaVirtualMIB 2 }

zxr10areaVirtualMd5Entry OBJECT-TYPE
        SYNTAX Zxr10areaVirtualMd5Entry
        MAX-ACCESS  not-accessible
        STATUS  current
        DESCRIPTION
            "An entry to area virtual md5."
        INDEX  { zxr10areaVirtualMd5ProId,zxr10areaVirtualMd5AreaId,
                 zxr10areaVirtualMd5AreaIp,zxr10areaVirtualMd5IpAddr,
                 zxr10areaVirtualMd5VirtualMd5key }
        ::= { zxr10areaVirtualMd5Table 1 }
            
Zxr10areaVirtualMd5Entry ::=
        SEQUENCE {
            zxr10areaVirtualMd5ProId
                Unsigned32,
            zxr10areaVirtualMd5AreaId
                Unsigned32,
            zxr10areaVirtualMd5AreaIp
                IpAddress,
            zxr10areaVirtualMd5IpAddr
                IpAddress,
            zxr10areaVirtualMd5VirtualMd5key
                Unsigned32,
            zxr10areaVirtualMd5Pword
                DisplayString,
            zxr10areaVirtualMd5Encryptword
                DisplayString,
            zxr10areaVirtualMd5DelayTime
                Unsigned32,
            zxr10areaVirtualMd5Md5
                Unsigned32,
            zxr10areaVirtualMd5Encrypted
                DisplayString
        }

zxr10areaVirtualMd5ProId OBJECT-TYPE
        SYNTAX Unsigned32
        MAX-ACCESS  read-only
        STATUS  current
        DESCRIPTION
            "ospf instance ID"
        ::= { zxr10areaVirtualMd5Entry 1 }

zxr10areaVirtualMd5AreaId OBJECT-TYPE
        SYNTAX Unsigned32
        MAX-ACCESS  read-only
        STATUS  current
        DESCRIPTION
            "area ID"
        ::= { zxr10areaVirtualMd5Entry 2 }

zxr10areaVirtualMd5AreaIp OBJECT-TYPE
        SYNTAX IpAddress
        MAX-ACCESS  read-only
        STATUS  current
        DESCRIPTION
            "area ID"
        ::= { zxr10areaVirtualMd5Entry 3 }

zxr10areaVirtualMd5IpAddr OBJECT-TYPE
        SYNTAX IpAddress
        MAX-ACCESS  read-only
        STATUS  current
        DESCRIPTION
            "ip address of area virtual"
        ::= { zxr10areaVirtualMd5Entry 4 }

zxr10areaVirtualMd5VirtualMd5key OBJECT-TYPE
        SYNTAX Unsigned32
        MAX-ACCESS  read-only
        STATUS  current
        DESCRIPTION
            "md5 key number"
        ::= { zxr10areaVirtualMd5Entry 5 }

zxr10areaVirtualMd5Pword OBJECT-TYPE
        SYNTAX DisplayString (SIZE (1..16))
        MAX-ACCESS  read-only
        STATUS  current
        DESCRIPTION
            "md5 password"
        ::= { zxr10areaVirtualMd5Entry 6 }

zxr10areaVirtualMd5Encryptword OBJECT-TYPE
        SYNTAX DisplayString (SIZE (1..16))
        MAX-ACCESS  read-only
        STATUS  current
        DESCRIPTION
            "md5 encrypt password"
        ::= { zxr10areaVirtualMd5Entry 7 }

zxr10areaVirtualMd5DelayTime OBJECT-TYPE
        SYNTAX Unsigned32
        MAX-ACCESS  read-only
        STATUS  current
        DESCRIPTION
            "md5 delay time"
        ::= { zxr10areaVirtualMd5Entry 8 }

zxr10areaVirtualMd5Md5 OBJECT-TYPE
        SYNTAX Unsigned32 (0..256)
        MAX-ACCESS  read-only
        STATUS  current
        DESCRIPTION
            "md5"
        ::= { zxr10areaVirtualMd5Entry 9 }

zxr10areaVirtualMd5Encrypted OBJECT-TYPE
        SYNTAX DisplayString (SIZE (24))
        MAX-ACCESS  read-only
        STATUS  current
        DESCRIPTION
            "md5 encrypted"
        ::= { zxr10areaVirtualMd5Entry 10 }



zxr10areaVirtualAuthTypeTable OBJECT-TYPE
        SYNTAX  SEQUENCE OF Zxr10areaVirtualAuthTypeEntry
        MAX-ACCESS  not-accessible
        STATUS  current
        DESCRIPTION
            "An table to ospf virtual auth"
        ::= { zxr10areaVirtualMIB 3 }

zxr10areaVirtualAuthTypeEntry OBJECT-TYPE
        SYNTAX Zxr10areaVirtualAuthTypeEntry
        MAX-ACCESS  not-accessible
        STATUS  current
        DESCRIPTION
            "An entry to ospf virtual auth."
        INDEX  { zxr10areaVirtualAuthTypeProId,
                 zxr10areaVirtualAuthTypeAreaId,
                 zxr10areaVirtualAuthTypeAreaIp,
                 zxr10areaVirtualAuthTypeIpAddr,
                 zxr10areaVirtualAuthTypeAuthenSimple }
        ::= { zxr10areaVirtualAuthTypeTable 1 }
            
Zxr10areaVirtualAuthTypeEntry ::=
        SEQUENCE {
            zxr10areaVirtualAuthTypeProId
                Unsigned32,
            zxr10areaVirtualAuthTypeAreaId
                Unsigned32,
            zxr10areaVirtualAuthTypeAreaIp
                IpAddress,
            zxr10areaVirtualAuthTypeIpAddr
                IpAddress,
            zxr10areaVirtualAuthTypeAuthenSimple
                Unsigned32,
            zxr10areaVirtualAuthTypeAuthenMd5
                Unsigned32,
            zxr10areaVirtualAuthTypeAuthenNull
                Unsigned32,
            zxr10areaVirtualAuthenKeychain
                DisplayString
        }

zxr10areaVirtualAuthTypeProId OBJECT-TYPE
        SYNTAX Unsigned32
        MAX-ACCESS  read-only
        STATUS  current
        DESCRIPTION
            "instance ID"
        ::= { zxr10areaVirtualAuthTypeEntry 1 }

zxr10areaVirtualAuthTypeAreaId OBJECT-TYPE
        SYNTAX Unsigned32
        MAX-ACCESS  read-only
        STATUS  current
        DESCRIPTION
            "area ID"
        ::= { zxr10areaVirtualAuthTypeEntry 2 }

zxr10areaVirtualAuthTypeAreaIp OBJECT-TYPE
        SYNTAX IpAddress
        MAX-ACCESS  read-only
        STATUS  current
        DESCRIPTION
            "area ID"
        ::= { zxr10areaVirtualAuthTypeEntry 3 }

zxr10areaVirtualAuthTypeIpAddr OBJECT-TYPE
        SYNTAX IpAddress
        MAX-ACCESS  read-only
        STATUS  current
        DESCRIPTION
            "ip address of area virtual"
        ::= { zxr10areaVirtualAuthTypeEntry 4 }

zxr10areaVirtualAuthTypeAuthenSimple OBJECT-TYPE
        SYNTAX Unsigned32 (0..1)
        MAX-ACCESS  read-only
        STATUS  current
        DESCRIPTION
            "simple auth"
        ::= { zxr10areaVirtualAuthTypeEntry 5 }

zxr10areaVirtualAuthTypeAuthenMd5 OBJECT-TYPE
        SYNTAX Unsigned32 (0..1)
        MAX-ACCESS  read-only
        STATUS  current
        DESCRIPTION
            "md5 auth"
        ::= { zxr10areaVirtualAuthTypeEntry 6 }

zxr10areaVirtualAuthTypeAuthenNull OBJECT-TYPE
        SYNTAX Unsigned32 (0..1)
        MAX-ACCESS  read-only
        STATUS  current
        DESCRIPTION
            "null auth"
        ::= { zxr10areaVirtualAuthTypeEntry 7 }

zxr10areaVirtualAuthenKeychain OBJECT-TYPE
        SYNTAX DisplayString (SIZE (1..31))
        MAX-ACCESS  read-only
        STATUS  current
        DESCRIPTION
            "keychain name"
        ::= { zxr10areaVirtualAuthTypeEntry 8 }

zxr10areaRangTable OBJECT-TYPE
        SYNTAX  SEQUENCE OF Zxr10areaRangEntry
        MAX-ACCESS  not-accessible
        STATUS  current
        DESCRIPTION
            "An table to ospf area range"
        ::= { zxr10ospfAreaMIB 6 }

zxr10areaRangEntry OBJECT-TYPE
        SYNTAX Zxr10areaRangEntry
        MAX-ACCESS  not-accessible
        STATUS  current
        DESCRIPTION
            "An entry to ospf area range."
        INDEX  { zxr10areaRangProId,zxr10areaRangAreaId,
                 zxr10areaRangAreaIp,
                 zxr10areaRangRangIpAddr,zxr10areaRangRangNetmask,
                 zxr10areaRangRangSummaryLink }
        ::= { zxr10areaRangTable 1 }
            
Zxr10areaRangEntry ::=
        SEQUENCE {
            zxr10areaRangProId
                Unsigned32,
            zxr10areaRangAreaId
                Unsigned32,
            zxr10areaRangAreaIp
                IpAddress,
            zxr10areaRangRangIpAddr
                IpAddress,
            zxr10areaRangRangNetmask
                IpAddress,
            zxr10areaRangRangSummaryLink
                INTEGER,
            zxr10areaRangRangNssaextLink
                Unsigned32,
            zxr10areaRangRangAdvflag
                Unsigned32,
            zxr10areaRangRangCostvalue
                Unsigned32,
            zxr10areaRangRangNssatag
                Unsigned32,
            zxr10areaRangRangNssaFlag
                Unsigned32
        }

zxr10areaRangProId OBJECT-TYPE
        SYNTAX Unsigned32
        MAX-ACCESS  read-only
        STATUS  current
        DESCRIPTION
            "ospf instance ID"
        ::= { zxr10areaRangEntry 1 }

zxr10areaRangAreaId OBJECT-TYPE
        SYNTAX Unsigned32
        MAX-ACCESS  read-only
        STATUS  current
        DESCRIPTION
            "area ID"
        ::= { zxr10areaRangEntry 2 }

zxr10areaRangAreaIp OBJECT-TYPE
        SYNTAX IpAddress
        MAX-ACCESS  read-only
        STATUS  current
        DESCRIPTION
            "area ID"
        ::= { zxr10areaRangEntry 3 }

zxr10areaRangRangIpAddr OBJECT-TYPE
        SYNTAX IpAddress
        MAX-ACCESS  read-only
        STATUS  current
        DESCRIPTION
            "ip address of area range"
        ::= { zxr10areaRangEntry 4 }

zxr10areaRangRangNetmask OBJECT-TYPE
        SYNTAX IpAddress
        MAX-ACCESS  read-only
        STATUS  current
        DESCRIPTION
            "mask of area range"
        ::= { zxr10areaRangEntry 5 }

zxr10areaRangRangSummaryLink OBJECT-TYPE
        SYNTAX INTEGER {summarylink(1),nssaexternallink(2)}
        MAX-ACCESS  read-only
        STATUS  current
        DESCRIPTION
            "type-3 area range"
        ::= { zxr10areaRangEntry 6 }

zxr10areaRangRangNssaextLink OBJECT-TYPE
        SYNTAX Unsigned32 (0..2)
        MAX-ACCESS  read-only
        STATUS  current
        DESCRIPTION
            "type-7 area range"
        ::= { zxr10areaRangEntry 7 }

zxr10areaRangRangAdvflag OBJECT-TYPE
        SYNTAX Unsigned32
        MAX-ACCESS  read-only
        STATUS  current
        DESCRIPTION
            "adverflag"
        ::= { zxr10areaRangEntry 8 }

zxr10areaRangRangCostvalue OBJECT-TYPE
        SYNTAX Unsigned32
        MAX-ACCESS  read-only
        STATUS  current
        DESCRIPTION
            "cost value of area range"
        ::= { zxr10areaRangEntry 9 }

zxr10areaRangRangNssatag OBJECT-TYPE
        SYNTAX Unsigned32
        MAX-ACCESS  read-only
        STATUS  current
        DESCRIPTION
            "tag of area range"
        ::= { zxr10areaRangEntry 10 }

zxr10areaRangRangNssaFlag OBJECT-TYPE
        SYNTAX Unsigned32 (0..1)
        MAX-ACCESS  read-only
        STATUS  deprecated
        DESCRIPTION
            "nssa flag of area range, this node is no longer in use"
        ::= { zxr10areaRangEntry 11 }



zxr10areaAuthenTable OBJECT-TYPE
        SYNTAX  SEQUENCE OF Zxr10areaAuthenEntry
        MAX-ACCESS  not-accessible
        STATUS  obsolete
        DESCRIPTION
            "An table to area auth"
        ::= { zxr10ospfAreaMIB 7 }

zxr10areaAuthenEntry OBJECT-TYPE
        SYNTAX Zxr10areaAuthenEntry
        MAX-ACCESS  not-accessible
        STATUS  obsolete
        DESCRIPTION
            "An entry to area auth."
        INDEX  { zxr10areaAuthenAreaId,zxr10areaAuthenProId,
                 zxr10areaAuthenAreaId1 }
        ::= { zxr10areaAuthenTable 1 }
            
Zxr10areaAuthenEntry ::=
        SEQUENCE {
            zxr10areaAuthenAreaId
                Unsigned32,
            zxr10areaAuthenProId
                Unsigned32,
            zxr10areaAuthenAreaId1
                IpAddress,
            zxr10areaAuthenSimpleAuthen
                Unsigned32,
            zxr10areaAuthenMd5
                Unsigned32
        }

zxr10areaAuthenAreaId OBJECT-TYPE
        SYNTAX Unsigned32
        MAX-ACCESS  read-only
        STATUS  obsolete
        DESCRIPTION
            "area ID"
        ::= { zxr10areaAuthenEntry 1 }

zxr10areaAuthenProId OBJECT-TYPE
        SYNTAX Unsigned32
        MAX-ACCESS  read-only
        STATUS  obsolete
        DESCRIPTION
            "ospf instance ID"
        ::= { zxr10areaAuthenEntry 2 }

zxr10areaAuthenAreaId1 OBJECT-TYPE
        SYNTAX IpAddress
        MAX-ACCESS  read-only
        STATUS  obsolete
        DESCRIPTION
            "area ID"
        ::= { zxr10areaAuthenEntry 3 }

zxr10areaAuthenSimpleAuthen OBJECT-TYPE
        SYNTAX Unsigned32 (0..256)
        MAX-ACCESS  read-only
        STATUS  obsolete
        DESCRIPTION
            "simple auth"
        ::= { zxr10areaAuthenEntry 4 }

zxr10areaAuthenMd5 OBJECT-TYPE
        SYNTAX Unsigned32 (0..256)
        MAX-ACCESS  read-only
        STATUS  obsolete
        DESCRIPTION
            "md5 auth"
        ::= { zxr10areaAuthenEntry 5 }
        

zxr10areaShamlinkTable OBJECT-TYPE
        SYNTAX  SEQUENCE OF Zxr10areaShamlinkEntry
        MAX-ACCESS  not-accessible
        STATUS  current
        DESCRIPTION
            "An table to shamlink"
        ::= { zxr10ospfAreaMIB 8 }

zxr10areaShamlinkEntry OBJECT-TYPE
        SYNTAX Zxr10areaShamlinkEntry
        MAX-ACCESS  not-accessible
        STATUS  current
        DESCRIPTION
            "An entry to shamlink."
        INDEX  { zxr10areaShamlinkProId,zxr10areaShamlinkAreaId,
                 zxr10areaShamlinkAreaIp,
                 zxr10areaShamlinkShamlinkSrcIpaddr,
                 zxr10areaShamlinkShamlinkDestIpaddr }
        ::= { zxr10areaShamlinkTable 1 }
            
Zxr10areaShamlinkEntry ::=
        SEQUENCE {
            zxr10areaShamlinkProId
                Unsigned32,
            zxr10areaShamlinkAreaId
                Unsigned32,
            zxr10areaShamlinkAreaIp
                IpAddress,
            zxr10areaShamlinkShamlinkSrcIpaddr
                IpAddress,
            zxr10areaShamlinkShamlinkDestIpaddr
                IpAddress,
            zxr10areaShamlinkShamlinkCost
                Unsigned32
        }

zxr10areaShamlinkProId OBJECT-TYPE
        SYNTAX Unsigned32
        MAX-ACCESS  read-only
        STATUS  current
        DESCRIPTION
            "ospf instance ID"
        ::= { zxr10areaShamlinkEntry 1 }

zxr10areaShamlinkAreaId OBJECT-TYPE
        SYNTAX Unsigned32
        MAX-ACCESS  read-only
        STATUS  current
        DESCRIPTION
            "area ID"
        ::= { zxr10areaShamlinkEntry 2 }

zxr10areaShamlinkAreaIp OBJECT-TYPE
        SYNTAX IpAddress
        MAX-ACCESS  read-only
        STATUS  current
        DESCRIPTION
            "area ID"
        ::= { zxr10areaShamlinkEntry 3 }

zxr10areaShamlinkShamlinkSrcIpaddr OBJECT-TYPE
        SYNTAX IpAddress
        MAX-ACCESS  read-only
        STATUS  current
        DESCRIPTION
            "source ip address of shamlink"
        ::= { zxr10areaShamlinkEntry 4 }

zxr10areaShamlinkShamlinkDestIpaddr OBJECT-TYPE
        SYNTAX IpAddress
        MAX-ACCESS  read-only
        STATUS  current
        DESCRIPTION
            "dest ip address of shamlink"
        ::= { zxr10areaShamlinkEntry 5 }

zxr10areaShamlinkShamlinkCost OBJECT-TYPE
        SYNTAX Unsigned32
        MAX-ACCESS  read-only
        STATUS  current
        DESCRIPTION
            "cost of shamlink"
        ::= { zxr10areaShamlinkEntry 6 }



zxr10areaStubTable OBJECT-TYPE
        SYNTAX  SEQUENCE OF Zxr10areaStubEntry
        MAX-ACCESS  not-accessible
        STATUS  current
        DESCRIPTION
            "An table to stub area"
        ::= { zxr10ospfAreaMIB 9 }

zxr10areaStubEntry OBJECT-TYPE
        SYNTAX Zxr10areaStubEntry
        MAX-ACCESS  not-accessible
        STATUS  current
        DESCRIPTION
            "An entry to stub area."
        INDEX  { zxr10areaStubAreaId,zxr10areaStubProId,
                 zxr10areaStubAreaIp }
        ::= { zxr10areaStubTable 1 }
            
Zxr10areaStubEntry ::=
        SEQUENCE {
            zxr10areaStubProId
                Unsigned32,
            zxr10areaStubAreaId
                Unsigned32,
            zxr10areaStubAreaIp
                IpAddress,
            zxr10areaStubStubNosummary
                Unsigned32,
            zxr10areaStubStubDefaultcost
                Unsigned32,
            zxr10areaStubDefaultOrigin
                Unsigned32
        }

zxr10areaStubProId OBJECT-TYPE
        SYNTAX Unsigned32
        MAX-ACCESS  read-only
        STATUS  current
        DESCRIPTION
            "ospf instance ID"
        ::= { zxr10areaStubEntry 1 }

zxr10areaStubAreaId OBJECT-TYPE
        SYNTAX Unsigned32
        MAX-ACCESS  read-only
        STATUS  current
        DESCRIPTION
            "area ID"
        ::= { zxr10areaStubEntry 2 }

zxr10areaStubAreaIp OBJECT-TYPE
        SYNTAX IpAddress
        MAX-ACCESS  read-only
        STATUS  current
        DESCRIPTION
            "area ID"
        ::= { zxr10areaStubEntry 3 }


zxr10areaStubStubNosummary OBJECT-TYPE
        SYNTAX Unsigned32 (1..2)
        MAX-ACCESS  read-only
        STATUS  current
        DESCRIPTION
            "no summary"
        ::= { zxr10areaStubEntry 5 }

zxr10areaStubStubDefaultcost OBJECT-TYPE
        SYNTAX Unsigned32
        MAX-ACCESS  read-only
        STATUS  current
        DESCRIPTION
            "default cost of stub area"
        ::= { zxr10areaStubEntry 6 }

zxr10areaStubDefaultOrigin OBJECT-TYPE
        SYNTAX Unsigned32
        MAX-ACCESS  read-only
        STATUS  current
        DESCRIPTION
            "origin default route"
        ::= { zxr10areaStubEntry 7 }

zxr10areaNssaTable OBJECT-TYPE
        SYNTAX  SEQUENCE OF Zxr10areaNssaEntry
        MAX-ACCESS  not-accessible
        STATUS  current
        DESCRIPTION
            "An table to ospf nssa area "
        ::= { zxr10ospfAreaMIB 10 }

zxr10areaNssaEntry OBJECT-TYPE
        SYNTAX Zxr10areaNssaEntry
        MAX-ACCESS  not-accessible
        STATUS  current
        DESCRIPTION
            "An entry to ospf nssa area."
        INDEX  { zxr10areaNssaAreaId,zxr10areaNssaProId,zxr10areaNssaAreaIp }
        ::= { zxr10areaNssaTable 1 }
            
Zxr10areaNssaEntry ::=
        SEQUENCE {
            zxr10areaNssaProId
                Unsigned32,
            zxr10areaNssaAreaId
                Unsigned32,
            zxr10areaNssaAreaIp
                IpAddress,
            zxr10areaNssaNssaDefaultImOn
                Unsigned32,
            zxr10areaNssaNssaMetric
                Unsigned32,
            zxr10areaNssaNssaMetricType
                Unsigned32,
            zxr10areaNssaNssaTranslatorRole
                Unsigned32,
            zxr10areaNssaNssaTransStabIntv
                Unsigned32,
            zxr10areaNssaNssaNoSummary
                Unsigned32,
            zxr10areaNssaNssaNoRedistribution
                Unsigned32,
            zxr10areaNssaNssaTranst7SuppFa
                Unsigned32
        }

zxr10areaNssaProId OBJECT-TYPE
        SYNTAX Unsigned32
        MAX-ACCESS  read-only
        STATUS  current
        DESCRIPTION
            "ospf instance ID"
        ::= { zxr10areaNssaEntry 1 }

zxr10areaNssaAreaId OBJECT-TYPE
        SYNTAX Unsigned32
        MAX-ACCESS  read-only
        STATUS  current
        DESCRIPTION
            "area ID"
        ::= { zxr10areaNssaEntry 2 }

zxr10areaNssaAreaIp OBJECT-TYPE
        SYNTAX IpAddress
        MAX-ACCESS  read-only
        STATUS  current
        DESCRIPTION
            "area ID"
        ::= { zxr10areaNssaEntry 3 }


zxr10areaNssaNssaDefaultImOn OBJECT-TYPE
        SYNTAX Unsigned32 (0..256)
        MAX-ACCESS  read-only
        STATUS  current
        DESCRIPTION
            "type 7 default"
        ::= { zxr10areaNssaEntry 5 }

zxr10areaNssaNssaMetric OBJECT-TYPE
        SYNTAX Unsigned32
        MAX-ACCESS  read-only
        STATUS  current
        DESCRIPTION
            "metric"
        ::= { zxr10areaNssaEntry 6 }

zxr10areaNssaNssaMetricType OBJECT-TYPE
        SYNTAX Unsigned32
        MAX-ACCESS  read-only
        STATUS  current
        DESCRIPTION
            "type"
        ::= { zxr10areaNssaEntry 7 }

zxr10areaNssaNssaTranslatorRole OBJECT-TYPE
        SYNTAX Unsigned32 (0..1)
        MAX-ACCESS  read-only
        STATUS  current
        DESCRIPTION
            "translator role"
        ::= { zxr10areaNssaEntry 8 }

zxr10areaNssaNssaTransStabIntv OBJECT-TYPE
        SYNTAX Unsigned32
        MAX-ACCESS  read-only
        STATUS  current
        DESCRIPTION
            "translator stability interval"
        ::= { zxr10areaNssaEntry 9 }

zxr10areaNssaNssaNoSummary OBJECT-TYPE
        SYNTAX Unsigned32 (1..2)
        MAX-ACCESS  read-only
        STATUS  current
        DESCRIPTION
            "no summary"
        ::= { zxr10areaNssaEntry 10 }

zxr10areaNssaNssaNoRedistribution OBJECT-TYPE
        SYNTAX Unsigned32 (1..2)
        MAX-ACCESS  read-only
        STATUS  current
        DESCRIPTION
            "no redistribute"
        ::= { zxr10areaNssaEntry 11 }

zxr10areaNssaNssaTranst7SuppFa OBJECT-TYPE
        SYNTAX Unsigned32 (1..2)
        MAX-ACCESS  read-only
        STATUS  current
        DESCRIPTION
            "support forwarding address"
        ::= { zxr10areaNssaEntry 12 }

zxr10ospfv2AreaTable OBJECT-TYPE
        SYNTAX  SEQUENCE OF Zxr10ospfv2AreaEntry
        MAX-ACCESS  not-accessible
        STATUS  current
        DESCRIPTION
            "An table to area"
        ::= { zxr10ospfAreaMIB 11 }

zxr10ospfv2AreaEntry OBJECT-TYPE
        SYNTAX Zxr10ospfv2AreaEntry
        MAX-ACCESS  not-accessible
        STATUS  current
        DESCRIPTION
            "An entry to area."
        INDEX  { zxr10ospfv2AreaProId,zxr10ospfv2AreaAreaId,
                 zxr10ospfv2AreaAreaId1 }
        ::= { zxr10ospfv2AreaTable 1 }
            
Zxr10ospfv2AreaEntry ::=
        SEQUENCE {
            zxr10ospfv2AreaProId
                Unsigned32,
            zxr10ospfv2AreaAreaId
                Unsigned32,
            zxr10ospfv2AreaAreaId1
                IpAddress
        }

zxr10ospfv2AreaProId OBJECT-TYPE
        SYNTAX Unsigned32
        MAX-ACCESS  not-accessible
        STATUS  current
        DESCRIPTION
            "ospf instance ID"
        ::= { zxr10ospfv2AreaEntry 1 }
        
zxr10ospfv2AreaAreaId OBJECT-TYPE
        SYNTAX Unsigned32
        MAX-ACCESS  not-accessible
        STATUS  current
        DESCRIPTION
            "area ID"
        ::= { zxr10ospfv2AreaEntry 2 }

zxr10ospfv2AreaAreaId1 OBJECT-TYPE
        SYNTAX IpAddress
        MAX-ACCESS  read-only
        STATUS  current
        DESCRIPTION
            "area ID"
        ::= { zxr10ospfv2AreaEntry 3 }
        
zxr10ospfv2TeAreaTable OBJECT-TYPE
        SYNTAX  SEQUENCE OF Zxr10ospfv2TeAreaEntry
        MAX-ACCESS  not-accessible
        STATUS  current
        DESCRIPTION
            "An table to MPLS traffic engineering area"
        ::= { zxr10ospfAreaMIB 12 }

zxr10ospfv2TeAreaEntry OBJECT-TYPE
        SYNTAX Zxr10ospfv2TeAreaEntry
        MAX-ACCESS  not-accessible
        STATUS  current
        DESCRIPTION
            "An entry to MPLS traffic engineering area."
        INDEX  { zxr10ospfv2TeAreaProId,zxr10ospfv2TeAreaAreaId,
                 zxr10ospfv2TeAreaAreaIp }
        ::= { zxr10ospfv2TeAreaTable 1 }
            
Zxr10ospfv2TeAreaEntry ::=
        SEQUENCE {
            zxr10ospfv2TeAreaProId
                Unsigned32,
            zxr10ospfv2TeAreaAreaId
                Unsigned32,
            zxr10ospfv2TeAreaAreaIp
                IpAddress
        }

zxr10ospfv2TeAreaProId OBJECT-TYPE
        SYNTAX Unsigned32
        MAX-ACCESS  not-accessible
        STATUS  current
        DESCRIPTION
            " instance ID"
        ::= { zxr10ospfv2TeAreaEntry 1 }
        
zxr10ospfv2TeAreaAreaId OBJECT-TYPE
        SYNTAX Unsigned32
        MAX-ACCESS  not-accessible
        STATUS  current
        DESCRIPTION
            "area ID"
        ::= { zxr10ospfv2TeAreaEntry 2 }

zxr10ospfv2TeAreaAreaIp OBJECT-TYPE
        SYNTAX IpAddress
        MAX-ACCESS  read-only
        STATUS  current
        DESCRIPTION
            "area ID"
        ::= { zxr10ospfv2TeAreaEntry 3 }

zxr10ospfv2areaAuthenTable OBJECT-TYPE
        SYNTAX  SEQUENCE OF Zxr10ospfv2areaAuthenEntry
        MAX-ACCESS  not-accessible
        STATUS  current
        DESCRIPTION
            "An table to area auth"
        ::= { zxr10ospfAreaMIB 13 }

zxr10ospfv2areaAuthenEntry OBJECT-TYPE
        SYNTAX Zxr10ospfv2areaAuthenEntry
        MAX-ACCESS  not-accessible
        STATUS  current
        DESCRIPTION
            "An entry to area auth."
        INDEX  { zxr10ospfv2areaAuthenProId,zxr10ospfv2areaAuthenAreaId,
                 zxr10ospfv2areaAuthenAreaId1 }
        ::= { zxr10ospfv2areaAuthenTable 1 }
            
Zxr10ospfv2areaAuthenEntry ::=
        SEQUENCE {
            zxr10ospfv2areaAuthenProId
                Unsigned32,
            zxr10ospfv2areaAuthenAreaId
                Unsigned32,
            zxr10ospfv2areaAuthenAreaId1
                IpAddress,
            zxr10ospfv2areaAuthenSimple
                Unsigned32,
            zxr10ospfv2areaAuthenMd5
                Unsigned32,
            zxr10ospfv2areaAuthenKeychain
                DisplayString
        }

zxr10ospfv2areaAuthenProId OBJECT-TYPE
        SYNTAX Unsigned32
        MAX-ACCESS  not-accessible
        STATUS  current
        DESCRIPTION
            "ospf instance ID"
        ::= { zxr10ospfv2areaAuthenEntry 1 }
        
zxr10ospfv2areaAuthenAreaId OBJECT-TYPE
        SYNTAX Unsigned32
        MAX-ACCESS  not-accessible
        STATUS  current
        DESCRIPTION
            "area ID"
        ::= { zxr10ospfv2areaAuthenEntry 2 }

zxr10ospfv2areaAuthenAreaId1 OBJECT-TYPE
        SYNTAX IpAddress
        MAX-ACCESS  not-accessible
        STATUS  current
        DESCRIPTION
            "area ID"
        ::= { zxr10ospfv2areaAuthenEntry 3 }

zxr10ospfv2areaAuthenSimple OBJECT-TYPE
        SYNTAX Unsigned32 (0..256)
        MAX-ACCESS  read-only
        STATUS  current
        DESCRIPTION
            "simple auth"
        ::= { zxr10ospfv2areaAuthenEntry 4 }

zxr10ospfv2areaAuthenMd5 OBJECT-TYPE
        SYNTAX Unsigned32 (0..256)
        MAX-ACCESS  read-only
        STATUS  current
        DESCRIPTION
            "md5 auth"
        ::= { zxr10ospfv2areaAuthenEntry 5 }

zxr10ospfv2areaAuthenKeychain OBJECT-TYPE
        SYNTAX DisplayString (SIZE (1..31))
        MAX-ACCESS  read-only
        STATUS  current
        DESCRIPTION
            "keychain name"
        ::= { zxr10ospfv2areaAuthenEntry 6 }

zxr10areaLdpIgpSyncTable OBJECT-TYPE
        SYNTAX  SEQUENCE OF Zxr10areaLdpIgpSyncEntry
        MAX-ACCESS  not-accessible
        STATUS  current
        DESCRIPTION
            "An table to area ldp igp sync"
        ::= { zxr10ospfAreaMIB 14 }

zxr10areaLdpIgpSyncEntry OBJECT-TYPE
        SYNTAX Zxr10areaLdpIgpSyncEntry
        MAX-ACCESS  not-accessible
        STATUS  current
        DESCRIPTION
            "An entry to area ldp igp sync"
        INDEX  { zxr10areaLdpIgpSyncProId,zxr10areaLdpIgpSyncAreaId,
                 zxr10areaLdpIgpSyncAreaIp }
        ::= { zxr10areaLdpIgpSyncTable 1 }

Zxr10areaLdpIgpSyncEntry ::=
        SEQUENCE {
            zxr10areaLdpIgpSyncProId
                Unsigned32,
            zxr10areaLdpIgpSyncAreaId
                Unsigned32,
            zxr10areaLdpIgpSyncAreaIp
                IpAddress,
            zxr10areaLdpIgpSyncStatus
                Unsigned32
        }

zxr10areaLdpIgpSyncProId OBJECT-TYPE
        SYNTAX Unsigned32
        MAX-ACCESS  not-accessible
        STATUS  current
        DESCRIPTION
            "ospf instance ID"
        ::= { zxr10areaLdpIgpSyncEntry 1 }

zxr10areaLdpIgpSyncAreaId OBJECT-TYPE
        SYNTAX Unsigned32
        MAX-ACCESS  not-accessible
        STATUS  current
        DESCRIPTION
            "area ID"
        ::= { zxr10areaLdpIgpSyncEntry 2 }

zxr10areaLdpIgpSyncAreaIp OBJECT-TYPE
        SYNTAX IpAddress
        MAX-ACCESS  not-accessible
        STATUS  current
        DESCRIPTION
            "area ID"
        ::= { zxr10areaLdpIgpSyncEntry 3 }

zxr10areaLdpIgpSyncStatus OBJECT-TYPE
        SYNTAX Unsigned32
        MAX-ACCESS  read-only
        STATUS  current
        DESCRIPTION
            "area ldp igp sync status"
        ::= { zxr10areaLdpIgpSyncEntry 4 }



zxr10areaLdpAutoConfigTable OBJECT-TYPE
        SYNTAX  SEQUENCE OF Zxr10areaLdpAutoConfigEntry
        MAX-ACCESS  not-accessible
        STATUS  current
        DESCRIPTION
            "An table to area ldp auto-config"
        ::= { zxr10ospfAreaMIB 15 }

zxr10areaLdpAutoConfigEntry OBJECT-TYPE
        SYNTAX Zxr10areaLdpAutoConfigEntry
        MAX-ACCESS  not-accessible
        STATUS  current
        DESCRIPTION
            "An entry to area ldp auto-config"
        INDEX  { zxr10areaLdpAutoConfigProId,zxr10areaLdpAutoConfigAreaId,
                 zxr10areaLdpAutoConfigAreaIp }
        ::= { zxr10areaLdpAutoConfigTable 1 }

Zxr10areaLdpAutoConfigEntry ::=
        SEQUENCE {
            zxr10areaLdpAutoConfigProId
                Unsigned32,
            zxr10areaLdpAutoConfigAreaId
                Unsigned32,
            zxr10areaLdpAutoConfigAreaIp
                IpAddress,
            zxr10areaLdpAutoConfigStatus
                Unsigned32
        }

zxr10areaLdpAutoConfigProId OBJECT-TYPE
        SYNTAX Unsigned32
        MAX-ACCESS  not-accessible
        STATUS  current
        DESCRIPTION
            "ospf instance ID"
        ::= { zxr10areaLdpAutoConfigEntry 1 }

zxr10areaLdpAutoConfigAreaId OBJECT-TYPE
        SYNTAX Unsigned32
        MAX-ACCESS  not-accessible
        STATUS  current
        DESCRIPTION
            "area ID"
        ::= { zxr10areaLdpAutoConfigEntry 2 }

zxr10areaLdpAutoConfigAreaIp OBJECT-TYPE
        SYNTAX IpAddress
        MAX-ACCESS  not-accessible
        STATUS  current
        DESCRIPTION
            "area ID"
        ::= { zxr10areaLdpAutoConfigEntry 3 }

zxr10areaLdpAutoConfigStatus OBJECT-TYPE
        SYNTAX Unsigned32 {enable(1),disable(2),noconfig(3)}  
        MAX-ACCESS  read-only
        STATUS  current
        DESCRIPTION
            "area ldp igp sync status"
        ::= { zxr10areaLdpAutoConfigEntry 4 }

zxr10AreaIfTable OBJECT-TYPE
        SYNTAX  SEQUENCE OF Zxr10AreaIfEntry
        MAX-ACCESS  not-accessible
        STATUS  current
        DESCRIPTION
            "An table to area interface"
        ::= { zxr10ospfAreaMIB 16 }

zxr10AreaIfEntry OBJECT-TYPE
        SYNTAX Zxr10AreaIfEntry
        MAX-ACCESS  not-accessible
        STATUS  current
        DESCRIPTION
            "An entry to area interface."
        INDEX  { zxr10AreaIfProId,
                 zxr10AreaIfName }
        ::= { zxr10AreaIfTable 1 }
            
Zxr10AreaIfEntry ::=
        SEQUENCE {
            zxr10AreaIfProId
                Unsigned32,
            zxr10AreaIfName
                DisplayString,
            zxr10AreaIfAreaId
                Unsigned32,
            zxr10AreaIfAreaIp
                Unsigned32,
            zxr10AreaIfAuthKey
                DisplayString,
            zxr10AreaIfCost
                Unsigned32,
            zxr10AreaIfDeadInterval
                Unsigned32,
            zxr10AreaIfHelloInterval
                Unsigned32,
            zxr10AreaIfMtuIgnore
                Unsigned32,
            zxr10AreaIfPriority
                Unsigned32,
            zxr10AreaIfResyncTimeout
                Unsigned32,
            zxr10AreaIfRetransmitInterval
                Unsigned32,
            zxr10AreaIfTransmitDelay
                Unsigned32,
            zxr10AreaIfTtlSecurity
                INTEGER,
            zxr10AreaIfLdpIgpSync
                Unsigned32,
            zxr10AreaIfLdpAutoConfig
                Unsigned32,
            zxr10AreaIfAuthEncrypted
                DisplayString,
            zxr10AreaIfSDCost
                INTEGER,
            zxr10AreaIfdampingCostAdjustType
                INTEGER,
            zxr10AreaIfdampingCostIncrease
                Unsigned32,
            zxr10AreaIfdampingTime
                Unsigned32                                                    
        }

zxr10AreaIfProId OBJECT-TYPE
        SYNTAX Unsigned32
        MAX-ACCESS  not-accessible
        STATUS  current
        DESCRIPTION
            "ospf instance ID"
        ::= { zxr10AreaIfEntry 1 }
        
zxr10AreaIfName OBJECT-TYPE
        SYNTAX DisplayString (SIZE (1..31))
        MAX-ACCESS  not-accessible
        STATUS  current
        DESCRIPTION
            "interface name"
        ::= { zxr10AreaIfEntry 2 }


zxr10AreaIfAreaId OBJECT-TYPE
        SYNTAX Unsigned32
        MAX-ACCESS  read-only
        STATUS  current
        DESCRIPTION
            "area ID"
        ::= { zxr10AreaIfEntry 3 }

zxr10AreaIfAreaIp OBJECT-TYPE
        SYNTAX Unsigned32
        MAX-ACCESS  read-only
        STATUS  current
        DESCRIPTION
            "area IP"
        ::= { zxr10AreaIfEntry 4 }

zxr10AreaIfAuthKey OBJECT-TYPE
        SYNTAX DisplayString (SIZE (1..8))
        MAX-ACCESS  read-only
        STATUS  current
        DESCRIPTION
            "simple auth key"
        ::= { zxr10AreaIfEntry 5 }

zxr10AreaIfCost OBJECT-TYPE
        SYNTAX Unsigned32
        MAX-ACCESS  read-only
        STATUS  current
        DESCRIPTION
            "cost of interface"
        ::= { zxr10AreaIfEntry 6 }

zxr10AreaIfDeadInterval OBJECT-TYPE
        SYNTAX Unsigned32
        MAX-ACCESS  read-only
        STATUS  current
        DESCRIPTION
            "dead-interval of interface"
        ::= { zxr10AreaIfEntry 7 }

zxr10AreaIfHelloInterval OBJECT-TYPE
        SYNTAX Unsigned32
        MAX-ACCESS  read-only
        STATUS  current
        DESCRIPTION
            "hello-interval of interface"
        ::= { zxr10AreaIfEntry 8 }

zxr10AreaIfMtuIgnore OBJECT-TYPE
        SYNTAX Unsigned32 (0..256)
        MAX-ACCESS  read-only
        STATUS  current
        DESCRIPTION
            "ignore mtu of interface"
        ::= { zxr10AreaIfEntry 9 }

zxr10AreaIfPriority OBJECT-TYPE
        SYNTAX Unsigned32 (0..255)
        MAX-ACCESS  read-only
        STATUS  current
        DESCRIPTION
            "priority of interface"
        ::= { zxr10AreaIfEntry 10 }

zxr10AreaIfResyncTimeout OBJECT-TYPE
        SYNTAX Unsigned32
        MAX-ACCESS  read-only
        STATUS  current
        DESCRIPTION
            "resync interval after which adjacency is reset 
             if oob-resync is not started"
        ::= { zxr10AreaIfEntry 11 }

zxr10AreaIfRetransmitInterval OBJECT-TYPE
        SYNTAX Unsigned32
        MAX-ACCESS  read-only
        STATUS  current
        DESCRIPTION
            "retransmit-interval of interface"
        ::= { zxr10AreaIfEntry 12 }

zxr10AreaIfTransmitDelay OBJECT-TYPE
        SYNTAX Unsigned32
        MAX-ACCESS  read-only
        STATUS  current
        DESCRIPTION
            "transmit-delay of interface"
        ::= { zxr10AreaIfEntry 13 }

zxr10AreaIfTtlSecurity OBJECT-TYPE
        SYNTAX INTEGER (1..254)
        MAX-ACCESS  read-only
        STATUS  current
        DESCRIPTION
            "ttl_security"
        ::= { zxr10AreaIfEntry 14 }

zxr10AreaIfLdpIgpSync OBJECT-TYPE
        SYNTAX Unsigned32 (0..2)
        MAX-ACCESS  read-only
        STATUS  current
        DESCRIPTION
            "ospf If ldp igp sync"
        ::= { zxr10AreaIfEntry 15 }

zxr10AreaIfLdpAutoConfig OBJECT-TYPE
        SYNTAX Unsigned32 (0..2)
        MAX-ACCESS  read-only
        STATUS  current
        DESCRIPTION
            "ospf If ldp auto-config"
        ::= { zxr10AreaIfEntry 16 }

zxr10AreaIfAuthEncrypted OBJECT-TYPE
        SYNTAX DisplayString (SIZE (24))
        MAX-ACCESS  read-only
        STATUS  current
        DESCRIPTION
            "ospf If auth encrypted"
        ::= { zxr10AreaIfEntry 17 }

zxr10AreaIfSDCost OBJECT-TYPE
        SYNTAX INTEGER
            {
                maximum(65535)
            }
        MAX-ACCESS  read-only
        STATUS  current
        DESCRIPTION
            "Interface cost when link is in SD status"
        ::= { zxr10AreaIfEntry 18 }

zxr10AreaIfdampingCostAdjustType OBJECT-TYPE
        SYNTAX INTEGER {increase(1),maximum(2),noconfig(3)}  
        MAX-ACCESS  read-only
        STATUS  current
        DESCRIPTION
            "Interface cost adjust type when link is in damping status"
        ::= { zxr10AreaIfEntry 19 }

zxr10AreaIfdampingCostIncrease OBJECT-TYPE
        SYNTAX Unsigned32 (100..10000)
        MAX-ACCESS  read-only
        STATUS  current
        DESCRIPTION
            "Interface increase cost when link is damping"
        ::= { zxr10AreaIfEntry 20 }
        
zxr10AreaIfdampingTime OBJECT-TYPE
        SYNTAX Unsigned32 (1..3600000)
        MAX-ACCESS  read-only
        STATUS  current
        DESCRIPTION
            "Interface damping time(millisecond)"
        ::= { zxr10AreaIfEntry 21 }        
        
zxr10AreaIfBfdTable OBJECT-TYPE
        SYNTAX  SEQUENCE OF Zxr10AreaIfBfdEntry
        MAX-ACCESS  not-accessible
        STATUS  current
        DESCRIPTION
            "An table to interface BFD"
        ::= { zxr10ospfAreaMIB 17 }

zxr10AreaIfBfdEntry OBJECT-TYPE
        SYNTAX Zxr10AreaIfBfdEntry
        MAX-ACCESS  not-accessible
        STATUS  current
        DESCRIPTION
            "An entry to interface BFD."
        INDEX  { zxr10AreaIfBfdProId,
                 zxr10AreaIfBfdIfName }
        ::= { zxr10AreaIfBfdTable 1 }
            
Zxr10AreaIfBfdEntry ::=
        SEQUENCE {
            zxr10AreaIfBfdProId
                Unsigned32,
            zxr10AreaIfBfdIfName
                DisplayString,
            zxr10AreaIfBfdAreaId
                Unsigned32,
            zxr10AreaIfBfdAreaIp
                Unsigned32,
            zxr10AreaIfBfdDisable
                Unsigned32,
            zxr10AreaIfBfdInterval
                Unsigned32,
            zxr10AreaIfBfdMinRx
                Unsigned32,
            zxr10AreaIfBfdMultiplier
                Unsigned32
        }

zxr10AreaIfBfdProId OBJECT-TYPE
        SYNTAX Unsigned32
        MAX-ACCESS  not-accessible
        STATUS  current
        DESCRIPTION
            "ospf instance ID"
        ::= { zxr10AreaIfBfdEntry 1 }
        
zxr10AreaIfBfdIfName OBJECT-TYPE
        SYNTAX DisplayString (SIZE (1..31))
        MAX-ACCESS  not-accessible
        STATUS  current
        DESCRIPTION
            "interface name"
        ::= { zxr10AreaIfBfdEntry 2 }

zxr10AreaIfBfdAreaId OBJECT-TYPE
        SYNTAX Unsigned32
        MAX-ACCESS  read-only
        STATUS  current
        DESCRIPTION
            "area ID"
        ::= { zxr10AreaIfBfdEntry 3 }

zxr10AreaIfBfdAreaIp OBJECT-TYPE
        SYNTAX Unsigned32
        MAX-ACCESS  read-only
        STATUS  current
        DESCRIPTION
            "area IP"
        ::= { zxr10AreaIfBfdEntry 4 }

zxr10AreaIfBfdDisable OBJECT-TYPE
        SYNTAX Unsigned32 (0..256)
        MAX-ACCESS  read-only
        STATUS  current
        DESCRIPTION
            "disable interface BFD"
        ::= { zxr10AreaIfBfdEntry 5 }
        
zxr10AreaIfBfdInterval OBJECT-TYPE
        SYNTAX Unsigned32 (10..990)
        MAX-ACCESS  read-only
        STATUS  current
        DESCRIPTION
            "interface BFD interval"
        ::= { zxr10AreaIfBfdEntry 6 }

zxr10AreaIfBfdMinRx OBJECT-TYPE
        SYNTAX Unsigned32 (10..990)
        MAX-ACCESS  read-only
        STATUS  current
        DESCRIPTION
            "interface BFD min_rx"
        ::= { zxr10AreaIfBfdEntry 7 }

zxr10AreaIfBfdMultiplier OBJECT-TYPE
        SYNTAX Unsigned32 (3..50)
        MAX-ACCESS  read-only
        STATUS  current
        DESCRIPTION
            "interface BFD"
        ::= { zxr10AreaIfBfdEntry 8 }



zxr10AreaIfAuthTypeTable OBJECT-TYPE
        SYNTAX  SEQUENCE OF Zxr10AreaIfAuthTypeEntry
        MAX-ACCESS  not-accessible
        STATUS  current
        DESCRIPTION
            "An table to interface auth"
        ::= { zxr10ospfAreaMIB 18 }

zxr10AreaIfAuthTypeEntry OBJECT-TYPE
        SYNTAX Zxr10AreaIfAuthTypeEntry
        MAX-ACCESS  not-accessible
        STATUS  current
        DESCRIPTION
            "An entry to interface auth."
        INDEX  { zxr10AreaIfAuthTypeProId,
                 zxr10AreaIfAuthTypeIfName }
        ::= { zxr10AreaIfAuthTypeTable 1 }
            
Zxr10AreaIfAuthTypeEntry ::=
        SEQUENCE {
            zxr10AreaIfAuthTypeProId
                Unsigned32,
            zxr10AreaIfAuthTypeIfName
                DisplayString,
            zxr10AreaIfAuthTypeAreaId
                Unsigned32,
            zxr10AreaIfAuthTypeAreaIp
                Unsigned32,
            zxr10AreaIfAuthType
                Unsigned32,
            zxr10AreaIfAuthKeychain
                DisplayString
        }

zxr10AreaIfAuthTypeProId OBJECT-TYPE
        SYNTAX Unsigned32
        MAX-ACCESS  not-accessible
        STATUS  current
        DESCRIPTION
            "ospf instance ID"
        ::= { zxr10AreaIfAuthTypeEntry 1 }
        
zxr10AreaIfAuthTypeIfName OBJECT-TYPE
        SYNTAX DisplayString (SIZE (1..31))
        MAX-ACCESS  not-accessible
        STATUS  current
        DESCRIPTION
            "interface name"
        ::= { zxr10AreaIfAuthTypeEntry 2 }

zxr10AreaIfAuthTypeAreaId OBJECT-TYPE
        SYNTAX Unsigned32
        MAX-ACCESS  read-only
        STATUS  current
        DESCRIPTION
            "area ID"
        ::= { zxr10AreaIfAuthTypeEntry 3 }

zxr10AreaIfAuthTypeAreaIp OBJECT-TYPE
        SYNTAX Unsigned32
        MAX-ACCESS  read-only
        STATUS  current
        DESCRIPTION
            "area IP"
        ::= { zxr10AreaIfAuthTypeEntry 4 }

zxr10AreaIfAuthType OBJECT-TYPE
        SYNTAX Unsigned32 (0..256)
        MAX-ACCESS  read-only
        STATUS  current
        DESCRIPTION
            "null auth"
        ::= { zxr10AreaIfAuthTypeEntry 5 }

zxr10AreaIfAuthKeychain OBJECT-TYPE
        SYNTAX DisplayString (SIZE (1..31))
        MAX-ACCESS  read-only
        STATUS  current
        DESCRIPTION
            "keychain name"
        ::= { zxr10AreaIfAuthTypeEntry 6 }
  

zxr10AreaIfTypeTable OBJECT-TYPE
        SYNTAX  SEQUENCE OF Zxr10AreaIfTypeEntry
        MAX-ACCESS  not-accessible
        STATUS  current
        DESCRIPTION
            "An table to interface type"
        ::= { zxr10ospfAreaMIB 19 }

zxr10AreaIfTypeEntry OBJECT-TYPE
        SYNTAX Zxr10AreaIfTypeEntry
        MAX-ACCESS  not-accessible
        STATUS  current
        DESCRIPTION
            "An entry to interface type."
        INDEX  { zxr10AreaIfTypeProId,
                 zxr10AreaIfTypeIfName }
        ::= { zxr10AreaIfTypeTable 1 }
            
Zxr10AreaIfTypeEntry ::=
        SEQUENCE {
            zxr10AreaIfTypeProId
                Unsigned32,
            zxr10AreaIfTypeIfName
                DisplayString,
            zxr10AreaIfTypeAreaId
                Unsigned32,
            zxr10AreaIfTypeAreaIp
                Unsigned32,
            zxr10AreaIfTypeType1
                INTEGER,
            zxr10AreaIfTypeType2
                Unsigned32
        }

zxr10AreaIfTypeProId OBJECT-TYPE
        SYNTAX Unsigned32
        MAX-ACCESS  not-accessible
        STATUS  current
        DESCRIPTION
            "ospf instance ID"
        ::= { zxr10AreaIfTypeEntry 1 }
        
zxr10AreaIfTypeIfName OBJECT-TYPE
        SYNTAX DisplayString (SIZE (1..31))
        MAX-ACCESS  not-accessible
        STATUS  current
        DESCRIPTION
            "interface name"
        ::= { zxr10AreaIfTypeEntry 2 }

zxr10AreaIfTypeAreaId OBJECT-TYPE
        SYNTAX Unsigned32
        MAX-ACCESS  read-only
        STATUS  current
        DESCRIPTION
            "area ID"
        ::= { zxr10AreaIfTypeEntry 3 }

zxr10AreaIfTypeAreaIp OBJECT-TYPE
        SYNTAX Unsigned32
        MAX-ACCESS  read-only
        STATUS  current
        DESCRIPTION
            "area IP"
        ::= { zxr10AreaIfTypeEntry 4 }

zxr10AreaIfTypeType1 OBJECT-TYPE
        SYNTAX INTEGER {broadcast(1),
                        nonbroadcast(2),
                        pointtopoint(3),
                        pointtomultipoint(5)}            
        MAX-ACCESS  read-only
        STATUS  current
        DESCRIPTION
            "interface type flag1"
        ::= { zxr10AreaIfTypeEntry 5 }

zxr10AreaIfTypeType2 OBJECT-TYPE
        SYNTAX Unsigned32 (0..256)
        MAX-ACCESS  read-only
        STATUS  current
        DESCRIPTION
            "interface type flag2"
        ::= { zxr10AreaIfTypeEntry 6 }
        
                               
zxr10AreaIfFrrTable OBJECT-TYPE
        SYNTAX  SEQUENCE OF Zxr10AreaIfFrrEntry
        MAX-ACCESS  not-accessible
        STATUS  current
        DESCRIPTION
            "An table to Frr"
        ::= { zxr10ospfAreaMIB 20 }

zxr10AreaIfFrrEntry OBJECT-TYPE
        SYNTAX Zxr10AreaIfFrrEntry
        MAX-ACCESS  not-accessible
        STATUS  current
        DESCRIPTION
            "An entry to Frr."
        INDEX  { zxr10AreaIfFrrProId,
                 zxr10AreaIfFrrIfName }
        ::= { zxr10AreaIfFrrTable 1 }
            
Zxr10AreaIfFrrEntry ::=
        SEQUENCE {
            zxr10AreaIfFrrProId
                Unsigned32,
            zxr10AreaIfFrrIfName
                DisplayString,
            zxr10AreaIfFrrAreaId
                Unsigned32,
            zxr10AreaIfFrrAreaIp
                Unsigned32,
            zxr10AreaIfFrrDisable
                Unsigned32
        }

zxr10AreaIfFrrProId OBJECT-TYPE
        SYNTAX Unsigned32
        MAX-ACCESS  not-accessible
        STATUS  current
        DESCRIPTION
            "ospf instance ID"
        ::= { zxr10AreaIfFrrEntry 1 }
        
zxr10AreaIfFrrIfName OBJECT-TYPE
        SYNTAX DisplayString (SIZE (1..31))
        MAX-ACCESS  not-accessible
        STATUS  current
        DESCRIPTION
            "interface name"
        ::= { zxr10AreaIfFrrEntry 2 }

zxr10AreaIfFrrAreaId OBJECT-TYPE
        SYNTAX Unsigned32
        MAX-ACCESS  read-only
        STATUS  current
        DESCRIPTION
            "area ID"
        ::= { zxr10AreaIfFrrEntry 3 }

zxr10AreaIfFrrAreaIp OBJECT-TYPE
        SYNTAX Unsigned32
        MAX-ACCESS  read-only
        STATUS  current
        DESCRIPTION
            "area IP"
        ::= { zxr10AreaIfFrrEntry 4 }

zxr10AreaIfFrrDisable OBJECT-TYPE
        SYNTAX Unsigned32 (0..256)
        MAX-ACCESS  read-only
        STATUS  current
        DESCRIPTION
            "disable Frr"
        ::= { zxr10AreaIfFrrEntry 6 }
        

zxr10AreaIfMdKeyTable OBJECT-TYPE
        SYNTAX  SEQUENCE OF Zxr10AreaIfMdKeyEntry
        MAX-ACCESS  not-accessible
        STATUS  current
        DESCRIPTION
            "An table to interface md5 auth"
        ::= { zxr10ospfAreaMIB 21 }

zxr10AreaIfMdKeyEntry OBJECT-TYPE
        SYNTAX Zxr10AreaIfMdKeyEntry
        MAX-ACCESS  not-accessible
        STATUS  current
        DESCRIPTION
            "An entry to interface md5 auth."
        INDEX  { zxr10AreaIfMdKeyProId,
                 zxr10AreaIfMdKeyIntfName,
                 zxr10AreaIfMdKeyKeyId }
        ::= { zxr10AreaIfMdKeyTable 1 }
            
Zxr10AreaIfMdKeyEntry ::=
        SEQUENCE {
            zxr10AreaIfMdKeyProId
                Unsigned32,
            zxr10AreaIfMdKeyIntfName
                DisplayString,
            zxr10AreaIfMdKeyKeyId
                Unsigned32,
            zxr10AreaIfMdKeyAreaId
                Unsigned32,
            zxr10AreaIfMdKeyAreaIp
                Unsigned32,
            zxr10AreaIfMdKeyMd5
                Unsigned32,
            zxr10AreaIfMdKeyDelay
                Unsigned32,
            zxr10AreaIfMdKeyEncypt
                DisplayString,
            zxr10AreaIfMdKeyPassword
                DisplayString,
            zxr10AreaIfMdKeyEncyptedPass
                DisplayString
        }

zxr10AreaIfMdKeyProId OBJECT-TYPE
        SYNTAX Unsigned32
        MAX-ACCESS  not-accessible
        STATUS  current
        DESCRIPTION
            "ospf instance ID"
        ::= { zxr10AreaIfMdKeyEntry 1 }

zxr10AreaIfMdKeyIntfName OBJECT-TYPE
        SYNTAX DisplayString (SIZE (1..31))
        MAX-ACCESS  not-accessible
        STATUS  current
        DESCRIPTION
            "interface name"
        ::= { zxr10AreaIfMdKeyEntry 2 }
        
zxr10AreaIfMdKeyKeyId OBJECT-TYPE
        SYNTAX Unsigned32 (1..255)
        MAX-ACCESS  not-accessible
        STATUS  current
        DESCRIPTION
            "md5 auth key ID"
        ::= { zxr10AreaIfMdKeyEntry 3 }

zxr10AreaIfMdKeyAreaId OBJECT-TYPE
        SYNTAX Unsigned32
        MAX-ACCESS  read-only
        STATUS  current
        DESCRIPTION
            "area ID"
        ::= { zxr10AreaIfMdKeyEntry 4 }

zxr10AreaIfMdKeyAreaIp OBJECT-TYPE
        SYNTAX Unsigned32
        MAX-ACCESS  read-only
        STATUS  current
        DESCRIPTION
            "area IP"
        ::= { zxr10AreaIfMdKeyEntry 5 }

zxr10AreaIfMdKeyMd5 OBJECT-TYPE
        SYNTAX Unsigned32 (0..256)
        MAX-ACCESS  read-only
        STATUS  current
        DESCRIPTION
            "md5 auth"
        ::= { zxr10AreaIfMdKeyEntry 6 }

zxr10AreaIfMdKeyDelay OBJECT-TYPE
        SYNTAX Unsigned32
        MAX-ACCESS  read-only
        STATUS  current
        DESCRIPTION
            "delay of interface md5 auth"
        ::= { zxr10AreaIfMdKeyEntry 7 }

zxr10AreaIfMdKeyEncypt OBJECT-TYPE
        SYNTAX DisplayString (SIZE (1..16))
        MAX-ACCESS  read-only
        STATUS  current
        DESCRIPTION
            "encypt interface md5 auth"
        ::= { zxr10AreaIfMdKeyEntry 8 }

zxr10AreaIfMdKeyPassword OBJECT-TYPE
        SYNTAX DisplayString (SIZE (1..16))
        MAX-ACCESS  read-only
        STATUS  current
        DESCRIPTION
            "password of interface md5 auth"
        ::= { zxr10AreaIfMdKeyEntry 9 }

zxr10AreaIfMdKeyEncyptedPass OBJECT-TYPE
        SYNTAX DisplayString (SIZE (24))
        MAX-ACCESS  read-only
        STATUS  current
        DESCRIPTION
            "encypted password of interface md5 auth"
        ::= { zxr10AreaIfMdKeyEntry 10 }

zxr10AreaNetworkTable OBJECT-TYPE
        SYNTAX  SEQUENCE OF Zxr10AreaNetworkEntry
        MAX-ACCESS  not-accessible
        STATUS  current
        DESCRIPTION
            "An table to network"
        ::= { zxr10ospfAreaMIB 22}

zxr10AreaNetworkEntry OBJECT-TYPE
        SYNTAX Zxr10AreaNetworkEntry
        MAX-ACCESS  not-accessible
        STATUS  current
        DESCRIPTION
            "An entry to network."
        INDEX  { zxr10AreaNetworkProId,zxr10AreaNetworkIpAddr,
                 zxr10AreaNetworkIpMask,zxr10AreaNetworkAreaId,
                 zxr10AreaNetworkAreaIp}
        ::= { zxr10AreaNetworkTable 1 }
            
Zxr10AreaNetworkEntry ::=
        SEQUENCE {
            zxr10AreaNetworkProId
                Unsigned32,
            zxr10AreaNetworkIpAddr
                IpAddress,
            zxr10AreaNetworkIpMask
                IpAddress,
            zxr10AreaNetworkAreaId
                Unsigned32,
            zxr10AreaNetworkAreaIp
                IpAddress
        }

zxr10AreaNetworkProId OBJECT-TYPE
        SYNTAX Unsigned32
        MAX-ACCESS  read-only
        STATUS  current
        DESCRIPTION
            "ospf instance ID"
        ::= { zxr10AreaNetworkEntry 1 }

zxr10AreaNetworkIpAddr OBJECT-TYPE
        SYNTAX IpAddress
        MAX-ACCESS  read-only
        STATUS  current
        DESCRIPTION
            "ip address"
        ::= { zxr10AreaNetworkEntry 2 }

zxr10AreaNetworkIpMask OBJECT-TYPE
        SYNTAX IpAddress
        MAX-ACCESS  read-only
        STATUS  current
        DESCRIPTION
            "mask"
        ::= { zxr10AreaNetworkEntry 3 }

zxr10AreaNetworkAreaId OBJECT-TYPE
        SYNTAX Unsigned32
        MAX-ACCESS  read-only
        STATUS  current
        DESCRIPTION
            "area ID"
        ::= { zxr10AreaNetworkEntry 4 }

zxr10AreaNetworkAreaIp OBJECT-TYPE
        SYNTAX IpAddress
        MAX-ACCESS  read-only
        STATUS  current
        DESCRIPTION
            "area IP"
        ::= { zxr10AreaNetworkEntry 5 }

zxr10AreaIfStaticRlfaTable OBJECT-TYPE
        SYNTAX  SEQUENCE OF Zxr10AreaIfStaticRlfaEntry
        MAX-ACCESS  not-accessible
        STATUS  current
        DESCRIPTION
            "A table to static remote lfa."
        ::= { zxr10ospfAreaMIB 23}

zxr10AreaIfStaticRlfaEntry OBJECT-TYPE
        SYNTAX Zxr10AreaIfStaticRlfaEntry
        MAX-ACCESS  not-accessible
        STATUS  current
        DESCRIPTION
            "An entry to static remote lfa."
        INDEX  { zxr10AreaIfStaticRlfaProId, 
                 zxr10AreaIfStaticRlfaIntfName,
                 zxr10AreaIfStaticRlfaAreaId,
                 zxr10AreaIfStaticRlfaAreaIp,
                 zxr10AreaIfStaticRlfaPrefixList}
        ::= { zxr10AreaIfStaticRlfaTable 1 }
            
Zxr10AreaIfStaticRlfaEntry ::=
        SEQUENCE {
            zxr10AreaIfStaticRlfaProId
                Unsigned32,
            zxr10AreaIfStaticRlfaIntfName
                DisplayString,
            zxr10AreaIfStaticRlfaAreaId
                Unsigned32,
            zxr10AreaIfStaticRlfaAreaIp
                IpAddress,
            zxr10AreaIfStaticRlfaPrefixList
                DisplayString,
            zxr10AreaIfStaticRlfaNextHop
                IpAddress
        }

zxr10AreaIfStaticRlfaProId OBJECT-TYPE
        SYNTAX Unsigned32
        MAX-ACCESS  not-accessible
        STATUS  current
        DESCRIPTION
            "ospf instance ID"
        ::= { zxr10AreaIfStaticRlfaEntry 1 }

zxr10AreaIfStaticRlfaIntfName OBJECT-TYPE
        SYNTAX DisplayString (SIZE (1..31))
        MAX-ACCESS  not-accessible
        STATUS  current
        DESCRIPTION
            "interface name"
        ::= { zxr10AreaIfStaticRlfaEntry 2 }

zxr10AreaIfStaticRlfaAreaId OBJECT-TYPE
        SYNTAX Unsigned32
        MAX-ACCESS  not-accessible
        STATUS  current
        DESCRIPTION
            "area ID"
        ::= { zxr10AreaIfStaticRlfaEntry 3 }

zxr10AreaIfStaticRlfaAreaIp OBJECT-TYPE
        SYNTAX IpAddress
        MAX-ACCESS  not-accessible
        STATUS  current
        DESCRIPTION
            "area IP"
        ::= { zxr10AreaIfStaticRlfaEntry 4 }

zxr10AreaIfStaticRlfaPrefixList OBJECT-TYPE
        SYNTAX DisplayString (SIZE (1..31))
        MAX-ACCESS  not-accessible
        STATUS  current
        DESCRIPTION
            "prefix_list name"
        ::= { zxr10AreaIfStaticRlfaEntry 5 }

zxr10AreaIfStaticRlfaNextHop OBJECT-TYPE
        SYNTAX IpAddress
        MAX-ACCESS  read-only
        STATUS  current
        DESCRIPTION
            "next hop"
        ::= { zxr10AreaIfStaticRlfaEntry 6 }

zxr10AreaDynamicRlfaTable OBJECT-TYPE
        SYNTAX  SEQUENCE OF Zxr10AreaDynamicRlfaEntry
        MAX-ACCESS  not-accessible
        STATUS  current
        DESCRIPTION
            "A table to dynamic remote lfa."
        ::= { zxr10ospfAreaMIB 24}

zxr10AreaDynamicRlfaEntry OBJECT-TYPE
        SYNTAX Zxr10AreaDynamicRlfaEntry
        MAX-ACCESS  not-accessible
        STATUS  current
        DESCRIPTION
            "An entry to dynamic remote lfa."
        INDEX  { zxr10AreaDynamicRlfaProId, 
                 zxr10AreaDynamicRlfaAreaId,
                 zxr10AreaDynamicRlfaAreaIp
               }
        ::= { zxr10AreaDynamicRlfaTable 1 }
            
Zxr10AreaDynamicRlfaEntry ::=
        SEQUENCE {
            zxr10AreaDynamicRlfaProId
                Unsigned32,
            zxr10AreaDynamicRlfaAreaId
                Unsigned32,
            zxr10AreaDynamicRlfaAreaIp
                IpAddress,
            zxr10AreaDynamicRlfaCapability
                INTEGER,
            zxr10AreaDynamicRlfaMaximumCost
                Unsigned32
        }

zxr10AreaDynamicRlfaProId OBJECT-TYPE
        SYNTAX Unsigned32
        MAX-ACCESS  not-accessible
        STATUS  current
        DESCRIPTION
            "ospf instance ID"
        ::= { zxr10AreaDynamicRlfaEntry 1 }

zxr10AreaDynamicRlfaAreaId OBJECT-TYPE
        SYNTAX Unsigned32
        MAX-ACCESS  not-accessible
        STATUS  current
        DESCRIPTION
            "area ID"
        ::= { zxr10AreaDynamicRlfaEntry 2 }

zxr10AreaDynamicRlfaAreaIp OBJECT-TYPE
        SYNTAX IpAddress
        MAX-ACCESS  not-accessible
        STATUS  current
        DESCRIPTION
            "area IP"
        ::= { zxr10AreaDynamicRlfaEntry 3 }

zxr10AreaDynamicRlfaCapability OBJECT-TYPE
        SYNTAX INTEGER{enable(1),disable(2)}
        MAX-ACCESS  read-only
        STATUS  current
        DESCRIPTION
            "capability : 1 enable, 2 disable"
        ::= { zxr10AreaDynamicRlfaEntry 4 }

zxr10AreaDynamicRlfaMaximumCost OBJECT-TYPE
        SYNTAX Unsigned32 (1..16777214)
        MAX-ACCESS  read-only
        STATUS  current
        DESCRIPTION
            "maximum cost"
        ::= { zxr10AreaDynamicRlfaEntry 5 }

zxr10ospfInterfaceMIB OBJECT IDENTIFIER ::= { zxr10ospfMIB 22 }

zxr10ospfInterfaceTable OBJECT-TYPE
        SYNTAX  SEQUENCE OF Zxr10ospfInterfaceEntry
        MAX-ACCESS  not-accessible
        STATUS  obsolete
        DESCRIPTION
            "An table to interface"
        ::= { zxr10ospfInterfaceMIB 1 }

zxr10ospfInterfaceEntry OBJECT-TYPE
        SYNTAX Zxr10ospfInterfaceEntry
        MAX-ACCESS  not-accessible
        STATUS  obsolete
        DESCRIPTION
            "An entry to interface."
        INDEX  { zxr10ospfInterfaceIntfName,zxr10ospfInterfaceProId }
        ::= { zxr10ospfInterfaceTable 1 }
            
Zxr10ospfInterfaceEntry ::=
        SEQUENCE {
            zxr10ospfInterfaceIntfName
                DisplayString,
            zxr10ospfInterfaceProId
                Unsigned32,
            zxr10ospfInterfaceAuthenticationKey
                DisplayString,
            zxr10ospfInterfaceCost
                Unsigned32,
            zxr10ospfInterfaceDeadInterval
                Unsigned32,
            zxr10ospfInterfaceFastFlood
                Unsigned32,
            zxr10ospfInterfaceDisableFastFlood
                Unsigned32,
            zxr10ospfInterfaceHelloInterval
                Unsigned32,
            zxr10ospfInterfaceMtuIgnore
                Unsigned32,
            zxr10ospfInterfacePriority
                Unsigned32,
            zxr10ospfInterfaceResyncTimeout
                Unsigned32,
            zxr10ospfInterfaceRetransmitInterval
                Unsigned32,
            zxr10ospfInterfaceTransmitDelay
                Unsigned32,
            zxr10ospfInterfaceTtlSecurity
                INTEGER
        }

zxr10ospfInterfaceIntfName OBJECT-TYPE
        SYNTAX DisplayString (SIZE (1..31))
        MAX-ACCESS  read-only
        STATUS  obsolete
        DESCRIPTION
            "interface name"
        ::= { zxr10ospfInterfaceEntry 1 }

zxr10ospfInterfaceProId OBJECT-TYPE
        SYNTAX Unsigned32
        MAX-ACCESS  read-only
        STATUS  obsolete
        DESCRIPTION
            "ospf instance ID"
        ::= { zxr10ospfInterfaceEntry 2 }

zxr10ospfInterfaceAuthenticationKey OBJECT-TYPE
        SYNTAX DisplayString (SIZE (1..8))
        MAX-ACCESS  read-only
        STATUS  obsolete
        DESCRIPTION
            "simple auth key"
        ::= { zxr10ospfInterfaceEntry 3 }

zxr10ospfInterfaceCost OBJECT-TYPE
        SYNTAX Unsigned32
        MAX-ACCESS  read-only
        STATUS  obsolete
        DESCRIPTION
            "cost of interface"
        ::= { zxr10ospfInterfaceEntry 4 }

zxr10ospfInterfaceDeadInterval OBJECT-TYPE
        SYNTAX Unsigned32
        MAX-ACCESS  read-only
        STATUS  obsolete
        DESCRIPTION
            "dead-interval of interface"
        ::= { zxr10ospfInterfaceEntry 5 }

zxr10ospfInterfaceFastFlood OBJECT-TYPE
        SYNTAX Unsigned32 (0..256)
        MAX-ACCESS  read-only
        STATUS  obsolete
        DESCRIPTION
            "fast-flood of interface"
        ::= { zxr10ospfInterfaceEntry 6 }

zxr10ospfInterfaceDisableFastFlood OBJECT-TYPE
        SYNTAX Unsigned32 (0..256)
        MAX-ACCESS  read-only
        STATUS  obsolete
        DESCRIPTION
            "disable fast-flood of interface"
        ::= { zxr10ospfInterfaceEntry 7 }

zxr10ospfInterfaceHelloInterval OBJECT-TYPE
        SYNTAX Unsigned32
        MAX-ACCESS  read-only
        STATUS  obsolete
        DESCRIPTION
            "hello-interval of interface"
        ::= { zxr10ospfInterfaceEntry 8 }

zxr10ospfInterfaceMtuIgnore OBJECT-TYPE
        SYNTAX Unsigned32 (0..256)
        MAX-ACCESS  read-only
        STATUS  obsolete
        DESCRIPTION
            "ignore mtu of interface"
        ::= { zxr10ospfInterfaceEntry 9 }

zxr10ospfInterfacePriority OBJECT-TYPE
        SYNTAX Unsigned32 (0..255)
        MAX-ACCESS  read-only
        STATUS  obsolete
        DESCRIPTION
            "priority of interface"
        ::= { zxr10ospfInterfaceEntry 10 }

zxr10ospfInterfaceResyncTimeout OBJECT-TYPE
        SYNTAX Unsigned32
        MAX-ACCESS  read-only
        STATUS  obsolete
        DESCRIPTION
            "resync interval after which adjacency is reset 
             if oob-resync is not started"
        ::= { zxr10ospfInterfaceEntry 11 }

zxr10ospfInterfaceRetransmitInterval OBJECT-TYPE
        SYNTAX Unsigned32
        MAX-ACCESS  read-only
        STATUS  obsolete
        DESCRIPTION
            "retransmit-interval of interface"
        ::= { zxr10ospfInterfaceEntry 12 }

zxr10ospfInterfaceTransmitDelay OBJECT-TYPE
        SYNTAX Unsigned32
        MAX-ACCESS  read-only
        STATUS  obsolete
        DESCRIPTION
            "transmit-delay of interface"
        ::= { zxr10ospfInterfaceEntry 13 }

zxr10ospfInterfaceTtlSecurity OBJECT-TYPE
        SYNTAX INTEGER (0..1000)
        MAX-ACCESS  read-only
        STATUS  obsolete
        DESCRIPTION
            "ttl_security"
        ::= { zxr10ospfInterfaceEntry 16 }
        

zxr10ospfIntfBfdTable OBJECT-TYPE
        SYNTAX  SEQUENCE OF Zxr10ospfIntfBfdEntry
        MAX-ACCESS  not-accessible
        STATUS  obsolete
        DESCRIPTION
            "An table to interface BFD"
        ::= { zxr10ospfInterfaceMIB 2 }

zxr10ospfIntfBfdEntry OBJECT-TYPE
        SYNTAX Zxr10ospfIntfBfdEntry
        MAX-ACCESS  not-accessible
        STATUS  obsolete
        DESCRIPTION
            "An entry to interface BFD."
        INDEX  { zxr10ospfIntfBfdIntfName,zxr10ospfIntfBfdProId }
        ::= { zxr10ospfIntfBfdTable 1 }
            
Zxr10ospfIntfBfdEntry ::=
        SEQUENCE {
            zxr10ospfIntfBfdIntfName
                DisplayString,
            zxr10ospfIntfBfdProId
                Unsigned32,
            zxr10ospfIntfBfdDisable
                Unsigned32
        }

zxr10ospfIntfBfdIntfName OBJECT-TYPE
        SYNTAX DisplayString (SIZE (1..31))
        MAX-ACCESS  read-only
        STATUS  obsolete
        DESCRIPTION
            "interface name"
        ::= { zxr10ospfIntfBfdEntry 1 }

zxr10ospfIntfBfdProId OBJECT-TYPE
        SYNTAX Unsigned32
        MAX-ACCESS  read-only
        STATUS  obsolete
        DESCRIPTION
            "ospf instance ID"
        ::= { zxr10ospfIntfBfdEntry 2 }

zxr10ospfIntfBfdDisable OBJECT-TYPE
        SYNTAX Unsigned32 (0..256)
        MAX-ACCESS  read-only
        STATUS  obsolete
        DESCRIPTION
            "disable interface BFD"
        ::= { zxr10ospfIntfBfdEntry 3 }


zxr10ospfIntfAuthTypeTable OBJECT-TYPE
        SYNTAX  SEQUENCE OF Zxr10ospfIntfAuthTypeEntry
        MAX-ACCESS  not-accessible
        STATUS  obsolete
        DESCRIPTION
            "An table to interface auth"
        ::= { zxr10ospfInterfaceMIB 3 }

zxr10ospfIntfAuthTypeEntry OBJECT-TYPE
        SYNTAX Zxr10ospfIntfAuthTypeEntry
        MAX-ACCESS  not-accessible
        STATUS  obsolete
        DESCRIPTION
            "An entry to interface auth."
        INDEX  { zxr10ospfIntfAuthTypeIntfName,zxr10ospfIntfAuthTypeProId }
        ::= { zxr10ospfIntfAuthTypeTable 1 }
            
Zxr10ospfIntfAuthTypeEntry ::=
        SEQUENCE {
            zxr10ospfIntfAuthTypeIntfName
                DisplayString,
            zxr10ospfIntfAuthTypeProId
                Unsigned32,
            zxr10ospfIntfAuthTypeNull
                Unsigned32,
            zxr10ospfIntfAuthTypeMd5
                Unsigned32,
            zxr10ospfIntfAuthTypeSimple
                Unsigned32
        }

zxr10ospfIntfAuthTypeIntfName OBJECT-TYPE
        SYNTAX DisplayString (SIZE (1..31))
        MAX-ACCESS  read-only
        STATUS  obsolete
        DESCRIPTION
            "interface name"
        ::= { zxr10ospfIntfAuthTypeEntry 1 }

zxr10ospfIntfAuthTypeProId OBJECT-TYPE
        SYNTAX Unsigned32
        MAX-ACCESS  read-only
        STATUS  obsolete
        DESCRIPTION
            "ospf instance ID"
        ::= { zxr10ospfIntfAuthTypeEntry 2 }

zxr10ospfIntfAuthTypeNull OBJECT-TYPE
        SYNTAX Unsigned32 (0..256)
        MAX-ACCESS  read-only
        STATUS  obsolete
        DESCRIPTION
            "null auth"
        ::= { zxr10ospfIntfAuthTypeEntry 3 }

zxr10ospfIntfAuthTypeMd5 OBJECT-TYPE
        SYNTAX Unsigned32 (0..256)
        MAX-ACCESS  read-only
        STATUS  obsolete
        DESCRIPTION
            "md5 auth"
        ::= { zxr10ospfIntfAuthTypeEntry 4 }

zxr10ospfIntfAuthTypeSimple OBJECT-TYPE
        SYNTAX Unsigned32 (0..256)
        MAX-ACCESS  read-only
        STATUS  obsolete
        DESCRIPTION
            "simple auth"
        ::= { zxr10ospfIntfAuthTypeEntry 5 }


zxr10ospfIntfMdKeyTable OBJECT-TYPE
        SYNTAX  SEQUENCE OF Zxr10ospfIntfMdKeyEntry
        MAX-ACCESS  not-accessible
        STATUS  obsolete
        DESCRIPTION
            "An table to interface md5 auth"
        ::= { zxr10ospfInterfaceMIB 4 }

zxr10ospfIntfMdKeyEntry OBJECT-TYPE
        SYNTAX Zxr10ospfIntfMdKeyEntry
        MAX-ACCESS  not-accessible
        STATUS  obsolete
        DESCRIPTION
            "An entry to interface md5 auth."
        INDEX  { zxr10ospfIntfMdKeyKeyId,zxr10ospfIntfMdKeyIntfName,
                 zxr10ospfIntfMdKeyProId }
        ::= { zxr10ospfIntfMdKeyTable 1 }
            
Zxr10ospfIntfMdKeyEntry ::=
        SEQUENCE {
            zxr10ospfIntfMdKeyKeyId
                Unsigned32,
            zxr10ospfIntfMdKeyIntfName
                DisplayString,
            zxr10ospfIntfMdKeyProId
                Unsigned32,
            zxr10ospfIntfMdKeyMd5
                Unsigned32,
            zxr10ospfIntfMdKeyDelay
                Unsigned32,
            zxr10ospfIntfMdKeyEncypt
                DisplayString,
            zxr10ospfIntfMdKeyPassword
                DisplayString,
            zxr10ospfIntfMdKeyEncyptedPass
                DisplayString
        }

zxr10ospfIntfMdKeyKeyId OBJECT-TYPE
        SYNTAX Unsigned32 (1..255)
        MAX-ACCESS  read-only
        STATUS  obsolete
        DESCRIPTION
            "md5 auth key ID"
        ::= { zxr10ospfIntfMdKeyEntry 1 }

zxr10ospfIntfMdKeyIntfName OBJECT-TYPE
        SYNTAX DisplayString (SIZE (1..31))
        MAX-ACCESS  read-only
        STATUS  obsolete
        DESCRIPTION
            "interface name"
        ::= { zxr10ospfIntfMdKeyEntry 2 }

zxr10ospfIntfMdKeyProId OBJECT-TYPE
        SYNTAX Unsigned32
        MAX-ACCESS  read-only
        STATUS  obsolete
        DESCRIPTION
            "ospf instance ID"
        ::= { zxr10ospfIntfMdKeyEntry 3 }

zxr10ospfIntfMdKeyMd5 OBJECT-TYPE
        SYNTAX Unsigned32 (0..256)
        MAX-ACCESS  read-only
        STATUS  obsolete
        DESCRIPTION
            "md5 auth"
        ::= { zxr10ospfIntfMdKeyEntry 4 }

zxr10ospfIntfMdKeyDelay OBJECT-TYPE
        SYNTAX Unsigned32
        MAX-ACCESS  read-only
        STATUS  obsolete
        DESCRIPTION
            "delay of interface md5 auth"
        ::= { zxr10ospfIntfMdKeyEntry 5 }

zxr10ospfIntfMdKeyEncypt OBJECT-TYPE
        SYNTAX DisplayString (SIZE (1..16))
        MAX-ACCESS  read-only
        STATUS  obsolete
        DESCRIPTION
            "encypt interface md5 auth"
        ::= { zxr10ospfIntfMdKeyEntry 6 }

zxr10ospfIntfMdKeyPassword OBJECT-TYPE
        SYNTAX DisplayString (SIZE (1..16))
        MAX-ACCESS  read-only
        STATUS  obsolete
        DESCRIPTION
            "password of interface md5 auth"
        ::= { zxr10ospfIntfMdKeyEntry 7 }

zxr10ospfIntfMdKeyEncyptedPass OBJECT-TYPE
        SYNTAX DisplayString (SIZE (24))
        MAX-ACCESS  read-only
        STATUS  obsolete
        DESCRIPTION
            "encypted password of interface md5 auth"
        ::= { zxr10ospfIntfMdKeyEntry 8 }       

zxr10ospfIntfTypeTable OBJECT-TYPE
        SYNTAX  SEQUENCE OF Zxr10ospfIntfTypeEntry
        MAX-ACCESS  not-accessible
        STATUS  obsolete
        DESCRIPTION
            "An table to interface type"
        ::= { zxr10ospfInterfaceMIB 5 }

zxr10ospfIntfTypeEntry OBJECT-TYPE
        SYNTAX Zxr10ospfIntfTypeEntry
        MAX-ACCESS  not-accessible
        STATUS  obsolete
        DESCRIPTION
            "An entry to interface type."
        INDEX  { zxr10ospfIntfTypeIntfName,zxr10ospfIntfTypeProId}
        ::= { zxr10ospfIntfTypeTable 1 }
            
Zxr10ospfIntfTypeEntry ::=
        SEQUENCE {
            zxr10ospfIntfTypeIntfName
                DisplayString,
            zxr10ospfIntfTypeProId
                Unsigned32,
            zxr10ospfIntfTypeType1
                INTEGER,
            zxr10ospfIntfTypeType2
                Unsigned32
        }

zxr10ospfIntfTypeIntfName OBJECT-TYPE
        SYNTAX DisplayString (SIZE (1..31))
        MAX-ACCESS  read-only
        STATUS  obsolete
        DESCRIPTION
            "interface name"
        ::= { zxr10ospfIntfTypeEntry 1 }

zxr10ospfIntfTypeProId OBJECT-TYPE
        SYNTAX Unsigned32
        MAX-ACCESS  read-only
        STATUS  obsolete
        DESCRIPTION
            "ospf instance ID"
        ::= { zxr10ospfIntfTypeEntry 2 }

zxr10ospfIntfTypeType1 OBJECT-TYPE
        SYNTAX INTEGER {broadcast(1),
                        nonbroadcast(2),
                        pointtopoint(3),
                        pointtomultipoint(5)}            
        MAX-ACCESS  read-only
        STATUS  obsolete
        DESCRIPTION
            "interface type flag1"
        ::= { zxr10ospfIntfTypeEntry 4 }

zxr10ospfIntfTypeType2 OBJECT-TYPE
        SYNTAX Unsigned32 (0..256)
        MAX-ACCESS  read-only
        STATUS  obsolete
        DESCRIPTION
            "interface type flag2"
        ::= { zxr10ospfIntfTypeEntry 5 }
        
        
zxr10ospfIntfFastRerouteTable OBJECT-TYPE
        SYNTAX  SEQUENCE OF Zxr10ospfIntfFastRerouteEntry
        MAX-ACCESS  not-accessible
        STATUS  obsolete
        DESCRIPTION
            "An table to frr"
        ::= { zxr10ospfInterfaceMIB 6 }

zxr10ospfIntfFastRerouteEntry OBJECT-TYPE
        SYNTAX Zxr10ospfIntfFastRerouteEntry
        MAX-ACCESS  not-accessible
        STATUS  obsolete
        DESCRIPTION
            "An entry to frr."
        INDEX  { zxr10ospfIntfFastRerouteIntfName,
                 zxr10ospfIntfFastRerouteProId }
        ::= { zxr10ospfIntfFastRerouteTable 1 }
            
Zxr10ospfIntfFastRerouteEntry ::=
        SEQUENCE {
            zxr10ospfIntfFastRerouteIntfName
                DisplayString,
            zxr10ospfIntfFastRerouteProId
                Unsigned32,
            zxr10ospfIntfFastRerouteBackupInterfaceName
                DisplayString,
            zxr10ospfIntfFastRerouteDisable
                Unsigned32
        }

zxr10ospfIntfFastRerouteIntfName OBJECT-TYPE
        SYNTAX DisplayString (SIZE (1..31))
        MAX-ACCESS  read-only
        STATUS  obsolete
        DESCRIPTION
            "interface name"
        ::= { zxr10ospfIntfFastRerouteEntry 1 }

zxr10ospfIntfFastRerouteProId OBJECT-TYPE
        SYNTAX Unsigned32
        MAX-ACCESS  read-only
        STATUS  obsolete
        DESCRIPTION
            "ospf instance ID"
        ::= { zxr10ospfIntfFastRerouteEntry 2 }

zxr10ospfIntfFastRerouteBackupInterfaceName OBJECT-TYPE
        SYNTAX DisplayString (SIZE (1..31))
        MAX-ACCESS  read-only
        STATUS  obsolete
        DESCRIPTION
            "backup frr interface"
        ::= { zxr10ospfIntfFastRerouteEntry 4 }

zxr10ospfIntfFastRerouteDisable OBJECT-TYPE
        SYNTAX Unsigned32 (0..256)
        MAX-ACCESS  read-only
        STATUS  obsolete
        DESCRIPTION
            "disable frr"
        ::= { zxr10ospfIntfFastRerouteEntry 5 }


zxr10ospfv2InterfaceTable OBJECT-TYPE
        SYNTAX  SEQUENCE OF Zxr10ospfv2InterfaceEntry
        MAX-ACCESS  not-accessible
        STATUS  obsolete
        DESCRIPTION
            "An table to interface"
        ::= { zxr10ospfInterfaceMIB 7 }

zxr10ospfv2InterfaceEntry OBJECT-TYPE
        SYNTAX Zxr10ospfv2InterfaceEntry
        MAX-ACCESS  not-accessible
        STATUS  obsolete
        DESCRIPTION
            "An entry to interface."
        INDEX  { zxr10ospfv2IfProId,zxr10ospfv2IfIntfName }
        ::= { zxr10ospfv2InterfaceTable 1 }
            
Zxr10ospfv2InterfaceEntry ::=
        SEQUENCE {
            zxr10ospfv2IfProId
                Unsigned32,
            zxr10ospfv2IfIntfName
                DisplayString,
            zxr10ospfv2IfAuthenticationKey
                DisplayString,
            zxr10ospfv2IfCost
                Unsigned32,
            zxr10ospfv2IfDeadInterval
                Unsigned32,
            zxr10ospfv2IfFastFlood
                Unsigned32,
            zxr10ospfv2IfDisableFastFlood
                Unsigned32,
            zxr10ospfv2IfHelloInterval
                Unsigned32,
            zxr10ospfv2IfMtuIgnore
                Unsigned32,
            zxr10ospfv2IfPriority
                Unsigned32,
            zxr10ospfv2IfResyncTimeout
                Unsigned32,
            zxr10ospfv2IfRetransmitInterval
                Unsigned32,
            zxr10ospfv2IfTransmitDelay
                Unsigned32,
            zxr10ospfv2IfTtlSecurity
                INTEGER,
            zxr10ospfv2IfLdpIgpSync
                Unsigned32,
            zxr10ospfv2IfLdpAutoConfig
                Unsigned32
        }

zxr10ospfv2IfProId OBJECT-TYPE
        SYNTAX Unsigned32
        MAX-ACCESS  not-accessible
        STATUS  obsolete
        DESCRIPTION
            "ospf instance ID"
        ::= { zxr10ospfv2InterfaceEntry 1 }
        
zxr10ospfv2IfIntfName OBJECT-TYPE
        SYNTAX DisplayString (SIZE (1..31))
        MAX-ACCESS  not-accessible
        STATUS  obsolete
        DESCRIPTION
            "interface name"
        ::= { zxr10ospfv2InterfaceEntry 2 }


zxr10ospfv2IfAuthenticationKey OBJECT-TYPE
        SYNTAX DisplayString (SIZE (1..8))
        MAX-ACCESS  read-only
        STATUS  obsolete
        DESCRIPTION
            "simple auth key"
        ::= { zxr10ospfv2InterfaceEntry 3 }

zxr10ospfv2IfCost OBJECT-TYPE
        SYNTAX Unsigned32
        MAX-ACCESS  read-only
        STATUS  obsolete
        DESCRIPTION
            "cost of interface"
        ::= { zxr10ospfv2InterfaceEntry 4 }

zxr10ospfv2IfDeadInterval OBJECT-TYPE
        SYNTAX Unsigned32
        MAX-ACCESS  read-only
        STATUS  obsolete
        DESCRIPTION
            "dead-interval of interface"
        ::= { zxr10ospfv2InterfaceEntry 5 }

zxr10ospfv2IfFastFlood OBJECT-TYPE
        SYNTAX Unsigned32 (0..256)
        MAX-ACCESS  read-only
        STATUS  obsolete
        DESCRIPTION
            "fast-flood of interface"
        ::= { zxr10ospfv2InterfaceEntry 6 }

zxr10ospfv2IfDisableFastFlood OBJECT-TYPE
        SYNTAX Unsigned32 (0..256)
        MAX-ACCESS  read-only
        STATUS  obsolete
        DESCRIPTION
            "disable fast-flood of interface"
        ::= { zxr10ospfv2InterfaceEntry 7 }

zxr10ospfv2IfHelloInterval OBJECT-TYPE
        SYNTAX Unsigned32
        MAX-ACCESS  read-only
        STATUS  obsolete
        DESCRIPTION
            "hello-interval of interface"
        ::= { zxr10ospfv2InterfaceEntry 8 }

zxr10ospfv2IfMtuIgnore OBJECT-TYPE
        SYNTAX Unsigned32 (0..256)
        MAX-ACCESS  read-only
        STATUS  obsolete
        DESCRIPTION
            "ignore mtu of interface"
        ::= { zxr10ospfv2InterfaceEntry 9 }

zxr10ospfv2IfPriority OBJECT-TYPE
        SYNTAX Unsigned32 (0..255)
        MAX-ACCESS  read-only
        STATUS  obsolete
        DESCRIPTION
            "priority of interface"
        ::= { zxr10ospfv2InterfaceEntry 10 }

zxr10ospfv2IfResyncTimeout OBJECT-TYPE
        SYNTAX Unsigned32
        MAX-ACCESS  read-only
        STATUS  obsolete
        DESCRIPTION
            "resync interval after which adjacency is reset 
             if oob-resync is not started"
        ::= { zxr10ospfv2InterfaceEntry 11 }

zxr10ospfv2IfRetransmitInterval OBJECT-TYPE
        SYNTAX Unsigned32
        MAX-ACCESS  read-only
        STATUS  obsolete
        DESCRIPTION
            "retransmit-interval of interface"
        ::= { zxr10ospfv2InterfaceEntry 12 }

zxr10ospfv2IfTransmitDelay OBJECT-TYPE
        SYNTAX Unsigned32
        MAX-ACCESS  read-only
        STATUS  obsolete
        DESCRIPTION
            "transmit-delay of interface"
        ::= { zxr10ospfv2InterfaceEntry 13 }

zxr10ospfv2IfTtlSecurity OBJECT-TYPE
        SYNTAX INTEGER (0..1000)
        MAX-ACCESS  read-only
        STATUS  obsolete
        DESCRIPTION
            "ttl_security"
        ::= { zxr10ospfv2InterfaceEntry 16 }

zxr10ospfv2IfLdpIgpSync OBJECT-TYPE
        SYNTAX Unsigned32 (0..2)
        MAX-ACCESS  read-only
        STATUS  obsolete
        DESCRIPTION
            "ospf intf ldp igp sync"
        ::= { zxr10ospfv2InterfaceEntry 17 }

zxr10ospfv2IfLdpAutoConfig OBJECT-TYPE
        SYNTAX Unsigned32 (0..2)
        MAX-ACCESS  read-only
        STATUS  obsolete
        DESCRIPTION
            "ospf intf ldp auto-config"
        ::= { zxr10ospfv2InterfaceEntry 18 }

zxr10ospfv2IntfBfdTable OBJECT-TYPE
        SYNTAX  SEQUENCE OF Zxr10ospfv2IntfBfdEntry
        MAX-ACCESS  not-accessible
        STATUS  obsolete
        DESCRIPTION
            "An table to interface BFD"
        ::= { zxr10ospfInterfaceMIB 8 }

zxr10ospfv2IntfBfdEntry OBJECT-TYPE
        SYNTAX Zxr10ospfv2IntfBfdEntry
        MAX-ACCESS  not-accessible
        STATUS  obsolete
        DESCRIPTION
            "An entry to interface BFD."
        INDEX  { zxr10ospfv2IntfBfdProId,zxr10ospfv2IntfBfdIntfName }
        ::= { zxr10ospfv2IntfBfdTable 1 }
            
Zxr10ospfv2IntfBfdEntry ::=
        SEQUENCE {
            zxr10ospfv2IntfBfdProId
                Unsigned32,
            zxr10ospfv2IntfBfdIntfName
                DisplayString,
            zxr10ospfv2IntfBfdDisable
                Unsigned32
        }

zxr10ospfv2IntfBfdProId OBJECT-TYPE
        SYNTAX Unsigned32
        MAX-ACCESS  not-accessible
        STATUS  obsolete
        DESCRIPTION
            "ospf instance ID"
        ::= { zxr10ospfv2IntfBfdEntry 1 }
        
zxr10ospfv2IntfBfdIntfName OBJECT-TYPE
        SYNTAX DisplayString (SIZE (1..31))
        MAX-ACCESS  not-accessible
        STATUS  obsolete
        DESCRIPTION
            "interface name"
        ::= { zxr10ospfv2IntfBfdEntry 2 }

zxr10ospfv2IntfBfdDisable OBJECT-TYPE
        SYNTAX Unsigned32 (0..256)
        MAX-ACCESS  read-only
        STATUS  obsolete
        DESCRIPTION
            "disable interface BFD"
        ::= { zxr10ospfv2IntfBfdEntry 3 }
        

zxr10ospfv2IntfAuthTypeTable OBJECT-TYPE
        SYNTAX  SEQUENCE OF Zxr10ospfv2IntfAuthTypeEntry
        MAX-ACCESS  not-accessible
        STATUS  obsolete
        DESCRIPTION
            "An table to interface auth"
        ::= { zxr10ospfInterfaceMIB 9 }

zxr10ospfv2IntfAuthTypeEntry OBJECT-TYPE
        SYNTAX Zxr10ospfv2IntfAuthTypeEntry
        MAX-ACCESS  not-accessible
        STATUS  obsolete
        DESCRIPTION
            "An entry to interface auth."
        INDEX  { zxr10ospfv2IntfAuthTypeProId,
                 zxr10ospfv2IntfAuthTypeIntfName }
        ::= { zxr10ospfv2IntfAuthTypeTable 1 }
            
Zxr10ospfv2IntfAuthTypeEntry ::=
        SEQUENCE {
            zxr10ospfv2IntfAuthTypeProId
                Unsigned32,
            zxr10ospfv2IntfAuthTypeIntfName
                DisplayString,
            zxr10ospfv2IntfAuthTypeNull
                Unsigned32,
            zxr10ospfv2IntfAuthTypeMd5
                Unsigned32,
            zxr10ospfv2IntfAuthTypeSimple
                Unsigned32
        }

zxr10ospfv2IntfAuthTypeProId OBJECT-TYPE
        SYNTAX Unsigned32
        MAX-ACCESS  not-accessible
        STATUS  obsolete
        DESCRIPTION
            "ospf instance ID"
        ::= { zxr10ospfv2IntfAuthTypeEntry 1 }
        
zxr10ospfv2IntfAuthTypeIntfName OBJECT-TYPE
        SYNTAX DisplayString (SIZE (1..31))
        MAX-ACCESS  not-accessible
        STATUS  obsolete
        DESCRIPTION
            "interface name"
        ::= { zxr10ospfv2IntfAuthTypeEntry 2 }

zxr10ospfv2IntfAuthTypeNull OBJECT-TYPE
        SYNTAX Unsigned32 (0..256)
        MAX-ACCESS  read-only
        STATUS  obsolete
        DESCRIPTION
            "null auth"
        ::= { zxr10ospfv2IntfAuthTypeEntry 3 }
        
        
zxr10ospfv2IntfAuthTypeMd5 OBJECT-TYPE
        SYNTAX Unsigned32 (0..256)
        MAX-ACCESS  read-only
        STATUS  obsolete
        DESCRIPTION
            "md5 auth"
        ::= { zxr10ospfv2IntfAuthTypeEntry 4 }

zxr10ospfv2IntfAuthTypeSimple OBJECT-TYPE
        SYNTAX Unsigned32 (0..256)
        MAX-ACCESS  read-only
        STATUS  obsolete
        DESCRIPTION
            "simple auth"
        ::= { zxr10ospfv2IntfAuthTypeEntry 5 }
        

zxr10ospfv2IntfMdKeyTable OBJECT-TYPE
        SYNTAX  SEQUENCE OF Zxr10ospfv2IntfMdKeyEntry
        MAX-ACCESS  not-accessible
        STATUS  obsolete
        DESCRIPTION
            "An table to interface md5 auth"
        ::= { zxr10ospfInterfaceMIB 10 }

zxr10ospfv2IntfMdKeyEntry OBJECT-TYPE
        SYNTAX Zxr10ospfv2IntfMdKeyEntry
        MAX-ACCESS  not-accessible
        STATUS  obsolete
        DESCRIPTION
            "An entry to interface md5 auth."
        INDEX  { zxr10ospfv2IntfMdKeyProId,zxr10ospfv2IntfMdKeyIntfName,
                 zxr10ospfv2IntfMdKeyKeyId }
        ::= { zxr10ospfv2IntfMdKeyTable 1 }
            
Zxr10ospfv2IntfMdKeyEntry ::=
        SEQUENCE {
            zxr10ospfv2IntfMdKeyProId
                Unsigned32,
            zxr10ospfv2IntfMdKeyIntfName
                DisplayString,
            zxr10ospfv2IntfMdKeyKeyId
                Unsigned32,
            zxr10ospfv2IntfMdKeyMd5
                Unsigned32,
            zxr10ospfv2IntfMdKeyDelay
                Unsigned32,
            zxr10ospfv2IntfMdKeyEncypt
                DisplayString,
            zxr10ospfv2IntfMdKeyPassword
                DisplayString,
            zxr10ospfv2IntfMdKeyEncyptedPass
                DisplayString
        }

zxr10ospfv2IntfMdKeyProId OBJECT-TYPE
        SYNTAX Unsigned32
        MAX-ACCESS  not-accessible
        STATUS  obsolete
        DESCRIPTION
            "ospf instance ID"
        ::= { zxr10ospfv2IntfMdKeyEntry 1 }

zxr10ospfv2IntfMdKeyIntfName OBJECT-TYPE
        SYNTAX DisplayString (SIZE (1..31))
        MAX-ACCESS  not-accessible
        STATUS  obsolete
        DESCRIPTION
            "interface name"
        ::= { zxr10ospfv2IntfMdKeyEntry 2 }
        
zxr10ospfv2IntfMdKeyKeyId OBJECT-TYPE
        SYNTAX Unsigned32 (1..255)
        MAX-ACCESS  not-accessible
        STATUS  obsolete
        DESCRIPTION
            "md5 auth key ID"
        ::= { zxr10ospfv2IntfMdKeyEntry 3 }

zxr10ospfv2IntfMdKeyMd5 OBJECT-TYPE
        SYNTAX Unsigned32 (0..256)
        MAX-ACCESS  read-only
        STATUS  obsolete
        DESCRIPTION
            "md5 auth"
        ::= { zxr10ospfv2IntfMdKeyEntry 4 }

zxr10ospfv2IntfMdKeyDelay OBJECT-TYPE
        SYNTAX Unsigned32
        MAX-ACCESS  read-only
        STATUS  obsolete
        DESCRIPTION
            "delay of interface md5 auth"
        ::= { zxr10ospfv2IntfMdKeyEntry 5 }

zxr10ospfv2IntfMdKeyEncypt OBJECT-TYPE
        SYNTAX DisplayString (SIZE (1..16))
        MAX-ACCESS  read-only
        STATUS  obsolete
        DESCRIPTION
            "encypt interface md5 auth"
        ::= { zxr10ospfv2IntfMdKeyEntry 6 }

zxr10ospfv2IntfMdKeyPassword OBJECT-TYPE
        SYNTAX DisplayString (SIZE (1..16))
        MAX-ACCESS  read-only
        STATUS  obsolete
        DESCRIPTION
            "password of interface md5 auth"
        ::= { zxr10ospfv2IntfMdKeyEntry 7 }

zxr10ospfv2IntfMdKeyEncyptedPass OBJECT-TYPE
        SYNTAX DisplayString (SIZE (24))
        MAX-ACCESS  read-only
        STATUS  obsolete
        DESCRIPTION
            "encypted password of interface md5 auth"
        ::= { zxr10ospfv2IntfMdKeyEntry 8 }
        

zxr10ospfv2IntfTypeTable OBJECT-TYPE
        SYNTAX  SEQUENCE OF Zxr10ospfv2IntfTypeEntry
        MAX-ACCESS  not-accessible
        STATUS  obsolete
        DESCRIPTION
            "An table to interface type"
        ::= { zxr10ospfInterfaceMIB 11 }

zxr10ospfv2IntfTypeEntry OBJECT-TYPE
        SYNTAX Zxr10ospfv2IntfTypeEntry
        MAX-ACCESS  not-accessible
        STATUS  obsolete
        DESCRIPTION
            "An entry to interface type."
        INDEX  { zxr10ospfv2IntfTypeProId,zxr10ospfv2IntfTypeIntfName }
        ::= { zxr10ospfv2IntfTypeTable 1 }
            
Zxr10ospfv2IntfTypeEntry ::=
        SEQUENCE {
            zxr10ospfv2IntfTypeProId
                Unsigned32,
            zxr10ospfv2IntfTypeIntfName
                DisplayString,
            zxr10ospfv2IntfTypeType1
                INTEGER,
            zxr10ospfv2IntfTypeType2
                Unsigned32
        }

zxr10ospfv2IntfTypeProId OBJECT-TYPE
        SYNTAX Unsigned32
        MAX-ACCESS  not-accessible
        STATUS  obsolete
        DESCRIPTION
            "ospf instance ID"
        ::= { zxr10ospfv2IntfTypeEntry 1 }
        
zxr10ospfv2IntfTypeIntfName OBJECT-TYPE
        SYNTAX DisplayString (SIZE (1..31))
        MAX-ACCESS  not-accessible
        STATUS  obsolete
        DESCRIPTION
            "interface name"
        ::= { zxr10ospfv2IntfTypeEntry 2 }

zxr10ospfv2IntfTypeType1 OBJECT-TYPE
        SYNTAX INTEGER {broadcast(1),
                        nonbroadcast(2),
                        pointtopoint(3),
                        pointtomultipoint(5)}            
        MAX-ACCESS  read-only
        STATUS  obsolete
        DESCRIPTION
            "interface type flag1"
        ::= { zxr10ospfv2IntfTypeEntry 4 }

zxr10ospfv2IntfTypeType2 OBJECT-TYPE
        SYNTAX Unsigned32 (0..256)
        MAX-ACCESS  read-only
        STATUS  obsolete
        DESCRIPTION
            "interface type flag2"
        ::= { zxr10ospfv2IntfTypeEntry 5 }
        
                               
zxr10ospfv2IntfFastRerouteTable OBJECT-TYPE
        SYNTAX  SEQUENCE OF Zxr10ospfv2IntfFastRerouteEntry
        MAX-ACCESS  not-accessible
        STATUS  obsolete
        DESCRIPTION
            "An table to frr"
        ::= { zxr10ospfInterfaceMIB 12 }

zxr10ospfv2IntfFastRerouteEntry OBJECT-TYPE
        SYNTAX Zxr10ospfv2IntfFastRerouteEntry
        MAX-ACCESS  not-accessible
        STATUS  obsolete
        DESCRIPTION
            "An entry to frr."
        INDEX  { zxr10ospfv2IfFastRerouteProId,
                 zxr10ospfv2IfFastRerouteIfName }
        ::= { zxr10ospfv2IntfFastRerouteTable 1 }
            
Zxr10ospfv2IntfFastRerouteEntry ::=
        SEQUENCE {
            zxr10ospfv2IfFastRerouteProId
                Unsigned32,
            zxr10ospfv2IfFastRerouteIfName
                DisplayString,
            zxr10ospfv2IfFastRerouteBkIfName
                DisplayString,
            zxr10ospfv2IfFastRerouteDisable
                Unsigned32
        }

zxr10ospfv2IfFastRerouteProId OBJECT-TYPE
        SYNTAX Unsigned32
        MAX-ACCESS  not-accessible
        STATUS  obsolete
        DESCRIPTION
            "ospf instance ID"
        ::= { zxr10ospfv2IntfFastRerouteEntry 1 }
        
zxr10ospfv2IfFastRerouteIfName OBJECT-TYPE
        SYNTAX DisplayString (SIZE (1..31))
        MAX-ACCESS  not-accessible
        STATUS  obsolete
        DESCRIPTION
            "interface name"
        ::= { zxr10ospfv2IntfFastRerouteEntry 2 }

zxr10ospfv2IfFastRerouteBkIfName OBJECT-TYPE
        SYNTAX DisplayString (SIZE (1..31))
        MAX-ACCESS  read-only
        STATUS  obsolete
        DESCRIPTION
            "backup frr interface"
        ::= { zxr10ospfv2IntfFastRerouteEntry 4 }

zxr10ospfv2IfFastRerouteDisable OBJECT-TYPE
        SYNTAX Unsigned32 (0..256)
        MAX-ACCESS  read-only
        STATUS  obsolete
        DESCRIPTION
            "disable frr"
        ::= { zxr10ospfv2IntfFastRerouteEntry 5 }
        
zxr10ospfv2PassiveIntfTable OBJECT-TYPE
        SYNTAX  SEQUENCE OF Zxr10ospfv2PassiveIntfEntry
        MAX-ACCESS  not-accessible
        STATUS  current
        DESCRIPTION
            "An table to passive interface"
        ::= { zxr10ospfMIB 23 }
        
zxr10ospfv2PassiveIntfEntry OBJECT-TYPE
        SYNTAX Zxr10ospfv2PassiveIntfEntry
        MAX-ACCESS  not-accessible
        STATUS  current
        DESCRIPTION
            "An entry to passive interface."
        INDEX  { zxr10ospfv2PassiveIntfProId,zxr10ospfv2PassiveIntfIntfName,
                 zxr10ospfv2PassiveIntfDefault }
        ::= { zxr10ospfv2PassiveIntfTable 1 }
            
Zxr10ospfv2PassiveIntfEntry ::=
        SEQUENCE {
            zxr10ospfv2PassiveIntfProId
                Unsigned32,
            zxr10ospfv2PassiveIntfIntfName
                DisplayString,
            zxr10ospfv2PassiveIntfDefault
                Unsigned32,
            zxr10ospfv2PassiveIntfDisable
                Unsigned32
        }

zxr10ospfv2PassiveIntfProId OBJECT-TYPE
        SYNTAX Unsigned32
        MAX-ACCESS  not-accessible
        STATUS  current
        DESCRIPTION
            "ospf instance ID"
        ::= { zxr10ospfv2PassiveIntfEntry 1 }
        
zxr10ospfv2PassiveIntfIntfName OBJECT-TYPE
        SYNTAX DisplayString (SIZE (1..31))
        MAX-ACCESS  not-accessible
        STATUS  current
        DESCRIPTION
            "interface name"
        ::= { zxr10ospfv2PassiveIntfEntry 2 }

zxr10ospfv2PassiveIntfDefault OBJECT-TYPE
        SYNTAX Unsigned32 (0..256)
        MAX-ACCESS  not-accessible
        STATUS  current
        DESCRIPTION
            "default set"
        ::= { zxr10ospfv2PassiveIntfEntry 3 }

zxr10ospfv2PassiveIntfDisable OBJECT-TYPE
        SYNTAX Unsigned32 (0..256)
        MAX-ACCESS  read-only
        STATUS  current
        DESCRIPTION
            "disable passive interface"
        ::= { zxr10ospfv2PassiveIntfEntry 4 }
        
zxr10ospfv2NeighborTable OBJECT-TYPE
        SYNTAX  SEQUENCE OF Zxr10ospfv2NeighborEntry
        MAX-ACCESS  not-accessible
        STATUS  current
        DESCRIPTION
            "An table to neighbor"
        ::= { zxr10ospfMIB 24 }

zxr10ospfv2NeighborEntry OBJECT-TYPE
        SYNTAX Zxr10ospfv2NeighborEntry
        MAX-ACCESS  not-accessible
        STATUS  current
        DESCRIPTION
            "An entry to neighbor."
        INDEX  { zxr10ospfv2NeighborProId,zxr10ospfv2NeighborIpAddress }
        ::= { zxr10ospfv2NeighborTable 1 }
            
Zxr10ospfv2NeighborEntry ::=
        SEQUENCE {
            zxr10ospfv2NeighborProId
                Unsigned32,
            zxr10ospfv2NeighborIpAddress
                IpAddress,
            zxr10ospfv2NeighborCost
                Unsigned32,
            zxr10ospfv2NeighborPriority
                Unsigned32,
            zxr10ospfv2NeighborPollInterval
                Unsigned32
        }

zxr10ospfv2NeighborProId OBJECT-TYPE
        SYNTAX Unsigned32
        MAX-ACCESS  not-accessible
        STATUS  current
        DESCRIPTION
            "ospf instance ID"
        ::= { zxr10ospfv2NeighborEntry 1 }

zxr10ospfv2NeighborIpAddress OBJECT-TYPE
        SYNTAX IpAddress
        MAX-ACCESS  not-accessible
        STATUS  current
        DESCRIPTION
            "ip address of neighbor"
        ::= { zxr10ospfv2NeighborEntry 2 }
        
zxr10ospfv2NeighborCost OBJECT-TYPE
        SYNTAX Unsigned32 (0..65535|65536)
        MAX-ACCESS  read-only
        STATUS  current
        DESCRIPTION
            "cost of neighbor.  The value 65536 is invalid."
        ::= { zxr10ospfv2NeighborEntry 3 }

zxr10ospfv2NeighborPriority OBJECT-TYPE
        SYNTAX Unsigned32
        MAX-ACCESS  read-only
        STATUS  current
        DESCRIPTION
            "priority of neighbor"
        ::= { zxr10ospfv2NeighborEntry 4 }

zxr10ospfv2NeighborPollInterval OBJECT-TYPE
        SYNTAX Unsigned32 (0|1..65535)
        MAX-ACCESS  read-only
        STATUS  current
        DESCRIPTION
            "pollinterval of neighbor. The value 0 is invalid."
        ::= { zxr10ospfv2NeighborEntry 5 }
        
zxr10ospfv2FilterTable OBJECT-TYPE
        SYNTAX  SEQUENCE OF Zxr10ospfv2FilterEntry
        MAX-ACCESS  not-accessible
        STATUS  current
        DESCRIPTION
            "An table to filter"
        ::= { zxr10ospfMIB 25 }

zxr10ospfv2FilterEntry OBJECT-TYPE
        SYNTAX Zxr10ospfv2FilterEntry
        MAX-ACCESS  not-accessible
        STATUS  current
        DESCRIPTION
            "An entry to filter."
        INDEX  { zxr10ospfv2FilterProId,zxr10ospfv2FilterIpAddr,
                 zxr10ospfv2FilterNetMask }
        ::= { zxr10ospfv2FilterTable 1 }
            
Zxr10ospfv2FilterEntry ::=
        SEQUENCE {
            zxr10ospfv2FilterProId
                Unsigned32,
            zxr10ospfv2FilterIpAddr
                IpAddress,
            zxr10ospfv2FilterNetMask
                IpAddress,
            zxr10ospfv2FilterExact
                Unsigned32,
            zxr10ospfv2FilterPreference
                Unsigned32
        }

zxr10ospfv2FilterProId OBJECT-TYPE
        SYNTAX Unsigned32
        MAX-ACCESS  not-accessible
        STATUS  current
        DESCRIPTION
            "ospf instance ID"
        ::= { zxr10ospfv2FilterEntry 1 }
        
zxr10ospfv2FilterIpAddr OBJECT-TYPE
        SYNTAX IpAddress
        MAX-ACCESS  not-accessible
        STATUS  current
        DESCRIPTION
            "the ip address of filter"
        ::= { zxr10ospfv2FilterEntry 2 }

zxr10ospfv2FilterNetMask OBJECT-TYPE
        SYNTAX IpAddress
        MAX-ACCESS  not-accessible
        STATUS  current
        DESCRIPTION
            "mask of filter"
        ::= { zxr10ospfv2FilterEntry 3 }

zxr10ospfv2FilterExact OBJECT-TYPE
        SYNTAX Unsigned32
        MAX-ACCESS  read-only
        STATUS  current
        DESCRIPTION
            "exact filter"
        ::= { zxr10ospfv2FilterEntry 4 }

zxr10ospfv2FilterPreference OBJECT-TYPE
        SYNTAX Unsigned32  (0|1..255)
        MAX-ACCESS  read-only
        STATUS  current
        DESCRIPTION
            "preference of filter. The value 0 is invalid."
        ::= { zxr10ospfv2FilterEntry 5 }

zxr10ospfv2BfdTable OBJECT-TYPE
        SYNTAX  SEQUENCE OF Zxr10ospfv2BfdEntry
        MAX-ACCESS  not-accessible
        STATUS  obsolete
        DESCRIPTION
            "An table to BFD"
        ::= { zxr10ospfMIB 26 }

zxr10ospfv2BfdEntry OBJECT-TYPE
        SYNTAX Zxr10ospfv2BfdEntry
        MAX-ACCESS  not-accessible
        STATUS  obsolete
        DESCRIPTION
            "An entry to BFD."
        INDEX  { zxr10ospfv2BfdProId,zxr10ospfv2BfdAreaId,
                 zxr10ospfv2BfdAreaId1}
        ::= { zxr10ospfv2BfdTable 1 }
            
Zxr10ospfv2BfdEntry ::=
        SEQUENCE {
            zxr10ospfv2BfdProId
                Unsigned32,
            zxr10ospfv2BfdAreaId
                Unsigned32,
            zxr10ospfv2BfdAreaId1
                IpAddress,
            zxr10ospfv2BfdAreaFlag
                Unsigned32,
            zxr10ospfv2BfdEnable
                Unsigned32
        }

zxr10ospfv2BfdProId OBJECT-TYPE
        SYNTAX Unsigned32
        MAX-ACCESS  not-accessible
        STATUS  obsolete
        DESCRIPTION
            "ospf instance ID"
        ::= { zxr10ospfv2BfdEntry 1 }
        
zxr10ospfv2BfdAreaId OBJECT-TYPE
        SYNTAX Unsigned32
        MAX-ACCESS  not-accessible
        STATUS  obsolete
        DESCRIPTION
            "area ID"
        ::= { zxr10ospfv2BfdEntry 2 }

zxr10ospfv2BfdAreaId1 OBJECT-TYPE
        SYNTAX IpAddress
        MAX-ACCESS  not-accessible
        STATUS  obsolete
        DESCRIPTION
            "area ID"
        ::= { zxr10ospfv2BfdEntry 3 }

zxr10ospfv2BfdAreaFlag OBJECT-TYPE
        SYNTAX Unsigned32 (1..2)
        MAX-ACCESS  not-accessible
        STATUS  obsolete
        DESCRIPTION
            "area BFD"
        ::= { zxr10ospfv2BfdEntry 4 }

zxr10ospfv2BfdEnable OBJECT-TYPE
        SYNTAX Unsigned32
        MAX-ACCESS  read-only
        STATUS  obsolete
        DESCRIPTION
            "enable BFD"
        ::= { zxr10ospfv2BfdEntry 5 }
 
zxr10ospfv2SummaryAddrTable OBJECT-TYPE
        SYNTAX  SEQUENCE OF Zxr10ospfv2SummaryAddrEntry
        MAX-ACCESS  not-accessible
        STATUS  current
        DESCRIPTION
            "An table to summary"
        ::= { zxr10ospfMIB 27 }

zxr10ospfv2SummaryAddrEntry OBJECT-TYPE
        SYNTAX Zxr10ospfv2SummaryAddrEntry
        MAX-ACCESS  not-accessible
        STATUS  current
        DESCRIPTION
            "An entry to summary."
        INDEX  { zxr10ospfv2SummaryAddrProId,zxr10ospfv2SummaryAddrIpAddr,
                 zxr10ospfv2SummaryAddrNetMask }
        ::= { zxr10ospfv2SummaryAddrTable 1 }
            
Zxr10ospfv2SummaryAddrEntry ::=
        SEQUENCE {
            zxr10ospfv2SummaryAddrProId
                Unsigned32,
            zxr10ospfv2SummaryAddrIpAddr
                IpAddress,
            zxr10ospfv2SummaryAddrNetMask
                IpAddress,
            zxr10ospfv2SummaryAddrCostValue
                Unsigned32
        }

zxr10ospfv2SummaryAddrProId OBJECT-TYPE
        SYNTAX Unsigned32
        MAX-ACCESS  not-accessible
        STATUS  current
        DESCRIPTION
            "ospf instance ID"
        ::= { zxr10ospfv2SummaryAddrEntry 1 }
        
zxr10ospfv2SummaryAddrIpAddr OBJECT-TYPE
        SYNTAX IpAddress
        MAX-ACCESS  not-accessible
        STATUS  current
        DESCRIPTION
            "summary address"
        ::= { zxr10ospfv2SummaryAddrEntry 2 }

zxr10ospfv2SummaryAddrNetMask OBJECT-TYPE
        SYNTAX IpAddress
        MAX-ACCESS  not-accessible
        STATUS  current
        DESCRIPTION
            "summary address net mask"
        ::= { zxr10ospfv2SummaryAddrEntry 3 }

zxr10ospfv2SummaryAddrCostValue OBJECT-TYPE
        SYNTAX Unsigned32 (0|1..16777214)
        MAX-ACCESS  read-only
        STATUS  current
        DESCRIPTION
            "cost value of summary address. The value 0 is invalid."
        ::= { zxr10ospfv2SummaryAddrEntry 4 }
                     
zxr10ospfv2AreaBfdTable OBJECT-TYPE
        SYNTAX  SEQUENCE OF Zxr10ospfv2AreaBfdEntry
        MAX-ACCESS  not-accessible
        STATUS  current
        DESCRIPTION
            "An table to BFD"
        ::= { zxr10ospfMIB 28 }

zxr10ospfv2AreaBfdEntry OBJECT-TYPE
        SYNTAX Zxr10ospfv2AreaBfdEntry
        MAX-ACCESS  not-accessible
        STATUS  current
        DESCRIPTION
            "An entry to BFD."
        INDEX  { zxr10ospfv2AreaBfdProId,zxr10ospfv2AreaBfdAreaId,
                 zxr10ospfv2AreaBfdAreaId1 }
        ::= { zxr10ospfv2AreaBfdTable 1 }
            
Zxr10ospfv2AreaBfdEntry ::=
        SEQUENCE {
            zxr10ospfv2AreaBfdProId
                Unsigned32,
            zxr10ospfv2AreaBfdAreaId
                Unsigned32,
            zxr10ospfv2AreaBfdAreaId1
                IpAddress,
            zxr10ospfv2AreaBfdEnable
                Unsigned32,
            zxr10ospfv2AreaBfdInterval
                Unsigned32,
            zxr10ospfv2AreaBfdMinRx
                Unsigned32,
            zxr10ospfv2AreaBfdMultiplier
                Unsigned32
        }

zxr10ospfv2AreaBfdProId OBJECT-TYPE
        SYNTAX Unsigned32
        MAX-ACCESS  not-accessible
        STATUS  current
        DESCRIPTION
            "ospf instance ID"
        ::= { zxr10ospfv2AreaBfdEntry 1 }
        
zxr10ospfv2AreaBfdAreaId OBJECT-TYPE
        SYNTAX Unsigned32
        MAX-ACCESS  not-accessible
        STATUS  current
        DESCRIPTION
            "area ID"
        ::= { zxr10ospfv2AreaBfdEntry 2 }

zxr10ospfv2AreaBfdAreaId1 OBJECT-TYPE
        SYNTAX IpAddress
        MAX-ACCESS  not-accessible
        STATUS  current
        DESCRIPTION
            "area ID"
        ::= { zxr10ospfv2AreaBfdEntry 3 }

zxr10ospfv2AreaBfdEnable OBJECT-TYPE
        SYNTAX Unsigned32
        MAX-ACCESS  read-only
        STATUS  current
        DESCRIPTION
            "enable BFD"
        ::= { zxr10ospfv2AreaBfdEntry 4 }

zxr10ospfv2AreaBfdInterval OBJECT-TYPE
        SYNTAX Unsigned32 (10..990)
        MAX-ACCESS  read-only
        STATUS  current
        DESCRIPTION
            "area BFD interval"
        ::= { zxr10ospfv2AreaBfdEntry 5 }

zxr10ospfv2AreaBfdMinRx OBJECT-TYPE
        SYNTAX Unsigned32 (10..990)
        MAX-ACCESS  read-only
        STATUS  current
        DESCRIPTION
            "area BFD min_rx"
        ::= { zxr10ospfv2AreaBfdEntry 6 }

zxr10ospfv2AreaBfdMultiplier OBJECT-TYPE
        SYNTAX Unsigned32 (3..50)
        MAX-ACCESS  read-only
        STATUS  current
        DESCRIPTION
            "area BFD"
        ::= { zxr10ospfv2AreaBfdEntry 7 }

zxr10ospfv2DynamicRlfaTable OBJECT-TYPE
        SYNTAX  SEQUENCE OF Zxr10ospfv2DynamicRlfaEntry
        MAX-ACCESS  not-accessible
        STATUS  current
        DESCRIPTION
            "An table to ospf dynamic remote lfa"
        ::= { zxr10ospfMIB 29 }

zxr10ospfv2DynamicRlfaEntry OBJECT-TYPE
        SYNTAX Zxr10ospfv2DynamicRlfaEntry
        MAX-ACCESS  not-accessible
        STATUS  current
        DESCRIPTION
            "An entry to ospf dynamic remote lfa"
        INDEX  { zxr10ospfv2DynamicRlfaProId }
        ::= { zxr10ospfv2DynamicRlfaTable 1 }
            
Zxr10ospfv2DynamicRlfaEntry ::=
        SEQUENCE {
            zxr10ospfv2DynamicRlfaProId
                Unsigned32,
            zxr10ospfv2DynamicRlfaCapability
                INTEGER,
            zxr10ospfv2DynamicRlfaMaximumCost
                Unsigned32
        }

zxr10ospfv2DynamicRlfaProId OBJECT-TYPE
        SYNTAX Unsigned32 (1..65535)
        MAX-ACCESS  read-only
        STATUS  current
        DESCRIPTION
            "ospf instance number"
        ::= { zxr10ospfv2DynamicRlfaEntry 1 }
        
zxr10ospfv2DynamicRlfaCapability OBJECT-TYPE
        SYNTAX INTEGER{enable(1),disable(2)}
        MAX-ACCESS  read-only
        STATUS  current
        DESCRIPTION
            "capability : 1 enable, 2 disable"
        ::= { zxr10ospfv2DynamicRlfaEntry 2 }
        
zxr10ospfv2DynamicRlfaMaximumCost OBJECT-TYPE
        SYNTAX Unsigned32 (1..16777214)
        MAX-ACCESS  read-only
        STATUS  current
        DESCRIPTION
            "ospf dynamic rlfa maximum-cost"
        ::= { zxr10ospfv2DynamicRlfaEntry 3 }

zxr10ospfv2FrrPriorityTable OBJECT-TYPE
        SYNTAX  SEQUENCE OF Zxr10ospfv2FrrPriorityEntry
        MAX-ACCESS  not-accessible
        STATUS  current
        DESCRIPTION
            "An table to ospf frr priority"
        ::= { zxr10ospfMIB 30 }

zxr10ospfv2FrrPriorityEntry OBJECT-TYPE
        SYNTAX Zxr10ospfv2FrrPriorityEntry
        MAX-ACCESS  not-accessible
        STATUS  current
        DESCRIPTION
            "An entry to ospf frr priority"
        INDEX  { zxr10ospfv2FrrPriorityProId }
        ::= { zxr10ospfv2FrrPriorityTable 1 }
            
Zxr10ospfv2FrrPriorityEntry ::=
        SEQUENCE {
            zxr10ospfv2FrrPriorityProId
                Unsigned32,
            zxr10ospfv2FrrPriorityLfa
                Unsigned32,
            zxr10ospfv2FrrPriorityDynamicRlfa
                Unsigned32,
            zxr10ospfv2FrrPriorityStaticRlfa
                Unsigned32
        }

zxr10ospfv2FrrPriorityProId OBJECT-TYPE
        SYNTAX Unsigned32 (1..65535)
        MAX-ACCESS  read-only
        STATUS  current
        DESCRIPTION
            "ospf instance number"
        ::= { zxr10ospfv2FrrPriorityEntry 1 }
        
zxr10ospfv2FrrPriorityLfa OBJECT-TYPE
        SYNTAX Unsigned32 (1..255)
        MAX-ACCESS  read-only
        STATUS  current
        DESCRIPTION
            "ospf lfa priority"
        ::= { zxr10ospfv2FrrPriorityEntry 2 }
        
zxr10ospfv2FrrPriorityDynamicRlfa OBJECT-TYPE
        SYNTAX Unsigned32 (1..255)
        MAX-ACCESS  read-only
        STATUS  current
        DESCRIPTION
            "ospf dynamic rlfa priority"
        ::= { zxr10ospfv2FrrPriorityEntry 3 }

zxr10ospfv2FrrPriorityStaticRlfa OBJECT-TYPE
        SYNTAX Unsigned32 (1..255)
        MAX-ACCESS  read-only
        STATUS  current
        DESCRIPTION
            "ospf static rlfa priority"
        ::= { zxr10ospfv2FrrPriorityEntry 4 }

zxr10ospfv2BgpLsTable OBJECT-TYPE
        SYNTAX  SEQUENCE OF Zxr10ospfv2BgpLsEntry
        MAX-ACCESS  not-accessible
        STATUS  current
        DESCRIPTION
            "An table to ospf BGP link-state"
        ::= { zxr10ospfMIB 31 }

zxr10ospfv2BgpLsEntry OBJECT-TYPE
        SYNTAX Zxr10ospfv2BgpLsEntry
        MAX-ACCESS  not-accessible
        STATUS  current
        DESCRIPTION
            "An entry to ospf BGP link-state"
        INDEX  { zxr10ospfv2BgpLsProcId, zxr10ospfv2BgpLsEnable }
        ::= { zxr10ospfv2BgpLsTable 1 }
            
Zxr10ospfv2BgpLsEntry ::=
        SEQUENCE {
            zxr10ospfv2BgpLsProcId
                Unsigned32,
            zxr10ospfv2BgpLsEnable
                TruthValue,
            zxr10ospfv2BgpLsInstanceId
                Unsigned32
        }

zxr10ospfv2BgpLsProcId OBJECT-TYPE
        SYNTAX Unsigned32 (1..65535)
        MAX-ACCESS  not-accessible
        STATUS  current
        DESCRIPTION
            "ospf process Id"
        ::= { zxr10ospfv2BgpLsEntry 1 }
        
zxr10ospfv2BgpLsEnable OBJECT-TYPE
        SYNTAX TruthValue
        MAX-ACCESS  not-accessible
        STATUS  current
        DESCRIPTION
            "ospf BGP link-state enable"
        ::= { zxr10ospfv2BgpLsEntry 2 }
        
zxr10ospfv2BgpLsInstanceId OBJECT-TYPE
        SYNTAX Unsigned32 (0..65535)
        MAX-ACCESS  read-only
        STATUS  current
        DESCRIPTION
            "ospf BGP link-state instance-id"
        ::= { zxr10ospfv2BgpLsEntry 3 }

END
