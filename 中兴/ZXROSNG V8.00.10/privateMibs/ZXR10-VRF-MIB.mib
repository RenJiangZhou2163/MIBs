ZXR10-VRF-MIB DEFINITIONS ::= BEGIN

IMPORTS
        MODULE-IDENTITY, OBJECT-TYPE,
        enterprises, Unsigned32, Counter64, IpAddress
                FROM SNMPv2-SMI
        DisplayString
                FROM SNMPv2-TC;

zxr10vrf MODULE-IDENTITY
        LAST-UPDATED "201605270000Z"
        ORGANIZATION "ZTE Corp."
        CONTACT-INFO
               "ZTE Corporation 
         Nanjing Institute of ZTE Corporation
         
         No.68 Zijinghua Rd. Yuhuatai District, Nanjing, China
         
         Tel: +86-25-52870000"
        DESCRIPTION
                "VRF configuration information"
        REVISION "201605270000Z"
        DESCRIPTION
                "add one node in zxr10addressFamilyModeEntry:
                 zxr10addressFamilyModeEvpnGwIp.
                  "
        REVISION "201507200000Z"
        DESCRIPTION
                "add one node in zxr10vrfEnabledObjectsTable:
                 zxr10vrfEnabledObjectsELC.
                  "
        REVISION "201407020000Z"
        DESCRIPTION
                "Modify the zxr10vrfDescription range from 80 up to 104.
                  "
        REVISION "201404220000Z"
        DESCRIPTION
                "add one table in zxr10addressFamilyModeV6MIB:
                 zxr10vrfTunnelPolicyV6Table,
                   zxr10vrfTunnelPolicyV6Entry,
                     zxr10vrfTunnelPolicyV6VrfName,
                     zxr10vrfTunnelPolicyV6AfiMode,
                     zxr10vrfTunnelPolicyV6PeerAddr,
                     zxr10vrfTunnelPolicyV6PolicyName
                  "
        REVISION "201402180000Z"
        DESCRIPTION
                "add one node in Zxr10addressFamilyModeEntry: 
                    zxr10addressFamilyModeNextHopHostOnly
                  "
        REVISION "201402110000Z"
        DESCRIPTION
                "modify the following nodes value range: 
                  zxr10vrfVrfName
                  zxr10vrfDescription
                  zxr10rdEnabledVrfName
                  zxr10rdRd
                  zxr10vrfEnabledObjectsEnabledVrfName
                  zxr10vrfRateLimitVrfName
                  zxr10globalRtEnabledVrfName
                  zxr10globalRtRtVrf
                  zxr10addressFamilyModeAddrFamilyEnabledVrfName
                  zxr10addressFamilyModeExportMap
                  zxr10addressFamilyModeImportMap
                  zxr10addressFamilyModeImportMulticastRoute
                  zxr10rtAddrFamilyEnabledVrfName
                  zxr10rtRtIpv4
                  zxr10staticOutlabelAddrFamilyEnabledVrfName
                  zxr10vrfTunnelPolicyVrfName
                  zxr10vrfTunnelPolicyPolicyName
                  zxr10addressFamilyModeV6AddrFamilyEnabledVrfName
                  zxr10addressFamilyModeV6ExportMap
                  zxr10addressFamilyModeV6ImportMap
                  zxr10addressFamilyV6MulticastRT
                  zxr10rtV6AddrFamilyEnabledVrfName
                  zxr10rtV6RtIpv6
                  zxr10vrfMplsLabelModeEnabledVrfName
                  "
        REVISION "201311270000Z"
        DESCRIPTION
                "add one node in Zxr10addressFamilyModeV6Entry: 
                    zxr10addressFamilyV6MulticastRT,
                  "
        REVISION "201308280000Z"
        DESCRIPTION
                "add three nodes in Zxr10addressFamilyModeV6Entry: 
                    zxr10addressFamilyV6MaxPrefix,
                    zxr10addressFamilyV6MaxWarning,
                    zxr10addressFamilyModeV6LocalPre
                  "
        REVISION "201308190000Z"
        DESCRIPTION
                "add one node in zxr10vrfEnabledObjectsTable:
                 zxr10vrfEnabledObjectsNatType
                  "
        REVISION "201306080000Z"
        DESCRIPTION
                "add one table in zxr10rdMIB: 
                 zxr10vrfRateLimitTable,
                   zxr10vrfRateLimitEntry,
                     zxr10vrfRateLimitVrfName,
                     zxr10vrfRateLimitPeer,
                     zxr10vrfRateLimitMode,
                     zxr10vrfRateLimitCirValue,
                     zxr10vrfRateLimitCbsValue,
                     zxr10vrfRateLimitPirValue,
                     zxr10vrfRateLimitPbsValue
                  "
        REVISION "201305170000Z"
        DESCRIPTION
                "add two nodes in zxr10vrfEnabledObjectsTable: 
                 zxr10vrfEnabledObjectsDsModeSer,
                 zxr10vrfEnabledObjectsDsModeCol
                  "
        REVISION "201305070000Z"
        DESCRIPTION
                "add an invalid-value in description: 
                            zxr10vrfEnabledObjectsStaticInlabel,
                            zxr10addressFamilyModeMaxPrefix,
                             zxr10addressFamilyModeMaxPrefixWarning
                              "
        REVISION "201102090000Z"
        DESCRIPTION
                "VRF configuration information"
        ::= { zxr10vrfMIBs 1 }

    zte OBJECT IDENTIFIER ::= { enterprises 3902 }

    zxr10 OBJECT IDENTIFIER ::= { zte 3}

    zxr10RosngMIB OBJECT IDENTIFIER ::= { zxr10 6000}

    zxr10vrfMIBs OBJECT IDENTIFIER ::= { zxr10RosngMIB 159}

        
zxr10vrfMIB OBJECT IDENTIFIER ::= { zxr10vrf 1 }

zxr10vrfTable OBJECT-TYPE
        SYNTAX  SEQUENCE OF Zxr10vrfEntry
        MAX-ACCESS  not-accessible
        STATUS  current
        DESCRIPTION
            "An table to VRF"  
        ::= { zxr10vrfMIB 1 }

zxr10vrfEntry OBJECT-TYPE
        SYNTAX Zxr10vrfEntry
        MAX-ACCESS  not-accessible
        STATUS  current
        DESCRIPTION
            "An entry to VRF"
        INDEX  { zxr10vrfVrfName }
        ::= { zxr10vrfTable 1 }
            
Zxr10vrfEntry ::=
        SEQUENCE {
            zxr10vrfVrfName
                DisplayString,
            zxr10vrfDescription
                DisplayString,
            zxr10vrfVpnid
                Unsigned32
        }

zxr10vrfVrfName OBJECT-TYPE
        SYNTAX DisplayString (SIZE (1..32))
        MAX-ACCESS  read-only
        STATUS  current
        DESCRIPTION
            "VRF name"
        ::= { zxr10vrfEntry 1 }

zxr10vrfDescription OBJECT-TYPE
        SYNTAX DisplayString (SIZE (1..104))
        MAX-ACCESS  read-only
        STATUS  current
        DESCRIPTION
            "VRF description"
        ::= { zxr10vrfEntry 2 }

zxr10vrfVpnid OBJECT-TYPE
        SYNTAX Unsigned32 (1..16384)
        MAX-ACCESS  read-only
        STATUS  current
        DESCRIPTION
            "VPN ID"
        ::= { zxr10vrfEntry 3 }


zxr10rdMIB OBJECT IDENTIFIER ::= { zxr10vrfMIB 2 }

zxr10rdTable OBJECT-TYPE
        SYNTAX  SEQUENCE OF Zxr10rdEntry
        MAX-ACCESS  not-accessible
        STATUS  current
        DESCRIPTION
            "An table to RD"
        ::= { zxr10rdMIB 1 }

zxr10rdEntry OBJECT-TYPE
        SYNTAX Zxr10rdEntry
        MAX-ACCESS  not-accessible
        STATUS  current
        DESCRIPTION
            "An entry to RD"
        INDEX  { zxr10rdEnabledVrfName,zxr10rdRd }
        ::= { zxr10rdTable 1 }
            
Zxr10rdEntry ::=
        SEQUENCE {
            zxr10rdEnabledVrfName
                DisplayString,
            zxr10rdRd
                DisplayString,
            zxr10rdVpnId
                Unsigned32
        }

zxr10rdEnabledVrfName OBJECT-TYPE
        SYNTAX DisplayString (SIZE (1..32))
        MAX-ACCESS  read-only
        STATUS  current
        DESCRIPTION
            "VRF name"
        ::= { zxr10rdEntry 1 }

zxr10rdRd OBJECT-TYPE
        SYNTAX DisplayString (SIZE (3..21))
        MAX-ACCESS  read-only
        STATUS  current
        DESCRIPTION
            "RD"
        ::= { zxr10rdEntry 2 }

zxr10rdVpnId OBJECT-TYPE
        SYNTAX Unsigned32 (1..16384)
        MAX-ACCESS  read-only
        STATUS  current
        DESCRIPTION
            "VPN ID"
        ::= { zxr10rdEntry 3 }



zxr10vrfEnabledObjectsTable OBJECT-TYPE
        SYNTAX  SEQUENCE OF Zxr10vrfEnabledObjectsEntry
        MAX-ACCESS  not-accessible
        STATUS  current
        DESCRIPTION
            "An table to VRF"
        ::= { zxr10rdMIB 2 }

zxr10vrfEnabledObjectsEntry OBJECT-TYPE
        SYNTAX Zxr10vrfEnabledObjectsEntry
        MAX-ACCESS  not-accessible
        STATUS  current
        DESCRIPTION
            "An entry to VRF"
        INDEX  { zxr10vrfEnabledObjectsEnabledVrfName }
        ::= { zxr10vrfEnabledObjectsTable 1 }
            
Zxr10vrfEnabledObjectsEntry ::=
        SEQUENCE {
            zxr10vrfEnabledObjectsEnabledVrfName
                DisplayString,
            zxr10vrfEnabledObjectsTtlMode
                Unsigned32,
            zxr10vrfEnabledObjectsDsMode
                Unsigned32,
            zxr10vrfEnabledObjectsStaticInlabel
                Unsigned32,  
            zxr10vrfEnabledObjectsDsModeSer
                INTEGER,
            zxr10vrfEnabledObjectsDsModeCol
                INTEGER,
            zxr10vrfEnabledObjectsNatType
                INTEGER,
            zxr10vrfEnabledObjectsELC
                INTEGER
        }

zxr10vrfEnabledObjectsEnabledVrfName OBJECT-TYPE
        SYNTAX DisplayString (SIZE (1..32))
        MAX-ACCESS  read-only
        STATUS  current
        DESCRIPTION
            "VRF name"
        ::= { zxr10vrfEnabledObjectsEntry 1 }

zxr10vrfEnabledObjectsTtlMode OBJECT-TYPE
        SYNTAX Unsigned32 {uniform(1),pipe(2)}                   
        MAX-ACCESS  read-only
        STATUS  current
        DESCRIPTION
            "ttl-mode"
        ::= { zxr10vrfEnabledObjectsEntry 2 }

zxr10vrfEnabledObjectsDsMode OBJECT-TYPE
        SYNTAX Unsigned32 {uniform(1),pipe(2),short-pipe(3)}        
        MAX-ACCESS  read-only
        STATUS  current
        DESCRIPTION
            "ds-mode"
        ::= { zxr10vrfEnabledObjectsEntry 3 }

zxr10vrfEnabledObjectsStaticInlabel OBJECT-TYPE
        SYNTAX Unsigned32 (16..1048575)
        MAX-ACCESS  read-only
        STATUS  current
        DESCRIPTION
            "static In-label,0 is invalid-value."
        ::= { zxr10vrfEnabledObjectsEntry 4 }

zxr10vrfEnabledObjectsDsModeSer OBJECT-TYPE
        SYNTAX INTEGER {be(1),af1(2),af2(3),af3(4),
                        af4(5),ef(6),cs6(7),cs7(8),invalid(100)}
        MAX-ACCESS  read-only
        STATUS  current
        DESCRIPTION
            "Ds-mode service class,invalid(100) is invalid-value"
        ::= { zxr10vrfEnabledObjectsEntry 6 }

zxr10vrfEnabledObjectsDsModeCol OBJECT-TYPE
        SYNTAX INTEGER {green(1),yellow(2),red(3),invalid(100)}
        MAX-ACCESS  read-only
        STATUS  current
        DESCRIPTION
            "Ds-mode color,invalid(100) is invalid-value."
        ::= { zxr10vrfEnabledObjectsEntry 7 }
zxr10vrfEnabledObjectsNatType OBJECT-TYPE
        SYNTAX INTEGER {inside(1),none(2)}
        MAX-ACCESS  read-only
        STATUS  current
        DESCRIPTION
            "Nat-type of VRF"
        ::= { zxr10vrfEnabledObjectsEntry 8 }
zxr10vrfEnabledObjectsELC OBJECT-TYPE
        SYNTAX INTEGER {enable(1),disable(2)}
        MAX-ACCESS  read-only
        STATUS  current
        DESCRIPTION
            "The entroy label capability of VRF."
        ::= { zxr10vrfEnabledObjectsEntry 9 }



zxr10vrfRateLimitTable OBJECT-TYPE
        SYNTAX  SEQUENCE OF Zxr10vrfRateLimitEntry
        MAX-ACCESS  not-accessible
        STATUS  current
        DESCRIPTION
            "An table to VRF rate limit strategy"
        ::= { zxr10rdMIB 3 }

zxr10vrfRateLimitEntry OBJECT-TYPE
        SYNTAX Zxr10vrfRateLimitEntry
        MAX-ACCESS  not-accessible
        STATUS  current
        DESCRIPTION
            "An entry to VRF rate limit strategy"
        INDEX  { zxr10vrfRateLimitVrfName,zxr10vrfRateLimitPeer }
        ::= { zxr10vrfRateLimitTable 1 }
            
Zxr10vrfRateLimitEntry ::=
        SEQUENCE {
            zxr10vrfRateLimitVrfName
                DisplayString,
            zxr10vrfRateLimitPeer
                IpAddress,
            zxr10vrfRateLimitMode
                INTEGER,
            zxr10vrfRateLimitCirValue
                Unsigned32,
            zxr10vrfRateLimitCbsValue
                Unsigned32,
            zxr10vrfRateLimitPirValue
                Unsigned32,
            zxr10vrfRateLimitPbsValue
                Unsigned32
        }

zxr10vrfRateLimitVrfName OBJECT-TYPE
        SYNTAX DisplayString (SIZE (1..32))
        MAX-ACCESS  not-accessible
        STATUS  current
        DESCRIPTION
            "VRF name"
        ::= { zxr10vrfRateLimitEntry 1 }

zxr10vrfRateLimitPeer OBJECT-TYPE
        SYNTAX IpAddress
        MAX-ACCESS  not-accessible
        STATUS  current
        DESCRIPTION
            "VRF peer"
        ::= { zxr10vrfRateLimitEntry 2 }

zxr10vrfRateLimitMode OBJECT-TYPE
        SYNTAX INTEGER {blind(1),aware(2)}
        MAX-ACCESS  read-only
        STATUS  current
        DESCRIPTION
            "VRF rate limit mode"
        ::= { zxr10vrfRateLimitEntry 3 }

zxr10vrfRateLimitCirValue OBJECT-TYPE
        SYNTAX Unsigned32 (8..20000000)
        MAX-ACCESS  read-only
        STATUS  current
        DESCRIPTION
            "Committed information rate(kbps),
               this value must be equal or smaller than zxr10vrfRateLimitPirValue."
        ::= { zxr10vrfRateLimitEntry 4 }

zxr10vrfRateLimitCbsValue OBJECT-TYPE
        SYNTAX Unsigned32 (1..5120000)
        MAX-ACCESS  read-only
        STATUS  current
        DESCRIPTION
            "Committed burst size(bytes)"
        ::= { zxr10vrfRateLimitEntry 5 }

zxr10vrfRateLimitPirValue OBJECT-TYPE
        SYNTAX Unsigned32 (8..20000000)
        MAX-ACCESS  read-only
        STATUS  current
        DESCRIPTION
            "Peak information rate(kbps)"
        ::= { zxr10vrfRateLimitEntry 6 }

zxr10vrfRateLimitPbsValue OBJECT-TYPE
        SYNTAX Unsigned32 (1..5120000)
        MAX-ACCESS  read-only
        STATUS  current
        DESCRIPTION
            "Peak Burst Size(bytes)"
        ::= { zxr10vrfRateLimitEntry 7 }



zxr10globalRtTable OBJECT-TYPE
        SYNTAX  SEQUENCE OF Zxr10globalRtEntry
        MAX-ACCESS  not-accessible
        STATUS  current
        DESCRIPTION
            "An table to RT"
        ::= { zxr10vrfMIB 3 }

zxr10globalRtEntry OBJECT-TYPE
        SYNTAX Zxr10globalRtEntry
        MAX-ACCESS  not-accessible
        STATUS  current
        DESCRIPTION
            "An entry to RT"
        INDEX  { zxr10globalRtEnabledVrfName,
                 zxr10globalRtRtVrf,
                 zxr10globalRtRtAction }
        ::= { zxr10globalRtTable 1 }
            
Zxr10globalRtEntry ::=
        SEQUENCE {
            zxr10globalRtEnabledVrfName
                DisplayString,
            zxr10globalRtRtVrf
                DisplayString,
            zxr10globalRtRtAction
                Unsigned32
        }

zxr10globalRtEnabledVrfName OBJECT-TYPE
        SYNTAX DisplayString (SIZE (1..32))
        MAX-ACCESS  read-only
        STATUS  current
        DESCRIPTION
            "VRF name"
        ::= { zxr10globalRtEntry 1 }

zxr10globalRtRtVrf OBJECT-TYPE
        SYNTAX DisplayString (SIZE (3..21))
        MAX-ACCESS  read-only
        STATUS  current
        DESCRIPTION
            "route-target"
        ::= { zxr10globalRtEntry 2 }

zxr10globalRtRtAction OBJECT-TYPE
        SYNTAX Unsigned32 {both(1),export(2),import(3)} 
        MAX-ACCESS  read-only
        STATUS  current
        DESCRIPTION
            "route-target"
        ::= { zxr10globalRtEntry 3 }


zxr10addressFamilyModeMIB OBJECT IDENTIFIER ::= { zxr10vrfMIB 4 }

zxr10addressFamilyModeTable OBJECT-TYPE
        SYNTAX  SEQUENCE OF Zxr10addressFamilyModeEntry
        MAX-ACCESS  not-accessible
        STATUS  current
        DESCRIPTION
            "An table to VRF IPv4 address family"
        ::= { zxr10addressFamilyModeMIB 1 }

zxr10addressFamilyModeEntry OBJECT-TYPE
        SYNTAX Zxr10addressFamilyModeEntry
        MAX-ACCESS  not-accessible
        STATUS  current
        DESCRIPTION
            "An entry to VRF IPv4 address family"
        INDEX  { zxr10addressFamilyModeAddrFamilyEnabledVrfName,
                 zxr10addressFamilyModeAddressFamilyModeFlags }
        ::= { zxr10addressFamilyModeTable 1 }
            
Zxr10addressFamilyModeEntry ::=
        SEQUENCE {
            zxr10addressFamilyModeAddrFamilyEnabledVrfName
                DisplayString,
            zxr10addressFamilyModeAddressFamilyModeFlags
                Unsigned32,
            zxr10addressFamilyModeExportMap
                DisplayString,
            zxr10addressFamilyModeImportMap
                DisplayString,
            zxr10addressFamilyModeMaxPrefix
                Unsigned32,
            zxr10addressFamilyModeMaxPrefixWarning
                Unsigned32,
            zxr10addressFamilyModeImportMulticastRoute
                DisplayString,
            zxr10addressFamilyModePriority
                Unsigned32,
            zxr10addressFamilyModeLocalPrefixEnable
                Unsigned32,
            zxr10addressFamilyModeNextHopHostOnly
                INTEGER,
            zxr10addressFamilyModeEvpnGwIp
                IpAddress
        }

zxr10addressFamilyModeAddrFamilyEnabledVrfName OBJECT-TYPE
        SYNTAX DisplayString (SIZE (1..32))
        MAX-ACCESS  read-only
        STATUS  current
        DESCRIPTION
            "VRF name"
        ::= { zxr10addressFamilyModeEntry 1 }

zxr10addressFamilyModeAddressFamilyModeFlags OBJECT-TYPE
        SYNTAX Unsigned32 {ipv4(1)}
        MAX-ACCESS  read-only
        STATUS  current
        DESCRIPTION
            "VRF IPv4 address family"
        ::= { zxr10addressFamilyModeEntry 2 }

zxr10addressFamilyModeExportMap OBJECT-TYPE
        SYNTAX DisplayString (SIZE (1..31))
        MAX-ACCESS  read-only
        STATUS  current
        DESCRIPTION
            "export map"
        ::= { zxr10addressFamilyModeEntry 3 }

zxr10addressFamilyModeImportMap OBJECT-TYPE
        SYNTAX DisplayString (SIZE (1..31))
        MAX-ACCESS  read-only
        STATUS  current
        DESCRIPTION
            "import map"
        ::= { zxr10addressFamilyModeEntry 4 }

zxr10addressFamilyModeMaxPrefix OBJECT-TYPE
        SYNTAX Unsigned32
        MAX-ACCESS  read-only
        STATUS  current
        DESCRIPTION
            "maxinum route,0 is invalid-value."
        ::= { zxr10addressFamilyModeEntry 5 }

zxr10addressFamilyModeMaxPrefixWarning OBJECT-TYPE
        SYNTAX Unsigned32 (0..100)          
        MAX-ACCESS  read-only
        STATUS  current
        DESCRIPTION
            "maxinum route prefix warning,0 is warning-only,
             1~100 is Threshold value (%) at which to give a warning,
             101 is invalid-value."
        ::= { zxr10addressFamilyModeEntry 6 }

zxr10addressFamilyModeImportMulticastRoute OBJECT-TYPE
        SYNTAX DisplayString (SIZE (9..21))
        MAX-ACCESS  read-only
        STATUS  current
        DESCRIPTION
            "special purpose for multicast vpn"
        ::= { zxr10addressFamilyModeEntry 7 }

zxr10addressFamilyModePriority OBJECT-TYPE
        SYNTAX Unsigned32 {low(1),middle(2),high(3)} 
        MAX-ACCESS  read-only
        STATUS  current
        DESCRIPTION
            "priority"
        ::= { zxr10addressFamilyModeEntry 8 }

zxr10addressFamilyModeLocalPrefixEnable OBJECT-TYPE
        SYNTAX Unsigned32 {disable(0),enable(1)} 
        MAX-ACCESS  read-only
        STATUS  current
        DESCRIPTION
            "loacl prefix"
        ::= { zxr10addressFamilyModeEntry 9 }

zxr10addressFamilyModeNextHopHostOnly OBJECT-TYPE
        SYNTAX INTEGER {enable(1),disable(2)} 
        MAX-ACCESS  read-only
        STATUS  current
        DESCRIPTION
            "next-hop host-only"
        ::= { zxr10addressFamilyModeEntry 10 }

zxr10addressFamilyModeEvpnGwIp OBJECT-TYPE
        SYNTAX IpAddress
        MAX-ACCESS  read-only
        STATUS  current
        DESCRIPTION
            "Gateway IP address for EVPN. 0.0.0.0 is invalid-value."
        ::= { zxr10addressFamilyModeEntry 11 }

zxr10rtTable OBJECT-TYPE
        SYNTAX  SEQUENCE OF Zxr10rtEntry
        MAX-ACCESS  not-accessible
        STATUS  current
        DESCRIPTION
            "An table to VRF RT"
        ::= { zxr10addressFamilyModeMIB 2 }

zxr10rtEntry OBJECT-TYPE
        SYNTAX Zxr10rtEntry
        MAX-ACCESS  not-accessible
        STATUS  current
        DESCRIPTION
            "An entry to VRF RT"
        INDEX  { zxr10rtAddrFamilyEnabledVrfName,
                 zxr10rtAddressFamilyModeFlags,
                 zxr10rtRtIpv4,
                 zxr10rtRtAction }
        ::= { zxr10rtTable 1 }
            
Zxr10rtEntry ::=
        SEQUENCE {
            zxr10rtAddrFamilyEnabledVrfName
                DisplayString,
            zxr10rtAddressFamilyModeFlags
                Unsigned32,
            zxr10rtRtIpv4
                DisplayString,
            zxr10rtRtAction
                Unsigned32
        }

zxr10rtAddrFamilyEnabledVrfName OBJECT-TYPE
        SYNTAX DisplayString (SIZE (1..32))
        MAX-ACCESS  read-only
        STATUS  current
        DESCRIPTION
            "VRF name"
        ::= { zxr10rtEntry 1 }

zxr10rtAddressFamilyModeFlags OBJECT-TYPE
        SYNTAX Unsigned32 {ipv4(1)}
        MAX-ACCESS  read-only
        STATUS  current
        DESCRIPTION
            "mode flag"
        ::= { zxr10rtEntry 2 }

zxr10rtRtIpv4 OBJECT-TYPE
        SYNTAX DisplayString (SIZE (3..21))
        MAX-ACCESS  read-only
        STATUS  current
        DESCRIPTION
            "route-target"
        ::= { zxr10rtEntry 3 }

zxr10rtRtAction OBJECT-TYPE
        SYNTAX Unsigned32 {both(1),export(2),import(3)} 
        MAX-ACCESS  read-only
        STATUS  current
        DESCRIPTION
            "route-target action"
        ::= { zxr10rtEntry 4 }



zxr10staticOutlabelTable OBJECT-TYPE
        SYNTAX  SEQUENCE OF Zxr10staticOutlabelEntry
        MAX-ACCESS  not-accessible
        STATUS  current
        DESCRIPTION
            "An table to VRF out label"
        ::= { zxr10addressFamilyModeMIB 3 }

zxr10staticOutlabelEntry OBJECT-TYPE
        SYNTAX Zxr10staticOutlabelEntry
        MAX-ACCESS  not-accessible
        STATUS  current
        DESCRIPTION
            "An entry to VRF out label"
        INDEX  { zxr10staticOutlabelAddrFamilyEnabledVrfName,
                 zxr10staticOutlabelAddressFamilyModeFlags,
                 zxr10staticOutlabelStaticOutlabelNh }
        ::= { zxr10staticOutlabelTable 1 }
            
Zxr10staticOutlabelEntry ::=
        SEQUENCE {
            zxr10staticOutlabelAddrFamilyEnabledVrfName
                DisplayString,
            zxr10staticOutlabelAddressFamilyModeFlags
                Unsigned32,
            zxr10staticOutlabelStaticOutlabelNh
                IpAddress,
            zxr10staticOutlabelStaticOutlabelLabel
                Unsigned32
        }

zxr10staticOutlabelAddrFamilyEnabledVrfName OBJECT-TYPE
        SYNTAX DisplayString (SIZE (1..32))
        MAX-ACCESS  read-only
        STATUS  current
        DESCRIPTION
            "VRF name"
        ::= { zxr10staticOutlabelEntry 1 }

zxr10staticOutlabelAddressFamilyModeFlags OBJECT-TYPE
        SYNTAX Unsigned32 {ipv4(1)}
        MAX-ACCESS  read-only
        STATUS  current
        DESCRIPTION
            "mode flag"
        ::= { zxr10staticOutlabelEntry 2 }

zxr10staticOutlabelStaticOutlabelNh OBJECT-TYPE
        SYNTAX IpAddress
        MAX-ACCESS  read-only
        STATUS  current
        DESCRIPTION
            "next-hop"
        ::= { zxr10staticOutlabelEntry 3 }

zxr10staticOutlabelStaticOutlabelLabel OBJECT-TYPE
        SYNTAX Unsigned32
        MAX-ACCESS  read-only
        STATUS  current
        DESCRIPTION
            "static out label"
        ::= { zxr10staticOutlabelEntry 4 }



zxr10vrfTunnelPolicyTable OBJECT-TYPE
        SYNTAX  SEQUENCE OF Zxr10vrfTunnelPolicyEntry
        MAX-ACCESS  not-accessible
        STATUS  current
        DESCRIPTION
            "An table to VRF tunnel policy"
        ::= { zxr10addressFamilyModeMIB 4 }

zxr10vrfTunnelPolicyEntry OBJECT-TYPE
        SYNTAX Zxr10vrfTunnelPolicyEntry
        MAX-ACCESS  not-accessible
        STATUS  current
        DESCRIPTION
            "An entry to VRF tunnel policy"
        INDEX  { zxr10vrfTunnelPolicyVrfName,
                 zxr10vrfTunnelPolicyAddressFamilyModeFlags,
                 zxr10vrfTunnelPolicyPeerAddr }
        ::= { zxr10vrfTunnelPolicyTable 1 }
            
Zxr10vrfTunnelPolicyEntry ::=
        SEQUENCE {
            zxr10vrfTunnelPolicyVrfName
                DisplayString,
            zxr10vrfTunnelPolicyAddressFamilyModeFlags
                Unsigned32,
            zxr10vrfTunnelPolicyPeerAddr
                IpAddress,
            zxr10vrfTunnelPolicyPolicyName
                DisplayString
        }


zxr10vrfTunnelPolicyVrfName OBJECT-TYPE
        SYNTAX DisplayString (SIZE (1..32))
        MAX-ACCESS  read-only
        STATUS  current
        DESCRIPTION
            "VRF name"
        ::= { zxr10vrfTunnelPolicyEntry 1 }

zxr10vrfTunnelPolicyAddressFamilyModeFlags OBJECT-TYPE
        SYNTAX Unsigned32 {ipv4(1)}
        MAX-ACCESS  read-only
        STATUS  current
        DESCRIPTION
            "mode flag"
        ::= { zxr10vrfTunnelPolicyEntry 2 }

zxr10vrfTunnelPolicyPeerAddr OBJECT-TYPE
        SYNTAX IpAddress
        MAX-ACCESS  read-only
        STATUS  current
        DESCRIPTION
            "PE address"
        ::= { zxr10vrfTunnelPolicyEntry 3 }

zxr10vrfTunnelPolicyPolicyName OBJECT-TYPE
        SYNTAX DisplayString (SIZE (1..63))
        MAX-ACCESS  read-only
        STATUS  current
        DESCRIPTION
            "tunnel policy name"
        ::= { zxr10vrfTunnelPolicyEntry 4 }


zxr10addressFamilyModeV6MIB OBJECT IDENTIFIER ::= { zxr10vrfMIB 5 }

zxr10addressFamilyModeV6Table OBJECT-TYPE
        SYNTAX  SEQUENCE OF Zxr10addressFamilyModeV6Entry
        MAX-ACCESS  not-accessible
        STATUS  current
        DESCRIPTION
            "An table to VRF IPv6 address family"
        ::= { zxr10addressFamilyModeV6MIB 1 }

zxr10addressFamilyModeV6Entry OBJECT-TYPE
        SYNTAX Zxr10addressFamilyModeV6Entry
        MAX-ACCESS  not-accessible
        STATUS  current
        DESCRIPTION
            "An entry to VRF IPv6 address family"
        INDEX  { zxr10addressFamilyModeV6AddrFamilyEnabledVrfName,
                 zxr10addressFamilyModeV6AddressFamilyModeFlags }
        ::= { zxr10addressFamilyModeV6Table 1 }
            
Zxr10addressFamilyModeV6Entry ::=
        SEQUENCE {
            zxr10addressFamilyModeV6AddrFamilyEnabledVrfName
                DisplayString,
            zxr10addressFamilyModeV6AddressFamilyModeFlags
                Unsigned32,
            zxr10addressFamilyModeV6ExportMap
                DisplayString,
            zxr10addressFamilyModeV6ImportMap
                DisplayString,
            zxr10addressFamilyV6MaxPrefix
                Unsigned32,
            zxr10addressFamilyV6MaxWarning
                Unsigned32,
            zxr10addressFamilyV6LocProtect
                INTEGER,
            zxr10addressFamilyV6MulticastRT
                DisplayString
        }

zxr10addressFamilyModeV6AddrFamilyEnabledVrfName OBJECT-TYPE
        SYNTAX DisplayString (SIZE (1..32))
        MAX-ACCESS  read-only
        STATUS  current
        DESCRIPTION
            "VRF name"
        ::= { zxr10addressFamilyModeV6Entry 1 }

zxr10addressFamilyModeV6AddressFamilyModeFlags OBJECT-TYPE
        SYNTAX Unsigned32 {ipv6(2)}
        MAX-ACCESS  read-only
        STATUS  current
        DESCRIPTION
            "mode flag"
        ::= { zxr10addressFamilyModeV6Entry 2 }

zxr10addressFamilyModeV6ExportMap OBJECT-TYPE
        SYNTAX DisplayString (SIZE (1..31))
        MAX-ACCESS  read-only
        STATUS  current
        DESCRIPTION
            "export map"
        ::= { zxr10addressFamilyModeV6Entry 3 }

zxr10addressFamilyModeV6ImportMap OBJECT-TYPE
        SYNTAX DisplayString (SIZE (1..31))
        MAX-ACCESS  read-only
        STATUS  current
        DESCRIPTION
            "import map"
        ::= { zxr10addressFamilyModeV6Entry 4 }

zxr10addressFamilyV6MaxPrefix OBJECT-TYPE
        SYNTAX Unsigned32
        MAX-ACCESS  read-only
        STATUS  current
        DESCRIPTION
            "ipv6 maxinum route,0 is invalid-value."
        ::= { zxr10addressFamilyModeV6Entry 5 }

zxr10addressFamilyV6MaxWarning OBJECT-TYPE
        SYNTAX Unsigned32 (0..100)          
        MAX-ACCESS  read-only
        STATUS  current
        DESCRIPTION
            "ipv6 maxinum route prefix warning,0 is warning-only,
             1~100 is Threshold value (%) at which to give a warning,
             101 is invalid-value."
        ::= { zxr10addressFamilyModeV6Entry 6 }

zxr10addressFamilyV6LocProtect OBJECT-TYPE
        SYNTAX INTEGER {enable(1),disable(2)} 
        MAX-ACCESS  read-only
        STATUS  current
        DESCRIPTION
            "ipv6 loacl prefix"
        ::= { zxr10addressFamilyModeV6Entry 7 }

zxr10addressFamilyV6MulticastRT OBJECT-TYPE
        SYNTAX DisplayString (SIZE (9..21))
        MAX-ACCESS  read-only
        STATUS  current
        DESCRIPTION
            "special purpose for multicast vpn"
        ::= { zxr10addressFamilyModeV6Entry 8 }

zxr10rtV6Table OBJECT-TYPE
        SYNTAX  SEQUENCE OF Zxr10rtV6Entry
        MAX-ACCESS  not-accessible
        STATUS  current
        DESCRIPTION
            "An table to VRF IPv6 RT"
        ::= { zxr10addressFamilyModeV6MIB 2 }

zxr10rtV6Entry OBJECT-TYPE
        SYNTAX Zxr10rtV6Entry
        MAX-ACCESS  not-accessible
        STATUS  current
        DESCRIPTION
            "An entry to VRF IPv6 RT"
        INDEX  { zxr10rtV6AddrFamilyEnabledVrfName,
                 zxr10rtV6AddressFamilyModeFlags,
                 zxr10rtV6RtIpv6,
                 zxr10rtV6RtAction }
        ::= { zxr10rtV6Table 1 }
            
Zxr10rtV6Entry ::=
        SEQUENCE {
            zxr10rtV6AddrFamilyEnabledVrfName
                DisplayString,
            zxr10rtV6AddressFamilyModeFlags
                Unsigned32,
            zxr10rtV6RtIpv6
                DisplayString,
            zxr10rtV6RtAction
                Unsigned32
        }

zxr10rtV6AddrFamilyEnabledVrfName OBJECT-TYPE
        SYNTAX DisplayString (SIZE (1..32))
        MAX-ACCESS  read-only
        STATUS  current
        DESCRIPTION
            "VRF name"
        ::= { zxr10rtV6Entry 1 }

zxr10rtV6AddressFamilyModeFlags OBJECT-TYPE
        SYNTAX Unsigned32 {ipv6(2)}
        MAX-ACCESS  read-only
        STATUS  current
        DESCRIPTION
            "mode flag"
        ::= { zxr10rtV6Entry 2 }

zxr10rtV6RtIpv6 OBJECT-TYPE
        SYNTAX DisplayString (SIZE (3..21))
        MAX-ACCESS  read-only
        STATUS  current
        DESCRIPTION
            "route-target"
        ::= { zxr10rtV6Entry 3 }

zxr10rtV6RtAction OBJECT-TYPE
        SYNTAX Unsigned32 {both(1),export(2),import(3)} 
        MAX-ACCESS  read-only
        STATUS  current
        DESCRIPTION
            "route-target"
        ::= { zxr10rtV6Entry 4 }

zxr10vrfTunnelPolicyV6Table OBJECT-TYPE
        SYNTAX  SEQUENCE OF Zxr10vrfTunnelPolicyV6Entry
        MAX-ACCESS  not-accessible
        STATUS  current
        DESCRIPTION
            "An table to VRF ipv6 tunnel policy"
        ::= { zxr10addressFamilyModeV6MIB 3 }

zxr10vrfTunnelPolicyV6Entry OBJECT-TYPE
        SYNTAX Zxr10vrfTunnelPolicyV6Entry
        MAX-ACCESS  not-accessible
        STATUS  current
        DESCRIPTION
            "An entry to VRF IPv6 tunnel policy"
        INDEX  { zxr10vrfTunnelPolicyV6VrfName,
                 zxr10vrfTunnelPolicyV6AfiMode,
                 zxr10vrfTunnelPolicyV6PeerAddr }
        ::= { zxr10vrfTunnelPolicyV6Table 1 }
            
Zxr10vrfTunnelPolicyV6Entry ::=
        SEQUENCE {
            zxr10vrfTunnelPolicyV6VrfName
                DisplayString,
            zxr10vrfTunnelPolicyV6AfiMode
                INTEGER,
            zxr10vrfTunnelPolicyV6PeerAddr
                DisplayString,
            zxr10vrfTunnelPolicyV6PolicyName
                DisplayString
        }


zxr10vrfTunnelPolicyV6VrfName OBJECT-TYPE
        SYNTAX DisplayString (SIZE (1..32))
        MAX-ACCESS  not-accessible
        STATUS  current
        DESCRIPTION
            "VRF name"
        ::= { zxr10vrfTunnelPolicyV6Entry 1 }

zxr10vrfTunnelPolicyV6AfiMode OBJECT-TYPE
        SYNTAX INTEGER {ipv6(2)}
        MAX-ACCESS  not-accessible
        STATUS  current
        DESCRIPTION
            "Address family mode flag"
        ::= { zxr10vrfTunnelPolicyV6Entry 2 }

zxr10vrfTunnelPolicyV6PeerAddr OBJECT-TYPE
        SYNTAX DisplayString
        MAX-ACCESS  not-accessible
        STATUS  current
        DESCRIPTION
            "PE ipv6 address"
        ::= { zxr10vrfTunnelPolicyV6Entry 3 }

zxr10vrfTunnelPolicyV6PolicyName OBJECT-TYPE
        SYNTAX DisplayString (SIZE (1..63))
        MAX-ACCESS  read-only
        STATUS  current
        DESCRIPTION
            "tunnel policy name"
        ::= { zxr10vrfTunnelPolicyV6Entry 4 }

zxr10vrfMplsLabelModeTable OBJECT-TYPE
        SYNTAX  SEQUENCE OF Zxr10vrfMplsLabelModeEntry
        MAX-ACCESS  not-accessible
        STATUS  current
        DESCRIPTION
            "An table to VRF mpls label mode"
        ::= { zxr10vrfMIB 6 }

zxr10vrfMplsLabelModeEntry OBJECT-TYPE
        SYNTAX Zxr10vrfMplsLabelModeEntry
        MAX-ACCESS  not-accessible
        STATUS  current
        DESCRIPTION
            "An entry to VRF mpls label mode"
        INDEX  { zxr10vrfMplsLabelModeEnabledVrfName,
                 zxr10vrfMplsLabelModeIpv6 }
        ::= { zxr10vrfMplsLabelModeTable 1 }
            
Zxr10vrfMplsLabelModeEntry ::=
        SEQUENCE {
            zxr10vrfMplsLabelModeEnabledVrfName
                DisplayString,
            zxr10vrfMplsLabelModeIpv6
                Unsigned32,
            zxr10vrfMplsLabelModeMplsLabelMode
                Unsigned32
        }

zxr10vrfMplsLabelModeEnabledVrfName OBJECT-TYPE
        SYNTAX DisplayString (SIZE (1..32))
        MAX-ACCESS  read-only
        STATUS  current
        DESCRIPTION
            "VRF name"
        ::= { zxr10vrfMplsLabelModeEntry 1 }

zxr10vrfMplsLabelModeIpv6 OBJECT-TYPE
        SYNTAX Unsigned32 {ipv6(1),ipv4(0)}              
        MAX-ACCESS  read-only
        STATUS  current
        DESCRIPTION
            "ipv6"
        ::= { zxr10vrfMplsLabelModeEntry 2 }

zxr10vrfMplsLabelModeMplsLabelMode OBJECT-TYPE
        SYNTAX Unsigned32 {per-prefix(2),per-vrf(3)}        
        MAX-ACCESS  read-only
        STATUS  current
        DESCRIPTION
            "label mode"
        ::= { zxr10vrfMplsLabelModeEntry 3 }



zxr10gMplsLabelModeTable OBJECT-TYPE
        SYNTAX  SEQUENCE OF Zxr10gMplsLabelModeEntry
        MAX-ACCESS  not-accessible
        STATUS  current
        DESCRIPTION
            "An table to VRF label mode"
        ::= { zxr10vrf 2 }

zxr10gMplsLabelModeEntry OBJECT-TYPE
        SYNTAX Zxr10gMplsLabelModeEntry
        MAX-ACCESS  not-accessible
        STATUS  current
        DESCRIPTION
            "An entry to VRF label mode"
        INDEX  { zxr10gMplsLabelModeIpv6 }
        ::= { zxr10gMplsLabelModeTable 1 }
            
Zxr10gMplsLabelModeEntry ::=
        SEQUENCE {
            zxr10gMplsLabelModeIpv6
                Unsigned32,
            zxr10gMplsLabelModeGLabelMode
                Unsigned32
        }

zxr10gMplsLabelModeIpv6 OBJECT-TYPE
        SYNTAX Unsigned32 {ipv6(1),ipv4(0)}              
        MAX-ACCESS  read-only
        STATUS  current
        DESCRIPTION
            "ipv6"
        ::= { zxr10gMplsLabelModeEntry 1 }

zxr10gMplsLabelModeGLabelMode OBJECT-TYPE
        SYNTAX Unsigned32 {per-prefix(2),per-vrf(3)}        
        MAX-ACCESS  read-only
        STATUS  current
        DESCRIPTION
            "mpls label mode"
        ::= { zxr10gMplsLabelModeEntry 2 }


END
