-- *****************************************************************
-- $Id: Zxr10VrfRoutes.mib 27 2009-07-13 08:47:59Z hejide $
--
-- Zxr10VrfRoutes.mib: ZTE Corporation Enterprise Structure of Management Information
--
-- JUNE 2005, hejide
--
-- Copyright (c) 2009 by ZTE Corporation
-- All rights reserved.
-- 
-- *****************************************************************
--
ZXR10-VRF-ROUTERS-MIB DEFINITIONS ::= BEGIN

IMPORTS
  MODULE-IDENTITY,OBJECT-IDENTITY,Unsigned32,
  OBJECT-TYPE,
  enterprises
    FROM SNMPv2-SMI
  DisplayString
        FROM SNMPv2-TC;
zte MODULE-IDENTITY      
    LAST-UPDATED "201705111000Z"  -- May 11, 2017   
 ORGANIZATION "ZTE Corporation"
    CONTACT-INFO
         "Meng meihua (He yunbo)
         Tel: +86-25-52871138
         E-Mail: meng.meihua@zte.com.cn
         "
    DESCRIPTION
        "ZXROSNG VRF ROUTE MIB" 
    REVISION "201705111000Z"  -- May 11, 2017
    DESCRIPTION
            "modify the sizelist of zxr10VrfIndex which is in the
            zxr10VrfRouteStatisticsTable."         
    REVISION "201304090000Z"  -- April 09, 2013
    DESCRIPTION
            "modify the description of zxr10VrfIndex which is in the
            zxr10VrfRouteStatisticsTable." 
    REVISION "200504120000Z"  -- April 12, 2005
    DESCRIPTION
       ""
  ::= { enterprises 3902 }  -- assigned by IANA
    
zxr10      OBJECT IDENTIFIER ::= { zte 3}
zxr10RosngMIB      OBJECT IDENTIFIER ::= { zxr10 6000 } 

zxr10VrfRoutesMIB OBJECT-IDENTITY
  STATUS current
  --DESCRIPTION
  -- ""
  --LAST-UPDATED "200907131200Z"
  --ORGANIZATION "ZTE Corporation Enterprise Structure of Management Information"
  --CONTACT-INFO
  --"ZTE Corporation Enterprise Structure of Management Information"

  DESCRIPTION
    "ZTE Corporation Enterprise Structure of Management Information."

  ::= { zxr10RosngMIB 2 } 
  
zxr10VrfRouteStatisticsTable OBJECT-TYPE
    SYNTAX  SEQUENCE OF Zxr10VrfRouteStatisticsEntry
    MAX-ACCESS  not-accessible
    STATUS  current
    DESCRIPTION
      "zxr10VrfRouteStatisticsTable"
    ::= { zxr10VrfRoutesMIB 1 }
         
zxr10VrfRouteStatisticsEntry  OBJECT-TYPE
    SYNTAX  Zxr10VrfRouteStatisticsEntry
    MAX-ACCESS  not-accessible
    STATUS  current
    DESCRIPTION
      "Zxr10VrfRouteStatisticsEntry"
    INDEX { zxr10VrfIndex }
    ::= { zxr10VrfRouteStatisticsTable 1 }         
        
Zxr10VrfRouteStatisticsEntry ::=
    SEQUENCE {
    zxr10VrfIndex
        DisplayString ,
    zxr10VrfTotalRoutes
        Unsigned32, 
    zxr10VrfConnectedRoutes
        Unsigned32,
    zxr10VrfStaticRoutes
        Unsigned32,
    zxr10VrfRIPRoutes
        Unsigned32,
    zxr10VrfOSPFRoutes
        Unsigned32,
    zxr10VrfISISRoutes
        Unsigned32,
    zxr10VrfBGPRoutes
      Unsigned32
    }       
zxr10VrfIndex OBJECT-TYPE 
  SYNTAX  DisplayString (SIZE (0..32))
  MAX-ACCESS  read-only
  STATUS  current
  DESCRIPTION
    "Vrf Name.If this attribute has NULL value, 
    it means that this is the global table."
  ::= { zxr10VrfRouteStatisticsEntry 1 }

zxr10VrfTotalRoutes OBJECT-TYPE
  SYNTAX  Unsigned32 (0..4294967295) 
  MAX-ACCESS  read-only
  STATUS  current
  DESCRIPTION
    "The routes of IPv4."
  ::= { zxr10VrfRouteStatisticsEntry 2 }
  
zxr10VrfConnectedRoutes OBJECT-TYPE
  SYNTAX  Unsigned32 (0..4294967295) 
  MAX-ACCESS  read-only
  STATUS  current
  DESCRIPTION
    "The Connected Routes of IPv4."
  ::= { zxr10VrfRouteStatisticsEntry 3 }

zxr10VrfStaticRoutes OBJECT-TYPE
  SYNTAX  Unsigned32 (0..4294967295) 
  MAX-ACCESS  read-only
  STATUS  current
  DESCRIPTION
    "The Static Routes of IPv4."
  ::= { zxr10VrfRouteStatisticsEntry 4 }

zxr10VrfRIPRoutes OBJECT-TYPE
  SYNTAX  Unsigned32 (0..4294967295)  
  MAX-ACCESS  read-only
  STATUS  current
  DESCRIPTION
    "The RIP Routes of IPv4."
  ::= { zxr10VrfRouteStatisticsEntry 5 }

zxr10VrfOSPFRoutes OBJECT-TYPE
  SYNTAX  Unsigned32 (0..4294967295)  
  MAX-ACCESS  read-only
  STATUS  current
  DESCRIPTION
    "The OSPF Routes of IPv4."
  ::= { zxr10VrfRouteStatisticsEntry 6 }

zxr10VrfISISRoutes OBJECT-TYPE
  SYNTAX  Unsigned32 (0..4294967295)  
  MAX-ACCESS  read-only
  STATUS  current
  DESCRIPTION
    "The ISIS Routes of IPv4."
  ::= { zxr10VrfRouteStatisticsEntry 7 }

zxr10VrfBGPRoutes OBJECT-TYPE
  SYNTAX  Unsigned32 (0..4294967295)  
  MAX-ACCESS  read-only
  STATUS  current
  DESCRIPTION
    "The BGP Routes of IPv4."
  ::= { zxr10VrfRouteStatisticsEntry 8 }
  
END
