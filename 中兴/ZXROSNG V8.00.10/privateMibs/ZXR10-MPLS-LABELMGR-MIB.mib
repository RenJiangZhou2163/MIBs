ZXR10-MPLS-LABELMGR-MIB DEFINITIONS ::= BEGIN  
     
IMPORTS
       OBJECT-TYPE, 
       MODULE-IDENTITY,  
       Counter32,enterprises
           FROM SNMPv2-SMI;    
             
mplsLabelmgrMIB MODULE-IDENTITY
         LAST-UPDATED "201005161200Z"  
         ORGANIZATION "Multiprotocol Label Switching (mpls)
                       Working Group"
         CONTACT-INFO
             "Joan Cucchiara (jcucchiara@crescentnetworks.com)
              Crescent Networks

              Hans Sjostrand (hans@ipunplugged.com)
              ipUnplugged

              James V. Luciani (jluciani@crescentnetworks.com)
              Crescent Networks

              Working Group Chairs:
              George Swallow,   email: swallow@cisco.com
              Vijay Srinivasan, email: vijay@cosinecom.com
              MPLS Working Group, email: mpls@uu.net
         "
         DESCRIPTION
             "This MIB contains managed object definitions for the
             'Label Management, labelmgr' document."
         ::= { zxr10RosngMIB 120 } 
     
      
      zte OBJECT IDENTIFIER ::= { enterprises 3902 }
      zxr10 OBJECT IDENTIFIER ::= { zte 3 }
      zxr10RosngMIB OBJECT IDENTIFIER ::= { zxr10 6000 }
     

--********************************************         
--difinition of objects ::  
--********************************************   

--*************zxr10LabelRangeTable***************      

zxr10LabelRangeTable OBJECT-TYPE
            SYNTAX     SEQUENCE OF Zxr10LabelRangeEntry
            MAX-ACCESS not-accessible
            STATUS     current
            DESCRIPTION
                    "LabelRange Table. This table contains label range, 
                    including the type of label pool, the label range in use 
                    and the label range configured."
            ::= { mplsLabelmgrMIB 1 } 
            
zxr10LabelRangeEntry OBJECT-TYPE
            SYNTAX     Zxr10LabelRangeEntry
            MAX-ACCESS not-accessible
            STATUS     current
            DESCRIPTION
                    "The parameter of label range entry."
            INDEX { zxr10LabelPoolType }
            ::= { zxr10LabelRangeTable 1 }
            
Zxr10LabelRangeEntry ::= SEQUENCE {
                zxr10LabelPoolType    
                    INTEGER,
                zxr10LabelRangeCfgMin
                    Counter32,       
                zxr10LabelRangeCfgMax
                    Counter32,                    
                zxr10LabelRangeInuseMin
                    Counter32,            
                zxr10LabelRangeInuseMax
                    Counter32                               
                }   
             
zxr10LabelPoolType  OBJECT-TYPE
            SYNTAX     INTEGER{   
                            global ( 0 ),
                            static ( 1 ),
                            ldp    ( 2 ),
                            pwe3   ( 3 ),
                            rsvp   ( 4 ),
                            bgp    ( 5 ),
                            bgpv6  ( 6 )  }
            MAX-ACCESS read-only
            STATUS     current
            DESCRIPTION
                    "The type of the label pool."
            ::= { zxr10LabelRangeEntry 1 } 
            
zxr10LabelRangeCfgMin  OBJECT-TYPE
            SYNTAX     Counter32
            MAX-ACCESS read-only
            STATUS     current
            DESCRIPTION
                    "The begin of label range configured. If its value is 0, it shows that it uses default
                    label range. If its value is different from the begin of label range in use, it shows that 
                    the configured label range doesn't work. It will take effect at the next reload."
            ::= { zxr10LabelRangeEntry 2 }  
            
zxr10LabelRangeCfgMax  OBJECT-TYPE
            SYNTAX     Counter32
            MAX-ACCESS read-only
            STATUS     current
            DESCRIPTION
                    "The end of label range configured. If its value is 0, it shows that it uses default
                    label range. If its value is different from the end of label range in use, it shows that 
                    the configured label range doesn't work. It will take effect at the next reload."
            ::= { zxr10LabelRangeEntry 3 }
            
zxr10LabelRangeInuseMin  OBJECT-TYPE
            SYNTAX     Counter32
            MAX-ACCESS read-only
            STATUS     current
            DESCRIPTION
                    "The begin of label range in use."
            ::= { zxr10LabelRangeEntry 4 }
            
zxr10LabelRangeInuseMax  OBJECT-TYPE
            SYNTAX     Counter32
            MAX-ACCESS read-only
            STATUS     current
            DESCRIPTION
                    "The end of label range in use."
            ::= { zxr10LabelRangeEntry 5 }
            

 END
