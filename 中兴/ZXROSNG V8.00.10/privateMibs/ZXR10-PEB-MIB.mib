ZXR10-PEB-MIB DEFINITIONS ::= BEGIN

IMPORTS
    MODULE-IDENTITY, OBJECT-TYPE, Unsigned32, enterprises
        FROM SNMPv2-SMI
    MacAddress
        FROM SNMPv2-TC
    DisplayString 
        FROM RFC1213-MIB;

zxr10PebMIB MODULE-IDENTITY
    LAST-UPDATED "201601210000Z"  
    ORGANIZATION "ZTE Corporation"
    CONTACT-INFO
        "Geng chunjing
         Tel : +86-25-52870000        
         E-Mail: geng.chunjing@zte.com.cn
         "
    DESCRIPTION
        "The MIB module to describe part of IEEE P802.1BR protocol data. 
         Include some private variable used when the protocol is completed."
    REVISION "201601210000Z"--2016-1-21 00:00
    DESCRIPTION
        "Modify the value list of pebPortStatusPortType.
         Modify the description of pebLldpPeTlv and pebPortCfgLldpPeTlv."
    REVISION "201507070000Z"--2015-7-7 00:00
    DESCRIPTION
        "Initial version of this MIB module."

    ::= { zxr10RosngMIB 510 }    

    zte OBJECT IDENTIFIER ::= { enterprises 3902 }
    zxr10 OBJECT IDENTIFIER ::= { zte 3 }
    zxr10RosngMIB OBJECT IDENTIFIER ::= { zxr10 6000} 
  
    zxr10PebGlobalObjects         OBJECT IDENTIFIER ::= { zxr10PebMIB 1 }
    zxr10PebPortCfgObjects        OBJECT IDENTIFIER ::= { zxr10PebMIB 2 }
    zxr10PebPortStatusObjects     OBJECT IDENTIFIER ::= { zxr10PebMIB 3 }
    zxr10PebNotifications         OBJECT IDENTIFIER ::= { zxr10PebMIB 4 }
    zxr10PebConformance           OBJECT IDENTIFIER ::= { zxr10PebMIB 5 }
    
--=======================================================================
--1. zxr10PebGlobalObjects 
--=======================================================================  
pebRole OBJECT-TYPE
    SYNTAX INTEGER { 
       controller(1), 
       extender(2),
       none(3)
    }
    MAX-ACCESS read-write
    STATUS current
    DESCRIPTION
            "The role of the device in the Extended Bridge system,
            include controller(Controlling Bridge) and extender(Bridge Port Extender).
 
            The value none means the device is not an Extended Bridge system device.
 
            The default value for pebRole object is none."
REFERENCE
            "802.1BR-d3-3cb clause 6.1 "
    DEFVAL  {none}
    ::= { zxr10PebGlobalObjects 1 }

pebLldpPeTlv OBJECT-TYPE
    SYNTAX INTEGER { 
       enable(1), 
       disable(2)
    }
    MAX-ACCESS read-write
    STATUS current
    DESCRIPTION
         "The global control of sending PE-TLV."
    ::= { zxr10PebGlobalObjects 2 }
  
--=======================================================================
--2. zxr10PebPortCfgTable 
--=======================================================================    
zxr10PebPortCfgTable
 OBJECT-TYPE
    SYNTAX      SEQUENCE OF Zxr10PebPortCfgEntry
    MAX-ACCESS  not-accessible
    STATUS      current
    DESCRIPTION
       "The table that controls PEB private configuration on individual port."
    ::= { zxr10PebPortCfgObjects 1 }
  
zxr10PebPortCfgEntry
 OBJECT-TYPE
    SYNTAX      Zxr10PebPortCfgEntry
    MAX-ACCESS  not-accessible
    STATUS      current
    DESCRIPTION
       "PEB configuration information for a particular port."
    INDEX { pebPortCfgPortIndex }
    ::= { zxr10PebPortCfgTable 1 }
  
    Zxr10PebPortCfgEntry ::=
    SEQUENCE { 
               pebPortCfgPortIndex             Unsigned32,
               pebPortCfgPortName              DisplayString,
               pebPortCfgPriority              Unsigned32,
               pebPortCfgLldpPeTlv             INTEGER
             }

pebPortCfgPortIndex OBJECT-TYPE
    SYNTAX Unsigned32(0..4294967295)
    MAX-ACCESS not-accessible
    STATUS current
    DESCRIPTION
            "The index value used to identify the port component associated with this entry."
    ::= { zxr10PebPortCfgEntry 1 }
pebPortCfgPortName   OBJECT-TYPE
    SYNTAX      DisplayString 
    MAX-ACCESS  read-only
    STATUS      current
    DESCRIPTION
            "The port name."
    ::= { zxr10PebPortCfgEntry 2 }

pebPortCfgPriority OBJECT-TYPE
    SYNTAX Unsigned32(0..255)
    MAX-ACCESS read-write
    STATUS current
    DESCRIPTION
            "The priority of the port. When transmitted from a Port capable of operating as a cascade Port (e.g. Ports of a Controlling Bridge or Extended Ports of an Extended Bridge), 
            indicates the cascade_port_priority used in determining which Port is to be used by a Bridge Port Extender as its Upstream Port. 
  
            Valid values are the range from 0 to 254. When transmitted from a Bridge Port Extender on an Upstream Port or a Port capable of becoming an Upstream Port, this parameter shall be set to 255. 
            
            The default value for pebPortCfgPriority object is 100."
REFERENCE
            "802.1BR-d3-3cb clause B.2.1"
    DEFVAL { 100 }
    ::= { zxr10PebPortCfgEntry 3 }
    
pebPortCfgLldpPeTlv OBJECT-TYPE 
    SYNTAX INTEGER { 
       enable(1), 
       disable(2)
    }
    MAX-ACCESS read-write 
    STATUS     current 
    DESCRIPTION 
            "The control of sending PE-TLV on a port."   
   ::= { zxr10PebPortCfgEntry 4 } 
   
-- =======================================================================
-- 3. zxr10PebPortStatusObjects 
-- ========================================================================
zxr10PebPortStatusTable
 OBJECT-TYPE
    SYNTAX      SEQUENCE OF Zxr10PebPortStatusEntry
    MAX-ACCESS  not-accessible
    STATUS      current
    DESCRIPTION
       "The table include port status infomation."
    ::= { zxr10PebPortStatusObjects 1 }

zxr10PebPortStatusEntry
 OBJECT-TYPE
    SYNTAX      Zxr10PebPortStatusEntry
    MAX-ACCESS  not-accessible
    STATUS      current
    DESCRIPTION
       "PEB status information for a particular port."
    INDEX { pebPortStatusPortIndex }
    ::= { zxr10PebPortStatusTable 1 }
  
    Zxr10PebPortStatusEntry ::=
    SEQUENCE { 
               pebPortStatusPortIndex             Unsigned32,
               pebPortStatusPortName              DisplayString,
               pebPortStatusMac                   MacAddress,
               pebPortStatusAccessPort            DisplayString,
               pebPortStatusPortType              INTEGER,
               pebPortStatus                      INTEGER,
               pebPortEcid                        DisplayString
             }
pebPortStatusPortIndex   OBJECT-TYPE
    SYNTAX      Unsigned32(0..4294967295) 
    MAX-ACCESS  not-accessible
    STATUS      current
    DESCRIPTION
            "The index value used to identify the port component associated with this entry."
    ::= { zxr10PebPortStatusEntry 1 }      
pebPortStatusPortName   OBJECT-TYPE
    SYNTAX      DisplayString 
    MAX-ACCESS  read-only
    STATUS      current
    DESCRIPTION
            "The port name."
    ::= { zxr10PebPortStatusEntry 2 }  
  
pebPortStatusMac   OBJECT-TYPE
    SYNTAX      MacAddress 
    MAX-ACCESS  read-only
    STATUS      current
    DESCRIPTION
            "MAC address of the device for the interface. 
             For ethernet interface on Controlling Bridge, the MAC address indicates the base MAC address of the device; 
             For BEP interface on Controlling Bridge, the MAC address indicates the MAC address of the associated External Bridge Port Extender.
             For the interface on External Bridge Port Extender, the MAC address indicates the base MAC address of the device.
             "
    ::= { zxr10PebPortStatusEntry 3 }
 
pebPortStatusAccessPort   OBJECT-TYPE
    SYNTAX      DisplayString 
    MAX-ACCESS  read-only
    STATUS      current
    DESCRIPTION
            "The interface on the Upstream equipment which is connected to the Upstream Port of the device for the specified interface.
             For ethernet interface on Controlling Bridge and interface on Port Externed Bridge, there is no access port.
             For BEP interace on Controlling Bridge, the access port is the associated cascade port.
            "
    ::= { zxr10PebPortStatusEntry 4 } 
 
pebPortStatusPortType   OBJECT-TYPE
    SYNTAX INTEGER { 
       cascade(1),
       upstream(2), 
       extended(3),
       null(4)
    }
    MAX-ACCESS  read-only
    STATUS      current
    DESCRIPTION
             "The type for the port."
    ::= { zxr10PebPortStatusEntry 5 }
 
pebPortStatus   OBJECT-TYPE
    SYNTAX INTEGER { 
       active(1), 
       inactive(2),
       offline(3)
    }
    MAX-ACCESS  read-only
    STATUS      current
    DESCRIPTION
             "The port status."
    ::= { zxr10PebPortStatusEntry 6 } 

pebPortEcid   OBJECT-TYPE
    SYNTAX      DisplayString 
    MAX-ACCESS  read-only
    STATUS      current
    DESCRIPTION
            "The ECID for the interface. 
             The value null is for the ethernet interface on Controlling Bridge.
             The value all is for the Upstream Port on External Bridge Port Extender.
            "
    ::= { zxr10PebPortStatusEntry 7 } 
 
--=======================================================================
--4. zxr10PebNotifications 
--=======================================================================
--=======================================================================
--5. zxr10PebNotifications 
--======================================================================= 
END
