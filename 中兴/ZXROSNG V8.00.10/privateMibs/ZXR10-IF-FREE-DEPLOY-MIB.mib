ZXR10-IF-FREE-DEPLOY-MIB DEFINITIONS ::= BEGIN

IMPORTS
    OBJECT-TYPE, MODULE-IDENTITY, Unsigned32,enterprises
            FROM SNMPv2-SMI
    DisplayString, RowStatus
            FROM SNMPv2-TC;     
            
zxr10IfFreeDeployMIB MODULE-IDENTITY
                LAST-UPDATED
                "201307150000Z"
                ORGANIZATION
                "ZTE Corporation"
                CONTACT-INFO
                "        Wang xin               
                    Tel:  +86-25-52870000           
                E-Mail: wang.xin110@zte.com.cn 
                "
                DESCRIPTION
                "The MIB module to describe the Interface Free Deploy enable."
                REVISION
                "201307150000Z" 
                DESCRIPTION
                " Initial version of this MIB module"
                ::= { zxr10RosngMIB 508}
                   
    zte OBJECT IDENTIFIER ::={enterprises 3902}
    zxr10 OBJECT IDENTIFIER ::={zte 3}
    zxr10RosngMIB OBJECT IDENTIFIER ::= { zxr10 6000}
             
    zxr10IfFreeDeployGlobalObjects  OBJECT IDENTIFIER ::= { zxr10IfFreeDeployMIB 1 }
    zxr10IfFreeDeployObjects        OBJECT IDENTIFIER ::= { zxr10IfFreeDeployMIB 2 }
    zxr10IfFreeDeployTraps          OBJECT IDENTIFIER ::= { zxr10IfFreeDeployMIB 3 }
    zxr10IfFreeDeployConformance    OBJECT IDENTIFIER ::= { zxr10IfFreeDeployMIB 4 }

-- =============================
-- 1. zxr10IfFreeDeployGlobalObjects 
-- =============================     
    
    
-- =============================
-- 2. zxr10IfFreeDeployObjects
-- =============================       
-- =============================
-- 2.1 zxr10IfFreeDeployAttrObjects
-- =============================  
zxr10IfFreeDeployAttrObjects OBJECT IDENTIFIER ::= { zxr10IfFreeDeployObjects 1 }
-- =============================
-- 2.1.1 zxr10FreeDeployGlobalAttrObjects
-- =============================    
zxr10FreeDeployGlobalAttrObjects  OBJECT IDENTIFIER ::= { zxr10IfFreeDeployAttrObjects 1 }
-- =============================
-- 2.1.2 zxr10IfFreeDeployAttrTable
-- =============================
zxr10IfFreeDeployAttrTable OBJECT-TYPE
        SYNTAX  SEQUENCE OF Zxr10IfFreeDeployAttrEntry
        MAX-ACCESS  not-accessible
        STATUS  current
        DESCRIPTION
                "Interface Free Deploy Enable"
        ::= { zxr10IfFreeDeployAttrObjects 2  }

zxr10IfFreeDeployAttrEntry OBJECT-TYPE
        SYNTAX   Zxr10IfFreeDeployAttrEntry
        MAX-ACCESS  not-accessible
        STATUS  current
        DESCRIPTION
                "Interface Free Deploy Enable"
        INDEX {zxr10IfFreeDeployAttrIfName}
        ::= { zxr10IfFreeDeployAttrTable 1 }

Zxr10IfFreeDeployAttrEntry ::=
        SEQUENCE {
                zxr10IfFreeDeployAttrIfName                DisplayString,
                zxr10IfFreeDeployAttrEnable                INTEGER
        }

zxr10IfFreeDeployAttrIfName OBJECT-TYPE
        SYNTAX   DisplayString(SIZE(1..31))
        MAX-ACCESS  not-accessible
        STATUS  current
        DESCRIPTION
                "The interface name"
        ::= { zxr10IfFreeDeployAttrEntry  1  }  

zxr10IfFreeDeployAttrEnable OBJECT-TYPE
        SYNTAX   INTEGER{enable(2), disable(1)}
        MAX-ACCESS  read-only
        STATUS  current
        DESCRIPTION
                "The interface Free Deploy Enable"
        ::= { zxr10IfFreeDeployAttrEntry  2  }       

-- =============================
--3. zxr10IfFreeDeployNotifications  
-- =============================   
    
    
-- =============================
--4. zxr10IfFreeDeployConformance    
-- =============================  
    
END
