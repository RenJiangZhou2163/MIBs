RC-SMI DEFINITIONS ::= BEGIN

IMPORTS
    MODULE-IDENTITY,
    OBJECT-IDENTITY,
    enterprises
        FROM SNMPv2-SMI;

rc MODULE-IDENTITY
    LAST-UPDATED "201212120000Z"  
    ORGANIZATION "Resource Control System"
    CONTACT-INFO
        "NULL"

    DESCRIPTION
        "RC SMI MIB"

    REVISION "201212120000Z"  
    DESCRIPTION
       ""
    ::= { enterprises 65000 }    
    
END
