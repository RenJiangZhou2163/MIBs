--  ************************************************
--  $Id: ZXR10-mac-config.mib 2010-04-10 $
--
--  ZXR10_mac.mib: ZXR10 mac config MIB file
--  
--  April 2010, 
--   
--  Copyright(c) 2010 by ZTE Corporaton
--  All rights reservered
--
--  ************************************************

ZXR10-MAC-MIB DEFINITIONS ::= BEGIN

IMPORTS
    MODULE-IDENTITY, 
    OBJECT-TYPE, 
    enterprises,
    Unsigned32 FROM SNMPv2-SMI -- [RFC2578]                    
    MacAddress
         FROM SNMPv2-TC
;

    zxr10MacConfig MODULE-IDENTITY
        LAST-UPDATED "201305021000Z"  --2013-05-02 10:00
        ORGANIZATION "ZTE Corporation."
        CONTACT-INFO
        "ZTE Corporation
         Nanjing Institute of ZTE Corporation

         No.68 Zijinghua Rd. Yuhuatai District, Nanjing, China

         Tel: +86-25-52870000"

        DESCRIPTION
              "ZXROSNG MAC config"
              
        REVISION "201305021000Z" --2013-05-02 10:00
        DESCRIPTION
        "
            delete tab
            delete '(1..4094)' not allowed
            delete definition : DisplayString,BOOL,LEARNSTRATEGY
                                HIGIGLEARN,SAFEMODEPOLICY,MAXNUMTYPE
                                MacFilterType,WorkingMode
            delete hyphen of enumerated label
        "
                    
        REVISION "201304021000Z" --2013-04-02 10:00
        DESCRIPTION
        "
        change to obsolete:
            macGlobalProtect
            macGlobalProtectTime
            macGlobalLearnStrategy
            macGlobalHigigLearn
            macGlobalLogAlarm
            macGlobalToPermanentAutoWrite
            macGlobalToPermanentAutoWriteInterval
            macInterfaceConfig
            macVlanConfig
            macItem
        "
              REVISION "201004100000Z"
        DESCRIPTION
              ""
     ::= { zxr10 888 }
          
       zte                          OBJECT IDENTIFIER ::= { enterprises 3902 }
       zxr10                        OBJECT IDENTIFIER ::= { zte 3 }

    
macGlobalConfig  OBJECT IDENTIFIER ::= { zxr10MacConfig  1 }

    macGlobalCurrentNum   OBJECT-TYPE
        SYNTAX              Unsigned32
            MAX-ACCESS      read-only
            STATUS          current
            DESCRIPTION     "Current MAC Number Total."
        ::=  { macGlobalConfig 1 }

    macGlobalMaxNum   OBJECT-TYPE
        SYNTAX            Unsigned32
            MAX-ACCESS      read-only
            STATUS          current
            DESCRIPTION   "Max MAC number Total."
        ::=  { macGlobalConfig  2 }

    macGlobalAgingTime   OBJECT-TYPE
        SYNTAX            Unsigned32
            MAX-ACCESS    read-only
            STATUS        current
            DESCRIPTION   "MAC aging-time."
    ::=  { macGlobalConfig  3 }

    macGlobalProtect   OBJECT-TYPE
        SYNTAX            INTEGER{
            disable(0),
            enable(1)
            } 
            MAX-ACCESS     read-only
            STATUS         obsolete
            DESCRIPTION   "Configuration of MAC protect global."
        ::=  { macGlobalConfig  4 }

    macGlobalProtectTime   OBJECT-TYPE
        SYNTAX             Unsigned32
            MAX-ACCESS     read-only
            STATUS         obsolete
            DESCRIPTION   "Configuration of MAC protect-time."
        ::=  { macGlobalConfig  5 }

    macGlobalLearning   OBJECT-TYPE
        SYNTAX                       INTEGER{
            disable(0),
            enable(1)
            } 
            MAX-ACCESS      read-only
            STATUS          current
            DESCRIPTION   "Configuration of MAC learning global. 
                            Default is enable."
        ::=  { macGlobalConfig  6 }

    macGlobalLearnStrategy   OBJECT-TYPE
        SYNTAX                      INTEGER{
            learnBySwchip(0),
            learnByNp(1)
        }
            MAX-ACCESS      read-only
            STATUS          obsolete
            DESCRIPTION   "Configuration of MAC learn-strategy, include:
                     by-switchchip and by-NP. Default is by-switchchip."
        ::=  { macGlobalConfig  7 }

    macGlobalHigigLearn   OBJECT-TYPE
        SYNTAX                    INTEGER{
            special(0),
            normal(1)
        }
            MAX-ACCESS      read-only
            STATUS          obsolete
            DESCRIPTION   "Configuration of MAC global higig learn, include: 
                    normal and special. Default is normal."
        ::=  { macGlobalConfig  8 }

    macGlobalLogAlarm   OBJECT-TYPE
        SYNTAX                         INTEGER{
            disable(0),
            enable(1)
            } 
            MAX-ACCESS      read-only
            STATUS          obsolete
            DESCRIPTION   "Configuration of MAC alarm for mac-move. 
                    Default is disable."
        ::=  { macGlobalConfig  9 }

    macGlobalToPermanentAutoWrite   OBJECT-TYPE
        SYNTAX                         INTEGER{
            disable(0),
            enable(1)
            } 
            MAX-ACCESS      read-only
            STATUS          obsolete
            DESCRIPTION   "Configuration of autowrite toPermanent 
                    MAC to FLASH. Default is disable."
        ::=  { macGlobalConfig  10 }

    macGlobalToPermanentAutoWriteInterval   OBJECT-TYPE
        SYNTAX              Unsigned32
            MAX-ACCESS      read-only
            STATUS          obsolete
            DESCRIPTION   "Interval for autowrite toPermanent MAC to FLASH.
                    Default is one day."
        ::=  { macGlobalConfig  11 }   

    macGlobalAlarmThreshold   OBJECT-TYPE
        SYNTAX              Unsigned32
            MAX-ACCESS      read-only
            STATUS          current
            DESCRIPTION   "MAC alarm threshold."
        ::=  { macGlobalConfig  12 }  

    macGlobalHistoryMaxNum   OBJECT-TYPE
        SYNTAX            Unsigned32
            MAX-ACCESS    read-only
            STATUS        current
            DESCRIPTION   "MAC history max num."
        ::=  { macGlobalConfig  13 } 

macInterfaceConfig  OBJECT IDENTIFIER ::= { zxr10MacConfig  2 }

    macInterfaceConfigTable  OBJECT-TYPE
        SYNTAX  SEQUENCE OF MacInterfaceConfigEntry
        MAX-ACCESS  not-accessible
        STATUS  obsolete
        DESCRIPTION
           "Configuration and status for MAC table on port."
        ::= { macInterfaceConfig 1 }
 
    macInterfaceConfigEntry  OBJECT-TYPE
        SYNTAX  MacInterfaceConfigEntry
        MAX-ACCESS  not-accessible
        STATUS  obsolete
        DESCRIPTION
           ""
        INDEX  { macIfIndex }
        ::= { macInterfaceConfigTable 1 }

    MacInterfaceConfigEntry ::= SEQUENCE {
               macIfIndex           Unsigned32,
               macIfName            OCTET STRING,
               macIfLearning        INTEGER,
               macIfMaxNum          Unsigned32,
               macIfCurrentNum      Unsigned32,
               macIfUnknownSourceFilter INTEGER,
               macIfProtect         INTEGER,
               macIfToPermanent     INTEGER,
               macIfSafeModePolicy  INTEGER,
               macIfMaxNumPolicy      INTEGER
        }

   macIfIndex  OBJECT-TYPE
      SYNTAX  Unsigned32
      MAX-ACCESS  read-only
      STATUS  obsolete
      DESCRIPTION
          "Port out-index."
      ::= { macInterfaceConfigEntry 1 }

   macIfName  OBJECT-TYPE
      SYNTAX  OCTET STRING
      MAX-ACCESS  read-only
      STATUS  obsolete
      DESCRIPTION
          "Port name."
      ::= { macInterfaceConfigEntry 2 }

   macIfLearning  OBJECT-TYPE
      SYNTAX          INTEGER{
            disable(0),
            enable(1)
        }
      MAX-ACCESS  read-only
      STATUS  obsolete
      DESCRIPTION
          "Configuration of MAC learning on port. Default is enable."
      ::= { macInterfaceConfigEntry 3 }

   macIfMaxNum  OBJECT-TYPE
      SYNTAX  Unsigned32
      MAX-ACCESS  read-only
      STATUS  obsolete
      DESCRIPTION
          "Configuration of max MAC number on port. Command of limit-num 
                  and unknow-filter-limit-num can change this value both."
      ::= { macInterfaceConfigEntry 4 }

   macIfCurrentNum  OBJECT-TYPE
      SYNTAX  Unsigned32
      MAX-ACCESS  read-only
      STATUS  obsolete
      DESCRIPTION
          "Current MAC number on port."
      ::= { macInterfaceConfigEntry 5 }

   macIfUnknownSourceFilter  OBJECT-TYPE
      SYNTAX          INTEGER{
            disable(0),
            enable(1)
        }
      MAX-ACCESS  read-only
      STATUS  obsolete
      DESCRIPTION
          "Configuration of discarding unknownsource MAC or not on port. 
                  Default is disable."
      ::= { macInterfaceConfigEntry 6 }

   macIfProtect  OBJECT-TYPE
      SYNTAX  INTEGER        {
            disable(0),
            enable(1)
        }
      MAX-ACCESS  read-only
      STATUS  obsolete
      DESCRIPTION
          "Configuration of MAC protect on port. Default is disable."
      ::= { macInterfaceConfigEntry 7 }

   macIfToPermanent  OBJECT-TYPE
      SYNTAX  INTEGER        {
            disable(0),
            enable(1)
        }
      MAX-ACCESS  read-only
      STATUS  obsolete
      DESCRIPTION
          "Configuration of MAC toPermanent function on port. 
                  Default is disable."
      ::= { macInterfaceConfigEntry 8 }

   macIfSafeModePolicy  OBJECT-TYPE
      SYNTAX          INTEGER{
            disable(0),
            enableAlarm(1),
            enableShutdown(2)
        }
      MAX-ACCESS  read-only
      STATUS  obsolete
      DESCRIPTION
          "Configuration of MAC policy for safemode on port. Including 
              disable, enableAlarm and enableShutdown. Default is disable."
      ::= { macInterfaceConfigEntry 9 }
      
   macIfMaxNumPolicy  OBJECT-TYPE
      SYNTAX          INTEGER{
            stopLearn(0),
            unknownFilt(1)           
        }
      MAX-ACCESS  read-only
      STATUS  obsolete
      DESCRIPTION
          "Configuration of MAC policy while reach max MAC on port. 
              Command of limit-num can set stopLearn, and 
              command of unknow-filter-limit-num can set unknownFilt. 
              Default is stopLearn."
      ::= { macInterfaceConfigEntry 10 }
      
--    MacVlantable
    macVlanConfig  OBJECT IDENTIFIER ::= { zxr10MacConfig  3 }

    macVlanConfigTable  OBJECT-TYPE
        SYNTAX  SEQUENCE OF MacVlanConfigEntry
        MAX-ACCESS  not-accessible
        STATUS  obsolete
        DESCRIPTION
           "Configuration and status for MAC table in vlan."
        ::= { macVlanConfig 1 }
 
    macVlanConfigEntry  OBJECT-TYPE
        SYNTAX  MacVlanConfigEntry
        MAX-ACCESS  not-accessible
        STATUS  obsolete
        DESCRIPTION
           ""
        INDEX  { macVlanIndex }
        ::= { macVlanConfigTable 1 }

    MacVlanConfigEntry ::= SEQUENCE {
               macVlanIndex           Unsigned32,
               macVlanLearning        INTEGER,
               macVlanCurrentNum      Unsigned32
        }

   macVlanIndex  OBJECT-TYPE
      SYNTAX  Unsigned32(1..4094)
      MAX-ACCESS  read-only
      STATUS  obsolete
      DESCRIPTION
          "Vlan ID."
      ::= { macVlanConfigEntry 1 }

   macVlanLearning  OBJECT-TYPE
      SYNTAX          INTEGER{
            disable(0),
            enable(1)
        }
      MAX-ACCESS  read-only
      STATUS  obsolete
      DESCRIPTION
          "Configuration of MAC learning in vlan."
      ::= { macVlanConfigEntry 2 }

   macVlanCurrentNum  OBJECT-TYPE
      SYNTAX  Unsigned32
      MAX-ACCESS  read-only
      STATUS  obsolete
      DESCRIPTION
          "Current MAC number in vlan."
      ::= { macVlanConfigEntry 3 }

--    MacItemtable

    macItem  OBJECT IDENTIFIER ::= { zxr10MacConfig  4 }

    macItemTable  OBJECT-TYPE
        SYNTAX  SEQUENCE OF MacItemEntry
        MAX-ACCESS  not-accessible
        STATUS  obsolete
        DESCRIPTION
           "MAC table items."
        ::= { macItem 1 }
 
    macItemEntry  OBJECT-TYPE
        SYNTAX  MacItemEntry
        MAX-ACCESS  not-accessible
        STATUS  obsolete
        DESCRIPTION
           ""
        INDEX  { macItemVlan, macItemAddr }
        ::= { macItemTable 1 }

    MacItemEntry ::= SEQUENCE {
        macItemVlan      Unsigned32,
        macItemAddr      MacAddress,
        macItemPortName  OCTET STRING,
        macItemFilterType    INTEGER,
        macItemWorkMode  INTEGER
         }

   macItemVlan  OBJECT-TYPE
      SYNTAX  Unsigned32(1..4094)
      MAX-ACCESS  read-only
      STATUS  obsolete
      DESCRIPTION
          "Vlan ID."
      ::= { macItemEntry 1 }

   macItemAddr  OBJECT-TYPE
      SYNTAX  MacAddress
      MAX-ACCESS  read-only
      STATUS  obsolete
      DESCRIPTION
          "Mac address."
      ::= { macItemEntry 2 }

   macItemPortName  OBJECT-TYPE
      SYNTAX  OCTET STRING
      MAX-ACCESS  read-only
      STATUS  obsolete
      DESCRIPTION
          "Port name."
      ::= { macItemEntry 3 }

   macItemFilterType  OBJECT-TYPE
      SYNTAX                     INTEGER{
                            noFilter(1),
                            srcFilter(2),
                            dstFilter(3),
                            bothFilter(4)
                    }
      MAX-ACCESS  read-only
      STATUS  obsolete
      DESCRIPTION
          "MAC filter type. Including noFilter, srcFilter, 
              dstFilter and bothFilter."
      ::= { macItemEntry 4 }

   macItemWorkMode  OBJECT-TYPE
      SYNTAX              INTEGER{
                           dynamic(0),
                           static(1),
                           permanent(2),
                           toStatic(3),
                           toPermanent(4)
             }
      MAX-ACCESS  read-only
      STATUS  obsolete
      DESCRIPTION
          "Status of item storage in MAC table. Including dynamic, 
              static, permanent, toStatic and toPermanent."
      ::= { macItemEntry 5}

END
