-- =================================================================
-- Copyright (c) 2004-2021 New H3C Tech. Co., Ltd. All rights reserved.
--
-- Description: This MIB file is used for inquiring for PPP access user
--              authentication information.
-- Reference:
-- Version:     V1.1
-- History:
--   V1.0 Initial version by hkf6733
--   V1.1 2021-09-01 add hh3cPPPConfigTable by wangzhenjun
-- =================================================================
HH3C-PPP-MIB DEFINITIONS ::= BEGIN

IMPORTS
    hh3cCommon
        FROM HH3C-OID-MIB
    OBJECT-TYPE, MODULE-IDENTITY, Integer32
        FROM SNMPv2-SMI
    InterfaceIndex
        FROM IF-MIB
    DisplayString
        FROM SNMPv2-TC;



hh3cPPP MODULE-IDENTITY
    LAST-UPDATED "202109010000Z"            -- September 01th, 2021 at 00:00 GMT
    ORGANIZATION
        "New H3C Technologies Co., Ltd."
    CONTACT-INFO
        "Platform Team New H3C Technologies Co., Ltd.
         Hai-Dian District Beijing P.R. China
         http://www.h3c.com
         Zip: 100085"
    DESCRIPTION
        "PPP management information base for managing devices that support PPP
        protocol."
    REVISION    "202109010000Z"
    DESCRIPTION
        "Supporting the configuration for PPP on interface vitual template."
    REVISION    "201802010000Z"
    DESCRIPTION
        "Initial version"
    ::= { hh3cCommon 175 }

--
-- Node definitions
--

hh3cPPPAuthObjects OBJECT IDENTIFIER ::= { hh3cPPP  1 }

hh3cPPPAuthTable OBJECT-TYPE
    SYNTAX SEQUENCE OF Hh3cPPPAuthEntry
    MAX-ACCESS not-accessible
    STATUS current
    DESCRIPTION
        "This table describes the authentication information for PPP access
        users.  The index of this table is the interface and authentication
        type."
    ::= { hh3cPPPAuthObjects 1 }

hh3cPPPAuthEntry OBJECT-TYPE
    SYNTAX Hh3cPPPAuthEntry
    MAX-ACCESS not-accessible
    STATUS current
    DESCRIPTION
        "Each entry in this table describes the authentication  information of
        a PPP access user.  The available information includes: The index of
        the interface on which the PPP authentication information are
        configured, authentication type and username on the interface."
    INDEX { hh3cPPPIfIndex, hh3cPPPAuthType }
        ::= { hh3cPPPAuthTable 1 }

Hh3cPPPAuthEntry ::=
    SEQUENCE {
        hh3cPPPIfIndex
            InterfaceIndex,
        hh3cPPPAuthType
            INTEGER,
        hh3cPPPUserName
            DisplayString
        }

hh3cPPPIfIndex OBJECT-TYPE
    SYNTAX InterfaceIndex
    MAX-ACCESS not-accessible
    STATUS current
    DESCRIPTION
        "The index of the interface on the PPP authentication information are
        configured."
        ::= { hh3cPPPAuthEntry 1 }

hh3cPPPAuthType OBJECT-TYPE
    SYNTAX INTEGER
        {
            unknown(1),
            pap(2),
            chap(3)
        }
    MAX-ACCESS not-accessible
    STATUS current
    DESCRIPTION
        "The type of authentication for for the peer."
    ::= { hh3cPPPAuthEntry 2 }

hh3cPPPUserName OBJECT-TYPE
    SYNTAX DisplayString (SIZE (1..80))
    MAX-ACCESS read-only
    STATUS current
    DESCRIPTION
        "The username for access user."
    ::= { hh3cPPPAuthEntry 3 }


hh3cPPPConfigTable OBJECT-TYPE
    SYNTAX SEQUENCE OF Hh3cPPPConfigEntry
    MAX-ACCESS not-accessible
    STATUS current
    DESCRIPTION
        "This table describes the authentication information for PPP access
        users.  The index of this table is the virtual template interface."
    ::= { hh3cPPPAuthObjects 2 }

hh3cPPPConfigEntry OBJECT-TYPE
    SYNTAX Hh3cPPPConfigEntry
    MAX-ACCESS not-accessible
    STATUS current
    DESCRIPTION
        "Each entry in this table describes the authentication information of
        virtual templat for PPP access users."
    INDEX { hh3cPPPConfigIfIndex }
        ::= { hh3cPPPConfigTable 1 }

Hh3cPPPConfigEntry ::=
    SEQUENCE {
        hh3cPPPConfigIfIndex        InterfaceIndex,
        hh3cPPPConfigAuthMode       INTEGER,
        hh3cPPPConfigNegTimeout     Integer32,
        hh3cPPPConfigKeepInterval   Integer32,
        hh3cPPPConfigKeepRetransmit Integer32
        }

hh3cPPPConfigIfIndex OBJECT-TYPE
    SYNTAX InterfaceIndex
    MAX-ACCESS not-accessible
    STATUS current
    DESCRIPTION
        "The index of the virtaul template interface on the PPP authentication
        infomation are configured."
    ::= { hh3cPPPConfigEntry 1 }

hh3cPPPConfigAuthMode OBJECT-TYPE
    SYNTAX INTEGER {
                none(1),
                pap(2),
                chap(3),
                msChap(4),
                msChapV2(5)
               }
    MAX-ACCESS read-write
    STATUS current
    DESCRIPTION
        "The value is type of authentication mode for the peer."
    DEFVAL { none }
    ::= { hh3cPPPConfigEntry 2 }

hh3cPPPConfigNegTimeout OBJECT-TYPE
    SYNTAX Integer32 (1..10)
    UNITS "seconds"
    MAX-ACCESS read-write
    STATUS current
    DESCRIPTION
        "The timeout of the negotiation."
    DEFVAL { 3 }
    ::= { hh3cPPPConfigEntry 3 }

hh3cPPPConfigKeepInterval OBJECT-TYPE
    SYNTAX Integer32 (0..32767)
    UNITS "seconds"
    MAX-ACCESS read-write
    STATUS current
    DESCRIPTION
        "The hold time value, the default value is dependent on device."
    ::= { hh3cPPPConfigEntry 4 }

hh3cPPPConfigKeepRetransmit OBJECT-TYPE
    SYNTAX Integer32 (1..255)
    MAX-ACCESS read-write
    STATUS current
    DESCRIPTION
        "The the maximum number of attempts for transmitting a
        keepalive message, the default value is dependent on device."
    ::= { hh3cPPPConfigEntry 5 }

END
