VPN-TC-STD-MIB DEFINITIONS ::= BEGIN
    
    IMPORTS
        MODULE-IDENTITY, mib-2
            FROM SNMPv2-SMI
    
        TEXTUAL-CONVENTION
            FROM SNMPv2-TC;

    vpnTcMIB MODULE-IDENTITY
        LAST-UPDATED "200511150000Z"  -- 15 November 2005
        ORGANIZATION
            "Layer 3 Virtual Private Networks (L3VPN) Working Group."
        CONTACT-INFO
            "Benson Schliesser
             bensons@savvis.net
    
             Thomas D. Nadeau
             tnadeau@cisco.com
    
             This TC MIB is a product of the PPVPN
             http://www.ietf.org/html.charters/ppvpn-charter.html
             and subsequently the L3VPN
             http://www.ietf.org/html.charters/l3vpn-charter.html
             working groups.
    
             Comments and discussion should be directed to
             l3vpn@ietf.org"
        DESCRIPTION
            "This MIB contains TCs for VPNs.
        
             Copyright (C) The Internet Society (2005).  This version
             of this MIB module is part of RFC 4265;  see the RFC
             itself for full legal notices."
        -- Revision history.
        REVISION "200511150000Z"  -- 15 November 2005
        DESCRIPTION "Initial version, published as RFC 4265."
        ::= { mib-2 129 }

    -- definition of textual conventions
    
    VPNId ::= TEXTUAL-CONVENTION
        STATUS current
        DESCRIPTION
            "The purpose of a VPN-ID is to uniquely identify a VPN.
             The Global VPN Identifier format is:
             3 octet VPN Authority, Organizationally Unique Identifier
             followed by 4 octet VPN index identifying VPN according
             to OUI"
        REFERENCE
            "Fox, B. and Gleeson, B., 'Virtual Private Networks
             Identifier', RFC 2685, September 1999."
        SYNTAX    OCTET STRING (SIZE (7))
    
    VPNIdOrZero ::= TEXTUAL-CONVENTION
        STATUS            current
        DESCRIPTION
            "This textual convention is an extension of the
             VPNId textual convention that defines a non-zero-length
             OCTET STRING to identify a physical entity.  This extension
             permits the additional value of a zero-length OCTET STRING.
             The semantics of the value zero-length OCTET STRING are
             object-specific and must therefore be defined
             as part of the description of any object that uses this
             syntax.  Examples of usage of this extension are
             situations where none or all VPN IDs need to be
             referenced."
        SYNTAX    OCTET STRING (SIZE (0 | 7))
    
    END
