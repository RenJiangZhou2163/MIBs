-- ============================================================================
-- Copyright (c) 2004-2019 New H3C Tech. Co., Ltd. All rights reserved.
-- Description:  This MIB file is used for configuration of L2TP(Layer 2
--               Tunneling Protocol).
--               include :1.L2TP statistics information
-- Reference:
-- Version: V1.1
-- History:
-- V1.0 2013-07-05 created by yanbotao
-- V1.1 2019-04-12 add hh3cL2tpStatTemporarySessions and hh3cL2tpTunnelTable by zhouduan
-- ============================================================================
HH3C-L2TP-MIB DEFINITIONS ::= BEGIN
IMPORTS
    hh3cCommon
        FROM HH3C-OID-MIB
    Integer32, Counter32, Unsigned32, IpAddress, OBJECT-TYPE, MODULE-IDENTITY
        FROM SNMPv2-SMI;

hh3cL2tp MODULE-IDENTITY
    LAST-UPDATED "201904121018Z"            -- April 12, 2019 at 10:18 GMT
    ORGANIZATION
        "New H3C Tech. Co., Ltd."
    CONTACT-INFO
        "Platform Team New H3C Tech. Co., Ltd.
        Hai-Dian District Beijing P.R. China
        http://www.h3c.com
        Zip:100085
        "
    DESCRIPTION
        "This MIB contains objects to manage configuration of L2TP.
        There are no constraints on this MIB."
    REVISION "201904121018Z"                -- April 12, 2019 at 10:18 GMT
    DESCRIPTION
        "The initial revision of this MIB module."
    ::= { hh3cCommon 139 }

--
-- Node definitions
--
--
-- Definitions of significant branches
--
hh3cL2tpObjects         OBJECT IDENTIFIER  ::= { hh3cL2tp 1 }
hh3cL2tpScalar          OBJECT IDENTIFIER  ::= { hh3cL2tpObjects 1 }
hh3cL2tpStats           OBJECT IDENTIFIER  ::= { hh3cL2tpScalar 1 }

--
-- The L2TP Scalar Status and Statistics Group
--

hh3cL2tpStatsTotalTunnels OBJECT-TYPE
    SYNTAX          Counter32
    MAX-ACCESS      read-only
    STATUS          current
    DESCRIPTION
        "The total number of tunnels at the time of querying."
    ::= { hh3cL2tpStats 1 }

hh3cL2tpStatsTotalSessions OBJECT-TYPE
    SYNTAX        Counter32
    MAX-ACCESS    read-only
    STATUS        current
    DESCRIPTION
        "The total number of sessions at the time of querying."
    ::= { hh3cL2tpStats 2 }

hh3cL2tpSessionRate  OBJECT-TYPE
    SYNTAX        Integer32
    MAX-ACCESS    read-only
    STATUS        current
    DESCRIPTION
        "The number of sessions that were created in the previous second."
    ::= { hh3cL2tpStats 3 }

hh3cL2tpStatsTemporarySessions  OBJECT-TYPE
    SYNTAX        Unsigned32
    MAX-ACCESS    read-only
    STATUS        current
    DESCRIPTION
        "The total number of temporary sessions at the time of querying."
    ::= { hh3cL2tpStats 4 }

hh3cL2tpTunnel          OBJECT IDENTIFIER  ::= { hh3cL2tpObjects 2 }

--
-- The hh3cL2tpTunnelTable table
--

hh3cL2tpTunnelTable  OBJECT-TYPE
    SYNTAX        SEQUENCE OF Hh3cL2tpTunnelEntry
    MAX-ACCESS    not-accessible
    STATUS        current
    DESCRIPTION
        "A table containing L2tp tunnel specific variables
        for this L2TP implementation."
    ::= { hh3cL2tpTunnel 1 }

hh3cL2tpTunnelEntry  OBJECT-TYPE
    SYNTAX        Hh3cL2tpTunnelEntry
    MAX-ACCESS    not-accessible
    STATUS        current
    DESCRIPTION
        "Basic information about a particular L2tp tunnel."
    INDEX     { hh3cL2tpTunnelType, hh3cL2tpLocalIpAddress, hh3cL2tpLocalTunnelID }
    ::= { hh3cL2tpTunnelTable 1 }

Hh3cL2tpTunnelEntry ::= SEQUENCE {
    hh3cL2tpTunnelType
        INTEGER,
    hh3cL2tpLocalIpAddress
        IpAddress,
    hh3cL2tpLocalTunnelID
        Unsigned32,
    hh3cL2tpSessions
        Unsigned32
    }

hh3cL2tpTunnelType  OBJECT-TYPE
    SYNTAX        INTEGER {
        global(1),
        instance(2)
    }
    MAX-ACCESS    not-accessible
    STATUS        current
    DESCRIPTION
        "The tunnel type, (1) global (2) instance."
    ::= { hh3cL2tpTunnelEntry 1 }

hh3cL2tpLocalIpAddress  OBJECT-TYPE
    SYNTAX        IpAddress
    MAX-ACCESS    not-accessible
    STATUS        current
    DESCRIPTION
        "The local tunnel IP address."
    ::= { hh3cL2tpTunnelEntry 2 }

hh3cL2tpLocalTunnelID  OBJECT-TYPE
    SYNTAX        Unsigned32 (1..65535)
    MAX-ACCESS    not-accessible
    STATUS        current
    DESCRIPTION
        "The local tunnel ID."
    ::= { hh3cL2tpTunnelEntry 3 }

hh3cL2tpSessions  OBJECT-TYPE
    SYNTAX        Unsigned32 (0..4294967295)
    MAX-ACCESS    read-only
    STATUS        current
    DESCRIPTION
        "The total number of sessions at the time of querying."
    ::= { hh3cL2tpTunnelEntry 4 }

END
