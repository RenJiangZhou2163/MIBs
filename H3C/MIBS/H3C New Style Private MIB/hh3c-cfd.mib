-- =====================================================================
-- Copyright (c) 2004-2021 New H3C Tech.  Co., Ltd.  All rights reserved.
--
-- Description: CFD MIB
-- Reference:
-- Version: V1.0
-- History:
--   V1.0 Initial version, created by wangmeng
-- =====================================================================
HH3C-CFD-MIB DEFINITIONS ::= BEGIN

IMPORTS
    hh3cCommon
        FROM HH3C-OID-MIB
    Integer32, OBJECT-TYPE, MODULE-IDENTITY, NOTIFICATION-TYPE
        FROM SNMPv2-SMI;

hh3cCfd MODULE-IDENTITY
    LAST-UPDATED "202107191126Z"    -- July 19, 2021 at 11:26 GMT
    ORGANIZATION
        "New H3C Technologies Co., Ltd."
    CONTACT-INFO
        "
        Platform Team New H3C Tech.  Co., Ltd.
        Hai-Dian District Beijing P.R.  China
        http://www.h3c.com
        Zip:100085
        "
    DESCRIPTION
        "The Connectivity Fault Detection(CFD) extend MIB."

    REVISION "202107191126Z"
    DESCRIPTION
        "The initial revision of this MIB module."
    ::= { hh3cCommon 207 }

-- trap --
hh3cCfdTrap      OBJECT IDENTIFIER ::= { hh3cCfd 1 }

-- All trap definitions should be placed under this object.
hh3CfdTrapPrex OBJECT IDENTIFIER ::= { hh3cCfdTrap 0 }

hh3cCfdTwowayDelay NOTIFICATION-TYPE
    OBJECTS
        {   hh3cCfdMepId,
            hh3cCfdSrvId,
            hh3cCfdTimeThreshold
        }
    STATUS       current
    DESCRIPTION
        "The result of two-way delay-measurement exceeded the threshold."
 ::= { hh3CfdTrapPrex 1 }

hh3cCfdTwowayDelayRecovery NOTIFICATION-TYPE
    OBJECTS
        {   hh3cCfdMepId,
            hh3cCfdSrvId,
            hh3cCfdTimeThreshold
        }
    STATUS       current
    DESCRIPTION
        "The result of two-way delay-measurement is under the threshold."
    ::= { hh3CfdTrapPrex 2 }

hh3cCfdSlmStatistic NOTIFICATION-TYPE
    OBJECTS
        {   hh3cCfdFrameEnd,
            hh3cCfdMepId,
            hh3cCfdSrvId,
            hh3cCfdStatisticThreshold
        }
     STATUS       current
     DESCRIPTION
         "The result of one-way LM is exceeded the threshold."
     ::= { hh3CfdTrapPrex 3 }

-- All objects used for TRAP only are defined here.
hh3cCfdTrapOjbects OBJECT IDENTIFIER ::= { hh3cCfdTrap 1 }

hh3cCfdMepId OBJECT-TYPE
    SYNTAX  Integer32(1..8191)
    MAX-ACCESS   accessible-for-notify
    STATUS       current
    DESCRIPTION
        "The MEP ID."
    ::= { hh3cCfdTrapOjbects 1 }

hh3cCfdSrvId OBJECT-TYPE
    SYNTAX  Integer32(1..32767)
    MAX-ACCESS   accessible-for-notify
    STATUS       current
    DESCRIPTION
        "The service instance ID."
    ::= { hh3cCfdTrapOjbects 2 }

hh3cCfdTimeThreshold OBJECT-TYPE
    SYNTAX  Integer32
    UNITS "microseconds"
    MAX-ACCESS   accessible-for-notify
    STATUS       current
    DESCRIPTION
        "The delay time threshold."
    ::= { hh3cCfdTrapOjbects 3 }

hh3cCfdFrameEnd OBJECT-TYPE
    SYNTAX  INTEGER {
            nearEnd(1),
            farEnd(2)
     }
    MAX-ACCESS   accessible-for-notify
    STATUS       current
    DESCRIPTION
        "The loose frame end of MEP.
        nearEnd: loose frame on source MEP.
        farEnd: loose frame on target MEP."
    ::= { hh3cCfdTrapOjbects 4 }

hh3cCfdStatisticThreshold OBJECT-TYPE
    SYNTAX      OCTET STRING(SIZE(0..8))
    MAX-ACCESS   accessible-for-notify
    STATUS       current
    DESCRIPTION
        "The packet frame threshold in percentage, in the range of 0 to 100.
        It can contain a maximum of 8 digits, including the dot (.),
        for example, 1.000001."
    ::= { hh3cCfdTrapOjbects 5 }
END
