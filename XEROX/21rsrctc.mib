XEROX-RESOURCES-TC DEFINITIONS ::= BEGIN

-- Module:  XCMI Document Resources Textual Conventions MIB module
-- Editor:  Paul Gloger
-- File:    21rsrctc.mib
-- Date:    April 14, 2000
-- Version: 4.02.int

--
-- BEGIN XEROX PRIVATE DATA
--
-- Notice:  This .int (internal) version of this MIB module contains
-- portions which are Xerox Private Data, and therefore this internal
-- version may not generally be publicly disclosed.  See the .pub
-- (publicly-disclosable) version of this module, parallel to and
-- derived from this .int version, for a version which may, with
-- appropriate control, generally be publicly disclosed.
--
-- ENDOF XEROX PRIVATE DATA
--

IMPORTS
--  MODULE-IDENTITY, OBJECT-TYPE
--      FROM SNMPv2-SMI                -  IETF RFC 1442/1902/2578
--  TEXTUAL-CONVENTION
--      FROM SNMPv2-TC                 -  IETF RFC 1443/1903/2579
--  xeroxCommonMIB
--      FROM XEROX-COMMON-MIB/
    xeroxCommonMIB
        FROM    XEROX-COMMON-MIB
    OBJECT-TYPE
        FROM    RFC-1212
    ;


xcmRsrcTC OBJECT IDENTIFIER
--  LAST-UPDATED "0004140000Z"
--  ORGANIZATION "Xerox Corporation -
--      Xerox Common Management Interface (XCMI) Working Group"
--  CONTACT-INFO "
--                    XCMI Editors
--      E-Mail:       xcmieditors@cp10.es.xerox.com
--
--      - 
--      -  BEGIN XEROX PRIVATE DATA
--      - 
--                    XCMI Working Group
--      E-Mail:       xcmiwg@cp10.es.xerox.com
--      Web:          http://www.cp10.es.xerox.com/xac/xcmiwg/
--
--                    Paul Gloger
--                    XR&T/XAC/Enterprise Management
--      Mailstop:     ESAE-231
--      Telephone:    8*823-6820 / 310-333-6820
--      E-Mail:       pgloger@cp10.es.xerox.com
--
--      - 
--      -  ENDOF XEROX PRIVATE DATA
--      - 
--      "
--  DESCRIPTION "
--      XCMI Document Resources MIB Textual Conventions,
--      Version 4.02.int.
--
--      Copyright (C) 1997-2000 Xerox Corporation. All Rights Reserved."
    ::= { xeroxCommonMIB 56 }


-- Establish enum values

XcmRsrcGroupSupport ::= 
--      STATUS          current
--      DESCRIPTION
--              "Indicators for each primary object group of the
--              Document Resources MIB, used to indicate which groups
--              are supported by this host system, specified by a
--              bit-mask:
--                  1 : xcmRsrcGeneral  -  2**0 : general/base MIB group
--                  2 : xcmRsrcInfo   -  2**1 : (generic) resource info.
--                  4 : xcmFontInfo     -  2**2 : general font group
--                  8 : xcmFontPCLInfo  -  2**3 : PCL font group"
    INTEGER (0..2147483647)
                        -- Cardinal32 = unsigned int = (0..2**31-1)

XcmRsrcType ::= 
--      -  This value is an IETF-Printer-MIB type 2 enumeration.
--      -  This value should probably be changed to an OID if this MIB
--      -  is made into an IETF or other public standard.
--      STATUS          current
--      DESCRIPTION
--              "The type of this resource, from the given enumeration."
    INTEGER  -- left brace delay
        {
                other(1),
                unknown(2),
                font(3),
                logo(4),
                form(5),
                image(6)
              }

XcmRsrcPersistence ::= 
--      -  This value is an IETF-Printer-MIB type 2 enumeration
--      STATUS          current
--      DESCRIPTION
--              "Describes the persistence of this resource.
--
--              Permanent, or resident, resources are built into the
--              device and cannot be removed.  They may, for example,
--              be in ROM, or on hard disk with read-only access.
--              (Note that HP PCL considers a resource to be 'permanent'
--              if it persists across jobs, but such resources are not
--              necessarily permanent by the definition used here.)
--
--              Nonvolatile resources may be removed by appropriate
--              action, but otherwise persist indefinitely, including
--              across device power cycles.  They may, for example, be
--              on hard disk, or in a ROM cartridge.  (The type of
--              action required to remove the resource, e.g. file
--              deletion or ROM cartridge removal, can generally be
--              deduced from the hrStorageType of the storage device
--              containing the resource.)
--
--              Volatile resources are lost across device power cycles.
--              They are typically in RAM.
--
--              Reference: 'xcmRsrcHrStorageIndex' in this Resources
--              MIB/ and 'hrStorageType' in IETF Host Resources MIB
--              (RFC 1514, September 1993) on page 8 (which directly
--              relate to the actual level of 'persistence')."
    INTEGER  -- left brace delay
        {
                other(1),
                unknown(2),
                volatile(3),    -- lost across power cycles
                nonvolatile(4), -- persistent across power cycles
                permanent(5)    -- cannot be removed
              }

XcmFontType ::= 
--      -  This value is an IETF-Printer-MIB type 2 enumeration.
--      -  This value should probably be changed to an OID if this MIB
--      -  is made into an IETF or other public standard.
--      STATUS          current
--      DESCRIPTION
--              "The representation type or format of this font,
--              from the given enumeration."
    INTEGER  -- left brace delay
        {
                other(1),
                unknown(2),
                psType1(3),  -- Adobe PostScript Type 1 (specially
                               -- encoded, outline-only, base font)
                psType3(4),  -- Adobe PostScript Type 3
                               -- (regularly PS-encoded base font)
                psType0(5),  -- Adobe PostScript Type 0 (composite font)
                psType42(6),  -- Adobe PostScript Type 42
                               -- (TrueType font in PS wrapper)
                psCIDType0(7),  -- Adobe PostScript CID (Character ID)-
                               -- Keyed font, CIDType 0
                psCIDType1(8),  -- Adobe PostScript CID (Character ID)-
                               -- Keyed font, CIDType 1
                psCIDType2(9),  -- Adobe PostScript CID (Character ID)-
                               -- Keyed font, CIDType 2
                pclSoftFont(10),  -- HP PCL SoftFont (bitmap font)
                pclIntellifont(11),  -- HP PCL Intellifont
                               -- (outline font)
                xeroxICF(12),  -- Xerox ICF (Internal Contour Format)
                psType14(13),  -- Adobe PostScript Type 14 ("Chameleon"
                               -- font - "tunings" to a "master" font)
                psType2(14)  -- Adobe PostScript Type 2 (specially
                               -- encoded using Type2 charstrings)
               }

XcmFontSpacing ::= 
--      -  This value is an IETF-Printer-MIB type 2 enumeration
--      STATUS          current
--      DESCRIPTION
--              "The kind of spacing of the characters in this font,
--              from the given enumeration."
    INTEGER  -- left brace delay
        {
                other(1),
                unknown(2),
                fixedSpacing(3),
                        -- same spacing for all characters in font
                proportionalSpacing(4)
                        -- spacing of each character is proportional to
                        -- its optical width
               }

XcmFontPCLStyle ::= 
--            -  This value is an IETF-Printer-MIB type 2 enumeration
--      STATUS          current
--      DESCRIPTION
--              "The style of the font, from the given enumeration.
--
--              See: 'PCL 5 Printer Language Technical Reference
--              Manual' and 'PCL 5 Comparision Guide' by
--              Hewlett-Packard Corporation."
    INTEGER  -- left brace delay
        {
                other(1),
                unknown(2),
                upright(3),
                italic(4),
                condensed(5),
                condensedItalic(6),
                compressed(7),
                expanded(8),
                outline(9),
                inline(10),
                shadowed(11),
                outlineShadowed(12)
              }

XcmFontPCLStrokeWeight ::= 
--            -  This value is an IETF-Printer-MIB type 2 enumeration
--      STATUS          current
--      DESCRIPTION
--              "The PCL stroke weight of the font, from the given
--              enumeration.
--
--              These enumeration values are generally equal to the
--              usual PCL stroke weight values + 10.
--
--              See: 'PCL 5 Printer Language Technical Reference
--              Manual' and 'PCL 5 Comparision Guide' by
--              Hewlett-Packard Corporation."
    INTEGER  -- left brace delay
        {
                other(1),
                unknown(2),
                ultraThin(3),
                extraThin(4),
                thin(5),
                extraLight(6),
                light(7),
                demiLight(8),
                semiLight(9),
                medium(10),
                semiBold(11),
                demiBold(12),
                bold(13),
                extraBold(14),
                black(15),
                extraBlack(16),
                ultraBlack(17)
              }

--
--          Document Resources TC Dummy Group - DO NOT USE!
--
--          These dummy objects are defined only to suppress compiler
--          warnings by making some local reference to textual
--          conventions defined in this TC module.  These dummy objects
--          have odd use of case in their names (i.e. 'xCm...') in
--          order to make obvious their related textual conventions.

xCmRsrcDummy OBJECT IDENTIFIER ::= { xcmRsrcTC 999 }

xCmRsrcGroupSupport OBJECT-TYPE
    SYNTAX      XcmRsrcGroupSupport
    ACCESS      read-only
    STATUS      mandatory
    DESCRIPTION "Dummy object - DO NOT USE"
    ::= { xCmRsrcDummy 1 }

xCmRsrcType OBJECT-TYPE
    SYNTAX      XcmRsrcType
    ACCESS      read-only
    STATUS      mandatory
    DESCRIPTION "Dummy object - DO NOT USE"
    ::= { xCmRsrcDummy 2 }

xCmRsrcPersistence OBJECT-TYPE
    SYNTAX      XcmRsrcPersistence
    ACCESS      read-only
    STATUS      mandatory
    DESCRIPTION "Dummy object - DO NOT USE"
    ::= { xCmRsrcDummy 3 }

xCmFontType OBJECT-TYPE
    SYNTAX      XcmFontType
    ACCESS      read-only
    STATUS      mandatory
    DESCRIPTION "Dummy object - DO NOT USE"
    ::= { xCmRsrcDummy 4 }

xCmFontSpacing OBJECT-TYPE
    SYNTAX      XcmFontSpacing
    ACCESS      read-only
    STATUS      mandatory
    DESCRIPTION "Dummy object - DO NOT USE"
    ::= { xCmRsrcDummy 5 }

xCmFontPCLStyle OBJECT-TYPE
    SYNTAX      XcmFontPCLStyle
    ACCESS      read-only
    STATUS      mandatory
    DESCRIPTION "Dummy object - DO NOT USE"
    ::= { xCmRsrcDummy 6 }

xCmFontPCLStrokeWeight OBJECT-TYPE
    SYNTAX      XcmFontPCLStrokeWeight
    ACCESS      read-only
    STATUS      mandatory
    DESCRIPTION "Dummy object - DO NOT USE"
    ::= { xCmRsrcDummy 7 }

END
