XEROX-SERVICE-MONITORING-TC DEFINITIONS ::= BEGIN
--  Module: Service Monitoring TC
--  Author: Ira McDonald, Rob Sklut, and Rob Westfall
--  File    58svctc.mib
--  Date:   21 October 2001 - Version 4.14.int

--  Textual Conventions companion to XCMI Service Monitoring MIB

IMPORTS
--  MODULE-IDENTITY, OBJECT-TYPE
--          FROM SNMPv2-SMI             -  IETF RFC 1442/1902/2578
--  TEXTUAL-CONVENTION
--          FROM SNMPv2-TC              -  IETF RFC 1443/1903/2579
--  xeroxCommonMIB
--          FROM XEROX-COMMON-MIB/
    xeroxCommonMIB
        FROM    XEROX-COMMON-MIB
    OBJECT-TYPE
        FROM    RFC-1212
    ;

xcmSvcMonTC OBJECT IDENTIFIER
--  LAST-UPDATED "0110210000Z" -  21 October 2001
--  ORGANIZATION "Xerox Corporation - XCMI Working Group"
--  CONTACT-INFO
--      "           XCMI Editors
--      Email:      xcmieditors@cp10.es.xerox.com
--
--      - 
--      -  BEGIN XEROX PRIVATE DATA
--      - 
--                  Ira McDonald
--      Postal:     High North Inc
--                  221 Ridge Ave
--                  Grand Marais, MI  49839
--      Voice:      906-494-2434 or 906-494-2697
--      Email:      imcdonald@crt.xerox.com
--
--                  Rob Sklut
--      Postal:     Xerox Corporation, MS 801-36D
--                  800 Phillips Rd
--                  Webster, NY  14580
--      Voice:      716-422-2902
--      Email:      RSklut@crt.xerox.com
--
--                  Robert Westfall
--      Postal:     Xerox Corporation, MS 207-01Z
--                  800 Phillips Rd
--                  Webster, NY  14580
--      Voice:      716-422-5717
--      Email:      Rob.Westfall@usa.xerox.com
--      - 
--      -  ENDOF XEROX PRIVATE DATA
--      - 
--      "
--  DESCRIPTION
--      "Version:   4.14.int
--
--      Textual Conventions companion to XCMI Service Monitoring MIB,
--      the MIB module for basic configuration and active management
--      of application services for network accessible host systems.
--
--      See:    IETF Network Services Monitoring MIB
--              (IETF RFC 1565, January 1994).
--      See:    IETF Host Resources MIB
--              (IETF RFC 2790, March 2000).
--      See:    OSI Reference Model - Part 1:  Basic Reference Model
--              (CCITT X.200:1992 | ISO 7498-1:1992).
--      See:    OSI Reference Model - Part 4:  Systems Management
--              (CCITT X.700:1992 | ISO 7498-4:1992).
--      See:    Document Printing Application - Part 1: Abstract Service
--              (ISO/IEC 10175-1 Final Text, March 1996).
--      See:    POSIX System Administration - Part 4: Print Interfaces
--              (IEEE 1387.4 / Draft 8, October 1994).
--
--      Copyright (C) 1996-2001 Xerox Corporation. All Rights Reserved."
    ::= { xeroxCommonMIB 73 }

--
--          The Service Monitoring TC
--
--          Textual Conventions

--.ts 'XcmSvcMonGroupSupport'
XcmSvcMonGroupSupport ::= 
--  STATUS      current
--  DESCRIPTION
--      "The terse conformance statement of ALL mandatory, conditionally
--      mandatory, and optional XCMI Service Monitoring MIB groups
--      supported by this management agent implementation (ie, version)
--      on this host system, specified in a bit-mask.
--
--      The current set of values (which MAY be extended in the future)
--      is given below:
--
--            1 : svcMonGeneralGroup            -  2**0
--            2 : svcMonQueueGroup              -  2**1
--            4 : svcMonQueueExtGroup           -  2**2
--            8 : svcMonServiceGroup            -  2**3
--           16 : svcMonServiceDetailGroup      -  2**4
--           32 : svcMonServiceMgmtGroup        -  2**5
--
--      Usage:  Conforming management agents SHALL accurately
--      report their support for XCMI Service Monitoring MIB groups."
    INTEGER (0..2147483647)  -- biggest int = 2**31-1

--.ts 'XcmSvcMonJobConfirmSupport'
XcmSvcMonJobConfirmSupport ::= 
--  STATUS      current
--  DESCRIPTION
--      "The support for handling job confirmation reports and/or job
--      notifications on this host system, specified in a bit-mask.
--
--      The current set of values (which MAY be extended in the future)
--      is given below:
--
--            1 : confirmOnError                -  2**0
--            2 : confirmOnWarning              -  2**1
--            4 : confirmOnAbort                -  2**2
--            8 : confirmOnCancel               -  2**3
--           16 : confirmOnComplete             -  2**4
--           32 : confirmOnReceive              -  2**5
--           64 : confirmOnDeliver              -  2**6
--          128 : confirmOnStateChange          -  2**7
--          256 : confirmOnStateReasonChange    -  2**8
--
--      Usage:  Conforming management agents SHALL accurately
--      report their support for job confirmation reports."
    INTEGER (0..2147483647)  -- biggest int = 2**31-1

--.ts 'XcmSvcMonServiceMgmtOperation'
XcmSvcMonServiceMgmtOperation ::= 
--  STATUS      current
--  DESCRIPTION
--      "The most recent service management operation specified for
--      this conceptual row in the 'xcmSvcMonServiceMgmtTable'.
--
--      Usage:  The operations specified in this textual convention are
--      derived from the 'object' and 'server' operations specified in
--      the POSIX.3 standard.
--
--      Note:   The enum of '0' (zero) in this textual convention is
--      illegal in strict SMIv1 (see section 3.2.1.1 of RFC 1155), so
--      this TC must be converted to an integer range for pure SMIv1."
--  REFERENCE
--      "See:   Section 4 'Print Utilities' (pages 71 to 212) of
--              POSIX Sys Admin (IEEE 1387.4 / Draft 8, October 1994).
--      See:    OBJECT clause in MODULE-COMPLIANCE macro of
--              XCMI Service Monitoring MIB, for compliance info."
    INTEGER  -- left brace delay
        (-2147483648..2147483647)
--      none(0),                        -  No operation
--      other(1),                       -  Other operation
--      unknown(2),                     -  Unknown operation
        --  POSIX - Service level operations (on host system)
--      serviceCreate(1201),            -  'pdcreate' (create service)
--      serviceDelete(1202),            -  'pddelete' (delete service)
--      serviceList(1203),              -  'pdls' (list svc attributes)
--      serviceSet(1204),               -  'pdset' (set svc attributes)
--      serviceClean(1205),             -  'pdclean' (remove all jobs)
--      serviceDisable(1206),           -  'pddisable' (stop new jobs)
--      serviceEnable(1207),            -  'pdenable' (allow new jobs)
--      servicePause(1208),             -  'pdpause' (pause service)
--      serviceResume(1209),            -  'pdresume' (resume service)
--      serviceShutdown(1210),          -  'pdshutdown' (end service)
        --  XCMI - Service level extensions (on host system)
--      serviceManage(2201),            -  manage service object(s)
--      serviceRestart(2202),           -  restart service
--      serviceInstall(2221),           -  install service object(s)
--      serviceUpgrade(2222),           -  upgrade service object(s)
--      serviceBackup(2223),            -  backup service object(s)
--      serviceRestore(2224),           -  restore service object(s)
--      serviceConfigure(2225),         -  configure service object(s)
--      serviceDiagnose(2226),          -  diagnose service object(s)
--      serviceResetCounters(2231),     -  reset service counters
--      serviceResetWarm(2232),         -  warm reset (no power cycle)
--      serviceResetCold(2233),         -  cold reset (w/ power cycle)
--      serviceResetFactory(2234),      -  factory defaults reset
--      serviceLogin(2241),             -  login w/ authentication
--      serviceLogout(2242)             -  logout w/ authentication
--  }

--.ts 'XcmSvcMonServiceMgmtData'
XcmSvcMonServiceMgmtData ::= 
--  STATUS      current
--  DESCRIPTION
--      "The most recent simple service management data specified for
--      this conceptual row in the 'xcmSvcMonServiceMgmtTable'."
--  REFERENCE
--      "See:   Section 4 'Print Utilities' (pages 71 to 212) of
--              POSIX Sys Admin (IEEE 1387.4 / Draft 8, October 1994).
--      See:    OBJECT clause in MODULE-COMPLIANCE macro of
--              XCMI Service Monitoring MIB, for compliance info."
    OCTET STRING (SIZE (0..255))

--.ts 'XcmSvcMonServiceDetailClass'
XcmSvcMonServiceDetailClass ::= 
--  STATUS      current
--  DESCRIPTION
--      "A service detail class,
--      used by system administrators and end users to specify
--      the correct class for this service detail."
    INTEGER  -- left brace delay
        {
        other(1),
        unknown(2),
        localOther(3),                  -- local other system
        remoteOther(4),                 -- remote other system
        --  Local general purpose servers
        localAccountingServer(100),     -- local accounting
        localApplicationServer(101),    -- local applications
        localDocumentServer(102),       -- local document repositories
        localFileServer(103),           -- local file systems
        localLoggingServer(104),        -- local logging
        localNameServer(105),           -- local name services
        localNotificationServer(106),   -- local notifications
        localSecurityServer(107),       -- local security services
        localMailServer(108),           -- local mail services
        --  Remote general purpose servers
        remoteAccountingServer(150),    -- remote accounting
        remoteApplicationServer(151),   -- remote applications
        remoteDocumentServer(152),      -- remote document repositories
        remoteFileServer(153),          -- remote file systems
        remoteLoggingServer(154),       -- remote logging
        remoteNameServer(155),          -- remote name services
        remoteNotificationServer(156),  -- remote notifications
        remoteSecurityServer(157),      -- remote security services
        remoteMailServer(158),          -- remote mail services
        --  Local job related servers
        localJobAccountingServer(200),  -- local job accounting
        localJobLoggingServer(201),     -- local job logging
        localJobProcessingServer(202),  -- local job processing
        localJobTemplateServer(203),    -- local job templates
        --  Remote job related servers
        remoteJobAccountingServer(250), -- remote job accounting
        remoteJobLoggingServer(251),    -- remote job logging
        remoteJobProcessingServer(252), -- remote job processing
        remoteJobTemplateServer(253),   -- remote job templates
        --  Local intermediate systems (interworking functional units)
        localPhysicalRelay(301),        -- physical relay (repeater)
        localDatalinkRelay(302),        -- datalink relay (bridge)
        localNetworkRelay(303),         -- network relay (router)
        localTransportRelay(304),       -- transport relay
        localSessionRelay(305),         -- session relay
        localPresentationRelay(306),    -- presentation relay
        localApplicationRelay(307),     -- application relay (gateway)
        --  Remote intermediate systems (interworking functional units)
        remotePhysicalRelay(351),       -- physical relay (repeater)
        remoteDatalinkRelay(352),       -- datalink relay (bridge)
        remoteNetworkRelay(353),        -- network relay (router)
        remoteTransportRelay(354),      -- transport relay
        remoteSessionRelay(355),        -- session relay
        remotePresentationRelay(356),   -- presentation relay
        remoteApplicationRelay(357),    -- application relay (gateway)
        --  Local network management systems
        localNetMgmtAgent(400),         -- network mgmt agent
        localNetMgmtEventSource(401),   -- network mgmt event source
        localNetMgmtEventTarget(402),   -- network mgmt event target
        localNetMgmtProxy(403),         -- network mgmt proxy
        localNetMgmtStation(404),       -- network mgmt station
        --  Remote network management systems
        remoteNetMgmtAgent(450),        -- network mgmt agent
        remoteNetMgmtEventSource(451),  -- network mgmt event source
        remoteNetMgmtEventTarget(452),  -- network mgmt event target
        remoteNetMgmtProxy(453),        -- network mgmt proxy
        remoteNetMgmtStation(454)       -- network mgmt station
    }

--.ts 'XcmSvcMonServiceDetailType'
XcmSvcMonServiceDetailType ::= 
--  STATUS      current
--  DESCRIPTION
--      "A system, service, or profile detail type,
--      used by system administrators and end users to specify
--      the correct type for this service detail.
--
--      Usage:  Conforming management stations and management agents
--      SHALL implement specified semantics for service detail types."
--
--      -   System other/unknown details
--    * 'other'
--    * 'unknown'
--
--      -   System general info
--      -   (details common to all devices and services are defined in
--      -   BOTH 'XcmHrDevDetailType' and 'XcmSvcMonServiceDetailType'
--      -   (see XCMI Ext to Host Resources TC for comparison)
--    * 'systemOther'
--    * 'systemUnknown'
--    * 'systemServiceTypeSupport'
--      - system service type support (MAY be multi-valued)
--      - (used to describe multifunction/distribution services)
--      - type - (XcmSvcMonServiceType)
--      - data - '...ValueInteger'
--      - (eg, 'jobServiceScanToMailList' or 'jobServicePrint')
--      - see - 'jobServiceMultifunction' in 'XcmSvcMonServiceType'
--      - see - 'systemServiceMultifunction' in 'XcmSvcMonServiceType'
--      - see - 'systemChannelMultifunction'
--      - in 'XcmSvcMonServiceDetailType'
--    * 'systemURI'
--      - system URI (Uniform Resource Identifier)
--      - (same usage as 'xcmCOInternetHTTPAddressURI' in XCMI CC TC)
--      - type - (XcmFixedLocaleDisplayString)
--      - subtype - '...ValueOID' (protocol in XCMI Comms Config TC)
--      - (eg, 'xcmCOInternetHTTP' (HTTP) or 'xcmCOInternetFTP' (FTP))
--      - data - '...ValueString'
--      - (eg, 'http://www.foo.com' (HTTP) or 'ftp://ftp.bar.com' (FTP))
--      - see - 'xcmCOInternetHTTPAddressURI' in XCMI Comms Config TC
--      - see - Generic URI Syntax (RFC 2396)
--      - compare - 'system[Protocol|ProtocolDetail' in XCMI Svc Mon TC
--      - compare - 'deviceHelpURI' in XCMI HRX TC
--    * 'systemOS'
--      - system operating system name
--      - type - (XcmFixedLocaleDisplayString)
--      - data - '...ValueString'
--      - see - IANA Operating System Name registry
--      - in directory 'ftp://ftp.isi.edu/in-notes/iana/assignments'
--      - in file 'operating-system-names'
--    * 'systemOSVersion'
--      - system operating system version
--      - type - (XcmFixedLocaleDisplayString)
--      - data - '...ValueString'
--    * 'systemDescription'
--      - system description
--      - type - (XcmFixedLocaleDisplayString)
--      - data - '...ValueString'
--      - (eg, 'Xerox DocuCentre 265 ST v1.0 - Network Scan v1.0.5')
--      - see - 'deviceDescription' in XCMI HRX TC
--      - see - 'hrDeviceDescr' in IETF HR MIB
--      - see - 'Usage of hrDeviceType and hrDeviceDescr' section of
--      - 'IETF Host Resources MIB Implementors Guide' in XCMI HRX TC
--    * 'systemName'
--      - system administrative name in directory (primary name)
--      - (same usage as 'xcmCOSpecialName' in XCMI Comms Config TC)
--      - type - (XcmFixedLocaleDisplayString)
--      - subtype - '...ValueOID' (directory in XCMI Comms Config TC)
--      - (eg, 'xcmCOInternetDNS')
--      - data - '...ValueString'
--      - (eg, 'showstopper.xerox.com')
--      - see - 'xcmCOSpecialName' in XCMI Comms Config TC
--      - see - 'systemAlias' in XCMI Svc Mon TC
--      - see - 'deviceName' and 'xcmHrDevInfoName' in XCMI HRX MIB
--      - see - DPA-1 9.4.1 'Printer-name'
--      - see - DPA-1 9.5.1 'Server-name'
--    * 'systemAddress'
--      - system address (host address or specific protocol address)
--      - (same usage as 'xcmCOSpecialAddress' in XCMI Comms Config TC)
--      - type - (XcmFixedLocaleDisplayString)
--      - subtype - '...ValueOID' (protocol in XCMI Comms Config TC)
--      - (eg, 'xcmCOInternetIP' (host) or 'xcmCOInternetFTP' (FTP))
--      - data - '...ValueString'
--      - (eg, '13.200.123.63' (host) or '13.200.123.63.515' (FTP))
--      - see - 'xcmCOSpecialAddress' in XCMI Comms Config TC
--      - compare - 'system[Protocol|ProtocolDetail' in XCMI Svc Mon TC
--      - compare - 'deviceHelpAddress' in XCMI HRX TC
--    * 'systemTree'
--      - system tree prefix to name/alias in directory
--      - type - (XcmFixedLocaleDisplayString)
--      - subtype - '...ValueOID' (directory in XCMI Comms Config TC)
--      - (eg, 'xcmCONetwareNDS')
--      - data - '...ValueString'
--      - (MAY also appear in 'systemName')
--      - see - 'deviceTree' in XCMI HRX TC
--    * 'systemContext'
--      - system context prefix to name/alias in directory
--      - type - (XcmFixedLocaleDisplayString)
--      - subtype - '...ValueOID' (directory in XCMI Comms Config TC)
--      - (eg, 'xcmCONetwareNDS')
--      - data - '...ValueString'
--      - (MAY also appear in 'systemName')
--      - see - 'deviceContext' in XCMI HRX TC
--    * 'systemVolume'
--      - system volume name in directory
--      - type - (XcmFixedLocaleDisplayString)
--      - subtype - '...ValueOID' (directory in XCMI Comms Config TC)
--      - (eg, 'xcmCONetwareNDS')
--      - data - '...ValueString'
--      - (eg, 'ARC_001:')
--      - see - 'systemName' in XCMI Svc Mon TC
--      - see - 'deviceName' and 'xcmHrDevInfoName' in XCMI HRX MIB
--    * 'systemPath'
--      - system default path in directory
--      - type - (XcmFixedLocaleDisplayString)
--      - subtype - '...ValueOID' (directory in XCMI Comms Config TC)
--      - (eg, 'xcmCONetwareNDS')
--      - data - '...ValueString'
--      - (eg, '/pub/mib/xcmiwork')
--      - see - 'systemName' in XCMI Svc Mon TC
--      - see - 'deviceName' and 'xcmHrDevInfoName' in XCMI HRX MIB
--    * 'systemCurrentLocale'
--      - system current locale (language/country and optional charset)
--      - type - (DisplayString) - XCMI standard 'locale tag'
--      - data - '...ValueString'
--      - format - IETF 'language tag' and optional IANA 'charset name'
--      - (IETF 'language tags' use ISO 639 language codes and suffix
--      - one or more ISO 3166 country, or IETF dialect/script subtags,
--      - with each subtag preceded by a hyphen)
--      - (XCMI 'locale tags' use IETF 'language tags' and MAY suffix
--      - EXACTLY one IANA 'charset name', preceded by a period)
--      - see - IETF Tags for Identification of Languages (RFC 1766)
--      - see - IETF Report of Character Set Workshop (RFC 2130)
--    * 'systemProtocol'
--      - system protocol identifier, enable/disable, and comment
--      - type - (TruthValue)
--      - subtype - '...ValueOID' (protocol in XCMI Comms Config TC)
--      - (eg, 'xcmCONetwareIPX')
--      - data - '...ValueInteger' (protocol enable/disable)
--      - (eg, '1' which means 'enable' or 'true')
--      - comment - '...ValueString' (protocol comment)
--      - (eg, 'NetWare 4.1 IPX protocol layer')
--      - (SHALL be parallel with 'systemAddress' if address required)
--      - see - 'systemAddress' in XCMI Svc Mon TC
--      - see - 'systemProtocolDetail' in XCMI Svc Mon TC
--      - compare - 'protocolTypedAddress' in XCMI Comms Config TC
--    * 'systemProtocolDetail'
--      - system protocol detail information (integer or string)
--      - type - (dynamic - see subtype - either string or integer)
--      - subtype - '...ValueOID' (detail in XCMI Comms Config TC)
--      - (eg, 'xcmCOSerialStopBits')
--      - data - '...Value[Integer|String]' (see XCMI Comms Config TC)
--      - (eg, '3' which means 1.5 stop bits for the above example)
--      - see - 'systemProtocol' in XCMI Svc Mon TC
--      - compare - 'systemAddress' in XCMI Svc Mon TC
--    * 'systemLoginName'
--      - system user login name in directory
--      - type - (XcmFixedLocaleDisplayString)
--      - subtype - '...ValueOID' (directory in XCMI Comms Config TC)
--      - (eg, 'xcmCONetwareNDS')
--      - data - '...ValueString'
--      - (eg, 'pgloger')
--      - see - 'xcmSecUserName' in XCMI Security MIB
--      - compare - 'deviceName' and 'xcmHrDevInfoName' in XCMI HRX MIB
--    * 'systemLoginPassword'
--      - system user login password in directory
--      - type - (XcmFixedLocaleDisplayString)
--      - subtype - '...ValueOID' (directory in XCMI Comms Config TC)
--      - (eg, 'xcmCONetwareNDS')
--      - data - '...ValueString'
--      - (eg, 'blazzle55')
--      - see - 'xcmSecUserPassword' in XCMI Security MIB
--    * 'systemLoginDate'
--      - system user last login date (MAY be multi-valued)
--      - type - (DateAndTime)
--      - data - '...ValueString'
--    * 'systemLogoutDate'
--      - system user last login date (MAY be multi-valued)
--      - type - (DateAndTime)
--      - data - '...ValueString'
--    * 'systemAlias'
--      - system administrative alias in directory (alternate name)
--      - (same usage as 'xcmCOSpecialName' in XCMI Comms Config TC)
--      - type - (XcmFixedLocaleDisplayString)
--      - subtype - '...ValueOID' (directory in XCMI Comms Config TC)
--      - (eg, 'xcmCOInternetDNS')
--      - data - '...ValueString'
--      - (eg, 'LaserRat')
--      - see - 'xcmCOSpecialName' in XCMI Comms Config TC
--      - see - 'systemName' in XCMI Svc Mon TC
--      - see - 'deviceAlias' in XCMI HRX TC
--      - see - DPA-1 9.4.2 'Printer-name-aliases'
--      - see - DPA-1 9.5.2 'Server-name-aliases'
--    * 'systemLocation'
--      - system physical location
--      - type - (XcmFixedLocaleDisplayString)
--      - data - '...ValueString'
--      - (eg, '3rd floor lobby')
--      - compare - 'deviceHelpLocation' in XCMI HRX TC
--      - see - DPA-1 9.4.3 'Printer-locations'
--    * 'systemOperatorMessage'
--      - system information message from operator to users
--      - type - (XcmFixedLocaleDisplayString)
--      - data - '...ValueString'
--      - (eg, 'Down until 2pm today')
--    * 'systemProblemMessage'
--      - system problem message to users
--      - type - (XcmFixedLocaleDisplayString)
--      - data - '...ValueString'
--      - (eg, 'Out of toner')
--
--      -   System help info (contact info)
--    * 'systemHelpName'
--      - system help person name and role
--      - type - (XcmFixedLocaleDisplayString)
--      - subtype - '...ValueOID' (directory in XCMI Comms Config TC)
--      - (eg, 'xcmCONetwareBindery')
--      - data - '...ValueString'
--      - (eg, 'Joe Hampton')
--      - role - '...ValueInteger' (XcmSecUserRole in XCMI Security TC)
--      - (eg, 'systemOperator')
--      - see - 'deviceHelpName' in XCMI HRX TC
--    * 'systemHelpAddress'
--      - system help person address and role
--      - type - (XcmFixedLocaleDisplayString)
--      - subtype - '...ValueOID' (protocol in XCMI Comms Config TC)
--      - (eg, 'xcmCOOsiwanFax')
--      - data - '...ValueString'
--      - (eg, '1-800-232-7979')
--      - role - '...ValueInteger' (XcmSecUserRole in XCMI Security TC)
--      - (eg, 'systemOperator')
--      - see - 'deviceHelpAddress' in XCMI HRX TC
--    * 'systemHelpDescription'
--      - system help person description
--      - type - (XcmFixedLocaleDisplayString)
--      - data - '...ValueString'
--      - (eg, 'has keys to supplies')
--      - see - 'deviceHelpDescription' in XCMI HRX TC
--    * 'systemHelpLocation'
--      - system help person physical location
--      - type - (XcmFixedLocaleDisplayString)
--      - data - '...ValueString'
--      - (eg, '3rd floor lobby')
--      - see - 'deviceHelpLocation' in XCMI HRX TC
--      - see - DPA-1 9.4.3 'Printer-locations'
--
--      -   System protocol security info
--    * 'systemProtocolSecurity'
--      - system security protocol identifier, enable/disable
--      - type - (TruthValue)
--      - subtype - '...ValueOID' (protocol in XCMI Comms Config TC)
--      - (eg, 'xcmCOInternetSSL3')
--      - data - '...ValueInteger' (protocol enable/disable)
--      - (eg, '1' which means 'enable' or 'true')
--      - (SHALL be parallel with 'systemProtocol')
--      - see - 'systemProtocol' in XCMI Svc Mon TC
--      - see - 'xcmCOSpecialSecurity' in XCMI Comms Config TC
--    * 'systemAuthMethod'
--      - system authentication method configured (single keyword)
--      - type - (XcmFixedLocaleDisplayString)
--      - data - '...ValueString'
--      - (eg, 'certificate')
--      - see - Section 4.4.2 'uri-authentication-supported'
--      -     - of IPP/1.1 Model (RFC 2911)
--    * 'systemAuthSupport'
--      - system authentication support - comma delimited keyword list
--      - type - (XcmFixedLocaleDisplayString)
--      - data - '...ValueString'
--      - (eg, 'basic,digest,certificate')
--      - see - Section 4.4.2 'uri-authentication-supported'
--      -     - of IPP/1.1 Model (RFC 2911)
--
--      -   System state info
--      -   (from ISO 10175 DPA-1 Section 9.5 'Server Object')
--      -   (see 9.1.6.4 'Generic attributes, their datatypes...')
--    * 'systemState'
--      - system state
--      - type - (XcmHrDpaState) in XCMI HRX TC
--      - data - '...ValueInteger'
--      - message - '...ValueString'
--      - see - DPA-1 9.1.6.4 'State'
--      - see - DPA-1 9.5 'Server object'
--    * 'systemConditions'
--      - system conditions (ie, 'state reasons')
--      - type - (XcmHrDpaConditions) in XCMI HRX TC
--      - data - '...ValueInteger'
--      - message - '...ValueString'
--      - see - DPA-3 D.2.3 'Server State Transitions'
--    * 'systemAvailability'
--      - system availability (ie, processing load level)
--      - type - (XcmHrDpaAvailability) in XCMI HRX TC
--      - data - '...ValueInteger'
--      - message - '...ValueString'
--      - see - DPA-1 9.1.6.6 'Availability'
--      - see - DPA-1 9.5 'Server object'
--    * 'systemEnabled'
--      - system enabled (receiving new jobs or input streams)
--      - type - (TruthValue)
--      - data - '...ValueInteger'
--      - message - '...ValueString'
--      - see - 'systemState' for pause/resume support
--      - see - DPA-1 9.4.74.16 'Enabled'
--      - see - DPA-1 9.5 'Server object'
--
--      -   System polling info
--    * 'systemPollingStartDate'
--      - system polling start date (when to start polling)
--      - type - (DateAndTime)
--      - data - '...ValueString'
--    * 'systemPollingStartTime'
--      - system polling start time (when to start polling)
--      - type - (XcmHrDevCalendarTimeOfDay) in XCMI HRX TC
--      - data - '...ValueInteger'
--    * 'systemPollingLastDate'
--      - system log of most recent successful poll date
--      - type - (DateAndTime)
--      - data - '...ValueString'
--    * 'systemPollingLastTime'
--      - system log of most recent successful poll time
--      - type - (XcmHrDevCalendarTimeOfDay) in XCMI HRX TC
--      - data - '...ValueInteger'
--    * 'systemPollingInterval'
--      - system polling interval
--      - type - (Cardinal32) seconds
--      - data - '...ValueInteger'
--    * 'systemPollingEnabled'
--      - system polling enabled (ie, polling is permitted)
--      - see - 'systemEnabled'
--      - type - (TruthValue)
--      - data - '...ValueInteger'
--
--      -   System supported and ready device name info (list)
--    * 'systemPhysicalNameSupport'
--      - type - (XcmFixedLocaleDisplayString)
--      - data - '...ValueString'
--      - see - 'devicePhysicalNameSupport' in XCMI HRX TC
--      - see - DPA-1 9.4.10 'Printer-associated-printers'
--      - see - DPA-1 9.5.6 'Physical-printers-supported' (servers)
--    * 'systemPhysicalNameReady'
--      - type - (XcmFixedLocaleDisplayString)
--      - data - '...ValueString'
--      - see - 'devicePhysicalNameReady' in XCMI HRX TC
--      - see - DPA-1 9.4.11 'Printers-ready'
--      - see - DPA-1 9.5.7 'Physical-printers-ready' (servers)
--    * 'systemLogicalNameSupport'
--      - type - (XcmFixedLocaleDisplayString)
--      - data - '...ValueString'
--      - see - 'deviceLogicalNameSupport' in XCMI HRX TC
--      - see - DPA-1 9.4.10 'Printer-associated-printers'
--      - see - DPA-1 9.5.8 'Logical-printers-supported' (servers)
--    * 'systemLogicalNameReady'
--      - type - (XcmFixedLocaleDisplayString)
--      - data - '...ValueString'
--      - see - 'deviceLogicalNameReady' in XCMI HRX TC
--      - see - DPA-1 9.4.11 'Printers-ready'
--      - see - DPA-1 9.5.9 'Logical-printers-ready' (servers)
--
--      -   System supported and ready device index info (list)
--    * 'systemPhysicalIndexSupport'
--      - type - (Cardinal32) 'hrDeviceIndex'
--      - data - '...ValueInteger'
--      - see - 'devicePhysicalIndexSupport' in XCMI HRX TC
--      - see - DPA-1 9.4.10 'Printer-associated-printers'
--      - see - DPA-1 9.5.6 'Physical-printers-supported' (servers)
--    * 'systemPhysicalIndexReady'
--      - type - (Cardinal32) 'hrDeviceIndex'
--      - data - '...ValueInteger'
--      - see - 'devicePhysicalIndexReady' in XCMI HRX TC
--      - see - DPA-1 9.4.11 'Printers-ready'
--      - see - DPA-1 9.5.7 'Physical-printers-ready' (servers)
--    * 'systemLogicalIndexSupport'
--      - type - (Cardinal32) 'hrDeviceIndex'
--      - data - '...ValueInteger'
--      - see - 'deviceLogicalIndexSupport' in XCMI HRX TC
--      - see - DPA-1 9.4.10 'Printer-associated-printers'
--      - see - DPA-1 9.5.8 'Logical-printers-supported' (servers)
--    * 'systemLogicalIndexReady'
--      - type - (Cardinal32) 'hrDeviceIndex'
--      - data - '...ValueInteger'
--      - see - 'deviceLogicalIndexReady' in XCMI HRX TC
--      - see - DPA-1 9.4.11 'Printers-ready'
--      - see - DPA-1 9.5.9 'Logical-printers-ready' (servers)
--
--      -   System supported and ready general info (lists except masks)
--    * 'systemObjectClassSupport'
--      - system object class support (bit-mask)
--      - type - (XcmHrDpaObjectClassSupport) in XCMI HRX TC
--      - data - '...ValueInteger'
--      - see - DPA-1 9.5.5 'Object-classes-supported' (servers)
--      - see - DPA-1 6.3 'DPA object classes'
--    * 'systemEventSupport'
--      - system event support (MAY be multi-valued)
--      - type - (OBJECT IDENTIFIER) - (event identifier object subtree)
--      - data - '...ValueOID'
--      - see - DPA-1 9.5.11 'Events-supported' (servers)
--    * 'systemJobValidateSupport'
--      - system job validate support (bit-mask)
--      - type - (XcmHrDpaJobValidateSupport) in XCMI HRX TC
--      - data - '...ValueInteger'
--      - see - DPA-1 9.5.10 'Job-validates-supported' (servers)
--      - see - DPA-1 9.2.4.12 'Job-validate' (jobs)
--    * 'systemModifyDocSupport'
--      - system modify documents support (within jobs)
--      - type - (TruthValue)
--      - data - '...ValueInteger'
--      - see - DPA-1 9.5.12 'Modify-individual-documents-supported'
--    * 'systemTransferMethodSupport'
--      - system transfer method support (MAY be multi-valued)
--      - type - (TruthValue)
--      - subtype - '...ValueOID' (protocol in XCMI Comms Config TC)
--      - data - in subtype above
--      - see - DPA-1 9.5.13 'Transfer-methods-supported'
--    * 'systemLocaleSupport'
--      - system locale support (MAY be multi-valued)
--      - type - (DisplayString) XCMI standard 'locale tag'
--      - data - '...ValueString'
--      - (eg, 'en-US.utf-8', which means 'English, US, UTF-8')
--      - see - 'systemCurrentLocale' in XCMI Svc Mon TC
--    * 'systemPosixVerbsSupport'
--      - system POSIX System Admin verbs support (bit-mask)
--      - type - (XcmSecPosixVerbs) in XCMI Security TC
--      - data - '...ValueInteger'
--    * 'systemJobStateSupport'
--      - system job state support (bit-mask)
--      - type - (XcmJMJobState) in XCMI Job Mon MIB -> bit-mask
--      - data - '...ValueInteger'
--      - compare - 'xcmGenBaseSNMPDomainSupport' in XCMI General MIB
--    * 'systemDeviceStatusSupport'
--      - system device status (state) support (bit-mask)
--      - type - (XcmHrDevInfoStatus) in XCMI HRX TC -> bit-mask
--      - data - '...ValueInteger'
--      - compare - 'xcmGenBaseSNMPDomainSupport' in XCMI General MIB
--    * 'systemDeviceXStatusSupport'
--      - system device extended status support (MAY be multi-valued)
--      - (list of 'XcmHrDevInfoStatus' values)
--      - type - (XcmHrDevInfoXStatus) in XCMI HRX TC
--      - data - '...ValueInteger'
--    * 'systemTranslatorSupport'
--      - type - (XcmFixedLocaleDisplayString)
--      - data - '...ValueString'
--      - see - 'deviceTranslatorSupport' in XCMI HRX TC
--      - see - DPA-1 9.4.74.5 'Translators-supported'
--    * 'systemTranslatorReady'
--      - type - (XcmFixedLocaleDisplayString)
--      - data - '...ValueString'
--      - see - 'deviceTranslatorReady' in XCMI HRX TC
--      - see - DPA-1 9.4.74.6 'Translators-ready'
--    * 'systemInitialValueJobSupport'
--      - type - (XcmFixedLocaleDisplayString)
--      - data - '...ValueString'
--      - see - 'deviceInitialValueJobSupport' in XCMI HRX TC
--      - see - DPA-1 9.4.74.13 'Initial-value-jobs-supported'
--    * 'systemInitialValueDocSupport
--      - type - (XcmFixedLocaleDisplayString)
--      - data - '...ValueString'
--      - see - 'deviceInitialValueDocSupport' in XCMI HRX TC
--      - see - DPA-1 9.4.74.14 'Initial-value-documents-supported'
--    * 'systemMultipleDocSupport'
--      - type - (TruthValue)
--      - data - '...ValueInteger'
--      - see - 'deviceMultipleDocSupport' in XCMI HRX TC
--      - see - DPA-1 9.4.74.3 'Multiple-documents-supported'
--    * 'systemCancelDocSupport'
--      - type - (TruthValue)
--      - data - '...ValueInteger'
--      - see - 'deviceCancelDocSupport' in XCMI HRX TC
--      - see - DPA-1 9.4.74.4 'Cancel-individual-documents-supported'
--    * 'systemForeignJobsVisible'
--      - type - (TruthValue)
--      - data - '...ValueInteger'
--      - see - 'deviceForeignJobsVisible' in XCMI HRX TC
--      - see - DPA-1 9.4.74.15 'Are-foreign-jobs-visible'
--    * 'systemJobConfirmEnabled'
--      - job confirmation enable/disable
--      - type - (TruthValue)
--      - data - '...ValueInteger'
--      - 'true' = 'enabled'
--      - 'false' = 'disabled'
--    * 'systemJobConfirmContent'
--      - job confirmation content (list of job attributes)
--      - type - (XcmFixedLocaleDisplayString)
--      - data - '...ValueString'
--      - (list of colon separated 'XcmHrDevMgmtCommandDataTag' values)
--      - (eg, 'JN:JF:DT:' == job name, document filename, date/time)
--      - data - '...ValueInteger' (content enable/disable)
--      - (1=true, 2=false, and 0=true for legacy interworking)
--      - see - 'XcmHrDevMgmtCommandDataTag' in XCMI HRX TC
--    * 'systemJobConfirmSupport'
--      - job confirmation support (bit-mask)
--      - type - (XcmSvcMonJobConfirmSupport) in XCMI Svc Mon TC
--      - data - '...ValueInteger'
--    * 'systemJobConfirmPolicy'
--      - job confirmation policy (ONE bit from bit-mask)
--      - type - (XcmSvcMonJobConfirmSupport) in XCMI Svc Mon TC
--      - data - '...ValueInteger'
--    * 'systemJobDefaultPDL'
--      - job default PDL format
--      - type - (XcmPrtInterpreterLangFamily) in XCMI Prt Ext TC
--      - data - '...ValueInteger'
--    * 'systemJobDefaultFeedResolution'
--      - job default resolution in feed direction
--      - type - (Cardinal32) DPI (dots per inch)
--      - data - '...ValueInteger'
--      - see - 'deviceFeedResolutionSupport' in XCMI HRX TC
--    * 'systemJobDefaultXFeedResolution'
--      - job default resolution in cross feed direction
--      - type - (Cardinal32) DPI (dots per inch)
--      - data - '...ValueInteger'
--      - see - 'deviceXFeedResolutionSupport' in XCMI HRX TC
--    * 'systemJobDefaultDepthResolution'
--      - job default resolution depth in bits
--      - type - (Cardinal32) bits
--      - data - '...ValueInteger'
--    * 'systemJobConfirmSheetColor'
--      - job confirmation sheet color
--      - type - (XcmFixedLocaleDisplayString)
--      - data - '...ValueString'
--      - (name of medium color from ISO 10175 or vendor extensions)
--      - (eg, 'blue')
--      - see - 'prtInputMediaColor' in IETF Printer MIB
--    * 'systemJobConfirmSheetType'
--      - job confirmation sheet type
--      - type - (XcmFixedLocaleDisplayString)
--      - data - '...ValueString'
--      - (name of medium type from ISO 10175 or vendor extensions)
--      - (eg, 'stationery')
--      - see - 'prtInputMediaType' in IETF Printer MIB
--
--      -   System filename info
--      -   (filename types below are subordinate to other details)
--    * 'systemFileSystemType'
--      - system file system type
--      - type - (hrFSTypes defined in IETF HR MIB)
--      - data - '...ValueOID'
--      - (eg, 'hrFSNTFS' - Windows NT file system)
--      - comment - '...ValueString' (file system comment)
--      - (eg, 'Windows NT file system')
--      - see - 'hrFSTypes' based OIDs defined in IETF HR MIB
--      - see - 'hrFSType' object in 'hrFSTable' in IETF HR MIB
--    * 'systemFilenameOther'
--    * 'systemFilenameUnknown'
--    * 'systemFilename'
--      - system filename (optional path, w/ root and extension)
--      - type - (XcmFixedLocaleDisplayString)
--      - data - '...ValueString'
--    * 'systemFilenameRoot'
--      - system filename root (w/out path or extension)
--      - type - (XcmFixedLocaleDisplayString)
--      - data - '...ValueString'
--      - compare - 'systemFilename' in XCMI Svc Mon TC
--    * 'systemFilenameExtension'
--      - system filename extension (w/out path or root)
--      - type - (XcmFixedLocaleDisplayString)
--      - data - '...ValueString'
--      - compare - 'systemFilename' in XCMI Svc Mon TC
--    * 'systemFilenameIncrement'
--      - system filename increment (used to generate unique filenames)
--      - type - (Ordinal32)
--      - data - '...ValueInteger'
--      - compare - 'systemFilename' in XCMI Svc Mon TC
--    * 'systemFilenameWildcards'
--      - system filename wildcard characters (listed in a string)
--      - type - (XcmFixedLocaleDisplayString)
--      - data - '...ValueString'
--      - compare - 'systemFilename' in XCMI Svc Mon TC
--    * 'systemFilenameDefault'
--      - system filename default (for missing operation parameters)
--      - type - (XcmFixedLocaleDisplayString)
--      - data - '...ValueString'
--      - see - 'systemFilename' in XCMI Svc Mon TC
--    * 'systemFilenameSoftLink'
--      - system filename which is a soft link
--      - type - (XcmFixedLocaleDisplayString)
--      - data - '...ValueString'
--      - see - 'systemFilename' in XCMI Svc Mon TC
--    * 'systemFilenameHardLink'
--      - system filename which is a hard link
--      - type - (XcmFixedLocaleDisplayString)
--      - data - '...ValueString'
--      - see - 'systemFilename' in XCMI Svc Mon TC
--    * 'systemFilenameConsole'
--      - system filename which is a console
--      - type - (XcmFixedLocaleDisplayString)
--      - data - '...ValueString'
--      - see - 'systemFilename' in XCMI Svc Mon TC
--    * 'systemFilenameDevice'
--      - system filename which is a device
--      - type - (XcmFixedLocaleDisplayString)
--      - data - '...ValueString'
--      - see - 'systemFilename' in XCMI Svc Mon TC
--    * 'systemFilenameDirectory'
--      - system filename which is a directory
--      - type - (XcmFixedLocaleDisplayString)
--      - data - '...ValueString'
--      - see - 'systemFilename' in XCMI Svc Mon TC
--    * 'systemFilenameAccessRights'
--      - system filename POSIX.2 access rights
--      - type - (XcmSecPosixRights) in XCMI Security TC
--      - data - '...ValueInteger'
--      - see - 'systemFilename' in XCMI Svc Mon TC
--
--      -   System job finishing and media info
--    * 'systemJobFinishingSupport'
--      - system job finishing support - comma delimited keyword list
--      - (any keywords from IPP 'finishings' attribute)
--      - (attribute MAY be multi-valued for a larger list)
--      - type - (XcmFixedLocaleDisplayString) - keyword or name list
--      - data - '...ValueString'
--      - (eg, 'staple,punch')
--      - see - 'finishings-supported' in Sect 4.2 of IPP/1.1 (RFC 2911)
--      - see - Section 4.2.6 'finishings' of IPP/1.1 Model (RFC 2911)
--    * 'systemJobFinishingDefault'
--      - system job finishing default - comma delimited keyword list
--      - (any keywords from IPP 'finishings' attribute)
--      - type - (XcmFixedLocaleDisplayString) - keyword or name list
--      - data - '...ValueString'
--      - (eg, 'staple')
--      - see - 'finishings-default' in Sect 4.2 of IPP/1.1 (RFC 2911)
--      - see - Section 4.2.6 'finishings' of IPP/1.1 Model (RFC 2911)
--    * 'systemJobSidesSupport'
--      - system job sides support - comma delimited keyword list
--      - (any keyword from IPP 'sides' attribute)
--      - (attribute MAY be multi-valued for a larger list)
--      - type - (XcmFixedLocaleDisplayString) - keyword or name list
--      - data - '...ValueString'
--      - (eg, 'one-sided', 'two-sided-long-edge')
--      - see - 'sides-supported' in Section 4.2 of IPP/1.1 (RFC 2911)
--      - see - Section 4.2.8 'sides' of IPP/1.1 Model (RFC 2911)
--    * 'systemJobSidesDefault'
--      - system job sides default - SINGLE keyword
--      - (any keyword from IPP 'sides' attribute)
--      - type - (XcmFixedLocaleDisplayString) - keyword or name
--      - data - '...ValueString'
--      - (eg, 'one-sided')
--      - see - 'sides-default' in Section 4.2 of IPP/1.1 (RFC 2911)
--      - see - Section 4.2.8 'sides' of IPP/1.1 Model (RFC 2911)
--    * 'systemJobOrientationSupport'
--      - system job orientation support - comma delimited keyword list
--      - (any keyword from IPP 'orientation' attribute)
--      - (attribute MAY be multi-valued for a larger list)
--      - type - (XcmFixedLocaleDisplayString) - keyword or name list
--      - data - '...ValueString'
--      - (eg, 'one-sided', 'two-sided-long-edge')
--      - see - 'orientation-requested-supported', Sect 4.2 of RFC 2911
--      - see - Section 4.2.10 'orientation-requested' in IPP (RFC 2911)
--    * 'systemJobOrientationDefault'
--      - system job orientation default - SINGLE keyword
--      - (any keyword from IPP 'orientation' attribute)
--      - type - (XcmFixedLocaleDisplayString) - keyword or name
--      - data - '...ValueString'
--      - (eg, 'one-sided')
--      - see - 'orientation-requested-default', Sect 4.2 of RFC 2911
--      - see - Section 4.2.10 'orientation-requested' in IPP (RFC 2911)
--    * 'systemJobMediaSupport'
--      - system job media support - comma delimited keyword list
--      - (any keyword from IPP 'media' attribute)
--      - (attribute MAY be multi-valued for a larger list)
--      - type - (XcmFixedLocaleDisplayString) - keyword or name list
--      - data - '...ValueString'
--      - (eg, 'na-letter')
--      - see - 'media-supported' in Section 4.2 of IPP/1.1 (RFC 2911)
--      - see - Section 4.2.11 'media' of IPP/1.1 Model (RFC 2911)
--    * 'systemJobMediaDefault'
--      - system job media default - SINGLE keyword
--      - (any keyword from IPP 'media' attribute)
--      - type - (XcmFixedLocaleDisplayString) - keyword or name
--      - data - '...ValueString'
--      - (eg, 'iso-a4')
--      - see - 'media-default' in Section 4.2 of IPP/1.1 (RFC 2911)
--      - see - Section 4.2.11 'media' of IPP/1.1 Model (RFC 2911)
--    * 'systemJobAttributeSupport'
--      - system job attribute support - comma delimited keyword list
--      - (any keyword from any IPP attribute)
--      - (attribute MAY be multi-valued for a larger list)
--      - type - (XcmFixedLocaleDisplayString) - keyword or name list
--      - data - '...ValueString'
--      - (eg, 'job-priority,copies,number-up')
--      - see - Section 4.2 'Job Template Attributes' of RFC 2911
--      - see - Section 4.3 'Job Description Attributes' of RFC 2911
--    * 'systemJobAttributeDefault'
--      - system job attribute default - SINGLE 'keyword = value' string
--      - (any keyword from any IPP attribute)
--      - (encoded as UTF-8 string by rules of SLPv2, RFC 2608)
--      - type - (XcmFixedLocaleDisplayString) - assignment string
--      - data - '...ValueString'
--      - (eg, 'number-up=4')
--      - see - Section 4.2 'Job Template Attributes' of RFC 2911
--      - see - Section 4.3 'Job Description Attributes' of RFC 2911
--
--      -   System lifetime usage and limits
--      -   (several usage counters MAY be defined for a single system)
--      -   (several usage limits MAY be defined for a single counter)
--      -   (usage counter and usage limit groups are defined as sharing
--      -   the same value of 'xcmSvcMonServiceDetailIndex')
--    * 'systemLifetimeUsage'
--      - system lifetime usage counter (MAY be multi-valued)
--      - (SHALL NOT be remotely reset, unlike 'deviceAccountingUsage')
--      - type - (Counter32)
--      - subtype - '...ValueString' (XcmGenMessageMapStringLabel)
--      - and (optional) trailing description after whitespace
--      - data - '...ValueInteger'
--      - (eg, power cycles and output lifetime counters)
--      - note - SHOULD be subtyped by well-formed Xerox message
--      - string label of the 'XcmGenMessageMapStringLabel' syntax
--      - defined in the XCMI General TC (06gentc)
--      - note - media counters ('media|Image|Impression|Sheet]')
--      - SHOULD be subtyped by well-formed Xerox message label
--      - of the media name, size, type, and/or color, for example:
--      - 'xs-iso-10175-mediaName-iso-a4-...' (size, plus type/color)
--      -   - supports unified IETF IPP 'media' job attribute
--      - 'xs-iso-10175-mediaSize-na-letter' (size, no type/color)
--      -   - supports exact DPA media size tags
--    * 'systemLifetimeLimit'
--      - stop system at usage limit (MAY be multi-valued)
--      - type - (Cardinal32)
--      - subtype - see parallel 'systemLifetimeUsage'
--      - data - '...ValueInteger'
--      - positive integer = limit in 'xcmSvcMonServiceDetailUnit' units
--      - zero = no limit specified
--
--      -   System lifetime errors and warnings
--      -   (several error counters MAY be defined for a single system)
--      -   (one error limit MAY be defined for a single error counter)
--      -   (error counter and error limit pairs are defined as sharing
--      -   the same value of 'xcmSvcMonServiceDetailIndex')
--    * 'systemLifetimeErrorCount'
--      - system lifetime error counter (MAY be multi-valued)
--      - type - (Counter32)
--      - subtype - '...ValueString' (XcmGenMessageMapStringLabel)
--      - and (optional) trailing description after whitespace
--      - data - '...ValueInteger'
--      - (eg, paper jam - see 'prtAlertCode' in IETF Printer MIB)
--      - note - SHOULD be subtyped by well-formed Xerox message
--      - string label of the 'XcmGenMessageMapStringLabel' syntax
--      - defined in the XCMI General TC (06gentc)
--    * 'systemLifetimeErrorLimit'
--      - system lifetime error limit (MAY be multi-valued)
--      - type - (Cardinal32)
--      - subtype - see parallel 'systemLifetimeErrorCount'
--      - data - '...ValueInteger'
--      - positive integer = limit in 'systemLifetimeErrorCount' units
--      - zero = no limit specified
--      - note - product-unique error handling at this limit
--    * 'systemLifetimeWarningCount'
--      - system lifetime warning counter (MAY be multi-valued)
--      - type - (Counter32)
--      - subtype - '...ValueString' (XcmGenMessageMapStringLabel)
--      - and (optional) trailing description after whitespace
--      - data - '...ValueInteger'
--      - (eg, paper low - see 'prtAlertCode' in IETF Printer MIB)
--      - note - SHOULD be subtyped by well-formed Xerox message
--      - string label of the 'XcmGenMessageMapStringLabel' syntax
--      - defined in the XCMI General TC (06gentc)
--    * 'systemLifetimeWarningLimit'
--      - system lifetime warning limit (MAY be multi-valued)
--      - type - (Cardinal32)
--      - subtype - see parallel 'systemLifetimeWarningCount'
--      - data - '...ValueInteger'
--      - positive integer = limit in 'systemLifetimeWarningCount' units
--      - zero = no limit specified
--      - note - product-unique warning handling at this limit
--
--      -   System accounting usage
--    * 'systemAccountingUsage'
--      - system accounting usage counter (MAY be multi-valued)
--      - (MAY be remotely reset, unlike 'systemLifetimeUsage')
--      - type - (Counter32)
--      - subtype - '...ValueString' (XcmGenMessageMapStringLabel)
--      - and (optional) trailing description after whitespace
--      - data - '...ValueInteger'
--      - (eg, monochrome and color page counters)
--      - see - 'systemLifetimeUsage' (which is NOT reset remotely)
--      - note - SHOULD be subtyped by a well-formed Xerox message
--      - string label of the 'XcmGenMessageMapStringLabel' syntax
--      - defined in the XCMI General TC (06gentc)
--
--      -   System job template info
--    * 'systemJobTemplateOther'
--    * 'systemJobTemplateUnknown'
--    * 'systemJobTemplateMaxStorage'
--      - job template maximum storage allocation
--      - type - (Cardinal32) kilobytes
--      - data - '...ValueInteger'
--    * 'systemJobTemplateMaxCount'
--      - job template maximum count
--      - type - (Gauge32)
--      - data - '...ValueInteger'
--    * 'systemJobTemplateCurrentCount'
--      - job template maximum count
--      - type - (Gauge32)
--      - data - '...ValueInteger'
--    * 'systemJobTemplateConfirmSheet'
--      - job template confirmation sheet enable/disable
--      - type - (TruthValue)
--      - data - '...ValueInteger'
--      - 'true' = 'enabled'
--      - 'false' = 'disabled'
--    * 'systemJobTemplateConfirmContent'
--      - job template confirmation content (list of job attributes)
--      - type - (XcmFixedLocaleDisplayString)
--      - data - '...ValueString'
--      - (list of colon separated 'XcmHrDevMgmtCommandDataTag' values)
--      - (eg, 'JN:JF:DT:' == job name, document filename, date/time)
--      - data - '...ValueInteger' (content enable/disable)
--      - (1=true, 2=false, and 0=true for legacy interworking)
--      - see - 'XcmHrDevMgmtCommandDataTag' in XCMI HRX TC
--    * 'systemJobTemplateConfirmSupport'
--      - job template confirmation support (bit-mask)
--      - type - (XcmSvcMonJobConfirmSupport) in XCMI Svc Mon TC
--      - data - '...ValueInteger'
--    * 'systemJobTemplateConfirmPolicy'
--      - job template confirmation policy (bit-mask)
--      - type - (XcmSvcMonJobConfirmSupport) in XCMI Svc Mon TC
--      - data - '...ValueInteger'
--    * 'systemJobTemplateConfirmSheetColor'
--      - job template confirmation sheet color
--      - type - (XcmFixedLocaleDisplayString)
--      - data - '...ValueString'
--      - (name of medium color from ISO 10175 or vendor extensions)
--      - (eg, 'blue')
--      - see - 'prtInputMediaColor' in IETF Printer MIB
--    * 'systemJobTemplateConfirmSheetType'
--      - job template confirmation sheet type
--      - type - (XcmFixedLocaleDisplayString)
--      - data - '...ValueString'
--      - (name of medium type from ISO 10175 or vendor extensions)
--      - (eg, 'stationery')
--      - see - 'prtInputMediaType' in IETF Printer MIB
--
--      -   System job cover sheet info
--    * 'systemJobCoverSheetEnabled'
--      - job cover sheet enable/disable
--      - type - (TruthValue)
--      - data - '...ValueInteger'
--      - 'true' = 'enabled'
--      - 'false' = 'disabled'
--    * 'systemJobCoverSheetContent'
--      - job cover sheet content (list of job attributes)
--      - type - (XcmFixedLocaleDisplayString)
--      - data - '...ValueString'
--      - (list of colon separated 'XcmHrDevMgmtCommandDataTag' values)
--      - (eg, 'JN:JF:DT:' == job name, document filename, date/time)
--      - data - '...ValueInteger' (content enable/disable)
--      - (1=true, 2=false, and 0=true for legacy interworking)
--      - see - 'XcmHrDevMgmtCommandDataTag' in XCMI HRX TC
--    * 'systemJobCoverSheetContentKey
--      - job cover sheet content keyword
--      - type - (XcmFixedLocaleDisplayString)
--      - data - '...ValueString'
--      - (keyword of non-MIB data from Local UI, PDL stream, etc.)
--      - (eg, 'disposition' = job disposition from Local UI)
--      - data - '...ValueInteger' (content enable/disable)
--      - (1=true, 2=false, and 0=true for legacy interworking)
--    * 'systemJobCoverSheetContentOID
--      - job cover sheet content OID
--      - type - (OBJECT IDENTIFIER)
--      - data - '...ValueOID'
--      - (base object identifier for job or device MIB object)
--      - (eg, 'xcmJobIdentifierUpstream' in XCMI Job Mon MIB)
--      - data - '...ValueInteger' (content enable/disable)
--      - (1=true, 2=false, and 0=true for legacy interworking)
--    * 'systemJobCoverSheetContentText
--      - job cover sheet content free text
--      - type - (XcmFixedLocaleDisplayString)
--      - data - '...ValueString'
--      - (free text for inclusion with job cover sheets)
--      - (eg, 'A message from Human Resources')
--      - data - '...ValueInteger' (content enable/disable)
--      - (1=true, 2=false, and 0=true for legacy interworking)
--
--      -   System job error sheet info
--    * 'systemJobErrorSheetEnabled'
--      - job error sheet enable/disable
--      - type - (TruthValue)
--      - data - '...ValueInteger'
--      - 'true' = 'enabled'
--      - 'false' = 'disabled'
--    * 'systemJobErrorSheetContent'
--      - job error sheet content (list of job attributes)
--      - type - (XcmFixedLocaleDisplayString)
--      - data - '...ValueString'
--      - (list of colon separated 'XcmHrDevMgmtCommandDataTag' values)
--      - (eg, 'JN:JF:DT:' == job name, document filename, date/time)
--      - data - '...ValueInteger' (content enable/disable)
--      - (1=true, 2=false, and 0=true for legacy interworking)
--      - see - 'XcmHrDevMgmtCommandDataTag' in XCMI HRX TC
--    * 'systemJobErrorSheetContentKey
--      - job error sheet content keyword
--      - type - (XcmFixedLocaleDisplayString)
--      - data - '...ValueString'
--      - (keyword of non-MIB data from Local UI, PDL stream, etc.)
--      - (eg, 'disposition' = job disposition from Local UI)
--      - data - '...ValueInteger' (content enable/disable)
--      - (1=true, 2=false, and 0=true for legacy interworking)
--    * 'systemJobErrorSheetContentOID
--      - job error sheet content OID
--      - type - (OBJECT IDENTIFIER)
--      - data - '...ValueOID'
--      - (base object identifier for job or device MIB object)
--      - (eg, 'xcmJobErrorCount' in XCMI Job Mon MIB)
--      - data - '...ValueInteger' (content enable/disable)
--      - (1=true, 2=false, and 0=true for legacy interworking)
--    * 'systemJobErrorSheetContentText
--      - job error sheet content free text
--      - type - (XcmFixedLocaleDisplayString)
--      - data - '...ValueString'
--      - (free text for inclusion with job error sheets)
--      - (eg, 'Please contact system operator')
--      - data - '...ValueInteger' (content enable/disable)
--      - (1=true, 2=false, and 0=true for legacy interworking)
--
--      -   System job show sender info
--    * 'systemJobShowSenderEnabled'
--      - job show sender enable/disable
--      - type - (TruthValue)
--      - data - '...ValueInteger'
--      - 'true' = 'enabled'
--      - 'false' = 'disabled'
--    * 'systemJobShowSenderContent'
--      - job show sender content (list of job attributes)
--      - type - (XcmFixedLocaleDisplayString)
--      - data - '...ValueString'
--      - (list of colon separated 'XcmHrDevMgmtCommandDataTag' values)
--      - (eg, 'JN:JF:DT:' == job name, document filename, date/time)
--      - data - '...ValueInteger' (content enable/disable)
--      - (1=true, 2=false, and 0=true for legacy interworking)
--      - see - 'XcmHrDevMgmtCommandDataTag' in XCMI HRX TC
--    * 'systemJobShowSenderContentKey
--      - job show sender content keyword
--      - type - (XcmFixedLocaleDisplayString)
--      - data - '...ValueString'
--      - (keyword of non-MIB data from Local UI, PDL stream, etc.)
--      - (eg, 'disposition' = job disposition from Local UI)
--      - data - '...ValueInteger' (content enable/disable)
--      - (1=true, 2=false, and 0=true for legacy interworking)
--    * 'systemJobShowSenderContentOID
--      - job show sender content OID
--      - type - (OBJECT IDENTIFIER)
--      - data - '...ValueOID'
--      - (base object identifier for job or device MIB object)
--      - (eg, 'xcmJobAuthorizationUserName' in XCMI Job Mon MIB)
--      - data - '...ValueInteger' (content enable/disable)
--      - (1=true, 2=false, and 0=true for legacy interworking)
--    * 'systemJobShowSenderContentText
--      - job show sender content free text
--      - type - (XcmFixedLocaleDisplayString)
--      - data - '...ValueString'
--      - (free text for inclusion with job sender info)
--      - (eg, 'Prepared by Accounts Payable')
--      - data - '...ValueInteger' (content enable/disable)
--      - (1=true, 2=false, and 0=true for legacy interworking)
--    * 'systemJobCopySenderEnabled'
--      - job copy sender enable/disable (via email or other delivery)
--      - type - (TruthValue)
--      - data - '...ValueInteger'
--      - 'true' = 'enabled'
--      - 'false' = 'disabled'
--
--      -   System job service channel info
--      -   (channels for receiving jobs, NOT for simple file transfer)
--      -   (SHALL be parallel with 'systemAddress' if address required)
--    * 'systemChannelOther'
--    * 'systemChannelUnknown'
--    * 'systemChannelDiagnostic'
--      - system channel for diagnostic jobs (MAY be multi-valued)
--      - (system protocol identifier, enable/disable, and comment)
--      - type - (TruthValue)
--      - subtype - '...ValueOID' (protocol in XCMI Comms Config TC)
--      - (eg, 'xcmCONetwarePServer')
--      - data - '...ValueInteger' (protocol enable/disable)
--      - (eg, '1' which means 'enable' or 'true')
--      - comment - '...ValueString' (protocol comment)
--      - (eg, 'NetWare 4.1 PServer protocol layer')
--      - (SHALL be parallel with 'systemAddress' if address required)
--      - see - 'systemAddress' in XCMI Svc Mon TC
--    * 'systemChannelFax'
--      - see - 'systemChannelDiagnostic' above
--    * 'systemChannelFileTransfer'
--      - see - 'systemChannelDiagnostic' above
--    * 'systemChannelImageProcess'
--      - see - 'systemChannelDiagnostic' above
--    * 'systemChannelMail'
--      - see - 'systemChannelDiagnostic' above
--    * 'systemChannelMultifunction'     -  aka Distribution
--      - see - 'systemChannelDiagnostic' above
--    * 'systemChannelPrint'
--      - see - 'systemChannelDiagnostic' above
--    * 'systemChannelScan'
--      - see - 'systemChannelDiagnostic' above
--    * 'systemChannelOCR'
--      - see - 'systemChannelDiagnostic' above
--    * 'systemChannelCopy'
--      - see - 'systemChannelDiagnostic' above
--    * 'systemJobIncompleteTimeout'
--      - system job incomplete timeout
--      - (delay until job with incomplete input is deleted)
--      - type - (Cardinal32) seconds
--      - data - '...ValueInteger'
--      - (zero=none or 1..n seconds)
--      - see - 'xcmCOInternetLPRJobTimeout' in XCMI CC TC
--      - compare - 'deviceJobIncompleteTimeout' in XCMI HRX TC
--    * 'systemJobProgrammingTimeout'
--      - system job programming timeout
--      - (delay until job programming settings are deleted)
--      - type - (Cardinal32) seconds
--      - data - '...ValueInteger'
--      - (zero=none or 1..n seconds)
--      - see - 'systemJobIncompleteTimeout' above
--      - compare - 'deviceJobProgrammingTimeout' in XCMI HRX TC
--    * 'systemJobHoldDeleteTimeout'
--      - system job hold until delete timeout
--      - (delay until held job is automatically deleted)
--      - type - (Cardinal32) seconds
--      - data - '...ValueInteger'
--      - (zero=none or 1..n seconds)
--      - see - 'systemJobIncompleteTimeout' above
--      - see - 'jobPause' in 'XcmSimpleJobMgmtOperation' in XCMI SJM TC
--      - compare - 'deviceJobHoldDeleteTimeout' in XCMI HRX TC
--    * 'systemJobPauseResumeTimeout'
--      - system job pause until resume timeout
--      - (delay until paused job is automatically resumed)
--      - type - (Cardinal32) seconds
--      - data - '...ValueInteger'
--      - (zero=none or 1..n seconds)
--      - see - 'systemJobIncompleteTimeout' above
--      - see - 'jobPause' in 'XcmSimpleJobMgmtOperation' in XCMI SJM TC
--      - compare - 'deviceJobPauseResumeTimeout' in XCMI HRX TC
--
--      -   System feature info
--    * 'systemActivityReportEnabled'
--      - system activity report enable/disable
--      - type - (TruthValue)
--      - data - '...ValueInteger'
--      - ('true(1)' = enable and 'false(2)' = disable)
--    * 'systemAccountingEnabled'
--      - system accounting enable/disable
--      - type - (TruthValue)
--      - data - '...ValueInteger'
--      - ('true(1)' = enable and 'false(2)' = disable)
--    * 'systemLoggingEnabled'
--      - system logging enable/disable
--      - type - (TruthValue)
--      - data - '...ValueInteger'
--      - ('true(1)' = enable and 'false(2)' = disable)
--    * 'systemNotificationEnabled'
--      - system notification (SNMP, SMTP, IPP, etc.) enable/disable
--      - type - (TruthValue)
--      - data - '...ValueInteger'
--      - ('true(1)' = enable and 'false(2)' = disable)
--
--      -   System mail info
--    * 'systemMailSubject'
--      - system subject field for outgoing mail message
--      - type - (XcmFixedLocaleDisplayString)
--      - data - '...ValueString'
--      - see - 'xcmCOInternetSMTPSubject' in XCMI CC TC
--    * 'systemMailSignatureLine'
--      - system signature line for outgoing mail message
--      - type - (XcmFixedLocaleDisplayString)
--      - data - '...ValueString'
--      - see - 'xcmCOInternetSMTPSignatureLine' in XCMI CC TC
--    * 'systemMailMaxInputText'
--      - system max text body size for incoming mail message
--      - type - (Cardinal32) bytes
--      - data - '...ValueInteger'
--      - (value of zero indicates incoming text body is NOT allowed)
--      - see - 'xcmCOInternetSMTPMaxInputText' in XCMI CC TC
--    * 'systemMailMaxInputAttach'
--      - system max attachment size for incoming mail message
--      - type - (Cardinal32) bytes
--      - data - '...ValueInteger'
--      - (value of zero indicates incoming attachment is NOT allowed)
--      - see - 'xcmCOInternetSMTPMaxInputAttach' in XCMI CC TC
--    * 'systemMailMaxOutputText'
--      - system max text body size for outgoing mail message
--      - type - (Cardinal32) bytes
--      - data - '...ValueInteger'
--      - (value of zero indicates outgoing text body is NOT allowed)
--      - see - 'xcmCOInternetSMTPMaxOutputText' in XCMI CC TC
--    * 'systemMailMaxOutputAttach'
--      - system max attachment size for outgoing mail message
--      - type - (Cardinal32) bytes
--      - data - '...ValueInteger'
--      - (value of zero indicates outgoing attachment is NOT allowed)
--      - see - 'xcmCOInternetSMTPMaxOutputAttach' in XCMI CC TC
--    * 'systemMailConfirmRequest'
--      - system confirm outgoing mail message
--      - type - (TruthValue)
--      - data - '...ValueInteger' (confirm outgoing enable/disable)
--      - see - 'xcmCOInternetSMTPConfirmRequest' in XCMI CC TC
--    * 'systemMailConfirmReply'
--      - system confirm incoming mail message
--      - type - (TruthValue)
--      - data - '...ValueInteger' (confirm incoming enable/disable)
--      - see - 'xcmCOInternetSMTPConfirmReply' in XCMI CC TC
--    * 'systemMailConfirmTimeout'
--      - system confirm outgoing mail message timeout
--      - type - (Cardinal32) seconds
--      - data - '...ValueInteger'
--      - (zero=none or 1..n seconds)
--      - see - 'xcmCOInternetSMTPConfirmTimeout' in XCMI CC TC
--    * 'systemMailFeatureReply'
--      - system feature report (capabilities) w/ confirm incoming reply
--      - type - (TruthValue)
--      - data - '...ValueInteger' (feature report enable/disable)
--      - see - 'xcmCOInternetSMTPFeatureReply' in XCMI CC TC
--    * 'systemMailAddress'
--      - system mail address - 'user@hostname' per RFC 822
--      - type - (XcmFixedLocaleDisplayString)
--      - data - '...ValueString'
--      - (eg, 'pr5250@xbc.xerox.com')
--      - see - 'xcmCOInternetSMTPMailAddress' in XCMI CC TC
--    * 'systemMailMaxInFragments'
--      - system max fragments for incoming mail message
--      - type - (Cardinal32)
--      - data - '...ValueInteger'
--      - (value of zero indicates incoming fragments are NOT allowed)
--      - see - 'xcmCOInternetSMTPMaxInFragments' in XCMI CC TC
--    * 'systemMailMaxOutFragments'
--      - system max fragments for outgoing mail message
--      - type - (Cardinal32)
--      - data - '...ValueInteger'
--      - (value of zero indicates outgoing fragments are NOT allowed)
--      - see - 'xcmCOInternetSMTPMaxOutFragments' in XCMI CC TC
--    * 'systemMailMaxInAttachments'
--      - system max attachments for incoming mail message
--      - type - (Cardinal32)
--      - data - '...ValueInteger'
--      - (value of zero indicates incoming attachments are NOT allowed)
--      - see - 'xcmCOInternetSMTPMaxInAttachments' in XCMI CC TC
--    * 'systemMailMaxOutAttachments'
--      - system max attachments for outgoing mail message
--      - type - (Cardinal32)
--      - data - '...ValueInteger'
--      - (value of zero indicates outgoing attachments are NOT allowed)
--      - see - 'xcmCOInternetSMTPMaxOutAttachments' in XCMI CC TC
--    * 'systemMailMaxInputSize'
--      - system max size in bytes for incoming mail message
--      - type - (Cardinal32) bytes
--      - data - '...ValueInteger'
--      - (value of zero indicates incoming messages are NOT allowed)
--      - see - 'xcmCOInternetSMTPMaxInputSize' in XCMI CC TC
--    * 'systemMailMaxOutputSize'
--      - system max size in bytes for outgoing mail message
--      - type - (Cardinal32) bytes
--      - data - '...ValueInteger'
--      - (value of zero indicates outgoing messages are NOT allowed)
--      - see - 'xcmCOInternetSMTPMaxOutputSize' in XCMI CC TC
--
--      -   System directory info
--    * 'systemDirectoryMaxSearchResult'
--      - system directory max search results (matching entries)
--      - type - (Cardinal32)
--      - data - '...ValueInteger'
--      - see - 'xcmCOInternetLDAPMaxSearchResult' in XCMI CC TC
--    * 'systemDirectorySearchTimeout'
--      - system directory search timeout (matching entries)
--      - type - (Cardinal32) seconds
--      - data - '...ValueInteger'
--      - (value of zero indicates infinite)
--      - see - 'xcmCOInternetLDAPSearchTimeout' in XCMI CC TC
--    * 'systemDirectoryLDAPServerType'
--      - system directory server type - SINGLE keyword
--      - type - (XcmFixedLocaleDisplayString) - keyword or name
--      - data '...ValueString'
--      - 'ads'      = Microsoft Active Directory Service (LDAP)
--      - 'domino'   = Lotus Domino (LDAP)
--      - 'exchange' = Microsoft Exchange (LDAP)
--      - 'netscape' = iPlanet Netscape (LDAP)
--      - 'netware'  = Novell NetWare (LDAP)
--      - 'other'    = other (LDAP) server
--    * 'systemDirectoryLDAPObjectClass'
--      - system LDAP object class - SINGLE keyword
--      - type - (XcmFixedLocaleDisplayString) - keyword or name
--      - data '...ValueString'
--      - (eg, 'person' for X.521 'person' - section 7.7 in RFC 2256)
--      - see - 'systemDirectoryLDAPAttribute' below
--    * 'systemDirectoryLDAPAttribute'
--      - system LDAP attribute - UTF-8 string per SLPv2 (RFC 2608)
--      - type - (XcmFixedLocaleDisplayString)
--      - subtype - '...ValueInteger' ('XcmCommsLDAPAttributeType)
--      - (eg, 'commonName(3)' - ITU-T X.500 and RFC 2256 'cn')
--      - data '...ValueString'
--      - see - 'XcmCommsLDAPAttributeType' in XCMI Comms Config TC
--      - see - Section 5 'Service Attributes' in SLPv2 (RFC 2608)
--      - see - 'systemDirectoryLDAPObjectClass' above
--    * 'systemDirectoryLDAPSearchEnabled'
--      - system LDAP directory name search enable/disable
--      - type - (TruthValue)
--      - data - '...ValueInteger'
--      - 'true' = 'enabled'
--      - 'false' = 'disabled'
--    * 'systemDirectoryLocalSearchEnabled'
--      - system local directory name search enable/disable
--      - type - (TruthValue)
--      - data - '...ValueInteger'
--      - 'true' = 'enabled'
--      - 'false' = 'disabled'
--    * 'systemDirectorySearchFilter'
--      - system directory search filter - UTF-8 string per RFC 2254
--      - type - (XcmFixedLocaleDisplayString)
--      - data '...ValueString'
--      - (eg, '(sn=*) & (givenName=*)' - last and first names PRESENT)
--      - see - Section 4 'String Search Filter Definition' in LDAPv3
--      -       String Representation of Search Filters (RFC 2254)
--    * 'systemDirectorySearchSortKey'
--      - system directory search sort key (MAY be multi-valued)
--      - (used to specify a list of attributes and ordering rules)
--      - type - (XcmFixedLocaleDisplayString) - ordering rule
--      - subtype - '...ValueInteger' ('XcmCommsLDAPAttributeType)
--      - (eg, 'surname(4)' - ITU-T X.500 and RFC 2256 'sn' - last name)
--      - data '...ValueString'
--      - (eg, 'caseIgnoreOrderingMatch' - RFC 2254, section 8.2)
--      - see - 'XcmCommsLDAPAttributeType' in XCMI Comms Config TC
--      - see - Section 1.1 'Request Control' in LDAPv3 Extension for
--      -       Server Side Sorting of Search Results (RFC 2891)
--      - see - Section 8.2 'Matching Rules used in Inequality Filters'
--      -       in LDAPv3 Attribute Syntax Definitions (RFC 2252)
--
--      -   System event registry info
--      -   (protocol-independent event registry)
--      -   (see 'xcmGenTrapClientTable' in XCMI General MIB)
--    * 'systemIncludeEventInteger'
--      - system include (accept) event by object enumeration
--      - type - (Cardinal32) object enumeration (product-specific)
--      - data - '...ValueInteger'
--    * 'systemExcludeEventInteger'
--      - system exclude (reject) event by object enumeration
--      - type - (Cardinal32) object enumeration (product-specific)
--      - data - '...ValueInteger'
--    * 'systemIncludeEventOID'
--      - system include (accept) event by object identifier
--      - type - (OBJECT IDENTIFIER) event OID (from MIBs, or non-SNMP)
--      - data - '...ValueOID'
--    * 'systemExcludeEventOID'
--      - system exclude (reject) event by object identifier
--      - type - (OBJECT IDENTIFIER) event OID (from MIBs, or non-SNMP)
--      - data - '...ValueOID'
--    * 'systemIncludeEventString'
--      - system include (accept) event by object name
--      - type - (DisplayString) event name (from MIBs, or non-SNMP)
--      - data - '...ValueString'
--    * 'systemExcludeEventString'
--      - system exclude (reject) event by object name
--      - type - (DisplayString) event name (from MIBs, or non-SNMP)
--      - data - '...ValueString'
--
--      -   System guest/alien job and log full policies
--    * 'systemGuestJobPolicy'
--      - system policy for jobs with 'guest' (empty) user/account
--      - type - (XcmSecGuestJobPolicy) in XCMI Security TC
--      - data - '...ValueInteger'
--      - see - 'deviceGuestJobPolicy' in XCMI HRX TC
--      - see - 'xcmSecServiceGuestJobPolicy' in XCMI Security MIB
--    * 'systemAlienJobPolicy'
--      - system policy for jobs with 'alien' (invalid) user/account
--      - type - (XcmSecGuestJobPolicy) in XCMI Security TC
--      - data - '...ValueInteger'
--      - see - 'deviceAlienJobPolicy' in XCMI HRX TC
--      - see - 'xcmSecServiceAlienJobPolicy' in XCMI Security MIB
--    * 'systemEventLogFullPolicy'
--      - system policy for handling event log full conditions
--      - type - (XcmGenLogFullPolicy) in XCMI General TC
--      - data - '...ValueInteger'
--      - see - 'deviceEventLogFullPolicy' in XCMI HRX TC
--      - see - 'xcmSecServiceEventLogFullPolicy' in XCMI Security MIB
--      - see - DPA-1 9.1.6.8 'Notification-profile' (events)
--      - see - DPA-1 9.4 'Printer Object attributes' (generic)
--    * 'systemJobLogFullPolicy'
--      - system policy for handling job log full conditions
--      - type - (XcmGenLogFullPolicy) in XCMI General TC
--      - data - '...ValueInteger'
--      - see - 'deviceJobLogFullPolicy' in XCMI HRX TC
--      - see - 'xcmSecServiceJobLogFullPolicy' in XCMI Security MIB
--      - see - DPA-1 9.1.6.9 'Logging-profile' (jobs)
--      - see - DPA-1 9.4 'Printer Object attributes' (generic)
--    * 'systemRequestLogFullPolicy'
--      - system policy for handling request log full conditions
--      - type - (XcmGenLogFullPolicy) in XCMI General TC
--      - data - '...ValueInteger'
--      - see - 'deviceRequestLogFullPolicy' in XCMI HRX TC
--      - see - 'xcmSecServiceRequestLogFullPolicy' in XCMI Security MIB
--  REFERENCE
--      "See:   'xcmSvcMonServiceDetailUnitClass' and
--              'xcmSvcMonServiceDetailUnit' for syntax of detail."
    INTEGER  -- left brace delay
        --  System other/unknown details
        {
        other(1),
        unknown(2),

        --  System general info
        systemOther(101),
        systemUnknown(102),
        systemServiceTypeSupport(108),
        systemURI(109),
        systemOS(110),
        systemOSVersion(111),
        systemDescription(112),
        systemName(113),
        systemAddress(114),
        systemTree(115),
        systemContext(116),
        systemVolume(117),
        systemPath(118),
        systemCurrentLocale(119),
        systemProtocol(120),
        systemProtocolDetail(121),
        systemLoginName(122),
        systemLoginPassword(123),
        systemLoginDate(124),
        systemLogoutDate(125),
        systemAlias(126),
        systemLocation(127),
        systemOperatorMessage(128),
        systemProblemMessage(129),

        --  System help info (contact info)
        systemHelpName(130),
        systemHelpAddress(131),
        systemHelpDescription(132),
        systemHelpLocation(133),

        --  System protocol security info
        systemProtocolSecurity(135),
        systemAuthMethod(136),
        systemAuthSupport(137),

        --  System state info
        systemState(140),
        systemConditions(141),
        systemAvailability(142),
        systemEnabled(143),

        --  System polling info
        systemPollingStartDate(150),
        systemPollingStartTime(151),
        systemPollingLastDate(152),
        systemPollingLastTime(153),
        systemPollingInterval(154),
        systemPollingEnabled(155),

        --  System supported and ready device name info (list)
        systemPhysicalNameSupport(160),
        systemPhysicalNameReady(161),
        systemLogicalNameSupport(162),
        systemLogicalNameReady(163),

        --  System supported and ready device index info (list)
        systemPhysicalIndexSupport(164),
        systemPhysicalIndexReady(165),
        systemLogicalIndexSupport(166),
        systemLogicalIndexReady(167),

        --  System supported and ready general info (lists except masks)
        systemObjectClassSupport(170),
        systemEventSupport(171),
        systemJobValidateSupport(172),
        systemModifyDocSupport(173),
        systemTransferMethodSupport(174),
        systemLocaleSupport(175),
        systemPosixVerbsSupport(176),
        systemJobStateSupport(177),
        systemDeviceStatusSupport(179),
        systemDeviceXStatusSupport(180),
        systemTranslatorSupport(181),
        systemTranslatorReady(182),
        systemInitialValJobSupport(183),
        systemInitialValDocSupport(184),
        systemMultipleDocSupport(185),
        systemCancelDocSupport(186),
        systemForeignJobsVisible(187),
        systemJobConfirmEnabled(190),
        systemJobConfirmContent(191),
        systemJobConfirmSupport(192),
        systemJobConfirmPolicy(193),
        systemJobDefaultPDL(194),
        systemJobDefaultFeedResolution(195),
        systemJobDefaultXFeedResolution(196),
        systemJobDefaultDepthResolution(197),
        systemJobConfirmSheetColor(198),
        systemJobConfirmSheetType(199),

        --  System filename info
        systemFileSystemType(200),
        systemFilenameOther(201),
        systemFilenameUnknown(202),
        systemFilename(210),
        systemFilenameRoot(211),
        systemFilenameExtension(212),
        systemFilenameIncrement(213),
        systemFilenameWildcards(214),
        systemFilenameDefault(215),
        systemFilenameSoftLink(216),
        systemFilenameHardLink(217),
        systemFilenameConsole(218),
        systemFilenameDevice(219),
        systemFilenameDirectory(220),
        systemFilenameAccessRights(221),

        --  System job finishing and media info
        systemJobFinishingSupport(230),
        systemJobFinishingDefault(231),
        systemJobSidesSupport(232),
        systemJobSidesDefault(233),
        systemJobOrientationSupport(234),
        systemJobOrientationDefault(235),
        systemJobMediaSupport(236),
        systemJobMediaDefault(237),
        systemJobAttributeSupport(238),
        systemJobAttributeDefault(239),

        --  System lifetime usage and limits
        systemLifetimeUsage(240),
        systemLifetimeLimit(241),

        --  System lifetime errors and warnings
        systemLifetimeErrorCount(242),
        systemLifetimeErrorLimit(243),
        systemLifetimeWarningCount(244),
        systemLifetimeWarningLimit(245),

        --  System accounting usage
        systemAccountingUsage(250),

        --  System job template info
        systemJobTemplateOther(251),
        systemJobTemplateUnknown(252),
        systemJobTemplateMaxStorage(260),
        systemJobTemplateMaxCount(261),
        systemJobTemplateCurrentCount(262),
        systemJobTemplateConfirmSheet(263),
        systemJobTemplateConfirmContent(264),
        systemJobTemplateConfirmSupport(265),
        systemJobTemplateConfirmPolicy(266),
        systemJobTemplateConfirmSheetColor(267),
        systemJobTemplateConfirmSheetType(268),

        --  System job cover sheet info
        systemJobCoverSheetEnabled(271),
        systemJobCoverSheetContent(272),
        systemJobCoverSheetContentKey(273),
        systemJobCoverSheetContentOID(274),
        systemJobCoverSheetContentText(275),

        --  System job error sheet info
        systemJobErrorSheetEnabled(281),
        systemJobErrorSheetContent(282),
        systemJobErrorSheetContentKey(283),
        systemJobErrorSheetContentOID(284),
        systemJobErrorSheetContentText(285),

        --  System job show sender info
        systemJobShowSenderEnabled(291),
        systemJobShowSenderContent(292),
        systemJobShowSenderContentKey(293),
        systemJobShowSenderContentOID(294),
        systemJobShowSenderContentText(295),
        systemJobCopySenderEnabled(299),

        --  System job service channel info
        systemChannelOther(301),
        systemChannelUnknown(302),
        systemChannelDiagnostic(310),
        systemChannelFax(311),
        systemChannelFileTransfer(312),
        systemChannelImageProcess(313),
        systemChannelMail(314),
        systemChannelMultifunction(315), -- aka Distribution
        systemChannelPrint(316),
        systemChannelScan(317),
        systemChannelOCR(318),
        systemChannelCopy(319),

        --  System job service timeouts
        systemJobIncompleteTimeout(331),
        systemJobProgrammingTimeout(332),
        systemJobHoldDeleteTimeout(333),
        systemJobPauseResumeTimeout(334),

        --  System feature info
        systemActivityReportEnabled(340),
        systemAccountingEnabled(341),
        systemLoggingEnabled(342),
        systemNotificationEnabled(343),

        --  System mail info
        systemMailSubject(350),
        systemMailSignatureLine(351),
        systemMailMaxInputText(360),
        systemMailMaxInputAttach(361),
        systemMailMaxOutputText(362),
        systemMailMaxOutputAttach(363),
        systemMailConfirmRequest(364),
        systemMailConfirmReply(365),
        systemMailConfirmTimeout(366),
        systemMailFeatureReply(367),
        systemMailAddress(368),
        systemMailMaxInFragments(369),
        systemMailMaxOutFragments(370),
        systemMailMaxInAttachments(371),
        systemMailMaxOutAttachments(372),
        systemMailMaxInputSize(373),
        systemMailMaxOutputSize(374),

        --  System directory info
        systemDirectoryMaxSearchResult(380),
        systemDirectorySearchTimeout(381),
        systemDirectoryLDAPServerType(382),
        systemDirectoryLDAPObjectClass(383),
        systemDirectoryLDAPAttribute(384),
        systemDirectoryLDAPSearchEnabled(385),
        systemDirectoryLocalSearchEnabled(386),
        systemDirectorySearchFilter(387),
        systemDirectorySearchSortKey(388),

        --  System event registry info
        systemIncludeEventInteger(400),
        systemExcludeEventInteger(401),
        systemIncludeEventOID(402),
        systemExcludeEventOID(403),
        systemIncludeEventString(404),
        systemExcludeEventString(405),

        --  System guest/alien job and log full policies
        systemGuestJobPolicy(500),
        systemAlienJobPolicy(501),
        systemEventLogFullPolicy(502),
        systemJobLogFullPolicy(503),
        systemRequestLogFullPolicy(504)
    }

--.ts 'XcmSvcMonServiceType'
XcmSvcMonServiceType ::= 
--  STATUS      current
--  DESCRIPTION
--      "The explicit type of this system and/or end-user service."
--  REFERENCE
--      "See:   'xcmJobServiceType...' in XCMI Job Monitoring MIB
--              'serviceType' in 'XcmCommsDirAttributeType' in
--              XCMI Comms Config TC."
    INTEGER  -- left brace delay
        {
        other(1),
        unknown(2),
        --  Job Services defined in 'xcmJobService...' in
        --  XCMI Job Monitoring TC
        jobServiceScanToFile(101),
        jobServiceScanToPrint(102),
        jobServiceScanToFax(103),
        jobServiceScanToMailList(104),
        jobServiceFaxToFile(105),
        jobServiceFaxToPrint(106),
        jobServiceFaxToMailList(107),
        jobServicePrint(108),
        jobServiceFileToFax(109),
        jobServiceFileToMailList(110),
        jobServiceCopy(111),
        jobServiceFileToFile(112),
        jobServiceMultifunction(113),    -- aka Distribution
        --  Admin Services defined in 'xcmHrAdmin...' in
        --  XCMI Ext to Host Resources TC
        adminObjectService(201),
        adminServerService(202),
        adminDeviceService(203),
        adminJobService(204),
        adminDocService(205),
        adminSecurityService(206),
        adminCommsService(207),
        --  System Services defined in 'systemChannel...' in
        --  'XcmSvcMonServiceDetailType' in XCMI Service Monitoring TC
        systemServiceDiagnostic(300),
        systemServiceFax(301),
        systemServiceFileTransfer(302),
        systemServiceImageProcess(303),
        systemServiceMail(304),
        systemServiceMultifunction(305), -- aka Distribution
        systemServicePrint(306),
        systemServiceScan(307),
        systemServiceOCR(308),
        systemServiceCopy(309),
        --  Local System Services defined in
        --  'XcmSvcMonServiceDetailClass' in XCMI Service Monitoring TC
        localAccountingService(400),
        localApplicationService(401),
        localDocumentService(402),
        localFileService(403),
        localLoggingService(404),
        localNameService(405),
        localNotificationService(406),
        localSecurityService(407),
        --  Remote System Services defined in
        --  'XcmSvcMonServiceDetailClass' in XCMI Service Monitoring TC
        remoteAccountingService(500),
        remoteApplicationService(501),
        remoteDocumentService(502),
        remoteFileService(503),
        remoteLoggingService(504),
        remoteNameService(505),
        remoteNotificationService(506),
        remoteSecurityService(507)
    }

--
--          The Service Monitoring TC Dummy Group (DO NOT USE)
--
--          DO NOT USE - Present to suppress compiler warnings ONLY!
--
--          Note:  The following objects have 'odd' use of case in their
--          names (ie, 'xCm...'), in order to make obvious their related
--          textual conventions

xCmSvcMonDummy   OBJECT IDENTIFIER ::= { xcmSvcMonTC 999 }

xCmSvcMonGroupSupport OBJECT-TYPE
    SYNTAX      XcmSvcMonGroupSupport
    ACCESS      read-only
    STATUS      mandatory
    DESCRIPTION "Dummy - DO NOT USE"
    ::= { xCmSvcMonDummy 1 }

xCmSvcMonServiceMgmtOperation OBJECT-TYPE
    SYNTAX      XcmSvcMonServiceMgmtOperation
    ACCESS      read-only
    STATUS      mandatory
    DESCRIPTION "Dummy - DO NOT USE"
    ::= { xCmSvcMonDummy 2 }

xCmSvcMonServiceMgmtData OBJECT-TYPE
    SYNTAX      XcmSvcMonServiceMgmtData
    ACCESS      read-only
    STATUS      mandatory
    DESCRIPTION "Dummy - DO NOT USE"
    ::= { xCmSvcMonDummy 3 }

xCmSvcMonServiceDetailClass OBJECT-TYPE
    SYNTAX      XcmSvcMonServiceDetailClass
    ACCESS      read-only
    STATUS      mandatory
    DESCRIPTION "Dummy - DO NOT USE"
    ::= { xCmSvcMonDummy 4 }

xCmSvcMonServiceDetailType OBJECT-TYPE
    SYNTAX      XcmSvcMonServiceDetailType
    ACCESS      read-only
    STATUS      mandatory
    DESCRIPTION "Dummy - DO NOT USE"
    ::= { xCmSvcMonDummy 5 }

xCmSvcMonServiceType OBJECT-TYPE
    SYNTAX      XcmSvcMonServiceType
    ACCESS      read-only
    STATUS      mandatory
    DESCRIPTION "Dummy - DO NOT USE"
    ::= { xCmSvcMonDummy 6 }

xCmSvcMonJobConfirmSupport OBJECT-TYPE
    SYNTAX      XcmSvcMonJobConfirmSupport
    ACCESS      read-only
    STATUS      mandatory
    DESCRIPTION "Dummy - DO NOT USE"
    ::= { xCmSvcMonDummy 7 }

END
