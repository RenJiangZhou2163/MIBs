XEROX-PRODUCT-ID-TC DEFINITIONS ::= BEGIN

-- Module:  XCMI Product Identifier Textual Conventions MIB
--
--
-- File:    93pidtc.mib
-- Date:    January 23, 2004           /* VersionUpdate */
-- Version: 5.301.int                /* VersionUpdate */

--
--

IMPORTS
    MODULE-IDENTITY, OBJECT-IDENTITY
            FROM SNMPv2-SMI             -- IETF RFC 1442/1902/2578
    xeroxCommonMIB
            FROM XEROX-COMMON-MIB;

xcmPidTC MODULE-IDENTITY
    LAST-UPDATED "0401230000Z"   -- January 23, 2003   /* VersionUpdate 
    ORGANIZATION "Xerox Corporation -
        Xerox Common Management Interface (XCMI) Working Group"
    CONTACT-INFO "
                      XCMI Editors
        E-Mail:       coherence@crt.xerox.com

        --
        --
        "

-- /* VersionUpdate */
    DESCRIPTION "
        XCMI Product ID Module,
        Version 5.301.int

        Copyright (C) 1997-2003 Xerox Corporation. All Rights Reserved."
    ::= { xeroxCommonMIB 62 }
        -- ::= {1.3.6.1.4.1.253.8.62}


xcmPidProductIdentifiers OBJECT-IDENTITY
    STATUS      current
    DESCRIPTION
        "The root of all identifiers defined in this module."
    ::= { xcmPidTC 1 }
        -- ::= {1.3.6.1.4.1.253.8.62.1}


----------------------------------------------------------------
-- Document Centre Systems
----------------------------------------------------------------

xcmPidDocuCentreSystems OBJECT-IDENTITY
    STATUS      current
    DESCRIPTION
        "Document Centre Systems product line identifier
                 (not a complete product identifier)."
    ::= { xcmPidProductIdentifiers 1 }
        -- ::= {1.3.6.1.4.1.253.8.62.1.1}

-- Document Centre/System 20

xcmPidDCS20 OBJECT-IDENTITY
    STATUS      current
    DESCRIPTION
        "Document Centre/System 20 product type identifier
                 (not a complete product identifier)."
    ::= { xcmPidDocuCentreSystems 1 }
        -- ::= {1.3.6.1.4.1.253.8.62.1.1.1}

xcmPidDCS20M1 OBJECT-IDENTITY
    STATUS      current
    DESCRIPTION
        "Document Centre/System 20 launch configuration model
                 identifier (not a complete product identifier)."
    ::= { xcmPidDCS20 1 }
        -- ::= {1.3.6.1.4.1.253.8.62.1.1.1.1}
            -- => SAP PID string = "111"

xcmPidDCS20M1V1 OBJECT-IDENTITY
    STATUS      current
    DESCRIPTION
        "Document Centre/System 20 launch configuration version,
                 and complete product identifier."
    ::= { xcmPidDCS20M1 1 }
        -- ::= {1.3.6.1.4.1.253.8.62.1.1.1.1.1}


-- Document Centre/System 35

xcmPidDCS35 OBJECT-IDENTITY
    STATUS      current
    DESCRIPTION
        "Document Centre/System 35 product type identifier
                 (not a complete product identifier)."
    ::= { xcmPidDocuCentreSystems 2 }
        -- ::= {1.3.6.1.4.1.253.8.62.1.1.2}

xcmPidDCS35M1 OBJECT-IDENTITY
    STATUS      current
    DESCRIPTION
        "Document Centre/System 35 launch configuration model
                 identifier (not a complete product identifier)."
    ::= { xcmPidDCS35 1 }
        -- ::= {1.3.6.1.4.1.253.8.62.1.1.2.1}
            -- => SAP PID string = "121"

xcmPidDCS35M1V1 OBJECT-IDENTITY
    STATUS      current
    DESCRIPTION
        "Document Centre/System 35 launch configuration version,
                 and complete product identifier."
    ::= { xcmPidDCS35M1 1 }
        -- ::= {1.3.6.1.4.1.253.8.62.1.1.2.1.1}

--
--

-- Document Centre 220  (20 ppm)

xcmPidDC220 OBJECT-IDENTITY
    STATUS      current
    DESCRIPTION
        "Document Centre 220 product type identifier
                 (not a complete product identifier)."
    ::= { xcmPidDocuCentreSystems 8 }
        -- ::= {1.3.6.1.4.1.253.8.62.1.1.8}

xcmPidDC220ST OBJECT-IDENTITY
    STATUS      current
    DESCRIPTION
        "Document Centre 220ST multi-func. system
                 model identifier (not a complete product identifier)."
    ::= { xcmPidDC220 1 }
        -- ::= {1.3.6.1.4.1.253.8.62.1.1.8.1}
            -- => SAP PID string = "181"

xcmPidDC220STV3 OBJECT-IDENTITY
    STATUS      current
    DESCRIPTION
        "Document Centre 220ST multi-func. system
                 second post-launch configuration version, and
                 complete product identifier."
    ::= { xcmPidDC220ST 3 }
        -- ::= {1.3.6.1.4.1.253.8.62.1.1.8.1.3}

xcmPidDC220STV4 OBJECT-IDENTITY
    STATUS      current
    DESCRIPTION
        "Document Centre 220ST multi-func. system
                 third post-launch configuration version, and
                 complete product identifier."
    ::= { xcmPidDC220ST 4 }
        -- ::= {1.3.6.1.4.1.253.8.62.1.1.8.1.4}


-- Document Centre 230  (30 ppm)

xcmPidDC230 OBJECT-IDENTITY
    STATUS      current
    DESCRIPTION
        "Document Centre 230 product type identifier
                 (not a complete product identifier)."
    ::= { xcmPidDocuCentreSystems 3 }
        -- ::= {1.3.6.1.4.1.253.8.62.1.1.3}

xcmPidDC230ST OBJECT-IDENTITY
    STATUS      current
    DESCRIPTION
        "Document Centre 230ST multi-func. system
                 model identifier (not a complete product identifier)."
    ::= { xcmPidDC230 1 }
        -- ::= {1.3.6.1.4.1.253.8.62.1.1.3.1}
            -- => SAP PID string = "131"

xcmPidDC230STV1 OBJECT-IDENTITY
    STATUS      current
    DESCRIPTION
        "Document Centre 230ST multi-func. system
                 launch configuration version, and
                 complete product identifier."
    ::= { xcmPidDC230ST 1 }
        -- ::= {1.3.6.1.4.1.253.8.62.1.1.3.1.1}

xcmPidDC230STV2 OBJECT-IDENTITY
    STATUS      current
    DESCRIPTION
        "Document Centre 230ST multi-func. system
                 first post-launch configuration version, and
                 complete product identifier."
    ::= { xcmPidDC230ST 2 }
        -- ::= {1.3.6.1.4.1.253.8.62.1.1.3.1.2}

xcmPidDC230STV3 OBJECT-IDENTITY
    STATUS      current
    DESCRIPTION
        "Document Centre 230ST multi-func. system
                 second post-launch configuration version, and
                 complete product identifier."
    ::= { xcmPidDC230ST 3 }
        -- ::= {1.3.6.1.4.1.253.8.62.1.1.3.1.3}

xcmPidDC230STV4 OBJECT-IDENTITY
    STATUS      current
    DESCRIPTION
        "Document Centre 230ST multi-func. system
                 third post-launch configuration version, and
                 complete product identifier."
    ::= { xcmPidDC230ST 4 }
        -- ::= {1.3.6.1.4.1.253.8.62.1.1.3.1.4}

xcmPidDC230STV5 OBJECT-IDENTITY
    STATUS      current
    DESCRIPTION
        "Document Centre 230ST multi-func. system
                 fourth post-launch configuration version, and
                 complete product identifier."
    ::= { xcmPidDC230ST 5 }
        -- ::= {1.3.6.1.4.1.253.8.62.1.1.3.1.5}


xcmPidDC230LP OBJECT-IDENTITY
    STATUS      current
    DESCRIPTION
        "Document Centre 230LP laser printer
                 model identifier (not a complete product identifier)."
    ::= { xcmPidDC230 2 }
        -- ::= {1.3.6.1.4.1.253.8.62.1.1.3.2}
            -- => SAP PID string = "132"

xcmPidDC230LPV1 OBJECT-IDENTITY
    STATUS      current
    DESCRIPTION
        "Document Centre 230LP laser printer
                 launch configuration version, and
                 complete product identifier."
    ::= { xcmPidDC230LP 1 }
        -- ::= {1.3.6.1.4.1.253.8.62.1.1.3.2.1}

xcmPidDC230LPV2 OBJECT-IDENTITY
    STATUS      current
    DESCRIPTION
        "Document Centre 230LP laser printer
                 first post-launch configuration version, and
                 complete product identifier."
    ::= { xcmPidDC230LP 2 }
        -- ::= {1.3.6.1.4.1.253.8.62.1.1.3.2.2}

xcmPidDC230LPV3 OBJECT-IDENTITY
    STATUS      current
    DESCRIPTION
        "Document Centre 230LP laser printer
                 second post-launch configuration version, and
                 complete product identifier."
    ::= { xcmPidDC230LP 3 }
        -- ::= {1.3.6.1.4.1.253.8.62.1.1.3.2.3}

xcmPidDC230LPV4 OBJECT-IDENTITY
    STATUS      current
    DESCRIPTION
        "Document Centre 230LP laser printer
                 third post-launch configuration version, and
                 complete product identifier."
    ::= { xcmPidDC230LP 4 }
        -- ::= {1.3.6.1.4.1.253.8.62.1.1.3.2.4}

xcmPidDC230LPV5 OBJECT-IDENTITY
    STATUS      current
    DESCRIPTION
        "Document Centre 230LP laser printer
                 fourth post-launch configuration version, and
                 complete product identifier."
    ::= { xcmPidDC230LP 5 }
        -- ::= {1.3.6.1.4.1.253.8.62.1.1.3.2.5}


-- Document Centre 230 Intel upgrade (30 ppm)

xcmPidDC230i OBJECT-IDENTITY
    STATUS      current
    DESCRIPTION
        "Document Centre 230i multi-func. system
                 model identifier (not a complete product identifier)."
    ::= { xcmPidDocuCentreSystems 22 }
        -- ::= {1.3.6.1.4.1.253.8.62.1.1.22}

xcmPidDC230iST OBJECT-IDENTITY
    STATUS      current
    DESCRIPTION
        "Document Centre 230iST multi-func. system
                 model identifier (not a complete product identifier)."
    ::= { xcmPidDC230i 1 }
        -- ::= {1.3.6.1.4.1.253.8.62.1.1.22.1}
            -- => SAP PID string = "1F1"

xcmPidDC230iSTV1 OBJECT-IDENTITY
    STATUS      current
    DESCRIPTION
        "Document Centre 230iST multi-func. system
                 launch configuration version, and
                 complete product identifier."
    ::= { xcmPidDC230iST 1 }
        -- ::= {1.3.6.1.4.1.253.8.62.1.1.22.1.1}

xcmPidDC230iSTV2 OBJECT-IDENTITY
    STATUS      current
    DESCRIPTION
        "Document Centre 230iST multi-func. system
                 first post-launch configuration version, and
                 complete product identifier."
    ::= { xcmPidDC230iST 2 }
        -- ::= {1.3.6.1.4.1.253.8.62.1.1.22.1.2}

--
--


-- Document Centre 240  (40 ppm)

xcmPidDC240 OBJECT-IDENTITY
    STATUS      current
    DESCRIPTION
        "Document Centre 240 product type identifier
                 (not a complete product identifier)."
    ::= { xcmPidDocuCentreSystems 5 }
        -- ::= {1.3.6.1.4.1.253.8.62.1.1.5}

xcmPidDC240ST OBJECT-IDENTITY
    STATUS      current
    DESCRIPTION
        "Document Centre 240ST multi-func. system
                 model identifier (not a complete product identifier)."
    ::= { xcmPidDC240 1 }
        -- ::= {1.3.6.1.4.1.253.8.62.1.1.5.1}
            -- => SAP PID string = "151"

xcmPidDC240STV1 OBJECT-IDENTITY
    STATUS      current
    DESCRIPTION
        "Document Centre 240ST multi-func. system launch configuration
                 version, and complete product identifier."
    ::= { xcmPidDC240ST 1 }
        -- ::= {1.3.6.1.4.1.253.8.62.1.1.5.1.1}

xcmPidDC240STV2 OBJECT-IDENTITY
    STATUS      current
    DESCRIPTION
        "Document Centre 240ST multi-func. system
                 first post-launch configuration version, and
                 complete product identifier."
    ::= { xcmPidDC240ST 2 }
        -- ::= {1.3.6.1.4.1.253.8.62.1.1.5.1.2}

xcmPidDC240STV3 OBJECT-IDENTITY
    STATUS      current
    DESCRIPTION
        "Document Centre 240ST multi-func. system
                 second post-launch configuration version, and
                 complete product identifier."
    ::= { xcmPidDC240ST 3 }
        -- ::= {1.3.6.1.4.1.253.8.62.1.1.5.1.3}


-- Document Centre 255  (55 ppm)

xcmPidDC255 OBJECT-IDENTITY
    STATUS      current
    DESCRIPTION
        "Document Centre 255 product type identifier
                 (not a complete product identifier)."
    ::= { xcmPidDocuCentreSystems 7 }
        -- ::= {1.3.6.1.4.1.253.8.62.1.1.7}

xcmPidDC255ST OBJECT-IDENTITY
    STATUS      current
    DESCRIPTION
        "Document Centre 255ST multi-func. system
                 model identifier (not a complete product identifier)."
    ::= { xcmPidDC255 1 }
        -- ::= {1.3.6.1.4.1.253.8.62.1.1.7.1}
            -- => SAP PID string = "171"

xcmPidDC255STV1 OBJECT-IDENTITY
    STATUS      current
    DESCRIPTION
        "Document Centre 255ST multi-func. system launch configuration
                 version, and complete product identifier."
    ::= { xcmPidDC255ST 1 }
        -- ::= {1.3.6.1.4.1.253.8.62.1.1.7.1.1}

xcmPidDC255STV2 OBJECT-IDENTITY
    STATUS      current
    DESCRIPTION
        "Document Centre 255ST multi-func. system
                 first post-launch configuration version, and
                 complete product identifier."
    ::= { xcmPidDC255ST 2 }
        -- ::= {1.3.6.1.4.1.253.8.62.1.1.7.1.2}

xcmPidDC255STV3 OBJECT-IDENTITY
    STATUS      current
    DESCRIPTION
        "Document Centre 255ST multi-func. system
                 second post-launch configuration version, and
                 complete product identifier."
    ::= { xcmPidDC255ST 3 }
        -- ::= {1.3.6.1.4.1.253.8.62.1.1.7.1.3}


xcmPidDC255LP OBJECT-IDENTITY
    STATUS      current
    DESCRIPTION
        "Document Centre 255LP laser printer
                 model identifier (not a complete product identifier)."
    ::= { xcmPidDC255 2 }
        -- ::= {1.3.6.1.4.1.253.8.62.1.1.7.2}
            -- => SAP PID string = "172"

xcmPidDC255LPV1 OBJECT-IDENTITY
    STATUS      current
    DESCRIPTION
        "Document Centre 255LP laser printer launch configuration
                 version, and complete product identifier."
    ::= { xcmPidDC255LP 1 }
        -- ::= {1.3.6.1.4.1.253.8.62.1.1.7.2.1}

xcmPidDC255LPV2 OBJECT-IDENTITY
    STATUS      current
    DESCRIPTION
        "Document Centre 255LP laser printer
                 first post-launch configuration version, and
                 complete product identifier."
    ::= { xcmPidDC255LP 2 }
        -- ::= {1.3.6.1.4.1.253.8.62.1.1.7.2.2}

xcmPidDC255LPV3 OBJECT-IDENTITY
    STATUS      current
    DESCRIPTION
        "Document Centre 255LP laser printer
                 second post-launch configuration version, and
                 complete product identifier."
    ::= { xcmPidDC255LP 3 }
        -- ::= {1.3.6.1.4.1.253.8.62.1.1.7.2.3}


-- Document Centre 265  (65 ppm)

xcmPidDC265 OBJECT-IDENTITY
    STATUS      current
    DESCRIPTION
        "Document Centre 265 product type identifier
                 (not a complete product identifier)."
    ::= { xcmPidDocuCentreSystems 4 }
        -- ::= {1.3.6.1.4.1.253.8.62.1.1.4}

xcmPidDC265ST OBJECT-IDENTITY
    STATUS      current
    DESCRIPTION
        "Document Centre 265ST multi-func. system
                 model identifier (not a complete product identifier)."
    ::= { xcmPidDC265 1 }
        -- ::= {1.3.6.1.4.1.253.8.62.1.1.4.1}
            -- => SAP PID string = "141"

xcmPidDC265STV1 OBJECT-IDENTITY
    STATUS      current
    DESCRIPTION
        "Document Centre 265ST multi-func. system launch configuration
                 version, and complete product identifier."
    ::= { xcmPidDC265ST 1 }
        -- ::= {1.3.6.1.4.1.253.8.62.1.1.4.1.1}

xcmPidDC265STV2 OBJECT-IDENTITY
    STATUS      current
    DESCRIPTION
        "Document Centre 265ST multi-func. system
                 first post-launch configuration version, and
                 complete product identifier."
    ::= { xcmPidDC265ST 2 }
        -- ::= {1.3.6.1.4.1.253.8.62.1.1.4.1.2}

xcmPidDC265STV3 OBJECT-IDENTITY
    STATUS      current
    DESCRIPTION
        "Document Centre 265ST multi-func. system
                 second post-launch configuration version, and
                 complete product identifier."
    ::= { xcmPidDC265ST 3 }
        -- ::= {1.3.6.1.4.1.253.8.62.1.1.4.1.3}


xcmPidDC265LP OBJECT-IDENTITY
    STATUS      current
    DESCRIPTION
        "Document Centre 265LP laser printer
                 model identifier (not a complete product identifier)."
    ::= { xcmPidDC265 2 }
        -- ::= {1.3.6.1.4.1.253.8.62.1.1.4.2}
            -- => SAP PID string = "142"

xcmPidDC265LPV1 OBJECT-IDENTITY
    STATUS      current
    DESCRIPTION
        "Document Centre 265LP laser printer launch configuration
                 version, and complete product identifier."
    ::= { xcmPidDC265LP 1 }
        -- ::= {1.3.6.1.4.1.253.8.62.1.1.4.2.1}

xcmPidDC265LPV2 OBJECT-IDENTITY
    STATUS      current
    DESCRIPTION
        "Document Centre 265LP laser printer
                 first post-launch configuration version, and
                 complete product identifier."
    ::= { xcmPidDC265LP 2 }
        -- ::= {1.3.6.1.4.1.253.8.62.1.1.4.2.2}

xcmPidDC265LPV3 OBJECT-IDENTITY
    STATUS      current
    DESCRIPTION
        "Document Centre 265LP laser printer
                 second post-launch configuration version, and
                 complete product identifier."
    ::= { xcmPidDC265LP 3 }
        -- ::= {1.3.6.1.4.1.253.8.62.1.1.4.2.3}

--
--

-- Document Centre 332  (32 ppm)

xcmPidDC332 OBJECT-IDENTITY
    STATUS      current
    DESCRIPTION
        "Document Centre 332 product type identifier
                 (not a complete product identifier)."
    ::= { xcmPidDocuCentreSystems 9 }
        -- ::= {1.3.6.1.4.1.253.8.62.1.1.9}

xcmPidDC332ST OBJECT-IDENTITY
    STATUS      current
    DESCRIPTION
        "Document Centre 332ST multi-func. system
                 model identifier (not a complete product identifier)."
    ::= { xcmPidDC332 1 }
        -- ::= {1.3.6.1.4.1.253.8.62.1.1.9.1}
            -- => SAP PID string = "191"

xcmPidDC332STV1 OBJECT-IDENTITY
    STATUS      current
    DESCRIPTION
        "Document Centre 332ST multi-func. system
                 launch configuration version, and
                 complete product identifier."
    ::= { xcmPidDC332ST 1 }
        -- ::= {1.3.6.1.4.1.253.8.62.1.1.9.1.1}

xcmPidDC332STV2 OBJECT-IDENTITY
    STATUS      current
    DESCRIPTION
        "Document Centre 332ST multi-func. system
                 first post-launch configuration version, and
                 complete product identifier."
    ::= { xcmPidDC332ST 2 }
        -- ::= {1.3.6.1.4.1.253.8.62.1.1.9.1.2}

--
--

-- Document Centre 340  (40 ppm)

xcmPidDC340 OBJECT-IDENTITY
    STATUS      current
    DESCRIPTION
        "Document Centre 340 product type identifier
                 (not a complete product identifier)."
    ::= { xcmPidDocuCentreSystems 6 }
        -- ::= {1.3.6.1.4.1.253.8.62.1.1.6}

xcmPidDC340ST OBJECT-IDENTITY
    STATUS      current
    DESCRIPTION
        "Document Centre 340ST multi-func. system
                 model identifier (not a complete product identifier)."
    ::= { xcmPidDC340 1 }
        -- ::= {1.3.6.1.4.1.253.8.62.1.1.6.1}
            -- => SAP PID string = "161"

xcmPidDC340STV1 OBJECT-IDENTITY
    STATUS      current
    DESCRIPTION
        "Document Centre 340ST multi-func. system
                 launch configuration version, and
                 complete product identifier."
    ::= { xcmPidDC340ST 1 }
        -- ::= {1.3.6.1.4.1.253.8.62.1.1.6.1.1}

xcmPidDC340STV2 OBJECT-IDENTITY
    STATUS      current
    DESCRIPTION
        "Document Centre 340ST multi-func. system
                 first post-launch configuration version, and
                 complete product identifier."
    ::= { xcmPidDC340ST 2 }
        -- ::= {1.3.6.1.4.1.253.8.62.1.1.6.1.2}

--
--

-- Document Centre 420  (20 ppm)

xcmPidDC420 OBJECT-IDENTITY
    STATUS      current
    DESCRIPTION
        "Document Centre 420 product type identifier
                 (not a complete product identifier)."
    ::= { xcmPidDocuCentreSystems 19 }
        -- ::= {1.3.6.1.4.1.253.8.62.1.1.19}

xcmPidDC420ST OBJECT-IDENTITY
    STATUS      current
    DESCRIPTION
        "Document Centre 420ST multi-func. system
                 model identifier (not a complete product identifier)."
    ::= { xcmPidDC420 1 }
        -- ::= {1.3.6.1.4.1.253.8.62.1.1.19.1}
            -- => SAP PID string = "1C1"

xcmPidDC420STV1 OBJECT-IDENTITY
    STATUS      current
    DESCRIPTION
        "Document Centre 420ST multi-func. system
                 launch configuration version, and
                 complete product identifier."
    ::= { xcmPidDC420ST 1 }
        -- ::= {1.3.6.1.4.1.253.8.62.1.1.19.1.1}

xcmPidDC420STV2 OBJECT-IDENTITY
    STATUS      current
    DESCRIPTION
        "Document Centre 420ST multi-func. system
                 first post-launch configuration version, and
                 complete product identifier."
    ::= { xcmPidDC420ST 2 }
        -- ::= {1.3.6.1.4.1.253.8.62.1.1.19.1.2}

--
-- Document Centre 432  (32 ppm)

xcmPidDC432 OBJECT-IDENTITY
    STATUS      current
    DESCRIPTION
        "Document Centre 432 product type identifier
                 (not a complete product identifier)."
    ::= { xcmPidDocuCentreSystems 20 }
        -- ::= {1.3.6.1.4.1.253.8.62.1.1.20}

xcmPidDC432ST OBJECT-IDENTITY
    STATUS      current
    DESCRIPTION
        "Document Centre 432ST multi-func. system
                 model identifier (not a complete product identifier)."
    ::= { xcmPidDC432 1 }
        -- ::= {1.3.6.1.4.1.253.8.62.1.1.20.1}
            -- => SAP PID string = "1D1"

xcmPidDC432STV1 OBJECT-IDENTITY
    STATUS      current
    DESCRIPTION
        "Document Centre 432ST multi-func. system
                 launch configuration version, and
                 complete product identifier."
    ::= { xcmPidDC432ST 1 }
        -- ::= {1.3.6.1.4.1.253.8.62.1.1.20.1.1}

xcmPidDC432STV2 OBJECT-IDENTITY
    STATUS      current
    DESCRIPTION
        "Document Centre 432ST multi-func. system
                 first post-launch configuration version, and
                 complete product identifier."
    ::= { xcmPidDC432ST 2 }
        -- ::= {1.3.6.1.4.1.253.8.62.1.1.20.1.2}

xcmPidDC432STV3 OBJECT-IDENTITY
    STATUS      current
    DESCRIPTION
        "Document Centre 432ST multi-func. system
                 second post-launch configuration version, and
                 complete product identifier."
    ::= { xcmPidDC432ST 3 }
        -- ::= {1.3.6.1.4.1.253.8.62.1.1.20.1.3}

xcmPidDC432STV4 OBJECT-IDENTITY
    STATUS      current
    DESCRIPTION
        "Document Centre 432ST multi-func. system
                 third post-launch configuration version, and
                 complete product identifier."
    ::= { xcmPidDC432ST 4 }
        -- ::= {1.3.6.1.4.1.253.8.62.1.1.20.1.4}

xcmPidDC432STV5 OBJECT-IDENTITY
    STATUS      current
    DESCRIPTION
        "Document Centre 432ST multi-func. system
                 fourth post-launch configuration version, and
                 complete product identifier."
    ::= { xcmPidDC432ST 5 }
        -- ::= {1.3.6.1.4.1.253.8.62.1.1.20.1.5}

--
--
--
--


-- Document Centre 440  (40 ppm)

xcmPidDC440 OBJECT-IDENTITY
    STATUS      current
    DESCRIPTION
        "Document Centre 440 product type identifier
                 (not a complete product identifier)."
    ::= { xcmPidDocuCentreSystems 21 }
        -- ::= {1.3.6.1.4.1.253.8.62.1.1.21}

xcmPidDC440ST OBJECT-IDENTITY
    STATUS      current
    DESCRIPTION
        "Document Centre 440ST multi-func. system
                 model identifier (not a complete product identifier)."
    ::= { xcmPidDC440 1 }
        -- ::= {1.3.6.1.4.1.253.8.62.1.1.21.1}
            -- => SAP PID string = "1E1"


xcmPidDC440STV1 OBJECT-IDENTITY
    STATUS      current
    DESCRIPTION
        "Document Centre 440ST multi-func. system
                 launch configuration version, and
                 complete product identifier."
    ::= { xcmPidDC440ST 1 }
        -- ::= {1.3.6.1.4.1.253.8.62.1.1.21.1.1}

xcmPidDC440STV2 OBJECT-IDENTITY
    STATUS      current
    DESCRIPTION
        "Document Centre 440ST multi-func. system
                 first post-launch configuration version, and
                 complete product identifier."
    ::= { xcmPidDC440ST 2 }
        -- ::= {1.3.6.1.4.1.253.8.62.1.1.21.1.2}

xcmPidDC440STV3 OBJECT-IDENTITY
    STATUS      current
    DESCRIPTION
        "Document Centre 440ST multi-func. system
                 second post-launch configuration version, and
                 complete product identifier."
    ::= { xcmPidDC440ST 3 }
        -- ::= {1.3.6.1.4.1.253.8.62.1.1.21.1.3}

--
--


-- Document Centre 4XX  (XX = 60, 70)

xcmPidDC4XX OBJECT-IDENTITY
    STATUS      current
    DESCRIPTION
        "Document Centre 4XX product type identifier
                 (not a complete product identifier)."
    ::= { xcmPidDocuCentreSystems 17 }
        -- ::= {1.3.6.1.4.1.253.8.62.1.1.17}

xcmPidDC460 OBJECT-IDENTITY
    STATUS      current
    DESCRIPTION
        "Document Centre 460 multi-functional system
                 model identifier (not a complete product identifier)."
    ::= { xcmPidDC4XX 2 }
        -- ::= {1.3.6.1.4.1.253.8.62.1.1.17.2}
            -- => SAP PID string = "1A2"

xcmPidDC460V1 OBJECT-IDENTITY
    STATUS      current
    DESCRIPTION
        "Document Centre 460 multi-functional system launch
                configuration version, and complete product identifier."
    ::= { xcmPidDC460 1 }
        -- ::= {1.3.6.1.4.1.253.8.62.1.1.17.2.1}

--
--

xcmPidDC470 OBJECT-IDENTITY
    STATUS      current
    DESCRIPTION
        "Document Centre 470 multi-functional system
                 model identifier (not a complete product identifier)."
    ::= { xcmPidDC4XX 4 }
        -- ::= {1.3.6.1.4.1.253.8.62.1.1.17.4}
            -- => SAP PID string = "1A4"

xcmPidDC470V1 OBJECT-IDENTITY
    STATUS      current
    DESCRIPTION
        "Document Centre 470 multi-functional system launch
                configuration version, and complete product identifier."
    ::= { xcmPidDC470 1 }
        -- ::= {1.3.6.1.4.1.253.8.62.1.1.17.4.1}

--
--

xcmPidDC4YY OBJECT-IDENTITY
    STATUS      current
    DESCRIPTION
        "Document Centre 4YY product type identifier
                 (not a complete product identifier)."
    ::= { xcmPidDocuCentreSystems 23 }
        -- ::= {1.3.6.1.4.1.253.8.62.1.1.23}

xcmPidDC480 OBJECT-IDENTITY
    STATUS      current
    DESCRIPTION
        "Document Centre 480 multi-functional system
                 model identifier (not a complete product identifier)."
    ::= { xcmPidDC4YY 1 }
        -- ::= {1.3.6.1.4.1.253.8.62.1.1.23.1}
            -- => SAP PID string = "1G1"

xcmPidDC480V1 OBJECT-IDENTITY
    STATUS      current
    DESCRIPTION
        "Document Centre 480 multi-functional system, UNUSED
                version, and complete product identifier."
    ::= { xcmPidDC480 1 }
        -- ::= {1.3.6.1.4.1.253.8.62.1.1.23.1.1}

--
--

-- Document Centre 425

xcmPidDC425 OBJECT-IDENTITY
    STATUS      current
    DESCRIPTION
        "Document Centre 425 product type identifier
                 (not a complete product identifier)."
    ::= { xcmPidDocuCentreSystems 24 }
        -- ::= {1.3.6.1.4.1.253.8.62.1.1.24}

xcmPidDC425ST OBJECT-IDENTITY
    STATUS      current
    DESCRIPTION
        "Document Centre 425ST multi-functional system
                 model identifier (not a complete product identifier)."
    ::= { xcmPidDC425 1 }
        -- ::= {1.3.6.1.4.1.253.8.62.1.1.24.1}
            -- => SAP PID string = "1H1"

xcmPidDC425STV1 OBJECT-IDENTITY
    STATUS      current
    DESCRIPTION
        "Document Centre 425ST multi-functional system launch
                configuration version, and complete product identifier."
    ::= { xcmPidDC425ST 1 }
        -- ::= {1.3.6.1.4.1.253.8.62.1.1.24.1.1}

--
--

-- Document Centre 555, 55 ppm

xcmPidDC555 OBJECT-IDENTITY
    STATUS      current
    DESCRIPTION
        "Document Centre 555 product type identifier
                 (not a complete product identifier)."
    ::= { xcmPidDocuCentreSystems 27 }
        -- ::= {1.3.6.1.4.1.253.8.62.1.1.27}

xcmPidDC555ST OBJECT-IDENTITY
    STATUS      current
    DESCRIPTION
        "Document Centre 555ST multi-functional system
                 model identifier (not a complete product identifier)."
    ::= { xcmPidDC555 1 }
        -- ::= {1.3.6.1.4.1.253.8.62.1.1.27.1}
            -- => SAP PID string = "1K1"

xcmPidDC555STV1 OBJECT-IDENTITY
    STATUS      current
    DESCRIPTION
        "Document Centre 555ST multi-functional system ECE pre-launch
                configuration version, and complete product identifier."
    ::= { xcmPidDC555ST 1 }
        -- ::= {1.3.6.1.4.1.253.8.62.1.1.27.1.1}

xcmPidDC555STV2 OBJECT-IDENTITY
    STATUS      current
    DESCRIPTION
        "Document Centre 555ST multi-functional system, 
                 launch configuration version, and
                 complete product identifier."
    ::= { xcmPidDC555ST 2 }
        -- ::= {1.3.6.1.4.1.253.8.62.1.1.27.1.2}

--
--


-- Document Centre 535, 35 ppm.

xcmPidDC535 OBJECT-IDENTITY
    STATUS  current
    DESCRIPTION
        "Document Centre 535 product type identifier
                 (not a complete product identifier)."
    ::= { xcmPidDocuCentreSystems 30 }
        -- ::= {1.3.6.1.4.1.253.8.62.1.1.30 }

xcmPidDC535ST OBJECT-IDENTITY
    STATUS  current
    DESCRIPTION
        "Document Centre 535 multi-function system model identifier
                 (not a complete product identifier)."
    ::= { xcmPidDC535 1 }
        -- ::= {1.3.6.1.4.1.253.8.62.1.1.30.1}
            -- => SAP PID string = "1N1"


xcmPidDC535STV1 OBJECT-IDENTITY
    STATUS  current
    DESCRIPTION
        "Document Centre 535 multi-function system
                 ECE pre-launch configuration version, and
                 complete product identifier."
    ::= { xcmPidDC535ST 1 }
        -- ::= {1.3.6.1.4.1.253.8.62.1.1.30.1.1}

xcmPidDC535STV2 OBJECT-IDENTITY
    STATUS  current
    DESCRIPTION
        "Document Centre 535 multi-function system
                 launch configuration version, and
                 complete product identifier."
    ::= { xcmPidDC535ST 2 }
        -- ::= {1.3.6.1.4.1.253.8.62.1.1.30.1.2}

--
--

-- Document Centre 545, 45 ppm.

xcmPidDC545 OBJECT-IDENTITY
    STATUS  current
    DESCRIPTION
        "Document Centre 545 product type identifier
                 (not a complete product identifier)."
    ::= { xcmPidDocuCentreSystems 31 }
        -- ::= {1.3.6.1.4.1.253.8.62.1.1.31}

xcmPidDC545ST OBJECT-IDENTITY
    STATUS  current
    DESCRIPTION
        "Document Centre 545 multi-function system model identifier
                 (not a complete product identifier)."
    ::= { xcmPidDC545 1 }
        -- ::= {1.3.6.1.4.1.253.8.62.1.1.31.1}
            -- => SAP PID string = "1O1"

xcmPidDC545STV1 OBJECT-IDENTITY
    STATUS  current
    DESCRIPTION
        "Document Centre 545 multi-function system
                 ECE pre-launch configuration version, and
                 complete product identifier."
    ::= { xcmPidDC545ST 1 }
        -- ::= {1.3.6.1.4.1.253.8.62.1.1.31.1.1}

xcmPidDC545STV2 OBJECT-IDENTITY
    STATUS  current
    DESCRIPTION
        "Document Centre 545 multi-function system
                 launch configuration version, and
                 complete product identifier."
    ::= { xcmPidDC545ST 2 }
        -- ::= {1.3.6.1.4.1.253.8.62.1.1.31.1.2}

--
--

----------------------------------------------------------------
-- Xerographic WorkCentre and WorkCentrePro MF Devices
----------------------------------------------------------------

xcmPidWorkCentreMFSystems OBJECT-IDENTITY
    STATUS      current
    DESCRIPTION
        "WorkCentre and WorkCentrePro Systems product line identifier
                 (not a complete product identifier)."
    ::= { xcmPidProductIdentifiers 20 }
        -- ::= {1.3.6.1.4.1.253.8.62.1.20}

--
--

--
--

--
--

--
-- 

--

--

--

--

--
--

--
--

--
--

--
--


--
--


--
--

--
--
-- WorkCentre MultiFunction Series

xcmPidWCMF OBJECT-IDENTITY
    STATUS      current
    DESCRIPTION
        "WorkCentre System identifier
                 (not a complete product identifier)."
    ::= { xcmPidWorkCentreMFSystems 2 }
        -- ::= {1.3.6.1.4.1.253.8.62.1.20.2 }

-- WorkCentre 423/428  

xcmPidWC423 OBJECT-IDENTITY
    STATUS      current
    DESCRIPTION
        "WorkCentre 423/428 copier/printer or copier/printer/fax/IFax 
         system identifier     (not a complete product identifier)."
    ::= { xcmPidWCMF 1 }
        -- ::= {1.3.6.1.4.1.253.8.62.1.20.2.1 }
            -- => SAP PID string = "D21"

xcmPidWC423V1 OBJECT-IDENTITY
    STATUS      current
    DESCRIPTION
        "WorkCentre 423/428 copier/printer or copier/printer/fax/IFax,
                 launch configuration version #1, and
                 complete product identifier."
    ::= { xcmPidWC423 1 }
        -- ::= {1.3.6.1.4.1.253.8.62.1.20.2.1.1}

xcmPidWC423V2 OBJECT-IDENTITY
    STATUS      current
    DESCRIPTION
        "WorkCentre 423/428  copier/printer or copier/printer/fax/IFax,
                 launch configuration version #2, and
                 complete product identifier."
    ::= { xcmPidWC423 2 }
        -- ::= {1.3.6.1.4.1.253.8.62.1.20.2.1.2}

xcmPidWC423V3 OBJECT-IDENTITY
    STATUS      current
    DESCRIPTION
        "WorkCentre 423/428  copier/printer or copier/printer/fax/IFax,
                 launch configuration version #3, and
                 complete product identifier."
    ::= { xcmPidWC423 3 }
        -- ::= {1.3.6.1.4.1.253.8.62.1.20.2.1.3}


-- WorkCentre M20i Copy / Print / FAX / Scan / Scan-to-Email
--                 Parallel Port, USB V2.0 Port, 10/100baseT Port

xcmPidWCM20i OBJECT-IDENTITY
    STATUS      current
    DESCRIPTION
        "WorkCentre M20i multi-function system identifier
                (not a complete product identifier)."
    ::= { xcmPidWCMF 7 }
        -- ::= {1.3.6.1.4.1.253.8.62.1.20.2.7 }
            -- => SAP PID string = "D27"
            -- => USB PID number = 16927 = 0x421F

xcmPidWCM20iV1 OBJECT-IDENTITY
    STATUS      current
    DESCRIPTION
        "WorkCentre M20i multi-function system, 
                 launch configuration version #1, and
                 complete product identifier."
    ::= { xcmPidWCM20i 1 }
        -- ::= {1.3.6.1.4.1.253.8.62.1.20.2.7.1}

xcmPidWCM20iV2 OBJECT-IDENTITY
    STATUS      current
    DESCRIPTION
        "WorkCentre M20i multi-function system,
                 launch configuration version #2, and
                 complete product identifier."
    ::= { xcmPidWCM20i 2 }
        -- ::= {1.3.6.1.4.1.253.8.62.1.20.2.7.2}

xcmPidWCM20iV3 OBJECT-IDENTITY
    STATUS      current
    DESCRIPTION
        "WorkCentre M20i multi-function system,
                 launch configuration version #3, and
                 complete product identifier."
    ::= { xcmPidWCM20i 3 }
        -- ::= {1.3.6.1.4.1.253.8.62.1.20.2.7.3}


-- WorkCentre M20 Copy / Print / Scan / Scan-to-Email
--                 Parallel Port, USB V2.0 Port, 10/100baseT Port

xcmPidWCM20 OBJECT-IDENTITY
    STATUS      current
    DESCRIPTION
        "WorkCentre M20 multi-function system identifier
                (not a complete product identifier)."
    ::= { xcmPidWCMF 25 }
        -- ::= {1.3.6.1.4.1.253.8.62.1.20.2.25 }
            -- => SAP PID string = "D2I"
            -- => USB PID number = 16938 = 0x422A

xcmPidWCM20V1 OBJECT-IDENTITY
    STATUS      current
    DESCRIPTION
        "WorkCentre M20 multi-function system, 
                 launch configuration version #1, and
                 complete product identifier."
    ::= { xcmPidWCM20 1 }
        -- ::= {1.3.6.1.4.1.253.8.62.1.20.2.25.1}


xcmPidWCM35 OBJECT-IDENTITY
    STATUS      current
    DESCRIPTION
        "WorkCentre M35 multi-function system identifier
                (not a complete product identifier)."
    ::= { xcmPidWCMF 2 }
        -- ::= {1.3.6.1.4.1.253.8.62.1.20.2.2 }
            -- => SAP PID string = "D22"

xcmPidWCM35V1 OBJECT-IDENTITY
    STATUS      current
    DESCRIPTION
        "WorkCentre M35 multi-function system, 
                 launch configuration version #1, and
                 complete product identifier."
    ::= { xcmPidWCM35 1 }
        -- ::= {1.3.6.1.4.1.253.8.62.1.20.2.2.1}

xcmPidWCM35V2 OBJECT-IDENTITY
    STATUS      current
    DESCRIPTION
        "WorkCentre M35 multi-function system,
                 launch configuration version #2, and
                 complete product identifier."
    ::= { xcmPidWCM35 2 }
        -- ::= {1.3.6.1.4.1.253.8.62.1.20.2.2.2}

xcmPidWCM35V3 OBJECT-IDENTITY
    STATUS      current
    DESCRIPTION
        "WorkCentre M35 multi-function system,
                 launch configuration version #3, and
                 complete product identifier."
    ::= { xcmPidWCM35 3 }
        -- ::= {1.3.6.1.4.1.253.8.62.1.20.2.2.3}

xcmPidWCM45 OBJECT-IDENTITY
    STATUS      current
    DESCRIPTION
        "WorkCentre M45 multi-function system identifier
                (not a complete product identifier)."
    ::= { xcmPidWCMF 3 }
        -- ::= {1.3.6.1.4.1.253.8.62.1.20.2.3 }
            -- => SAP PID string = "D23"

xcmPidWCM45V1 OBJECT-IDENTITY
    STATUS      current
    DESCRIPTION
        "WorkCentre M45 multi-function system, 
                 launch configuration version #1, and
                 complete product identifier."
    ::= { xcmPidWCM45 1 }
        -- ::= {1.3.6.1.4.1.253.8.62.1.20.2.3.1}

xcmPidWCM45V2 OBJECT-IDENTITY
    STATUS      current
    DESCRIPTION
        "WorkCentre M45 multi-function system,
                 launch configuration version #2, and
                 complete product identifier."
    ::= { xcmPidWCM45 2 }
        -- ::= {1.3.6.1.4.1.253.8.62.1.20.2.3.2}

xcmPidWCM45V3 OBJECT-IDENTITY
    STATUS      current
    DESCRIPTION
        "WorkCentre M45 multi-function system,
                 launch configuration version #3, and
                 complete product identifier."
    ::= { xcmPidWCM45 3 }
        -- ::= {1.3.6.1.4.1.253.8.62.1.20.2.3.3}
xcmPidWCM55 OBJECT-IDENTITY
    STATUS      current
    DESCRIPTION
        "WorkCentre M55 multi-function system identifier
                (not a complete product identifier)."
    ::= { xcmPidWCMF 4 }
        -- ::= {1.3.6.1.4.1.253.8.62.1.20.2.4 }
            -- => SAP PID string = "D24"


xcmPidWCM55V1 OBJECT-IDENTITY
    STATUS      current
    DESCRIPTION
        "WorkCentre M55 multi-function system, 
                 launch configuration version #1, and
                 complete product identifier."
    ::= { xcmPidWCM55 1 }
        -- ::= {1.3.6.1.4.1.253.8.62.1.20.2.4.1}

xcmPidWCM55V2 OBJECT-IDENTITY
    STATUS      current
    DESCRIPTION
        "WorkCentre M55 multi-function system,
                 launch configuration version #2, and
                 complete product identifier."
    ::= { xcmPidWCM55 2 }
        -- ::= {1.3.6.1.4.1.253.8.62.1.20.2.4.2}

xcmPidWCM55V3 OBJECT-IDENTITY
    STATUS      current
    DESCRIPTION
        "WorkCentre M55 multi-function system,
                 launch configuration version #3, and
                 complete product identifier."
    ::= { xcmPidWCM55 3 }
        -- ::= {1.3.6.1.4.1.253.8.62.1.20.2.4.3}


----------------------------------------------------------------
-- Desktop DocuPrint Printers
----------------------------------------------------------------

xcmPidDesktopDocuPrintPrinters OBJECT-IDENTITY
    STATUS      current
    DESCRIPTION
        "Desktop DocuPrint Printers product line identifier
                 (not a complete product identifier)."
    ::= { xcmPidProductIdentifiers 2 }
        -- ::= {1.3.6.1.4.1.253.8.62.1.2}

--
--

-- Desktop DocuPrint 4517

xcmPid4517 OBJECT-IDENTITY
    STATUS      current
    DESCRIPTION
        "Desktop DocuPrint 4517 product type identifier
                 (not a complete product identifier)."
    ::= { xcmPidDesktopDocuPrintPrinters 2 }
        -- ::= {1.3.6.1.4.1.253.8.62.1.2.2}

xcmPid4517PlusM1 OBJECT-IDENTITY
    STATUS      current
    DESCRIPTION
        "Desktop DocuPrint 4517+ launch configuration model identifier
                 (not a complete product identifier)."
    ::= { xcmPid4517 1 }
        -- ::= {1.3.6.1.4.1.253.8.62.1.2.2.1}
            -- => SAP PID string = "221"

xcmPid4517PlusM1V1 OBJECT-IDENTITY
    STATUS      current
    DESCRIPTION
        "Desktop DocuPrint 4517+ launch configuration model and version,
                 and complete product identifier."
    ::= { xcmPid4517PlusM1 1 }
        -- ::= {1.3.6.1.4.1.253.8.62.1.2.2.1.1}


-- Desktop DocuPrint N17

xcmPidDocuPrintN17 OBJECT-IDENTITY
    STATUS      current
    DESCRIPTION
        "Desktop DocuPrint N17 launch configuration model
                 identifier (not a complete product identifier)."
    ::= { xcmPid4517 2 }
        -- ::= {1.3.6.1.4.1.253.8.62.1.2.2.2}
            -- => SAP PID string = "222"

xcmPidDocuPrintN17V1 OBJECT-IDENTITY
    STATUS      current
    DESCRIPTION
        "Desktop DocuPrint N17 launch configuration model and
                 version, and complete product identifier."
    ::= { xcmPidDocuPrintN17 1 }
        -- ::= {1.3.6.1.4.1.253.8.62.1.2.2.2.1}


--
--


-- Desktop DocuPrint C55

xcmPidDocuPrintC55 OBJECT-IDENTITY
    STATUS      current
    DESCRIPTION
        "Desktop DocuPrint C55 product type identifier
                 (not a complete product identifier)."
    ::= { xcmPidDesktopDocuPrintPrinters 3 }
        -- ::= {1.3.6.1.4.1.253.8.62.1.2.3}

xcmPidDocuPrintC55M1 OBJECT-IDENTITY
    STATUS      current
    DESCRIPTION
        "Desktop DocuPrint C55 launch configuration model identifier
                 (not a complete product identifier)."
    ::= { xcmPidDocuPrintC55 1 }
        -- ::= {1.3.6.1.4.1.253.8.62.1.2.3.1}
            -- => SAP PID string = "231"

xcmPidDocuPrintC55M1V1 OBJECT-IDENTITY
    STATUS      current
    DESCRIPTION
        "Desktop DocuPrint C55 launch configuration model and version,
                 and complete product identifier."
    ::= { xcmPidDocuPrintC55M1 1 }
        -- ::= {1.3.6.1.4.1.253.8.62.1.2.3.1.1}

xcmPidDocuPrintC55M1V2 OBJECT-IDENTITY
    STATUS      current
    DESCRIPTION
        "Desktop DocuPrint C55 launch configuration model /
                 post-launch configuration version,
                 and complete product identifier."
    ::= { xcmPidDocuPrintC55M1 2 }
        -- ::= {1.3.6.1.4.1.253.8.62.1.2.3.1.2}


-- Desktop DocuPrint NC60


xcmPidDocuPrintNC60 OBJECT-IDENTITY
    STATUS      current
    DESCRIPTION
        "Desktop DocuPrint NC60 launch configuration model identifier
                 (not a complete product identifier)."
    ::= { xcmPidDocuPrintC55 2 }
        -- ::= {1.3.6.1.4.1.253.8.62.1.2.3.2}
            -- => SAP PID string = "232"

xcmPidDocuPrintNC60V1 OBJECT-IDENTITY
    STATUS      current
    DESCRIPTION
        "Desktop DocuPrint NC60 launch configuration model and version,
                 and complete product identifier."
    ::= { xcmPidDocuPrintNC60 1 }
        -- ::= {1.3.6.1.4.1.253.8.62.1.2.3.2.1}


--
--

-- Desktop DocuPrint P1210

xcmPidP1210 OBJECT-IDENTITY
    STATUS      current
    DESCRIPTION
        "Desktop DocuPrint P1210 product type identifier
                 (not a complete product identifier)."
    ::= { xcmPidDesktopDocuPrintPrinters 4 }
        -- ::= {1.3.6.1.4.1.253.8.62.1.2.4}

xcmPidP1210M1 OBJECT-IDENTITY
    STATUS      current
    DESCRIPTION
        "Desktop DocuPrint P1210 launch configuration model identifier
                 (not a complete product identifier)."
    ::= { xcmPidP1210 1 }
        -- ::= {1.3.6.1.4.1.253.8.62.1.2.4.1}
            -- => SAP PID string = "241"

xcmPidP1210M1V1 OBJECT-IDENTITY
    STATUS      current
    DESCRIPTION
        "Desktop DocuPrint P1210 launch configuration model and version,
                 and complete product identifier."
    ::= { xcmPidP1210M1 1 }
        -- ::= {1.3.6.1.4.1.253.8.62.1.2.4.1.1}

--
--


----------------------------------------------------------------
-- WorkGroup & MidRange DocuPrint Printers
----------------------------------------------------------------

xcmPidWorkGroupDocuPrintPrinters OBJECT-IDENTITY
    STATUS      current
    DESCRIPTION
        "WorkGroup & MidRange DocuPrint Printers product line identifier
                 (not a complete product identifier)."
    ::= { xcmPidProductIdentifiers 3 }
        -- ::= {1.3.6.1.4.1.253.8.62.1.3}

--
--

-- WorkGroup DocuPrint Nnn

xcmPidDocuPrintNnn OBJECT-IDENTITY
    STATUS      current
    DESCRIPTION
        "WorkGroup DocuPrint Nnn product type identifier
                 (not a complete product identifier)."
    ::= { xcmPidWorkGroupDocuPrintPrinters 2 }
        -- ::= {1.3.6.1.4.1.253.8.62.1.3.2}

xcmPidDocuPrintN32 OBJECT-IDENTITY
    STATUS      current
    DESCRIPTION
        "WorkGroup DocuPrint N32 model identifier
                 (not a complete product identifier)."
    ::= { xcmPidDocuPrintNnn 1 }
        -- ::= {1.3.6.1.4.1.253.8.62.1.3.2.1}
            -- => SAP PID string = "321"

xcmPidDocuPrintN32V1 OBJECT-IDENTITY
    STATUS      current
    DESCRIPTION
        "WorkGroup DocuPrint N32 launch configuration version,
                 and complete product identifier."
    ::= { xcmPidDocuPrintN32 1 }
        -- ::= {1.3.6.1.4.1.253.8.62.1.3.2.1.1}

xcmPidDocuPrintN32V2 OBJECT-IDENTITY
    STATUS      current
    DESCRIPTION
        "WorkGroup DocuPrint N32 post-launch configuration version,
                 and complete product identifier."
    ::= { xcmPidDocuPrintN32 2 }
        -- ::= {1.3.6.1.4.1.253.8.62.1.3.2.1.2}


xcmPidDocuPrintN24 OBJECT-IDENTITY
    STATUS      current
    DESCRIPTION
        "WorkGroup DocuPrint N24 model identifier
                 (not a complete product identifier)."
    ::= { xcmPidDocuPrintNnn 2 }
        -- ::= {1.3.6.1.4.1.253.8.62.1.3.2.2}
            -- => SAP PID string = "322"

xcmPidDocuPrintN24V1 OBJECT-IDENTITY
    STATUS      current
    DESCRIPTION
        "WorkGroup DocuPrint N24 launch configuration version,
                 and complete product identifier."
    ::= { xcmPidDocuPrintN24 1 }
        -- ::= {1.3.6.1.4.1.253.8.62.1.3.2.2.1}

xcmPidDocuPrintN24V2 OBJECT-IDENTITY
    STATUS      current
    DESCRIPTION
        "WorkGroup DocuPrint N24 post-launch configuration version,
                 and complete product identifier."
    ::= { xcmPidDocuPrintN24 2 }
        -- ::= {1.3.6.1.4.1.253.8.62.1.3.2.2.2}


xcmPidDocuPrintN40 OBJECT-IDENTITY
    STATUS      current
    DESCRIPTION
        "WorkGroup DocuPrint N40 model identifier
                 (not a complete product identifier)."
    ::= { xcmPidDocuPrintNnn 3 }
        -- ::= {1.3.6.1.4.1.253.8.62.1.3.2.3}
            -- => SAP PID string = "323"

xcmPidDocuPrintN40V1 OBJECT-IDENTITY
    STATUS      current
    DESCRIPTION
        "WorkGroup DocuPrint N40 launch configuration version,
                 and complete product identifier."
    ::= { xcmPidDocuPrintN40 1 }
        -- ::= {1.3.6.1.4.1.253.8.62.1.3.2.3.1}

--
--

xcmPidDocuPrintN2025 OBJECT-IDENTITY
    STATUS      current
    DESCRIPTION
        "WorkGroup DocuPrint N2025 model identifier
                 (not a complete product identifier)."
    ::= { xcmPidDocuPrintNnn 17 }
        -- ::= {1.3.6.1.4.1.253.8.62.1.3.2.17}
            -- => SAP PID string = "32A"

xcmPidDocuPrintN2025V1 OBJECT-IDENTITY
    STATUS      current
    DESCRIPTION
        "WorkGroup DocuPrint N2025 launch configuration version,
                 and complete product identifier."
    ::= { xcmPidDocuPrintN2025 1 }
        -- ::= {1.3.6.1.4.1.253.8.62.1.3.2.17.1}

xcmPidDocuPrintN2025V2 OBJECT-IDENTITY
    STATUS      current
    DESCRIPTION
        "WorkGroup DocuPrint N2025 first post-launch
                 configuration version, and complete
                 product identifier."
    ::= { xcmPidDocuPrintN2025 2 }
        -- ::= {1.3.6.1.4.1.253.8.62.1.3.2.17.2}

xcmPidDocuPrintN2125 OBJECT-IDENTITY
    STATUS      current
    DESCRIPTION
        "WorkGroup DocuPrint N2125 model identifier
                 (not a complete product identifier)."
    ::= { xcmPidDocuPrintNnn 18 }
        -- ::= {1.3.6.1.4.1.253.8.62.1.3.2.18}
            -- => SAP PID string = "32B"

xcmPidDocuPrintN2125V1 OBJECT-IDENTITY
    STATUS      current
    DESCRIPTION
        "WorkGroup DocuPrint N2125 launch configuration version,
                 and complete product identifier."
    ::= { xcmPidDocuPrintN2125 1 }
        -- ::= {1.3.6.1.4.1.253.8.62.1.3.2.18.1}

xcmPidDocuPrintN2125V2 OBJECT-IDENTITY
    STATUS      current
    DESCRIPTION
        "WorkGroup DocuPrint N2125 first post-launch
                 configuration version, and complete
                 product identifier."
    ::= { xcmPidDocuPrintN2125 2 }
        -- ::= {1.3.6.1.4.1.253.8.62.1.3.2.18.2}

xcmPidDocuPrintN2425 OBJECT-IDENTITY
    STATUS      current
    DESCRIPTION
        "WorkGroup DocuPrint N2425 model identifier
                 (not a complete product identifier)."
    ::= { xcmPidDocuPrintNnn 19 }
        -- ::= {1.3.6.1.4.1.253.8.62.1.3.2.19}
            -- => SAP PID string = "32C"

xcmPidDocuPrintN2425V1 OBJECT-IDENTITY
    STATUS      current
    DESCRIPTION
        "WorkGroup DocuPrint N2425 launch configuration version,
                 and complete product identifier."
    ::= { xcmPidDocuPrintN2425 1 }
        -- ::= {1.3.6.1.4.1.253.8.62.1.3.2.19.1}


xcmPidDocuPrintN2825 OBJECT-IDENTITY
    STATUS      current
    DESCRIPTION
        "WorkGroup DocuPrint N2825 model identifier
                 (not a complete product identifier)."
    ::= { xcmPidDocuPrintNnn 20 }
        -- ::= {1.3.6.1.4.1.253.8.62.1.3.2.20}
            -- => SAP PID string = "32D"

xcmPidDocuPrintN2825V1 OBJECT-IDENTITY
    STATUS      current
    DESCRIPTION
        "WorkGroup DocuPrint N2825 launch configuration version,
                 and complete product identifier."
    ::= { xcmPidDocuPrintN2825 1 }
        -- ::= {1.3.6.1.4.1.253.8.62.1.3.2.20.1}

xcmPidDocuPrintN2825V2 OBJECT-IDENTITY
    STATUS      current
    DESCRIPTION
        "WorkGroup DocuPrint N2825 first post-launch
                 configuration version, and complete
                 product identifier."
    ::= { xcmPidDocuPrintN2825 2 }
        -- ::= {1.3.6.1.4.1.253.8.62.1.3.2.20.2}

--
--

xcmPidDocuPrintN3225 OBJECT-IDENTITY
    STATUS      current
    DESCRIPTION
        "WorkGroup DocuPrint N3225 model identifier
                 (not a complete product identifier)."
    ::= { xcmPidDocuPrintNnn 21 }
        -- ::= {1.3.6.1.4.1.253.8.62.1.3.2.21}
            -- => SAP PID string = "32E"

xcmPidDocuPrintN3225V1 OBJECT-IDENTITY
    STATUS      current
    DESCRIPTION
        "WorkGroup DocuPrint N3225 launch configuration version,
                 and complete product identifier."
    ::= { xcmPidDocuPrintN3225 1 }
        -- ::= {1.3.6.1.4.1.253.8.62.1.3.2.21.1}

xcmPidDocuPrintN3225V2 OBJECT-IDENTITY
    STATUS      current
    DESCRIPTION
        "WorkGroup DocuPrint N3225 first post-launch
                 configuration version, and complete
                 product identifier."
    ::= { xcmPidDocuPrintN3225 2 }
        -- ::= {1.3.6.1.4.1.253.8.62.1.3.2.21.2}

xcmPidDocuPrintN4025 OBJECT-IDENTITY
    STATUS      current
    DESCRIPTION
        "WorkGroup DocuPrint N4025 model identifier
                 (not a complete product identifier)."
    ::= { xcmPidDocuPrintNnn 22 }
        -- ::= {1.3.6.1.4.1.253.8.62.1.3.2.22}
            -- => SAP PID string = "32F"

xcmPidDocuPrintN4025V1 OBJECT-IDENTITY
    STATUS      current
    DESCRIPTION
        "WorkGroup DocuPrint N4025 launch configuration version,
                 and complete product identifier."
    ::= { xcmPidDocuPrintN4025 1 }
        -- ::= {1.3.6.1.4.1.253.8.62.1.3.2.22.1}

xcmPidDocuPrintN4025V2 OBJECT-IDENTITY
    STATUS      current
    DESCRIPTION
        "WorkGroup DocuPrint N4025 first post-launch
                 configuration version, and complete
                 product identifier."
    ::= { xcmPidDocuPrintN4025 2 }
        -- ::= {1.3.6.1.4.1.253.8.62.1.3.2.22.2}

xcmPidDocuPrintN4525 OBJECT-IDENTITY
    STATUS      current
    DESCRIPTION
        "WorkGroup DocuPrint N4525 model identifier
                 (not a complete product identifier)."
    ::= { xcmPidDocuPrintNnn 36 }
        -- ::= {1.3.6.1.4.1.253.8.62.1.3.2.36}
            -- => SAP PID string = "32T"

xcmPidDocuPrintN4525V1 OBJECT-IDENTITY
    STATUS      current
    DESCRIPTION
        "WorkGroup DocuPrint N4525 launch configuration version,
                 and complete product identifier."
    ::= { xcmPidDocuPrintN4525 1 }
        -- ::= {1.3.6.1.4.1.253.8.62.1.3.2.36.1}

xcmPidPhaser5400 OBJECT-IDENTITY
    STATUS      current
    DESCRIPTION
        "WorkGroup Phaser 5400 model identifier
                 (not a complete product identifier)."
    ::= { xcmPidDocuPrintNnn 37 }
        -- ::= {1.3.6.1.4.1.253.8.62.1.3.2.37}
            -- => SAP PID string = "32U"

xcmPidPhaser5400V1 OBJECT-IDENTITY
    STATUS      current
    DESCRIPTION
        "WorkGroup Phaser 5400 launch configuration version,
                 and complete product identifier."
    ::= { xcmPidPhaser5400 1 }
        -- ::= {1.3.6.1.4.1.253.8.62.1.3.2.37.1}

-- Olivetti OEM version PID and SAP PID string assignments:
--   DP N2025: {1.3.6.1.4.1.279.253.62.1.3.2.23.1}, "32G"
--   DP N2125: {1.3.6.1.4.1.279.253.62.1.3.2.24.1}, "32H"
--   DP N2425: {1.3.6.1.4.1.279.253.62.1.3.2.25.1}, "32I"
--   DP N2825: {1.3.6.1.4.1.279.253.62.1.3.2.26.1}, "32J"
--   DP N3225: {1.3.6.1.4.1.279.253.62.1.3.2.27.1}, "32K"
--   DP N4025: {1.3.6.1.4.1.279.253.62.1.3.2.28.1}, "32L"


-- "OEM#2" OEM version PID and SAP PID string assignments:
--   DP N2025: {1.3.6.1.4.1.???.253.62.1.3.2.29.1}, "32M"
--   DP N2125: {1.3.6.1.4.1.???.253.62.1.3.2.30.1}, "32N"
--   DP N2425: {1.3.6.1.4.1.???.253.62.1.3.2.31.1}, "32O"
--   DP N2825: {1.3.6.1.4.1.???.253.62.1.3.2.32.1}, "32P"
--   DP N3225: {1.3.6.1.4.1.???.253.62.1.3.2.33.1}, "32Q"
--   DP N4025: {1.3.6.1.4.1.???.253.62.1.3.2.34.1}, "32R"


-- WorkGroup DocuPrint NCnn Color Laser Printers

xcmPidDocuPrintNCnn OBJECT-IDENTITY
    STATUS      current
    DESCRIPTION
        "WorkGroup DocuPrint NCnn Color Laser Printers product type
                 identifier (not a complete product identifier)."
    ::= { xcmPidWorkGroupDocuPrintPrinters 3 }
        -- ::= {1.3.6.1.4.1.253.8.62.1.3.3}

xcmPidDocuPrintNC70 OBJECT-IDENTITY
    STATUS      current
    DESCRIPTION
        "WorkGroup DocuPrint NC70 Color Laser Printer
                 model identifier (not a complete product identifier)."
    ::= { xcmPidDocuPrintNCnn 1 }
        -- ::= {1.3.6.1.4.1.253.8.62.1.3.3.1}
            -- => SAP PID string = "331"

xcmPidDocuPrintNC70V1 OBJECT-IDENTITY
    STATUS      current
    DESCRIPTION
        "WorkGroup DocuPrint NC70 Color Laser Printer
                 launch configuration version,
                 and complete product identifier."
    ::= { xcmPidDocuPrintNC70 1 }
        -- ::= {1.3.6.1.4.1.253.8.62.1.3.3.1.1}


xcmPidDocuPrintNC80 OBJECT-IDENTITY
    STATUS      current
    DESCRIPTION
        "WorkGroup DocuPrint NC80 Color Laser Printer
                 model identifier (not a complete product identifier)."
    ::= { xcmPidDocuPrintNCnn 2 }
        -- ::= {1.3.6.1.4.1.253.8.62.1.3.3.2}
            -- => SAP PID string = "332"

xcmPidDocuPrintNC80V1 OBJECT-IDENTITY
    STATUS      current
    DESCRIPTION
        "WorkGroup DocuPrint NC80 Color Laser Printer
                 launch configuration version,
                 and complete product identifier."
    ::= { xcmPidDocuPrintNC80 1 }
        -- ::= {1.3.6.1.4.1.253.8.62.1.3.3.2.1}
--
--

xcmPidXeroxPhaserPrinters OBJECT-IDENTITY
    STATUS      current
    DESCRIPTION
        "Xerox Phaser Printers product line identifier
                 (not a complete product identifier)."
    ::= { xcmPidProductIdentifiers 19 }
        -- ::= {1.3.6.1.4.1.253.8.62.1.19}

--     Xerox Phaser 3yyy = PLP Family

xcmPidPhaser3yyyFamily OBJECT-IDENTITY
    STATUS      current
    DESCRIPTION
        "Xerox Phaser 3yyy Family product line identifier
                 (not a complete product identifier)."
    ::= { xcmPidXeroxPhaserPrinters 1 }
        -- ::= {1.3.6.1.4.1.253.8.62.1.19.1}

-- Phaser 3450 Family, 25 ppm monochrome Laser printer
-- 3450B is the Base configuration
-- 3450D adds: Duplex
-- 3450DN adds: Network connection

xcmPidPhaser3450 OBJECT-IDENTITY
    STATUS      current
    DESCRIPTION
        "Xerox Phaser 3450 Laser Printer model identifier
                 (not a complete product identifier)."
    ::= { xcmPidPhaser3yyyFamily 1 }
        -- ::= {1.3.6.1.4.1.253.8.62.1.19.1.1}
            -- => SAP PID string = "C11"
            -- => USB PID number = 15589 = 0x3CE5

xcmPidPhaser3450D OBJECT-IDENTITY
    STATUS      current
    DESCRIPTION
        "Xerox Phaser 3450D Laser Printer launch configuration model,
                  version, and complete product identifier."
    ::= { xcmPidPhaser3450 2 }
        -- ::= {1.3.6.1.4.1.253.8.62.1.19.1.1.2}

xcmPidPhaser3450DN OBJECT-IDENTITY
    STATUS      current
    DESCRIPTION
        "Xerox Phaser 3450DN Laser Printer launch configuration model,
                  version, and complete product identifier."
    ::= { xcmPidPhaser3450 3 }
        -- ::= {1.3.6.1.4.1.253.8.62.1.19.1.1.3}

xcmPidPhaser3450B OBJECT-IDENTITY
    STATUS      current
    DESCRIPTION
        "Xerox Phaser 3450B Laser Printer launch configuration model,
                  version, and complete product identifier."
    ::= { xcmPidPhaser3450 4 }
        -- ::= {1.3.6.1.4.1.253.8.62.1.19.1.1.4}

--     Xerox Phaser 4yyy = Monochrome, A4 Family

xcmPidPhaser4yyyFamily OBJECT-IDENTITY
    STATUS      current
    DESCRIPTION
        "Xerox Phaser 4yyy Family product line identifier
                 (not a complete product identifier)."
    ::= { xcmPidXeroxPhaserPrinters 2 }
        -- ::= {1.3.6.1.4.1.253.8.62.1.19.2}

-- Phaser 4400 Family, 26 ppm Laser printer
-- 4400B is the Base configuration
-- 4400N  adds: built-in 10/100 Ethernet
-- 4400DT adds: 550 Sheet Feeder
--              Duplex
-- 4400DX adds: Hard Disk
--              +32 MB RAM

xcmPidPhaser4400 OBJECT-IDENTITY
    STATUS      current
    DESCRIPTION
        "Xerox Phaser 4400 Laser Printer model identifier
                 (not a complete product identifier)."
    ::= { xcmPidPhaser4yyyFamily 1 }
        -- ::= {1.3.6.1.4.1.253.8.62.1.19.2.1}
            -- => SAP PID string = "C21"

xcmPidPhaser4400N OBJECT-IDENTITY
    STATUS      current
    DESCRIPTION
        "Xerox Phaser 4400N Laser Printer launch configuration model,
                  version, and complete product identifier."
    ::= { xcmPidPhaser4400 1 }
        -- ::= {1.3.6.1.4.1.253.8.62.1.19.2.1.1}

xcmPidPhaser4400DT OBJECT-IDENTITY
    STATUS      current
    DESCRIPTION
        "Xerox Phaser 4400DT Laser Printer launch configuration model,
                  version, and complete product identifier."
    ::= { xcmPidPhaser4400 2 }
        -- ::= {1.3.6.1.4.1.253.8.62.1.19.2.1.2}

xcmPidPhaser4400DX OBJECT-IDENTITY
    STATUS      current
    DESCRIPTION
        "Xerox Phaser 4400DX Laser Printer launch configuration model,
                  version, and complete product identifier."
    ::= { xcmPidPhaser4400 3 }
        -- ::= {1.3.6.1.4.1.253.8.62.1.19.2.1.3}

xcmPidPhaser4400B OBJECT-IDENTITY
    STATUS      current
    DESCRIPTION
        "Xerox Phaser 4400B Laser Printer launch configuration model,
                  version, and complete product identifier."
    ::= { xcmPidPhaser4400 4 }
        -- ::= {1.3.6.1.4.1.253.8.62.1.19.2.1.4}

--
-- Phaser 4500 Family, 35-ppm A4 Monochrome Laser Printer
-- 4500B is the base configuration (no network, 16MB)
-- 4500N: built-in 10/100 Ethernet + (True 1200 X 1200 Print Quality)
-- 4500DT: 4500N + 550 Sheet Feeder and Auto Duplexer
-- 4500DX: 4500DT + Hard Disk + Offset Output Tray


xcmPidPhaser4500 OBJECT-IDENTITY
    STATUS      current
    DESCRIPTION
        "Xerox Phaser 4500 Laser Printer model identifier
                 (not a complete product identifier)."
    ::= { xcmPidPhaser4yyyFamily 2 }
        -- ::= {1.3.6.1.4.1.253.8.62.1.19.2.2}
            -- => SAP PID string = "C22"
            -- => USB PID number = 15624 = 0x3D08

xcmPidPhaser4500N OBJECT-IDENTITY
    STATUS      current
    DESCRIPTION
        "Xerox Phaser 4500N Laser Printer launch configuration model,
                  version, and complete product identifier."
    ::= { xcmPidPhaser4500 1 }
        -- ::= {1.3.6.1.4.1.253.8.62.1.19.2.2.1}

xcmPidPhaser4500DT OBJECT-IDENTITY
    STATUS      current
    DESCRIPTION
        "Xerox Phaser 4500DT Laser Printer launch configuration model,
                  version, and complete product identifier."
    ::= { xcmPidPhaser4500 2 }
        -- ::= {1.3.6.1.4.1.253.8.62.1.19.2.2.2}

xcmPidPhaser4500DX OBJECT-IDENTITY
    STATUS      current
    DESCRIPTION
        "Xerox Phaser 4500DX Laser Printer launch configuration model,
                  version, and complete product identifier."
    ::= { xcmPidPhaser4500 3 }
        -- ::= {1.3.6.1.4.1.253.8.62.1.19.2.2.3}

xcmPidPhaser4500B OBJECT-IDENTITY
    STATUS      current
    DESCRIPTION
        "Xerox Phaser 4500B Laser Printer launch configuration model,
                  version, and complete product identifier."
    ::= { xcmPidPhaser4500 4 }
        -- ::= {1.3.6.1.4.1.253.8.62.1.19.2.2.4}
--
--
--
--
--     Xerox Phaser 5yyy = Monochrome, A3 Family

xcmPidPhaser5yyyFamily OBJECT-IDENTITY
    STATUS      current
    DESCRIPTION
        "Xerox Phaser 5yyy Family product line identifier
                 (not a complete product identifier)."
    ::= { xcmPidXeroxPhaserPrinters 3 }
        -- ::= {1.3.6.1.4.1.253.8.62.1.19.3}

--

--
--     Xerox Phaser 6yyy = Color, A4 Family
--
--

xcmPidPhaser6yyyFamily OBJECT-IDENTITY
    STATUS      current
    DESCRIPTION
        "Xerox Phaser 6yyy Family product line identifier
                 (not a complete product identifier)."
    ::= { xcmPidXeroxPhaserPrinters 4 }
        -- ::= {1.3.6.1.4.1.253.8.62.1.19.4}

--
--

-- Phaser 6200 Family, 16/16 ppm Color Laser printer
-- 6200B is the Base configuration (no network, 64MB)
-- 6200N adds: built-in 10/100 Ethernet
-- 6200DP: 6200N + 64MB (128 total) and Auto Duplex
-- 6200DX: 6200DP + 128MB (256 total), 2-500 Sheet Input Tray
--         and a cart

xcmPidPhaser6200 OBJECT-IDENTITY
    STATUS      current
    DESCRIPTION
        "Xerox Phaser 6200 Laser Printer model identifier
                 (not a complete product identifier)."
    ::= { xcmPidPhaser6yyyFamily 1 }
        -- ::= {1.3.6.1.4.1.253.8.62.1.19.4.1}
            -- => SAP PID string = "C41"

xcmPidPhaser6200B OBJECT-IDENTITY
    STATUS      current
    DESCRIPTION
        "Xerox Phaser 6200B Laser Printer launch configuration model,
                  version, and complete product identifier."
    ::= { xcmPidPhaser6200 1 }
        -- ::= {1.3.6.1.4.1.253.8.62.1.19.4.1.1}

xcmPidPhaser6200N OBJECT-IDENTITY
    STATUS      current
    DESCRIPTION
        "Xerox Phaser 6200N Laser Printer launch configuration model,
                  version, and complete product identifier."
    ::= { xcmPidPhaser6200 2 }
        -- ::= {1.3.6.1.4.1.253.8.62.1.19.4.1.2}

xcmPidPhaser6200DP OBJECT-IDENTITY
    STATUS      current
    DESCRIPTION
        "Xerox Phaser 6200DP Laser Printer launch configuration model,
                  version, and complete product identifier."
    ::= { xcmPidPhaser6200 3 }
        -- ::= {1.3.6.1.4.1.253.8.62.1.19.4.1.3}

xcmPidPhaser6200DX OBJECT-IDENTITY
    STATUS      current
    DESCRIPTION
        "Xerox Phaser 6200DX Laser Printer launch configuration model,
                  version, and complete product identifier."
    ::= { xcmPidPhaser6200 4 }
        -- ::= {1.3.6.1.4.1.253.8.62.1.19.4.1.4}

-- Phaser 6250 Family, 26-ppm Single Pass A4 Color Laser Printer
-- 6250B is the Base configuration (No Network, 128MB RAM)
-- 6250N adds: Built-in 10/100 Ethernet, 256MB RAM, Pipeline performance
-- 6250DP: 6250N + Auto Duplex, Photomode
-- 6250DT: 6250DP + Single Auxiliary Tray + 256 (512MB total)
-- 6250DX: 6250DT + Internal HD

xcmPidPhaser6250 OBJECT-IDENTITY
    STATUS      current
    DESCRIPTION
        "Xerox Phaser 6250 Laser Printer model identifier
                 (not a complete product identifier)."
    ::= { xcmPidPhaser6yyyFamily 3 }
        -- ::= {1.3.6.1.4.1.253.8.62.1.19.4.3}
            -- => SAP PID string = "C43"

xcmPidPhaser6250B OBJECT-IDENTITY
    STATUS      current
    DESCRIPTION
        "Xerox Phaser 6250B Laser Printer,
                  the Base configuration (No Network, 128MB RAM)
                  launch configuration model,
                  version, and complete product identifier."
    ::= { xcmPidPhaser6250 1 }
        -- ::= {1.3.6.1.4.1.253.8.62.1.19.4.3.1}

xcmPidPhaser6250N OBJECT-IDENTITY
    STATUS      current
    DESCRIPTION
        "Xerox Phaser 6250N Laser Printer 
                  adds: Built-in 10/100 Ethernet, 256MB RAM, Pipeline pe
                  launch configuration model,
                  version, and complete product identifier."
    ::= { xcmPidPhaser6250 2 }
        -- ::= {1.3.6.1.4.1.253.8.62.1.19.4.3.2}

xcmPidPhaser6250DP OBJECT-IDENTITY
    STATUS      current
    DESCRIPTION
        "Xerox Phaser 6250DP Laser Printer 
                  6250N + Auto Duplex, Photomode
                  launch configuration model,
                  version, and complete product identifier."
    ::= { xcmPidPhaser6250 3 }
        -- ::= {1.3.6.1.4.1.253.8.62.1.19.4.3.3}

xcmPidPhaser6250DT OBJECT-IDENTITY
    STATUS      current
    DESCRIPTION
        "Xerox Phaser 6250DT Laser Printer 
                  6250DP + Single Auxiliary Tray + 256 (512MB total)
                  launch configuration model,
                  version, and complete product identifier."
    ::= { xcmPidPhaser6250 5 }
        -- ::= {1.3.6.1.4.1.253.8.62.1.19.4.3.5}

xcmPidPhaser6250DX OBJECT-IDENTITY
    STATUS      current
    DESCRIPTION
        "Xerox Phaser 6250DX Laser Printer 
                  6250DT + Internal HD
                  launch configuration model,
                  version, and complete product identifier."
    ::= { xcmPidPhaser6250 4 }
        -- ::= {1.3.6.1.4.1.253.8.62.1.19.4.3.4}

--     Xerox Phaser 7yyy = Color, A3 Family

xcmPidPhaser7yyyFamily OBJECT-IDENTITY
    STATUS      current
    DESCRIPTION
        "Xerox Phaser 7yyy Family product line identifier
                 (not a complete product identifier)."
    ::= { xcmPidXeroxPhaserPrinters 5 }
        -- ::= {1.3.6.1.4.1.253.8.62.1.19.5}

-- Phaser 7300 Family, 30/37 ppm Color Laser printer
-- 7300B is the Base configuration (no network, 128)
-- 7300N  adds: built-in 10/100 Ethernet
-- 7300DN: 7300N + Auto Duplex
-- 7300DT: 7300N + 128 (256 total), 550 Sheet Feeder,
--         Auto Duplex and a hard disk
-- 7300DX: 7300DT + 128 (384 total), 2-550 Sheet Feeder
--         (3 Auxiliary Trays Total)

xcmPidPhaser7300 OBJECT-IDENTITY
    STATUS      current
    DESCRIPTION
        "Xerox Phaser 7300 Laser Printer model identifier
                 (not a complete product identifier)."
    ::= { xcmPidPhaser7yyyFamily 1 }
        -- ::= {1.3.6.1.4.1.253.8.62.1.19.5.1}
            -- => SAP PID string = "C51"

xcmPidPhaser7300DN OBJECT-IDENTITY
    STATUS      current
    DESCRIPTION
        "Xerox Phaser 7300DN Laser Printer launch configuration model,
                  version, and complete product identifier."
    ::= { xcmPidPhaser7300 1 }
        -- ::= {1.3.6.1.4.1.253.8.62.1.19.5.1.1}

xcmPidPhaser7300N OBJECT-IDENTITY
    STATUS      current           
    DESCRIPTION
        "Xerox Phaser 7300N Laser Printer launch configuration model,
                  version, and complete product identifier."
    ::= { xcmPidPhaser7300 2 }
        -- ::= {1.3.6.1.4.1.253.8.62.1.19.5.1.2}

xcmPidPhaser7300DT OBJECT-IDENTITY
    STATUS      current
    DESCRIPTION
        "Xerox Phaser 7300DT Laser Printer launch configuration model,
                  version, and complete product identifier."
    ::= { xcmPidPhaser7300 3 }
        -- ::= {1.3.6.1.4.1.253.8.62.1.19.5.1.3}

xcmPidPhaser7300DX OBJECT-IDENTITY
    STATUS      current
    DESCRIPTION
        "Xerox Phaser 7300DX Laser Printer launch configuration model,
                  version, and complete product identifier."
    ::= { xcmPidPhaser7300 4 }
        -- ::= {1.3.6.1.4.1.253.8.62.1.19.5.1.4}

xcmPidPhaser7300B OBJECT-IDENTITY
    STATUS      current
    DESCRIPTION
        "Xerox Phaser 7300B Laser Printer launch configuration model,
                  version, and complete product identifier."
    ::= { xcmPidPhaser7300 5 }
        -- ::= {1.3.6.1.4.1.253.8.62.1.19.5.1.5}

-- Phaser 7750 Family, 35/35 ppm Color Laser Printer
-- 7750B is the base configuration (no network, 128MB)
-- 7750DN: built-in 10/100 Ethernet, 256MB, Auto Duplex & Hard Drive, Ph
-- 7750GX: 7750DN + Lower Tray, 512MB and 128SDRAM
-- 7750DXF: 7750GX + Hi Cap feeder + Finisher

xcmPidPhaser7750 OBJECT-IDENTITY
    STATUS      current
    DESCRIPTION
        "Xerox Phaser 7750 Laser Printer model identifier
                 (not a complete product identifier)."
    ::= { xcmPidPhaser7yyyFamily 3 }
        -- ::= {1.3.6.1.4.1.253.8.62.1.19.5.3}
            -- => SAP PID string = "C53"

xcmPidPhaser7750B OBJECT-IDENTITY
    STATUS      current
    DESCRIPTION
        "Xerox Phaser 7750B Laser Printer launch configuration model,
                  version, and complete product identifier."
    ::= { xcmPidPhaser7750 1 }
        -- ::= {1.3.6.1.4.1.253.8.62.1.19.5.3.1}

xcmPidPhaser7750DN OBJECT-IDENTITY
    STATUS      current          
    DESCRIPTION
        "Xerox Phaser 7750DN Laser Printer launch configuration model,
                  version, and complete product identifier."
    ::= { xcmPidPhaser7750 2 }
        -- ::= {1.3.6.1.4.1.253.8.62.1.19.5.3.2}

xcmPidPhaser7750GX OBJECT-IDENTITY
    STATUS      current
    DESCRIPTION
        "Xerox Phaser 7750GX Laser Printer launch configuration model,
                  version, and complete product identifier."
    ::= { xcmPidPhaser7750 3 }
        -- ::= {1.3.6.1.4.1.253.8.62.1.19.5.3.3}

xcmPidPhaser7750DXF OBJECT-IDENTITY
    STATUS      current
    DESCRIPTION
        "Xerox Phaser 7750DXF Laser Printer launch configuration model,
                  version, and complete product identifier."
    ::= { xcmPidPhaser7750 4 }
        -- ::= {1.3.6.1.4.1.253.8.62.1.19.5.3.4}

--     Xerox Phaser 8yyy = Color, OSI Family

xcmPidPhaser8yyyFamily OBJECT-IDENTITY
    STATUS      current
    DESCRIPTION
        "Xerox Phaser 7yyy Family product line identifier
                 (not a complete product identifier)."
    ::= { xcmPidXeroxPhaserPrinters 6 }
        -- ::= {1.3.6.1.4.1.253.8.62.1.19.6}

-- Phaser 8400 Family, 16/20 ppm Solid Ink Color printer
-- 8400B is the Base configuration (no network, 64MB)
-- 8840BD: 8400B + Pipelining and Auto Duplex
-- 8400N:  8400B + built-in 10/100 Ethernet
-- 8400DP: 8400N + 64MB (128 total), pipelining and Auto Duplex
-- 8400DX: 8400DP + Hard disk, High cap feeder and Job collation.

xcmPidPhaser8400 OBJECT-IDENTITY
    STATUS      current
    DESCRIPTION
        "Xerox Phaser 8400 Laser Printer model identifier
                 (not a complete product identifier)."
    ::= { xcmPidPhaser8yyyFamily 1 }
        -- ::= {1.3.6.1.4.1.253.8.62.1.19.6.1}
            -- => SAP PID string = "C61"
            -- ==> USB PID 65521 
            -- Note that the USB PID of 14017 is not used.

xcmPidPhaser8400B OBJECT-IDENTITY
    STATUS      current
    DESCRIPTION
        "Xerox Phaser 8400B Laser Printer launch configuration model,
                  and complete product identifier. The 8400B is not
                  network connected so this SNMP id is not used."
    ::= { xcmPidPhaser8400 1 }
        -- ::= {1.3.6.1.4.1.253.8.62.1.19.6.1.1}

xcmPidPhaser8400N OBJECT-IDENTITY
    STATUS      current
    DESCRIPTION
        "Xerox Phaser 8400N Laser Printer launch configuration model,
                  and complete product identifier."
    ::= { xcmPidPhaser8400 2 }
        -- ::= {1.3.6.1.4.1.253.8.62.1.19.6.1.2}


xcmPidPhaser8400DP OBJECT-IDENTITY
    STATUS      current
    DESCRIPTION
        "Xerox Phaser 8400DP Laser Printer launch configuration model,
                  and complete product identifier."
    ::= { xcmPidPhaser8400 3 }
        -- ::= {1.3.6.1.4.1.253.8.62.1.19.6.1.3}

xcmPidPhaser8400DX OBJECT-IDENTITY
    STATUS      current
    DESCRIPTION
        "Xerox Phaser 8400DX Laser Printer launch configuration model,
                  and complete product identifier."
    ::= { xcmPidPhaser8400 4 }
        -- ::= {1.3.6.1.4.1.253.8.62.1.19.6.1.4}

xcmPidPhaser8400BD OBJECT-IDENTITY
    STATUS      current
    DESCRIPTION
        "Xerox Phaser 8400BD Laser Printer launch configuration model,
                  This is not network connected so the SNMP id is not 
                  used."
    ::= { xcmPidPhaser8400 5 }
        -- ::= {1.3.6.1.4.1.253.8.62.1.19.6.1.5}

----------------------------------------------------------------
-- MidRange Color Printers
----------------------------------------------------------------

xcmPidMidRangeColorPrinters OBJECT-IDENTITY
    STATUS      current
    DESCRIPTION
        "MidRange Color Printers product line identifier
                 (not a complete product identifier)."
    ::= { xcmPidProductIdentifiers 4 }
        -- ::= {1.3.6.1.4.1.253.8.62.1.4}

--
--

-- MidRange Color Printer Document Centre ColorSeries 50

xcmPidDCColorSeries50 OBJECT-IDENTITY
    STATUS      current
    DESCRIPTION
        "Document Centre ColorSeries 50 mid-range color printer product
                 type identifier (not a complete product identifier)."
    ::= { xcmPidMidRangeColorPrinters 2 }
        -- ::= {1.3.6.1.4.1.253.8.62.1.4.2}

xcmPidDCColorSeries50M1 OBJECT-IDENTITY
    STATUS      current
    DESCRIPTION
        "Document Centre ColorSeries 50 mid-range color printer
                 launch configuration model identifier
                 (not a complete product identifier)."
    ::= { xcmPidDCColorSeries50 1 }
        -- ::= {1.3.6.1.4.1.253.8.62.1.4.2.1}
            -- => SAP PID string = "421"

xcmPidDCColorSeries50M1V1 OBJECT-IDENTITY
    STATUS      current
    DESCRIPTION
        "Document Centre ColorSeries 50 mid-range color printer
                 launch configuration version,
                 and complete product identifier."
    ::= { xcmPidDCColorSeries50M1 1 }
        -- ::= {1.3.6.1.4.1.253.8.62.1.4.2.1.1}

--
--

--
--

--
--


----------------------------------------------------------------
-- Production DocuPrint Printers
----------------------------------------------------------------

xcmPidProductionDocuPrintPrinters OBJECT-IDENTITY
    STATUS      current
    DESCRIPTION
        "Production DocuPrint Printers product line identifier
                 (not a complete product identifier)."
    ::= { xcmPidProductIdentifiers 6 }
        -- ::= {1.3.6.1.4.1.253.8.62.1.6}


-- Production DocuPrint 65

xcmPidDocuPrint65 OBJECT-IDENTITY
    STATUS      current
    DESCRIPTION
        "Production DocuPrint 65 product type identifier
                 (not a complete product identifier)."
    ::= { xcmPidProductionDocuPrintPrinters 1 }
        -- ::= {1.3.6.1.4.1.253.8.62.1.6.1}

xcmPidDocuPrint65M1 OBJECT-IDENTITY
    STATUS      current
    DESCRIPTION
        "Production DocuPrint 65 launch configuration model identifier
                 (not a complete product identifier)."
    ::= { xcmPidDocuPrint65 1 }
        -- ::= {1.3.6.1.4.1.253.8.62.1.6.1.1}
            -- => SAP PID string = "611"

xcmPidDocuPrint65M1V1 OBJECT-IDENTITY
    STATUS      current
    DESCRIPTION
        "Production DocuPrint 65 launch configuration version,
                 and complete product identifier."
    ::= { xcmPidDocuPrint65M1 1 }
        -- ::= {1.3.6.1.4.1.253.8.62.1.6.1.1.1}

--
--

----------------------------------------------------------------
-- DocuPrint NPS (Network Printing Systems) Printers
----------------------------------------------------------------

xcmPidDocuPrintNPS OBJECT-IDENTITY
    STATUS      current
    DESCRIPTION
        "DocuPrint NPS (Network Printing Systems) product line
                 identifier (not a complete product identifier)."
    ::= { xcmPidProductIdentifiers 9 }
        -- ::= {1.3.6.1.4.1.253.8.62.1.9}


-- DocuPrint NPS DP4050 Printer

xcmPidDP4050NPS OBJECT-IDENTITY
    STATUS      current
    DESCRIPTION
        "DocuPrint NPS DP4050 product type identifier
                 (not a complete product identifier)."
    ::= { xcmPidDocuPrintNPS 1 }
        -- ::= {1.3.6.1.4.1.253.8.62.1.9.1}

xcmPidDP4050NPSM1 OBJECT-IDENTITY
    STATUS      current
    DESCRIPTION
        "DocuPrint NPS DP4050 launch configuration model identifier
                 (not a complete product identifier)."
    ::= { xcmPidDP4050NPS 1 }
        -- ::= {1.3.6.1.4.1.253.8.62.1.9.1.1}
            -- => SAP PID string = "911"

xcmPidDP4050NPSM1V1 OBJECT-IDENTITY
    STATUS      current
    DESCRIPTION
        "DocuPrint NPS DP4050 launch configuration version,
                 and complete product identifier."
    ::= { xcmPidDP4050NPSM1 1 }
        -- ::= {1.3.6.1.4.1.253.8.62.1.9.1.1.1}


-- DocuPrint NPS DP4090 Printer

xcmPidDP4090NPS OBJECT-IDENTITY
    STATUS      current
    DESCRIPTION
        "DocuPrint NPS DP4090 product type identifier
                 (not a complete product identifier)."
    ::= { xcmPidDocuPrintNPS 2 }
        -- ::= {1.3.6.1.4.1.253.8.62.1.9.2}

xcmPidDP4090NPSM1 OBJECT-IDENTITY
    STATUS      current
    DESCRIPTION
        "DocuPrint NPS DP4090 launch configuration model identifier
                 (not a complete product identifier)."
    ::= { xcmPidDP4090NPS 1 }
        -- ::= {1.3.6.1.4.1.253.8.62.1.9.2.1}
            -- => SAP PID string = "921"

xcmPidDP4090NPSM1V1 OBJECT-IDENTITY
    STATUS      current
    DESCRIPTION
        "DocuPrint NPS DP4090 launch configuration version,
                 and complete product identifier."
    ::= { xcmPidDP4090NPSM1 1 }
        -- ::= {1.3.6.1.4.1.253.8.62.1.9.2.1.1}


-- DocuPrint NPS DP4850 Printer

xcmPidDP4850NPS OBJECT-IDENTITY
    STATUS      current
    DESCRIPTION
        "DocuPrint NPS DP4850 product type identifier
                 (not a complete product identifier)."
    ::= { xcmPidDocuPrintNPS 3 }
        -- ::= {1.3.6.1.4.1.253.8.62.1.9.3}

xcmPidDP4850NPSM1 OBJECT-IDENTITY
    STATUS      current
    DESCRIPTION
        "DocuPrint NPS DP4850 launch configuration model identifier
                 (not a complete product identifier)."
    ::= { xcmPidDP4850NPS 1 }
        -- ::= {1.3.6.1.4.1.253.8.62.1.9.3.1}
            -- => SAP PID string = "931"

xcmPidDP4850NPSM1V1 OBJECT-IDENTITY
    STATUS      current
    DESCRIPTION
        "DocuPrint NPS DP4850 launch configuration version,
                 and complete product identifier."
    ::= { xcmPidDP4850NPSM1 1 }
        -- ::= {1.3.6.1.4.1.253.8.62.1.9.3.1.1}


-- DocuPrint NPS DP4890 Printer

xcmPidDP4890NPS OBJECT-IDENTITY
    STATUS      current
    DESCRIPTION
        "DocuPrint NPS DP4890 product type identifier
                 (not a complete product identifier)."
    ::= { xcmPidDocuPrintNPS 4 }
        -- ::= {1.3.6.1.4.1.253.8.62.1.9.4}

xcmPidDP4890NPSM1 OBJECT-IDENTITY
    STATUS      current
    DESCRIPTION
        "DocuPrint NPS DP4890 launch configuration model identifier
                 (not a complete product identifier)."
    ::= { xcmPidDP4890NPS 1 }
        -- ::= {1.3.6.1.4.1.253.8.62.1.9.4.1}
            -- => SAP PID string = "941"

xcmPidDP4890NPSM1V1 OBJECT-IDENTITY
    STATUS      current
    DESCRIPTION
        "DocuPrint NPS DP4890 launch configuration version,
                 and complete product identifier."
    ::= { xcmPidDP4890NPSM1 1 }
        -- ::= {1.3.6.1.4.1.253.8.62.1.9.4.1.1}


-- DocuPrint NPS DP4635 Printer

xcmPidDP4635NPS OBJECT-IDENTITY
    STATUS      current
    DESCRIPTION
        "DocuPrint NPS DP4635 product type identifier
                 (not a complete product identifier)."
    ::= { xcmPidDocuPrintNPS 5 }
        -- ::= {1.3.6.1.4.1.253.8.62.1.9.5}

xcmPidDP4635NPSM1 OBJECT-IDENTITY
    STATUS      current
    DESCRIPTION
        "DocuPrint NPS DP4635 launch configuration model identifier
                 (not a complete product identifier)."
    ::= { xcmPidDP4635NPS 1 }
        -- ::= {1.3.6.1.4.1.253.8.62.1.9.5.1}
            -- => SAP PID string = "951"

xcmPidDP4635NPSM1V1 OBJECT-IDENTITY
    STATUS      current
    DESCRIPTION
        "DocuPrint NPS DP4635 launch configuration version,
                 and complete product identifier."
    ::= { xcmPidDP4635NPSM1 1 }
        -- ::= {1.3.6.1.4.1.253.8.62.1.9.5.1.1}

-- DocuPrint NPS DP4635 Micr Printer

xcmPidDP4635NPSMicr OBJECT-IDENTITY
    STATUS      current
    DESCRIPTION
        "DocuPrint NPS DP4635 Micr launch configuration model identifier
                 (not a complete product identifier)."
    ::= { xcmPidDP4635NPS 2 }
        -- ::= {1.3.6.1.4.1.253.8.62.1.9.5.2}
            -- => SAP PID string = "952"

xcmPidDP4635NPSMicrV1 OBJECT-IDENTITY
    STATUS      current
    DESCRIPTION
        "DocuPrint NPS DP4635 Micr launch configuration version,
                 and complete product identifier."
    ::= { xcmPidDP4635NPSMicr 1 }
        -- ::= {1.3.6.1.4.1.253.8.62.1.9.5.2.1}


-- DocuPrint NPS DP180 Printer

xcmPidDP180NPS OBJECT-IDENTITY
    STATUS      current
    DESCRIPTION
        "DocuPrint NPS DP180 product type identifier
                 (not a complete product identifier)."
    ::= { xcmPidDocuPrintNPS 6 }
        -- ::= {1.3.6.1.4.1.253.8.62.1.9.6}

xcmPidDP180NPSM1 OBJECT-IDENTITY
    STATUS      current
    DESCRIPTION
        "DocuPrint NPS DP180 launch configuration model identifier
                 (not a complete product identifier)."
    ::= { xcmPidDP180NPS 1 }
        -- ::= {1.3.6.1.4.1.253.8.62.1.9.6.1}
            -- => SAP PID string = "961"

xcmPidDP180NPSM1V1 OBJECT-IDENTITY
    STATUS      current
    DESCRIPTION
        "DocuPrint NPS DP180 launch configuration version,
                 and complete product identifier."
    ::= { xcmPidDP180NPSM1 1 }
        -- ::= {1.3.6.1.4.1.253.8.62.1.9.6.1.1}

-- DocuPrint NPS DP180 Micr Printer

xcmPidDP180NPSMicr OBJECT-IDENTITY
    STATUS      current
    DESCRIPTION
        "DocuPrint NPS DP180 Micr launch configuration model identifier
                 (not a complete product identifier)."
    ::= { xcmPidDP180NPS 2 }
        -- ::= {1.3.6.1.4.1.253.8.62.1.9.6.2}
            -- => SAP PID string = "962"

xcmPidDP180NPSMicrV1 OBJECT-IDENTITY
    STATUS      current
    DESCRIPTION
        "DocuPrint NPS DP180 Micr launch configuration version,
                 and complete product identifier."
    ::= { xcmPidDP180NPSMicr 1 }
        -- ::= {1.3.6.1.4.1.253.8.62.1.9.6.2.1}


-- DocuPrint NPS DP96 Printer

xcmPidDP96NPS OBJECT-IDENTITY
    STATUS      current
    DESCRIPTION
        "DocuPrint NPS DP96 product type identifier
                 (not a complete product identifier)."
    ::= { xcmPidDocuPrintNPS 7 }
        -- ::= {1.3.6.1.4.1.253.8.62.1.9.7}

xcmPidDP96NPSM1 OBJECT-IDENTITY
    STATUS      current
    DESCRIPTION
        "DocuPrint NPS DP96 launch configuration model identifier
                 (not a complete product identifier)."
    ::= { xcmPidDP96NPS 1 }
        -- ::= {1.3.6.1.4.1.253.8.62.1.9.7.1}
            -- => SAP PID string = "971"

xcmPidDP96NPSM1V1 OBJECT-IDENTITY
    STATUS      current
    DESCRIPTION
        "DocuPrint NPS DP96 launch configuration version,
                 and complete product identifier."
    ::= { xcmPidDP96NPSM1 1 }
        -- ::= {1.3.6.1.4.1.253.8.62.1.9.7.1.1}

-- DocuPrint NPS DP96 Micr Printer

xcmPidDP96NPSMicr OBJECT-IDENTITY
    STATUS      current
    DESCRIPTION
        "DocuPrint NPS DP96 Micr launch configuration model identifier
                 (not a complete product identifier)."
    ::= { xcmPidDP96NPS 2 }
        -- ::= {1.3.6.1.4.1.253.8.62.1.9.7.2}
            -- => SAP PID string = "972"

xcmPidDP96NPSMicrV1 OBJECT-IDENTITY
    STATUS      current
    DESCRIPTION
        "DocuPrint NPS DP96 Micr launch configuration version,
                 and complete product identifier."
    ::= { xcmPidDP96NPSMicr 1 }
        -- ::= {1.3.6.1.4.1.253.8.62.1.9.7.2.1}

-- DocuPrint NPS DP92c Printer

xcmPidDP92cNPS OBJECT-IDENTITY
    STATUS      current
    DESCRIPTION
        "DocuPrint NPS DP92c product type identifier
                 (not a complete product identifier)."
    ::= { xcmPidDocuPrintNPS 8 }
        -- ::= {1.3.6.1.4.1.253.8.62.1.9.8}

xcmPidDP92cNPSM1 OBJECT-IDENTITY
    STATUS      current
    DESCRIPTION
        "DocuPrint NPS DP92c launch configuration model identifier
                 (not a complete product identifier)."
    ::= { xcmPidDP92cNPS 1 }
        -- ::= {1.3.6.1.4.1.253.8.62.1.9.8.1}
            -- => SAP PID string = "981"

xcmPidDP92cNPSM1V1 OBJECT-IDENTITY
    STATUS      current
    DESCRIPTION
        "DocuPrint NPS DP92c launch configuration version,
                 and complete product identifier."
    ::= { xcmPidDP92cNPSM1 1 }
        -- ::= {1.3.6.1.4.1.253.8.62.1.9.8.1.1}

-- DocuPrint NPS DP155 Printer

xcmPidDP155NPS OBJECT-IDENTITY
    STATUS      current
    DESCRIPTION
        "DocuPrint NPS DP155 product type identifier
                 (not a complete product identifier)."
    ::= { xcmPidDocuPrintNPS 9 }
        -- ::= {1.3.6.1.4.1.253.8.62.1.9.9}

xcmPidDP155NPSM1 OBJECT-IDENTITY
    STATUS      current
    DESCRIPTION
        "DocuPrint NPS DP155 launch configuration model identifier
                 (not a complete product identifier)."
    ::= { xcmPidDP155NPS 1 }
        -- ::= {1.3.6.1.4.1.253.8.62.1.9.9.1}
            -- => SAP PID string = "991"

xcmPidDP155NPSM1V1 OBJECT-IDENTITY
    STATUS      current
    DESCRIPTION
        "DocuPrint NPS DP155 launch configuration version,
                 and complete product identifier."
    ::= { xcmPidDP155NPSM1 1 }
        -- ::= {1.3.6.1.4.1.253.8.62.1.9.9.1.1}

-- DocuPrint NPS DP155 Micr Printer

xcmPidDP155NPSMicr OBJECT-IDENTITY
    STATUS      current
    DESCRIPTION
        "DocuPrint NPS DP155 Micr launch configuration model identifier
                 (not a complete product identifier)."
    ::= { xcmPidDP155NPS 2 }
        -- ::= {1.3.6.1.4.1.253.8.62.1.9.9.2}
            -- => SAP PID string = "992"

xcmPidDP155NPSMicrV1 OBJECT-IDENTITY
    STATUS      current
    DESCRIPTION
        "DocuPrint NPS DP155 Micr launch configuration version,
                 and complete product identifier."
    ::= { xcmPidDP155NPSMicr 1 }
        -- ::= {1.3.6.1.4.1.253.8.62.1.9.9.2.1}

-- DocuPrint NPS DP115 Printer

xcmPidDP115NPS OBJECT-IDENTITY
    STATUS      current
    DESCRIPTION
        "DocuPrint NPS DP115 product type identifier
                 (not a complete product identifier)."
    ::= { xcmPidDocuPrintNPS 17 }
        -- ::= {1.3.6.1.4.1.253.8.62.1.9.17}

xcmPidDP115NPSM1 OBJECT-IDENTITY
    STATUS      current
    DESCRIPTION
        "DocuPrint NPS DP115 launch configuration model identifier
                 (not a complete product identifier)."
    ::= { xcmPidDP115NPS 1 }
        -- ::= {1.3.6.1.4.1.253.8.62.1.9.17.1}
            -- => SAP PID string = "9A1"

xcmPidDP115NPSM1V1 OBJECT-IDENTITY
    STATUS      current
    DESCRIPTION
        "DocuPrint NPS DP115 launch configuration version,
                 and complete product identifier."
    ::= { xcmPidDP115NPSM1 1 }
        -- ::= {1.3.6.1.4.1.253.8.62.1.9.17.1.1}

-- DocuPrint NPS DP115 Micr Printer

xcmPidDP115NPSMicr OBJECT-IDENTITY
    STATUS      current
    DESCRIPTION
        "DocuPrint NPS DP115 Micr launch configuration model identifier
                 (not a complete product identifier)."
    ::= { xcmPidDP115NPS 2 }
        -- ::= {1.3.6.1.4.1.253.8.62.1.9.17.2}
            -- => SAP PID string = "9A2"

xcmPidDP115NPSMicrV1 OBJECT-IDENTITY
    STATUS      current
    DESCRIPTION
        "DocuPrint NPS DP115 Micr launch configuration version,
                 and complete product identifier."
    ::= { xcmPidDP115NPSMicr 1 }
        -- ::= {1.3.6.1.4.1.253.8.62.1.9.17.2.1}

-- DocuPrint NPS DP100 Printer

xcmPidDP100NPS OBJECT-IDENTITY
    STATUS      current
    DESCRIPTION
        "DocuPrint NPS DP100 product type identifier
                 (not a complete product identifier)."
    ::= { xcmPidDocuPrintNPS 18 }
        -- ::= {1.3.6.1.4.1.253.8.62.1.9.18}

xcmPidDP100NPSM1 OBJECT-IDENTITY
    STATUS      current
    DESCRIPTION
        "DocuPrint NPS DP100 launch configuration model identifier
                 (not a complete product identifier)."
    ::= { xcmPidDP100NPS 1 }
        -- ::= {1.3.6.1.4.1.253.8.62.1.9.18.1}
            -- => SAP PID string = "9B1"

xcmPidDP100NPSM1V1 OBJECT-IDENTITY
    STATUS      current
    DESCRIPTION
        "DocuPrint NPS DP100 launch configuration version,
                 and complete product identifier."
    ::= { xcmPidDP100NPSM1 1 }
        -- ::= {1.3.6.1.4.1.253.8.62.1.9.18.1.1}

-- DocuPrint NPS DP100 Micr Printer

xcmPidDP100NPSMicr OBJECT-IDENTITY
    STATUS      current
    DESCRIPTION
        "DocuPrint NPS DP100 Micr launch configuration model identifier
                 (not a complete product identifier)."
    ::= { xcmPidDP100NPS 2 }
        -- ::= {1.3.6.1.4.1.253.8.62.1.9.18.2}
            -- => SAP PID string = "9B2"

xcmPidDP100NPSMicrV1 OBJECT-IDENTITY
    STATUS      current
    DESCRIPTION
        "DocuPrint NPS DP100 Micr launch configuration version,
                 and complete product identifier."
    ::= { xcmPidDP100NPSMicr 1 }
        -- ::= {1.3.6.1.4.1.253.8.62.1.9.18.2.1}

-- DocuColor 2045 and 2060 NPS/IPS

xcmPidDC2000FamilyNPS OBJECT-IDENTITY
    STATUS      current
    DESCRIPTION
        "DocuColor 2000 NPS Family product line identifier
                 (not a complete product identifier)."
    ::= { xcmPidDocuPrintNPS 19 }
        -- ::= {1.3.6.1.4.1.253.8.62.1.9.19}

xcmPidDocuColor2045NPS OBJECT-IDENTITY
    STATUS      current
    DESCRIPTION
        "Xerox DocuColor 2045 NPS/IPS product type identifier
                 (not a complete product identifier)."
    ::= { xcmPidDC2000FamilyNPS 1 }
        -- ::= {1.3.6.1.4.1.253.8.62.1.9.19.1}
            -- => SAP PID string = "9C1"

xcmPidDocuColor2045NPSV1 OBJECT-IDENTITY
    STATUS      current
    DESCRIPTION
        "Xerox DocuColor 2045 NPS/IPS launch configuration
                 version, and complete product identifier."
    ::= { xcmPidDocuColor2045NPS 1 }
        -- ::= {1.3.6.1.4.1.253.8.62.1.9.19.1.1}

xcmPidDocuColor2060NPS OBJECT-IDENTITY
    STATUS      current
    DESCRIPTION
        "Xerox DocuColor 2060 NPS/IPS product type identifier
                 (not a complete product identifier)."
    ::= { xcmPidDC2000FamilyNPS 2 }
        -- ::= {1.3.6.1.4.1.253.8.62.1.9.19.2}
            -- => SAP PID string = "9C2"

xcmPidDocuColor2060NPSV1 OBJECT-IDENTITY
    STATUS      current
    DESCRIPTION
        "Xerox DocuColor 2060 NPS/IPS launch configuration
                 version, and complete product identifier."
    ::= { xcmPidDocuColor2060NPS 1 }
        -- ::= {1.3.6.1.4.1.253.8.62.1.9.19.2.1}

xcmPidDocuColor5252NPS OBJECT-IDENTITY
    STATUS      current
    DESCRIPTION
        "Xerox DocuColor 5252 NPS/IPS product type identifier
                 (not a complete product identifier)."
    ::= { xcmPidDC2000FamilyNPS 3 }
        -- ::= {1.3.6.1.4.1.253.8.62.1.9.19.3}
            -- => SAP PID string = "9C3"

xcmPidDocuColor5252NPSV1 OBJECT-IDENTITY
    STATUS      current
    DESCRIPTION
        "Xerox DocuColor 5252 NPS/IPS launch configuration
                 version, and complete product identifier."
    ::= { xcmPidDocuColor5252NPS 1 }
        -- ::= {1.3.6.1.4.1.253.8.62.1.9.19.3.1}

------------------------------------------------------
-- 
-- DocuColor 6000 NPS/IPS Family per Nick Briggs
-- No USB connectivity
------------------------------------------------------

xcmPidDC6000FamilyNPS OBJECT-IDENTITY
    STATUS      current
    DESCRIPTION
        "DocuColor 6000 NPS Family product line identifier
                 (not a complete product identifier)."
    ::= { xcmPidDocuPrintNPS 20 }
        -- ::= {1.3.6.1.4.1.253.8.62.1.9.20}

xcmPidDocuColor6060NPS OBJECT-IDENTITY
    STATUS      current
    DESCRIPTION
        "Xerox DocuColor 6060 NPS/IPS product type identifier
                 (not a complete product identifier)."
    ::= { xcmPidDC6000FamilyNPS 1 }
        -- ::= {1.3.6.1.4.1.253.8.62.1.9.20.1}
            -- => SAP PID string = "9D1"

xcmPidDocuColor6060NPSV1 OBJECT-IDENTITY
    STATUS      current
    DESCRIPTION
        "Xerox DocuColor 6060 NPS/IPS launch configuration
                 version, and complete product identifier."
    ::= { xcmPidDocuColor6060NPS 1 }
        -- ::= {1.3.6.1.4.1.253.8.62.1.9.20.1.1}


--
--

----------------------------------------------------------------
-- DocuPrint EPS Printers
----------------------------------------------------------------

xcmPidDocuPrintEPS OBJECT-IDENTITY
    STATUS      current
    DESCRIPTION
        "DocuPrint EPS product line
                 identifier (not a complete product identifier)."
    ::= { xcmPidProductIdentifiers 18 }
        -- ::= {1.3.6.1.4.1.253.8.62.1.18}

-- DocuPrint DP180 EPS Printer

xcmPidDP180EPS OBJECT-IDENTITY
    STATUS      current           -- actually deprecated
    DESCRIPTION
        "DocuPrint DP180 EPS product type identifier
                 (not a complete product identifier)."
    ::= { xcmPidDocuPrintEPS 1 }
        -- ::= {1.3.6.1.4.1.253.8.62.1.18.1}

xcmPidDP180EPSM1 OBJECT-IDENTITY
    STATUS      current           -- actually deprecated
    DESCRIPTION
        "DocuPrint DP180 EPS launch configuration model identifier
                 (not a complete product identifier)."
    ::= { xcmPidDP180EPS 1 }
        -- ::= {1.3.6.1.4.1.253.8.62.1.18.1.1}
            -- => SAP PID string = "B11"

xcmPidDP180EPSM1V1 OBJECT-IDENTITY
    STATUS      current           -- actually deprecated
    DESCRIPTION
        "DocuPrint DP180 EPS launch configuration version,
                 and complete product identifier."
    ::= { xcmPidDP180EPSM1 1 }
        -- ::= {1.3.6.1.4.1.253.8.62.1.18.1.1.1}

-- DocuPrint 2000 Series EPS Printers

xcmPidDP2000EPS OBJECT-IDENTITY
    STATUS      current
    DESCRIPTION
        "DocuPrint 2000 Series EPS product type identifier
                 (not a complete product identifier)."
    ::= { xcmPidDocuPrintEPS 2 }
        -- ::= {1.3.6.1.4.1.253.8.62.1.18.2}

xcmPidDP2000S100EPS OBJECT-IDENTITY
    STATUS      current
    DESCRIPTION
        "DocuPrint 2000 Series 100 EPS launch configuration
                 model identifier
                 (not a complete product identifier)."
    ::= { xcmPidDP2000EPS 1 }
        -- ::= {1.3.6.1.4.1.253.8.62.1.18.2.1}
            -- => SAP PID string = "B21"

xcmPidDP2000S100EPSV1 OBJECT-IDENTITY
    STATUS      current
    DESCRIPTION
        "DocuPrint 2000 Series 100 EPS launch configuration
                 version and complete product identifier."
    ::= { xcmPidDP2000S100EPS 1 }
        -- ::= {1.3.6.1.4.1.253.8.62.1.18.2.1.1}

xcmPidDP2000S115EPS OBJECT-IDENTITY
    STATUS      current
    DESCRIPTION
        "DocuPrint 2000 Series 115 EPS launch configuration
                 model identifier
                 (not a complete product identifier)."
    ::= { xcmPidDP2000EPS 2 }
        -- ::= {1.3.6.1.4.1.253.8.62.1.18.2.2}
            -- => SAP PID string = "B22"

xcmPidDP2000S115EPSV1 OBJECT-IDENTITY
    STATUS      current
    DESCRIPTION
        "DocuPrint 2000 Series 115 EPS launch configuration
                 version and complete product identifier."
    ::= { xcmPidDP2000S115EPS 1 }
        -- ::= {1.3.6.1.4.1.253.8.62.1.18.2.2.1}

xcmPidDP2000S135EPS OBJECT-IDENTITY
    STATUS      current
    DESCRIPTION
        "DocuPrint 2000 Series 135 EPS launch configuration
                 model identifier
                 (not a complete product identifier)."
    ::= { xcmPidDP2000EPS 3 }
        -- ::= {1.3.6.1.4.1.253.8.62.1.18.2.3}
            -- => SAP PID string = "B23"

xcmPidDP2000S135EPSV1 OBJECT-IDENTITY
    STATUS      current
    DESCRIPTION
        "DocuPrint 2000 Series 135 EPS launch configuration
                 version and complete product identifier."
    ::= { xcmPidDP2000S135EPS 1 }
        -- ::= {1.3.6.1.4.1.253.8.62.1.18.2.3.1}

xcmPidDP2000S155EPS OBJECT-IDENTITY
    STATUS      current
    DESCRIPTION
        "DocuPrint 2000 Series 155 EPS launch configuration
                 model identifier
                 (not a complete product identifier)."
    ::= { xcmPidDP2000EPS 4 }
        -- ::= {1.3.6.1.4.1.253.8.62.1.18.2.4}
            -- => SAP PID string = "B24"

xcmPidDP2000S155EPSV1 OBJECT-IDENTITY
    STATUS      current
    DESCRIPTION
        "DocuPrint 2000 Series 155 EPS launch configuration
                 version and complete product identifier."
    ::= { xcmPidDP2000S155EPS 1 }
        -- ::= {1.3.6.1.4.1.253.8.62.1.18.2.4.1}

xcmPidDP2000S180EPS OBJECT-IDENTITY
    STATUS      current
    DESCRIPTION
        "DocuPrint 2000 Series 180 EPS launch configuration
                 model identifier
                 (not a complete product identifier)."
    ::= { xcmPidDP2000EPS 5 }
        -- ::= {1.3.6.1.4.1.253.8.62.1.18.2.5}
            -- => SAP PID string = "B25"

xcmPidDP2000S180EPSV1 OBJECT-IDENTITY
    STATUS      current
    DESCRIPTION
        "DocuPrint 2000 Series 180 EPS launch configuration
                 version and complete product identifier."
    ::= { xcmPidDP2000S180EPS 1 }
        -- ::= {1.3.6.1.4.1.253.8.62.1.18.2.5.1}

-- DocuPrint 2000 Series EPS MICR Printers

xcmPidDP2000S100EPSMX OBJECT-IDENTITY
    STATUS      current
    DESCRIPTION
        "DocuPrint 2000 Series 100 EPS MX launch configuration
                 model identifier
                 (not a complete product identifier)."
    ::= { xcmPidDP2000EPS 8 }
        -- ::= {1.3.6.1.4.1.253.8.62.1.18.2.8}
            -- => SAP PID string = "B28"

xcmPidDP2000S100EPSMXV1 OBJECT-IDENTITY
    STATUS      current
    DESCRIPTION
        "DocuPrint 2000 Series 100 EPS MX launch configuration
                 version and complete product identifier."
    ::= { xcmPidDP2000S100EPSMX 1 }
        -- ::= {1.3.6.1.4.1.253.8.62.1.18.2.8.1}

xcmPidDP2000S115EPSMX OBJECT-IDENTITY
    STATUS      current
    DESCRIPTION
        "DocuPrint 2000 Series 115 EPS MX launch configuration
                 model identifier
                 (not a complete product identifier)."
    ::= { xcmPidDP2000EPS 9 }
        -- ::= {1.3.6.1.4.1.253.8.62.1.18.2.9}
            -- => SAP PID string = "B29"

xcmPidDP2000S115EPSMXV1 OBJECT-IDENTITY
    STATUS      current
    DESCRIPTION
        "DocuPrint 2000 Series 115 EPS MX launch configuration
                 version and complete product identifier."
    ::= { xcmPidDP2000S115EPSMX 1 }
        -- ::= {1.3.6.1.4.1.253.8.62.1.18.2.9.1}

xcmPidDP2000S135EPSMX OBJECT-IDENTITY
    STATUS      current
    DESCRIPTION
        "DocuPrint 2000 Series 135 EPS MX launch configuration
                 model identifier
                 (not a complete product identifier)."
    ::= { xcmPidDP2000EPS 17 }
        -- ::= {1.3.6.1.4.1.253.8.62.1.18.2.17}
            -- => SAP PID string = "B2A"

xcmPidDP2000S135EPSMXV1 OBJECT-IDENTITY
    STATUS      current
    DESCRIPTION
        "DocuPrint 2000 Series 135 EPS MX launch configuration
                 version and complete product identifier."
    ::= { xcmPidDP2000S135EPSMX 1 }
        -- ::= {1.3.6.1.4.1.253.8.62.1.18.2.17.1}

xcmPidDP2000S155EPSMX OBJECT-IDENTITY
    STATUS      current
    DESCRIPTION
        "DocuPrint 2000 Series 155 EPS MX launch configuration
                 model identifier
                 (not a complete product identifier)."
    ::= { xcmPidDP2000EPS 18 }
        -- ::= {1.3.6.1.4.1.253.8.62.1.18.2.18}
            -- => SAP PID string = "B2B"

xcmPidDP2000S155EPSMXV1 OBJECT-IDENTITY
    STATUS      current
    DESCRIPTION
        "DocuPrint 2000 Series 155 EPS MX launch configuration
                 version and complete product identifier."
    ::= { xcmPidDP2000S155EPSMX 1 }
        -- ::= {1.3.6.1.4.1.253.8.62.1.18.2.18.1}

xcmPidDP2000S180EPSMX OBJECT-IDENTITY
    STATUS      current
    DESCRIPTION
        "DocuPrint 2000 Series 180 EPS MX launch configuration
                 model identifier
                 (not a complete product identifier)."
    ::= { xcmPidDP2000EPS 19 }
        -- ::= {1.3.6.1.4.1.253.8.62.1.18.2.19}
            -- => SAP PID string = "B2C"

xcmPidDP2000S180EPSMXV1 OBJECT-IDENTITY
    STATUS      current
    DESCRIPTION
        "DocuPrint 2000 Series 180 EPS MX launch configuration
                 version and complete product identifier."
    ::= { xcmPidDP2000S180EPSMX 1 }
        -- ::= {1.3.6.1.4.1.253.8.62.1.18.2.19.1}

-- DocuPrint 6075

xcmPidDP2000S6075 OBJECT-IDENTITY
    STATUS      current
    DESCRIPTION
        "DocuPrint 6075 launch configuration model identifier
                 (not a complete product identifier)."
    ::= { xcmPidDP2000EPS 6 }
        -- ::= {1.3.6.1.4.1.253.8.62.1.18.2.6}
            -- => SAP PID string = "B26"

xcmPidDP2000S6075V1 OBJECT-IDENTITY
    STATUS      current
    DESCRIPTION
        "DocuPrint 6075 launch configuration
                 version and complete product identifier."
    ::= { xcmPidDP2000S6075 1 }
        -- ::= {1.3.6.1.4.1.253.8.62.1.18.2.6.1}

-- DocuPrint 6090

xcmPidDP2000S6090 OBJECT-IDENTITY
    STATUS      current
    DESCRIPTION
        "DocuPrint 6090 launch configuration model identifier
                 (not a complete product identifier)."
    ::= { xcmPidDP2000EPS 7 }
        -- ::= {1.3.6.1.4.1.253.8.62.1.18.2.7}
            -- => SAP PID string = "B27"

xcmPidDP2000S6090V1 OBJECT-IDENTITY
    STATUS      current
    DESCRIPTION
        "DocuPrint 6090 launch configuration
                 version and complete product identifier."
    ::= { xcmPidDP2000S6090 1 }
        -- ::= {1.3.6.1.4.1.253.8.62.1.18.2.7.1}

-- DocuPrint DP180 Micr EPS Printer

xcmPidDP180EPSMicr OBJECT-IDENTITY
    STATUS      current           -- actually deprecated
    DESCRIPTION
        "DocuPrint DP180 Micr EPS launch configuration model identifier
                 (not a complete product identifier)."
    ::= { xcmPidDP180EPS 2 }
        -- ::= {1.3.6.1.4.1.253.8.62.1.18.1.2}
            -- => SAP PID string = "B12"

xcmPidDP180EPSMicrV1 OBJECT-IDENTITY
    STATUS      current           -- actually deprecated
    DESCRIPTION
        "DocuPrint DP180 Micr EPS launch configuration version,
                 and complete product identifier."
    ::= { xcmPidDP180EPSMicr 1 }
        -- ::= {1.3.6.1.4.1.253.8.62.1.18.1.2.1}

--
--

----------------------------------------------------------------
-- DocuTechs
----------------------------------------------------------------

xcmPidDocuTechs OBJECT-IDENTITY
    STATUS      current
    DESCRIPTION
        "DocuTech product line identifier
                 (not a complete product identifier)."
    ::= { xcmPidProductIdentifiers 5 }
        -- ::= {1.3.6.1.4.1.253.8.62.1.5}


--
--

-- DocuTech 6100 (DocuSP 6100)

xcmPidDocuTech6100 OBJECT-IDENTITY
    STATUS      current
    DESCRIPTION
        "DocuTech 6100 product type identifier
                 (not a complete product identifier)."
    ::= { xcmPidDocuTechs 4 }
        -- ::= {1.3.6.1.4.1.253.8.62.1.5.4}

xcmPidDocuTech6100M1 OBJECT-IDENTITY
    STATUS      current
    DESCRIPTION
        "DocuTech 6100 launch configuration model identifier
                 (not a complete product identifier)."
    ::= { xcmPidDocuTech6100 1 }
        -- ::= {1.3.6.1.4.1.253.8.62.1.5.4.1}
            -- => SAP PID string = "541"

xcmPidDocuTech6100M1V1 OBJECT-IDENTITY
    STATUS      current
    DESCRIPTION
        "DocuTech 6100 launch configuration version,
                 and complete product identifier."
    ::= { xcmPidDocuTech6100M1 1 }
        -- ::= {1.3.6.1.4.1.253.8.62.1.5.4.1.1}

xcmPidDocuTech6100M1V2 OBJECT-IDENTITY
    STATUS      current
    DESCRIPTION
        "DocuTech 6100 launch configuration version,
                 and complete product identifier."
    ::= { xcmPidDocuTech6100M1 2 }
        -- ::= {1.3.6.1.4.1.253.8.62.1.5.4.1.2}

-- DocuTech 6115 (DocuSP 6115)

xcmPidDocuTech6115 OBJECT-IDENTITY
    STATUS      current
    DESCRIPTION
        "DocuTech 6115 product type identifier
                 (not a complete product identifier)."
    ::= { xcmPidDocuTechs 5 }
        -- ::= {1.3.6.1.4.1.253.8.62.1.5.5}

xcmPidDocuTech6115M1 OBJECT-IDENTITY
    STATUS      current
    DESCRIPTION
        "DocuTech 6115 launch configuration model identifier
                 (not a complete product identifier)."
    ::= { xcmPidDocuTech6115 1 }
        -- ::= {1.3.6.1.4.1.253.8.62.1.5.5.1}
            -- => SAP PID string = "551"

xcmPidDocuTech6115M1V1 OBJECT-IDENTITY
    STATUS      current
    DESCRIPTION
        "DocuTech 6115 launch configuration version,
                 and complete product identifier."
    ::= { xcmPidDocuTech6115M1 1 }
        -- ::= {1.3.6.1.4.1.253.8.62.1.5.5.1.1}

xcmPidDocuTech6115M1V2 OBJECT-IDENTITY
    STATUS      current
    DESCRIPTION
        "DocuTech 6115 launch configuration version,
                 and complete product identifier."
    ::= { xcmPidDocuTech6115M1 2 }
        -- ::= {1.3.6.1.4.1.253.8.62.1.5.5.1.2}

-- DocuTech 6135 (DocuSP 6135)

xcmPidDocuTech6135 OBJECT-IDENTITY
    STATUS      current
    DESCRIPTION
        "DocuTech 6135 product type identifier
                 (not a complete product identifier)."
    ::= { xcmPidDocuTechs 2 }
        -- ::= {1.3.6.1.4.1.253.8.62.1.5.2}

xcmPidDocuTech6135M1 OBJECT-IDENTITY
    STATUS      current
    DESCRIPTION
        "DocuTech 6135 launch configuration model identifier
                 (not a complete product identifier)."
    ::= { xcmPidDocuTech6135 1 }
        -- ::= {1.3.6.1.4.1.253.8.62.1.5.2.1}
            -- => SAP PID string = "521"

xcmPidDocuTech6135M1V1 OBJECT-IDENTITY
    STATUS      current
    DESCRIPTION
        "DocuTech 6135 launch configuration version,
                 and complete product identifier."
    ::= { xcmPidDocuTech6135M1 1 }
        -- ::= {1.3.6.1.4.1.253.8.62.1.5.2.1.1}

xcmPidDocuTech6135M1V2 OBJECT-IDENTITY
    STATUS      current
    DESCRIPTION
        "DocuTech 6135 launch configuration version,
                 and complete product identifier."
    ::= { xcmPidDocuTech6135M1 2 }
        -- ::= {1.3.6.1.4.1.253.8.62.1.5.2.1.2}

-- DocuTech 6155 (DocuSP 6155)

xcmPidDocuTech6155 OBJECT-IDENTITY
    STATUS      current
    DESCRIPTION
        "DocuTech 6155 product type identifier
                 (not a complete product identifier)."
    ::= { xcmPidDocuTechs 6 }
        -- ::= {1.3.6.1.4.1.253.8.62.1.5.6}

xcmPidDocuTech6155M1 OBJECT-IDENTITY
    STATUS      current
    DESCRIPTION
        "DocuTech 6155 launch configuration model identifier
                 (not a complete product identifier)."
    ::= { xcmPidDocuTech6155 1 }
        -- ::= {1.3.6.1.4.1.253.8.62.1.5.6.1}
            -- => SAP PID string = "561"

xcmPidDocuTech6155M1V1 OBJECT-IDENTITY
    STATUS      current
    DESCRIPTION
        "DocuTech 6155 launch configuration version,
                 and complete product identifier."
    ::= { xcmPidDocuTech6155M1 1 }
        -- ::= {1.3.6.1.4.1.253.8.62.1.5.6.1.1}

xcmPidDocuTech6155M1V2 OBJECT-IDENTITY
    STATUS      current
    DESCRIPTION
        "DocuTech 6155 launch configuration version,
                 and complete product identifier."
    ::= { xcmPidDocuTech6155M1 2 }
        -- ::= {1.3.6.1.4.1.253.8.62.1.5.6.1.2}

-- DocuTech 6180 (DocuSP 6180)


xcmPidDocuTech6180 OBJECT-IDENTITY
    STATUS      current
    DESCRIPTION
        "DocuTech 6180 product type identifier
                 (not a complete product identifier)."
    ::= { xcmPidDocuTechs 3 }
        -- ::= {1.3.6.1.4.1.253.8.62.1.5.3}

xcmPidDocuTech6180M1 OBJECT-IDENTITY
    STATUS      current
    DESCRIPTION
        "DocuTech 6180 launch configuration model identifier
                 (not a complete product identifier)."
    ::= { xcmPidDocuTech6180 1 }
        -- ::= {1.3.6.1.4.1.253.8.62.1.5.3.1}
            -- => SAP PID string = "531"

xcmPidDocuTech6180M1V1 OBJECT-IDENTITY
    STATUS      current
    DESCRIPTION
        "DocuTech 6180 launch configuration version,
                 and complete product identifier."
    ::= { xcmPidDocuTech6180M1 1 }
        -- ::= {1.3.6.1.4.1.253.8.62.1.5.3.1.1}

xcmPidDocuTech6180M1V2 OBJECT-IDENTITY
    STATUS      current
    DESCRIPTION
        "DocuTech 6180 launch configuration version,
                 and complete product identifier."
    ::= { xcmPidDocuTech6180M1 2 }
        -- ::= {1.3.6.1.4.1.253.8.62.1.5.3.1.2}

-- DocuTech 6075 (DocuSP 6075)

xcmPidDocuTech6075 OBJECT-IDENTITY
    STATUS      current
    DESCRIPTION
        "DocuTech 6075 product type identifier
                 (not a complete product identifier)."
    ::= { xcmPidDocuTechs 7 }
        -- ::= {1.3.6.1.4.1.253.8.62.1.5.7}

xcmPidDocuTech6075M1 OBJECT-IDENTITY
    STATUS      current
    DESCRIPTION
        "DocuTech 6075 launch configuration model identifier
                 (not a complete product identifier)."
    ::= { xcmPidDocuTech6075 1 }
        -- ::= {1.3.6.1.4.1.253.8.62.1.5.7.1}
            -- => SAP PID string = "571"

xcmPidDocuTech6075M1V1 OBJECT-IDENTITY
    STATUS      current
    DESCRIPTION
        "DocuTech 6075 launch configuration version,
                 and complete product identifier."
    ::= { xcmPidDocuTech6075M1 1 }
        -- ::= {1.3.6.1.4.1.253.8.62.1.5.7.1.1}

-- DocuTech 6090 (DocuSP 6090)

xcmPidDocuTech6090 OBJECT-IDENTITY
    STATUS      current
    DESCRIPTION
        "DocuTech 6090 product type identifier
                 (not a complete product identifier)."
    ::= { xcmPidDocuTechs 8 }
        -- ::= {1.3.6.1.4.1.253.8.62.1.5.8}

xcmPidDocuTech6090M1 OBJECT-IDENTITY
    STATUS      current
    DESCRIPTION
        "DocuTech 6090 launch configuration model identifier
                 (not a complete product identifier)."
    ::= { xcmPidDocuTech6090 1 }
        -- ::= {1.3.6.1.4.1.253.8.62.1.5.8.1}
            -- => SAP PID string = "581"

xcmPidDocuTech6090M1V1 OBJECT-IDENTITY
    STATUS      current
    DESCRIPTION
        "DocuTech 6090 launch configuration version,
                 and complete product identifier."
    ::= { xcmPidDocuTech6090M1 1 }
        -- ::= {1.3.6.1.4.1.253.8.62.1.5.8.1.1}

--
--


--
--

xcmPidXeroxDocuWide OBJECT-IDENTITY
    STATUS      current
    DESCRIPTION
        "Xerox DocuWide Printers product line identifier
                 (not a complete product identifier)."
    ::= { xcmPidProductIdentifiers 22 }
        -- ::= {1.3.6.1.4.1.253.8.62.1.22}

--
--

--
--

END


--
