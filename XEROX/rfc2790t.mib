HOST-RESOURCES-TYPES DEFINITIONS ::= BEGIN
--  Module: Compilable IETF Host Resources Types - XCMI Version 5.00
--  Editor: Ira McDonald
--  File:   rfc2790t.mv1 (SMIv1 version)
--  Date:   27 November 2001

--
--  Change Log for this corrected compilable version
--
--  - Changed LAST-UPDATED and REVISIONS clauses in MODULE-COMPLIANCE
--    macro to use 2-digit years instead of 4-digit years
--    (for compatibility with many compilers)

IMPORTS
-- MODULE-IDENTITY, OBJECT-IDENTITY        FROM SNMPv2-SMI
-- hrMIBAdminInfo, hrStorage, hrDevice     FROM HOST-RESOURCES-MIB/
    hrMIBAdminInfo,
    hrStorage,
    hrDevice
        FROM    HOST-RESOURCES-MIB
    ;

hostResourcesTypesModule OBJECT IDENTIFIER
-- LAST-UPDATED "200003060000Z"    -  6 March, 2000
-- LAST-UPDATED "0003060000Z"      -  6 March, 2000 (compatibility form)
-- ORGANIZATION "IETF Host Resources MIB Working Group"
-- CONTACT-INFO
--     "Steve Waldbusser
--     Postal: Lucent Technologies, Inc.
--             1213 Innsbruck Dr.
--             Sunnyvale, CA 94089
--             USA
--     Phone: 650-318-1251
--     Fax:   650-318-1633
--     Email: waldbusser@ins.com
--
--     In addition, the Host Resources MIB mailing list is dedicated
--     to discussion of this MIB. To join the mailing list, send a
--     request message to hostmib-request@andrew.cmu.edu. The mailing
--     list address is hostmib@andrew.cmu.edu."
-- DESCRIPTION
--     "This MIB module registers type definitions for
--     storage types, device types, and file system types.
--
--     After the initial revision, this module will be
--     maintained by IANA."
-- REVISION "200003060000Z"    -  6 March 2000
-- REVISION "0003060000Z"      -  6 March 2000 (compatibility form)
-- DESCRIPTION
--     "The original version of this module, published as RFC
--     2790."
   ::= { hrMIBAdminInfo 4 }

-- Registrations for some storage types, for use with hrStorageType
hrStorageTypes          OBJECT IDENTIFIER ::= { hrStorage 1 }

hrStorageOther OBJECT IDENTIFIER
--  STATUS current
--  DESCRIPTION
--      "The storage type identifier used when no other defined
--      type is appropriate."
    ::= { hrStorageTypes 1 }

hrStorageRam OBJECT IDENTIFIER
--  STATUS current
--  DESCRIPTION
--      "The storage type identifier used for RAM."
    ::= { hrStorageTypes 2 }

hrStorageVirtualMemory OBJECT IDENTIFIER
--  STATUS current
--  DESCRIPTION
--      "The storage type identifier used for virtual memory,
--      temporary storage of swapped or paged memory."
    ::= { hrStorageTypes 3 }

hrStorageFixedDisk OBJECT IDENTIFIER
--  STATUS current
--  DESCRIPTION
--      "The storage type identifier used for non-removable
--      rigid rotating magnetic storage devices."
    ::= { hrStorageTypes 4 }

hrStorageRemovableDisk OBJECT IDENTIFIER
--  STATUS current
--  DESCRIPTION
--      "The storage type identifier used for removable rigid
--      rotating magnetic storage devices."
    ::= { hrStorageTypes 5 }

hrStorageFloppyDisk OBJECT IDENTIFIER
--  STATUS current
--  DESCRIPTION
--      "The storage type identifier used for non-rigid rotating
--      magnetic storage devices."
    ::= { hrStorageTypes 6 }

hrStorageCompactDisc OBJECT IDENTIFIER
--  STATUS current
--  DESCRIPTION
--      "The storage type identifier used for read-only rotating
--      optical storage devices."
    ::= { hrStorageTypes 7 }

hrStorageRamDisk OBJECT IDENTIFIER
--  STATUS current
--  DESCRIPTION
--      "The storage type identifier used for a file system that
--      is stored in RAM."
    ::= { hrStorageTypes 8 }

hrStorageFlashMemory OBJECT IDENTIFIER
--  STATUS current
--  DESCRIPTION
--      "The storage type identifier used for flash memory."
    ::= { hrStorageTypes 9 }

hrStorageNetworkDisk OBJECT IDENTIFIER
--  STATUS current
--  DESCRIPTION
--      "The storage type identifier used for a
--      networked file system."
    ::= { hrStorageTypes 10 }

-- Registrations for some device types, for use with hrDeviceType
hrDeviceTypes             OBJECT IDENTIFIER ::= { hrDevice 1 }

hrDeviceOther OBJECT IDENTIFIER
--  STATUS current
--  DESCRIPTION
--      "The device type identifier used when no other defined
--      type is appropriate."
    ::= { hrDeviceTypes 1 }

hrDeviceUnknown OBJECT IDENTIFIER
--  STATUS current
--  DESCRIPTION
--      "The device type identifier used when the device type is
--      unknown."
    ::= { hrDeviceTypes 2 }

hrDeviceProcessor OBJECT IDENTIFIER
--  STATUS current
--  DESCRIPTION
--      "The device type identifier used for a CPU."
    ::= { hrDeviceTypes 3 }

hrDeviceNetwork OBJECT IDENTIFIER
--  STATUS current
--  DESCRIPTION
--      "The device type identifier used for a network interface."
    ::= { hrDeviceTypes 4 }

hrDevicePrinter OBJECT IDENTIFIER
--  STATUS current
--  DESCRIPTION
--      "The device type identifier used for a printer."
    ::= { hrDeviceTypes 5 }

hrDeviceDiskStorage OBJECT IDENTIFIER
--  STATUS current
--  DESCRIPTION
--      "The device type identifier used for a disk drive."
    ::= { hrDeviceTypes 6 }

hrDeviceVideo OBJECT IDENTIFIER
--  STATUS current
--  DESCRIPTION
--      "The device type identifier used for a video device."
    ::= { hrDeviceTypes 10 }

hrDeviceAudio OBJECT IDENTIFIER
--  STATUS current
--  DESCRIPTION
--      "The device type identifier used for an audio device."
    ::= { hrDeviceTypes 11 }

hrDeviceCoprocessor OBJECT IDENTIFIER
--  STATUS current
--  DESCRIPTION
--      "The device type identifier used for a co-processor."
    ::= { hrDeviceTypes 12 }

hrDeviceKeyboard OBJECT IDENTIFIER
--  STATUS current
--  DESCRIPTION
--      "The device type identifier used for a keyboard device."
    ::= { hrDeviceTypes 13 }

hrDeviceModem OBJECT IDENTIFIER
--  STATUS current
--  DESCRIPTION
--      "The device type identifier used for a modem."
    ::= { hrDeviceTypes 14 }

hrDeviceParallelPort OBJECT IDENTIFIER
--  STATUS current
--  DESCRIPTION
--      "The device type identifier used for a parallel port."
    ::= { hrDeviceTypes 15 }

hrDevicePointing OBJECT IDENTIFIER
--  STATUS current
--  DESCRIPTION
--      "The device type identifier used for a pointing device
--      (e.g., a mouse)."
    ::= { hrDeviceTypes 16 }

hrDeviceSerialPort OBJECT IDENTIFIER
--  STATUS current
--  DESCRIPTION
--      "The device type identifier used for a serial port."
    ::= { hrDeviceTypes 17 }

hrDeviceTape OBJECT IDENTIFIER
--  STATUS current
--  DESCRIPTION
--      "The device type identifier used for a tape storage device."
    ::= { hrDeviceTypes 18 }

hrDeviceClock OBJECT IDENTIFIER
--  STATUS current
--  DESCRIPTION
--      "The device type identifier used for a clock device."
    ::= { hrDeviceTypes 19 }

hrDeviceVolatileMemory OBJECT IDENTIFIER
--  STATUS current
--  DESCRIPTION
--      "The device type identifier used for a volatile memory
--      storage device."
    ::= { hrDeviceTypes 20 }

hrDeviceNonVolatileMemory OBJECT IDENTIFIER
--  STATUS current
--  DESCRIPTION
--      "The device type identifier used for a non-volatile memory
--      storage device."
    ::= { hrDeviceTypes 21 }

-- Registrations for some popular File System types,
-- for use with hrFSType.
hrFSTypes               OBJECT IDENTIFIER ::= { hrDevice 9 }

hrFSOther OBJECT IDENTIFIER
--  STATUS  current
--  DESCRIPTION
--      "The file system type identifier used when no other
--      defined type is appropriate."
    ::= { hrFSTypes 1 }

hrFSUnknown OBJECT IDENTIFIER
--  STATUS  current
--  DESCRIPTION
--      "The file system type identifier used when the type of
--      file system is unknown."
    ::= { hrFSTypes 2 }

hrFSBerkeleyFFS OBJECT IDENTIFIER
--  STATUS  current
--  DESCRIPTION
--      "The file system type identifier used for the
--      Berkeley Fast File System."
    ::= { hrFSTypes 3 }

hrFSSys5FS OBJECT IDENTIFIER
--  STATUS  current
--  DESCRIPTION
--      "The file system type identifier used for the
--      System V File System."
    ::= { hrFSTypes 4 }

hrFSFat OBJECT IDENTIFIER
--  STATUS  current
--  DESCRIPTION
--      "The file system type identifier used for
--      DOS's FAT file system."
    ::= { hrFSTypes 5 }

hrFSHPFS OBJECT IDENTIFIER
--  STATUS  current
--  DESCRIPTION
--      "The file system type identifier used for OS/2's
--      High Performance File System."
    ::= { hrFSTypes 6 }

hrFSHFS OBJECT IDENTIFIER
--  STATUS  current
--  DESCRIPTION
--      "The file system type identifier used for the
--      Macintosh Hierarchical File System."
    ::= { hrFSTypes 7 }

hrFSMFS OBJECT IDENTIFIER
--  STATUS  current
--  DESCRIPTION
--      "The file system type identifier used for the
--      Macintosh File System."
    ::= { hrFSTypes 8 }

hrFSNTFS OBJECT IDENTIFIER
--  STATUS  current
--  DESCRIPTION
--      "The file system type identifier used for the
--      Windows NT File System."
    ::= { hrFSTypes 9 }

hrFSVNode OBJECT IDENTIFIER
--  STATUS  current
--  DESCRIPTION
--      "The file system type identifier used for the
--      VNode File System."
    ::= { hrFSTypes 10 }

hrFSJournaled OBJECT IDENTIFIER
--  STATUS  current
--  DESCRIPTION
--      "The file system type identifier used for the
--      Journaled File System."
    ::= { hrFSTypes 11 }

hrFSiso9660 OBJECT IDENTIFIER
--  STATUS  current
--  DESCRIPTION
--      "The file system type identifier used for the
--      ISO 9660 File System for CD's."
    ::= { hrFSTypes 12 }

hrFSRockRidge OBJECT IDENTIFIER
--  STATUS  current
--  DESCRIPTION
--      "The file system type identifier used for the
--      RockRidge File System for CD's."
    ::= { hrFSTypes 13 }

hrFSNFS OBJECT IDENTIFIER
--  STATUS  current
--  DESCRIPTION
--      "The file system type identifier used for the
--      NFS File System."
    ::= { hrFSTypes 14 }

hrFSNetware OBJECT IDENTIFIER
--  STATUS  current
--  DESCRIPTION
--      "The file system type identifier used for the
--      Netware File System."
    ::= { hrFSTypes 15 }

hrFSAFS OBJECT IDENTIFIER
--  STATUS  current
--  DESCRIPTION
--      "The file system type identifier used for the
--      Andrew File System."
    ::= { hrFSTypes 16 }

hrFSDFS OBJECT IDENTIFIER
--  STATUS  current
--  DESCRIPTION
--      "The file system type identifier used for the
--      OSF DCE Distributed File System."
    ::= { hrFSTypes 17 }

hrFSAppleshare OBJECT IDENTIFIER
--  STATUS  current
--  DESCRIPTION
--      "The file system type identifier used for the
--      AppleShare File System."
    ::= { hrFSTypes 18 }

hrFSRFS OBJECT IDENTIFIER
--  STATUS  current
--  DESCRIPTION
--      "The file system type identifier used for the
--      RFS File System."
    ::= { hrFSTypes 19 }

hrFSDGCFS OBJECT IDENTIFIER
--  STATUS  current
--  DESCRIPTION
--      "The file system type identifier used for the
--      Data General DGCFS."
    ::= { hrFSTypes 20 }

hrFSBFS OBJECT IDENTIFIER
--  STATUS  current
--  DESCRIPTION
--      "The file system type identifier used for the
--      SVR4 Boot File System."
    ::= { hrFSTypes 21 }

hrFSFAT32 OBJECT IDENTIFIER
--  STATUS  current
--  DESCRIPTION
--      "The file system type identifier used for the
--      Windows FAT32 File System."
    ::= { hrFSTypes 22 }

hrFSLinuxExt2 OBJECT IDENTIFIER
--  STATUS  current
--  DESCRIPTION
--      "The file system type identifier used for the
--      Linux EXT2 File System."
    ::= { hrFSTypes 23 }

END
