--  ZXR10-DHCP-SNOOPING-MIB.mib: ZXR10 DHCP snooping MIB file
--  
--  Dec. 2005,
--   
--  Copyright(c) 2005 by ZTE Corporation
--  All rights reserved
--
--  ************************************************

ZXR10-DHCPSNOOPING-MIB DEFINITIONS ::=BEGIN

IMPORTS
    MODULE-IDENTITY,
    OBJECT-TYPE, Integer32,Unsigned32  FROM SNMPv2-SMI
    MacAddress, DisplayString  FROM SNMPv2-TC
    IpAddress   FROM RFC1213-MIB        
    enterprises FROM SNMPv2-SMI;
                     
    zxr10dhcpv4Snooping MODULE-IDENTITY
        LAST-UPDATED "201812121400Z"  
        ORGANIZATION "ZTE Corporation"
        CONTACT-INFO
        "       Xiao Nian kun
         Tel : +86-25-52870000        
         E-Mail: xiao.niankun@zte.com.cn
         "
        DESCRIPTION
            "The MIB module to describe the DHCP Snooping protocol."  
            
        REVISION  "201812121400Z"   
            DESCRIPTION     
            "Modify: Add enumeration value of node dhcpv4SnoopingOptionpolicy 
             and dhcpv4SnoopingIfOptPolicy."
            
        REVISION  "201808161000Z"   
        DESCRIPTION     
            "Add enumeration value of node dhcpv4SnoopingOptionFormat, 
             dhcpv4SnoopingIfOptFormat and dhcpv4SnoopingIfOptPolicy, 
             modify enumeration definition of node
             dhcpv4SnoopingOptionUserCfgPolicy, dhcpv4SnoopingOptionFormat,
             dhcpv4SnoopingIfTrustStatus and dhcpv4SnoopingIfOptFormat."
        ::= { zxr10switch 33}

    zte OBJECT IDENTIFIER   ::= { enterprises 3902 }
    zxr10 OBJECT IDENTIFIER ::= { zte 3}

    zxr10switch OBJECT IDENTIFIER ::= { zxr10 102} 

-- global parameters 
dhcpv4Snoopingglobalstate   OBJECT-TYPE  
        SYNTAX   INTEGER{enable(1),disable(0)}
        MAX-ACCESS  read-only
        STATUS  current
        DESCRIPTION
            "Function of DHCPv4 snooping is available,
             enable: receive the DHCPv4 packets,
             disable: discard the DHCPv4 packets."
        ::= { zxr10dhcpv4Snooping 1 }    
 
-- global maxuser 
         
dhcpv4Snoopingglobalmaxuser   OBJECT-TYPE  
        SYNTAX   Integer32
        MAX-ACCESS  read-only
        STATUS  current
        DESCRIPTION
            "The maximum user of the switch, it ranges from 1 to 2048."
        ::= { zxr10dhcpv4Snooping 2 }  
 -- global ramble   
dhcpv4Snoopingglobalramblestate   OBJECT-TYPE  
        SYNTAX   INTEGER{enable(1),disable(0)}
        MAX-ACCESS  read-only
        STATUS  current
        DESCRIPTION
            "Function of ramble is opened or not."
        ::= { zxr10dhcpv4Snooping 3 }
-- global mac verify 
dhcpv4SnoopingglobalmacVerifystate   OBJECT-TYPE  
        SYNTAX   INTEGER{enable(1),disable(0)}
        MAX-ACCESS  read-only
        STATUS  current
        DESCRIPTION
            "Function of MAC-verify is opened or not."
        ::= { zxr10dhcpv4Snooping 4 }    
        
-- dhcpv4 option parameters      


dhcpv4SnoopingOptionFormat  OBJECT-TYPE
    SYNTAX     INTEGER {
                          chinaTel(1),
                          dslForum(2),
                          telenor(3),
                          userCfg(4),
                          cisco(5),
                          chinaUni(6)
                       }    
    MAX-ACCESS read-only
    STATUS     current
    DESCRIPTION
           "The option82 format."
    ::= { zxr10dhcpv4Snooping 5 }

dhcpv4SnoopingOptionstate OBJECT-TYPE
    SYNTAX INTEGER { 
                     disable(0),
                     enable(1)
                   }
    MAX-ACCESS read-only
    STATUS     current
    DESCRIPTION
           "Whether the option82 is enable or not."
    ::= { zxr10dhcpv4Snooping 6 }


dhcpv4SnoopingOptionpolicy OBJECT-TYPE
    SYNTAX     INTEGER  {                          
                          keep(2),
                          replace(3),
                          stripping(4)
                        }
    MAX-ACCESS read-only
    STATUS     current
    DESCRIPTION
           "Whether the content of the option82 should be replaced or stripped by switch."
    ::= { zxr10dhcpv4Snooping 7 }

dhcpv4SnoopingOptionRemoteId OBJECT-TYPE
    SYNTAX     DisplayString
    MAX-ACCESS read-only
    STATUS     current
    DESCRIPTION
        "The string of the remote-id."
    ::= { zxr10dhcpv4Snooping 8 }
   
dhcpv4SnoopingOptionCircuitId OBJECT-TYPE   
    SYNTAX     DisplayString 
    MAX-ACCESS read-only
    STATUS     current
    DESCRIPTION
        "The string of the circuit-id."
    ::= { zxr10dhcpv4Snooping 9 }
                                         
dhcpv4SnoopingOptionAccessNodeId OBJECT-TYPE   
    SYNTAX     DisplayString 
    MAX-ACCESS read-only
    STATUS     current
    DESCRIPTION
        "The string of access-node-identifier."
    ::= { zxr10dhcpv4Snooping 10 }
                                         
dhcpv4SnoopingOptionUserCfgPolicy  OBJECT-TYPE
    SYNTAX     INTEGER {
                          interface(1),
                          global(2),
                          vlan(3)
                       }    
    MAX-ACCESS read-only
    STATUS     current
    DESCRIPTION
           "The policy of user-cfg includes 3 types of way which are based on 
            interface, global, VLAN."
    ::= { zxr10dhcpv4Snooping 11 }
    
dhcpv4SnoopingOptionCurrentUserNum  OBJECT-TYPE
    SYNTAX     Integer32    
    MAX-ACCESS read-only
    STATUS     current
    DESCRIPTION
           "The current number of user who is online."
    ::= { zxr10dhcpv4Snooping 12 }        
 
-- dhcpv4 file parameters 
dhcpv4Snoopingglobalfiletimeout  OBJECT-TYPE
    SYNTAX     Integer32    
    MAX-ACCESS read-only
    STATUS     current
    DESCRIPTION
           "This object indicates the time interval at which DHCP bindings 
            information will be written to the flash."
    ::= { zxr10dhcpv4Snooping 18 } 
    
dhcpv4Snoopingglobalfileupload  OBJECT-TYPE
    SYNTAX     Integer32    
    MAX-ACCESS read-only
    STATUS     current
    DESCRIPTION
           "This object indicates the time interval at which DHCP bindings 
            information will be written to the database file denoted by 
            cdsDatabaseFile object."
    ::= { zxr10dhcpv4Snooping 19 }     

 
-- dhcpv4 vlan parameters 

dhcpv4SnoopingGlobalVlanTable OBJECT-TYPE
    SYNTAX     SEQUENCE OF Dhcpv4SnoopingGlobalVlanEntry 
    MAX-ACCESS not-accessible
    STATUS     current
    DESCRIPTION
           "The table includes DHCPv4 snooping parameters of option."
    ::= { zxr10dhcpv4Snooping 13 }

dhcpv4SnoopingGlobalVlanEntry OBJECT-TYPE
    SYNTAX     Dhcpv4SnoopingGlobalVlanEntry
    MAX-ACCESS not-accessible
    STATUS     current
    DESCRIPTION
           "An entry includes DHCPv4 snooping parameters of option."
    INDEX { dhcpv4SnoopingVlanId }
    ::= { dhcpv4SnoopingGlobalVlanTable 1 }

Dhcpv4SnoopingGlobalVlanEntry ::=
    SEQUENCE {        
               dhcpv4SnoopingVlanId         Unsigned32,
               dhcpv4SnoopingVlanState      INTEGER,  
               dhcpv4SnoopingVlanRemoteId   DisplayString,
               dhcpv4SnoopingVlanCircuitId  DisplayString
             }    
    
dhcpv4SnoopingVlanId  OBJECT-TYPE
    SYNTAX     Unsigned32   
    MAX-ACCESS read-only
    STATUS     current
    DESCRIPTION
           "VLAN ID."
    ::= { dhcpv4SnoopingGlobalVlanEntry 1 }

dhcpv4SnoopingVlanState OBJECT-TYPE
        SYNTAX   INTEGER{enable(1),disable(0)}
        MAX-ACCESS      read-only
        STATUS          current
        DESCRIPTION
            "Function of DHCPv4 snooping is opened under VLAN,
             enable: receive the DHCPv4 packets,
             disable: discard the DHCPv4 packets."
    ::= { dhcpv4SnoopingGlobalVlanEntry 2 }  
    
dhcpv4SnoopingVlanRemoteId OBJECT-TYPE   
    SYNTAX     DisplayString 
    MAX-ACCESS read-only
    STATUS     current
    DESCRIPTION
        "The string of remote-id."
    ::= { dhcpv4SnoopingGlobalVlanEntry 3 } 
    
dhcpv4SnoopingVlanCircuitId OBJECT-TYPE   
    SYNTAX     DisplayString 
    MAX-ACCESS read-only
    STATUS     current
    DESCRIPTION
        "The string of the circuit-id."
    ::= { dhcpv4SnoopingGlobalVlanEntry 4 }     
    
    
    

-- Interface parameters 

dhcpv4SnoopingIfTable OBJECT-TYPE
    SYNTAX     SEQUENCE OF Dhcpv4SnoopingIfEntry 
    MAX-ACCESS not-accessible
    STATUS     current
    DESCRIPTION
           "The table includes DHCPv4 snooping running parameters of each 
            interface."
    ::= { zxr10dhcpv4Snooping 14 }

dhcpv4SnoopingIfEntry OBJECT-TYPE
    SYNTAX     Dhcpv4SnoopingIfEntry
    MAX-ACCESS not-accessible
    STATUS     current
    DESCRIPTION
           "An entry includes DHCPv4 snooping running parameters of each 
            interface."
    INDEX { dhcpv4SnoopingIfIndex
                 }
    ::= { dhcpv4SnoopingIfTable 1 }

    

Dhcpv4SnoopingIfEntry ::=
    SEQUENCE {        
        dhcpv4SnoopingIfIndex              Integer32,
        dhcpv4SnoopingIfName               DisplayString,
        dhcpv4SnoopingIfTrustStatus        INTEGER,
        dhcpv4SnoopingIfQuotaNum           Integer32,
        dhcpv4SnoopingIfCurUserNum         Integer32,   
        dhcpv4SnoopingIfRemoteId           DisplayString,
        dhcpv4SnoopingIfCircuitId          DisplayString,
        dhcpv4SnoopingIfPacketRate         Integer32,
        dhcpv4SnoopingIfSleepTime          Integer32
    }    
dhcpv4SnoopingIfIndex  OBJECT-TYPE
    SYNTAX     Integer32
    MAX-ACCESS read-only
    STATUS     current
    DESCRIPTION
           "The index value that uniquely identifies the interface to
            which this entry is applicable. The interface identified by
            a particular value of this index is the same interface as
            identified by the same value of the IF-MIB's ifIndex."
    ::= { dhcpv4SnoopingIfEntry 1 }
    
dhcpv4SnoopingIfName  OBJECT-TYPE
    SYNTAX     DisplayString
    MAX-ACCESS read-only
    STATUS     current
    DESCRIPTION
           "name of the interface "
    ::= { dhcpv4SnoopingIfEntry 2 }

dhcpv4SnoopingIfTrustStatus OBJECT-TYPE
    SYNTAX     INTEGER  {
                          dhcpv4Untrust(0),
                          dhcpv4Trust(1)
                        }
    MAX-ACCESS read-only
    STATUS     current
    DESCRIPTION
           "The trust status of the interface,  
           dhcpv4Untrust(0): discard DHCPv4 adv/reply packet,
           dhcpv4Trust(1): permit DHCPv4 adv/reply packet.
           "
    ::= { dhcpv4SnoopingIfEntry 3 }
    
dhcpv4SnoopingIfQuotaNum OBJECT-TYPE
    SYNTAX     Integer32 
    MAX-ACCESS read-only
    STATUS     current
    DESCRIPTION
           "The max quota number of the interface, it ranges from 1 to 2048."
    ::= { dhcpv4SnoopingIfEntry 4 }  
    
dhcpv4SnoopingIfCurUserNum OBJECT-TYPE   
    SYNTAX     Integer32 
    MAX-ACCESS read-only
    STATUS     current
    DESCRIPTION
        "The current number of user under the interface who is online."
    ::= { dhcpv4SnoopingIfEntry 5 }
dhcpv4SnoopingIfRemoteId OBJECT-TYPE   
    SYNTAX     DisplayString 
    MAX-ACCESS read-only
    STATUS     current
    DESCRIPTION
        "The string of remote-id."
    ::= { dhcpv4SnoopingIfEntry 6 }
dhcpv4SnoopingIfCircuitId OBJECT-TYPE   
    SYNTAX     DisplayString 
    MAX-ACCESS read-only
    STATUS     current
    DESCRIPTION
        "The string of the circuit-id."
    ::= { dhcpv4SnoopingIfEntry 7 }                                        
                                         
dhcpv4SnoopingIfPacketRate OBJECT-TYPE   
    SYNTAX     Integer32 
    MAX-ACCESS read-only
    STATUS     current
    DESCRIPTION
        "This object indicates rate limit value for DHCP snooping
        purpose. If the value of this object is 0, no rate limit is
        applied for DHCP traffic at this interface."
    ::= { dhcpv4SnoopingIfEntry 8 }
    
dhcpv4SnoopingIfSleepTime OBJECT-TYPE   
    SYNTAX     Integer32 
    MAX-ACCESS read-only
    STATUS     current
    DESCRIPTION
        "This object indicates sleep limit value for DHCP snooping purpose."
    ::= { dhcpv4SnoopingIfEntry 9 }    
-- Port+Vlan parameters 

dhcpv4SnoopingPortVlanTable OBJECT-TYPE
    SYNTAX     SEQUENCE OF Dhcpv4SnoopingPortVlanEntry 
    MAX-ACCESS not-accessible
    STATUS     current
    DESCRIPTION
           "The table includes DHCPv4 snooping running parameters of each 
            interface."
    ::= { zxr10dhcpv4Snooping 15 }

dhcpv4SnoopingPortVlanEntry OBJECT-TYPE
    SYNTAX     Dhcpv4SnoopingPortVlanEntry
    MAX-ACCESS not-accessible
    STATUS     current
    DESCRIPTION
           "An entry includes DHCPv4 snooping running parameters of each 
            interface."
    INDEX { dhcpv4SnoopingIfOptIndex,
            dhcpv4SnoopingIfOptVlanId
             }
    ::= { dhcpv4SnoopingPortVlanTable 1 }

    

Dhcpv4SnoopingPortVlanEntry ::=
    SEQUENCE {      
        dhcpv4SnoopingIfOptIndex           Integer32,
        dhcpv4SnoopingIfOptName            DisplayString,
        dhcpv4SnoopingIfOptVlanId          Integer32,  
        dhcpv4SnoopingIfOptVlanPort        INTEGER,
        dhcpv4SnoopingIfOptFormat          INTEGER,
        dhcpv4SnoopingIfOptState           INTEGER,
        dhcpv4SnoopingIfOptPolicy          INTEGER,
        dhcpv4SnoopingIfOptRemoteId        DisplayString,
        dhcpv4SnoopingIfOptCircuitId       DisplayString
        
    }    
dhcpv4SnoopingIfOptIndex  OBJECT-TYPE
    SYNTAX     Integer32
    MAX-ACCESS read-only
    STATUS     current
    DESCRIPTION
           "The index value that uniquely identifies the interface to
            which this entry is applicable. The interface identified by
            a particular value of this index is the same interface as
            identified by the same value of the IF-MIB's ifIndex."
    ::= { dhcpv4SnoopingPortVlanEntry 1 }
    
dhcpv4SnoopingIfOptName  OBJECT-TYPE
    SYNTAX     DisplayString
    MAX-ACCESS read-only
    STATUS     current
    DESCRIPTION
           "Name of the interface."
    ::= { dhcpv4SnoopingPortVlanEntry 2 }
   
dhcpv4SnoopingIfOptVlanId OBJECT-TYPE
    SYNTAX     Integer32 
    MAX-ACCESS read-only
    STATUS     current
    DESCRIPTION        
    "VLAN ID."
    ::= { dhcpv4SnoopingPortVlanEntry 3 }   
    
dhcpv4SnoopingIfOptVlanPort OBJECT-TYPE
    SYNTAX     INTEGER { 
                 disable(0),
                 enable(1)                 
               }
 
    MAX-ACCESS read-only
    STATUS     current
    DESCRIPTION
           "disable: the option82 function is unavailable, 
            enable: the option82 function is available based on Port+VLAN.     
           "          
    ::= { dhcpv4SnoopingPortVlanEntry 4 }  
    
dhcpv4SnoopingIfOptFormat OBJECT-TYPE
    SYNTAX     INTEGER {
                          chinaTel(1),
                          dslForum(2),
                          telenor(3),
                          userCfg(4),
                          cisco(5),
                          chinaUni(6)
                       } 
    MAX-ACCESS read-only
    STATUS     current
    DESCRIPTION
           "The option82 format."
    ::= { dhcpv4SnoopingPortVlanEntry 5 }  
    
dhcpv4SnoopingIfOptState OBJECT-TYPE
    SYNTAX     INTEGER { 
                 disable(0),
                 enable(1)
                 
               }

    MAX-ACCESS read-only
    STATUS     current
    DESCRIPTION
          "disable: the option82 can't be inserted under interface module,
           enable: the option82 can be inserted based on interface module.
           "
    ::= { dhcpv4SnoopingPortVlanEntry 6 }

dhcpv4SnoopingIfOptPolicy  OBJECT-TYPE
    SYNTAX     INTEGER {unconfigured(1),keep(2),replace(3),stripping(4)}    
    MAX-ACCESS read-only
    STATUS     current
    DESCRIPTION
           "The reforwarding policy."
    ::= { dhcpv4SnoopingPortVlanEntry 7 }

dhcpv4SnoopingIfOptRemoteId OBJECT-TYPE   
    SYNTAX     DisplayString 
    MAX-ACCESS read-only
    STATUS     current
    DESCRIPTION
        "The string of remote-id."
    ::= { dhcpv4SnoopingPortVlanEntry 8 }
   
dhcpv4SnoopingIfOptCircuitId OBJECT-TYPE   
    SYNTAX     DisplayString 
    MAX-ACCESS read-only
    STATUS     current
    DESCRIPTION
        "The string of the circuit-id."
    ::= { dhcpv4SnoopingPortVlanEntry 9 }


-- DHCPv4 Dynamic Binding Table

dhcpv4SnoopingDynamicBindingTable OBJECT-TYPE
    SYNTAX     SEQUENCE OF Dhcpv4SnoopingDynamicBindingEntry
    MAX-ACCESS not-accessible
    STATUS     current
    DESCRIPTION
           "The binding state table containing the state of binding 
            between source address and anchor."
    ::= { zxr10dhcpv4Snooping 16 }

dhcpv4SnoopingDynamicBindingEntry OBJECT-TYPE
    SYNTAX     Dhcpv4SnoopingDynamicBindingEntry
    MAX-ACCESS not-accessible
    STATUS     current
    DESCRIPTION
           "MAC, VLAN and VPN is the key to locate the user-bind information."
    INDEX { 
            dhcpv4SnoopingDynamicBindingMacAddr,
            dhcpv4SnoopingDynamicBindingVlanId,
            dhcpv4SnoopingDynamicBindingVpls
           }
    ::= { dhcpv4SnoopingDynamicBindingTable 1 }

Dhcpv4SnoopingDynamicBindingEntry ::= 
    SEQUENCE {        
        dhcpv4SnoopingDynamicBindingIfIndex        Integer32,
        dhcpv4SnoopingDynamicBindingIfName         DisplayString,
        dhcpv4SnoopingDynamicBindingIpAddress      IpAddress,
        dhcpv4SnoopingDynamicBindingMacAddr           MacAddress,
        dhcpv4SnoopingDynamicBindingState            INTEGER,
        dhcpv4SnoopingDynamicBindingLifetime        Integer32,
        dhcpv4SnoopingDynamicBindingVlanId            Integer32,
        dhcpv4SnoopingDynamicBindingVpls            DisplayString
}

dhcpv4SnoopingDynamicBindingIfIndex OBJECT-TYPE
    SYNTAX     Integer32
    MAX-ACCESS read-only
    STATUS     current
    DESCRIPTION
           "The unique value generated for the interface."
    ::= { dhcpv4SnoopingDynamicBindingEntry 1 }


dhcpv4SnoopingDynamicBindingIfName OBJECT-TYPE
    SYNTAX     DisplayString
    MAX-ACCESS read-only
    STATUS     current
    DESCRIPTION
           "Name of the interface."
    ::= { dhcpv4SnoopingDynamicBindingEntry 2 }

    
dhcpv4SnoopingDynamicBindingIpAddress OBJECT-TYPE
    SYNTAX     IpAddress
    MAX-ACCESS read-only
    STATUS     current
    DESCRIPTION
           "The binding source IP address."
    ::= { dhcpv4SnoopingDynamicBindingEntry 3 }

dhcpv4SnoopingDynamicBindingMacAddr OBJECT-TYPE
    SYNTAX     MacAddress
    MAX-ACCESS read-only
    STATUS     current
    DESCRIPTION
           "The binding source MAC address."
    ::= { dhcpv4SnoopingDynamicBindingEntry 4 }


dhcpv4SnoopingDynamicBindingState OBJECT-TYPE
    SYNTAX     INTEGER  {
                   start(0),
                   bound(1)
               }
    MAX-ACCESS read-only
    STATUS     current
    DESCRIPTION
           "The state of the binding entry."
    ::= { dhcpv4SnoopingDynamicBindingEntry 5 }

dhcpv4SnoopingDynamicBindingLifetime OBJECT-TYPE
    SYNTAX     Integer32
    MAX-ACCESS read-only
    STATUS     current
    DESCRIPTION
           "The remaining lifetime of the entry. 
           If saviObjectsBindingType=static, a value of 2147483647 
           represents infinity."
    ::= { dhcpv4SnoopingDynamicBindingEntry 6 }
dhcpv4SnoopingDynamicBindingVlanId OBJECT-TYPE
    SYNTAX     Integer32
    MAX-ACCESS read-only
    STATUS     current
    DESCRIPTION
           "VLAN ID that the user belong to."
    ::= { dhcpv4SnoopingDynamicBindingEntry 7 }
    
dhcpv4SnoopingDynamicBindingVpls OBJECT-TYPE
    SYNTAX     DisplayString
    MAX-ACCESS read-only
    STATUS     current
    DESCRIPTION
           "Name of the VPLS."
    ::= { dhcpv4SnoopingDynamicBindingEntry 8 }


-- DHCPv4 Static Binding Table

dhcpv4SnoopingStaticBindingTable OBJECT-TYPE
    SYNTAX     SEQUENCE OF Dhcpv4SnoopingStaticBindingEntry
    MAX-ACCESS not-accessible
    STATUS     current
    DESCRIPTION
           "The binding state table containing the state of binding 
            between source address and anchor."
    ::= { zxr10dhcpv4Snooping 17 }

dhcpv4SnoopingStaticBindingEntry OBJECT-TYPE
    SYNTAX     Dhcpv4SnoopingStaticBindingEntry
    MAX-ACCESS not-accessible
    STATUS     current
    DESCRIPTION
           "MAC, VLAN and VPN is the key to locate the user-bind information."
    INDEX { 
            dhcpv4SnoopingStaticBindingMacAddr,
            dhcpv4SnoopingStaticBindingVlanId,
            dhcpv4SnoopingStaticBindingVpls
           }
    ::= { dhcpv4SnoopingStaticBindingTable 1 }

Dhcpv4SnoopingStaticBindingEntry ::= 
    SEQUENCE {        
        dhcpv4SnoopingStaticBindingIfIndex        Integer32,
        dhcpv4SnoopingStaticBindingIfName         DisplayString,
        dhcpv4SnoopingStaticBindingIpAddress      IpAddress,
        dhcpv4SnoopingStaticBindingMacAddr          MacAddress,
        dhcpv4SnoopingStaticBindingState          INTEGER,
        dhcpv4SnoopingStaticBindingLifetime          Integer32,
        dhcpv4SnoopingStaticBindingVlanId          Integer32,
        dhcpv4SnoopingStaticBindingVpls           DisplayString
        }

dhcpv4SnoopingStaticBindingIfIndex OBJECT-TYPE
    SYNTAX     Integer32
    MAX-ACCESS read-only
    STATUS     current
    DESCRIPTION
           "The unique value generated for the interface."
    ::= { dhcpv4SnoopingStaticBindingEntry 1 }


dhcpv4SnoopingStaticBindingIfName OBJECT-TYPE
    SYNTAX     DisplayString
    MAX-ACCESS read-only
    STATUS     current
    DESCRIPTION
           "Name of the interface."
    ::= { dhcpv4SnoopingStaticBindingEntry 2 }

    
dhcpv4SnoopingStaticBindingIpAddress OBJECT-TYPE
    SYNTAX     IpAddress
    MAX-ACCESS read-only
    STATUS     current
    DESCRIPTION
           "The binding source IP address."
    ::= { dhcpv4SnoopingStaticBindingEntry 3 }

dhcpv4SnoopingStaticBindingMacAddr OBJECT-TYPE
    SYNTAX     MacAddress
    MAX-ACCESS read-only
    STATUS     current
    DESCRIPTION
           "The binding source MAC address."
    ::= { dhcpv4SnoopingStaticBindingEntry 4 }


dhcpv4SnoopingStaticBindingState OBJECT-TYPE
    SYNTAX     INTEGER  {
                   start(0),
                   bound(1)
               }
    MAX-ACCESS read-only
    STATUS     current
    DESCRIPTION
           "The state of the binding entry."
    ::= { dhcpv4SnoopingStaticBindingEntry 5 }

dhcpv4SnoopingStaticBindingLifetime OBJECT-TYPE
    SYNTAX     Integer32
    MAX-ACCESS read-only
    STATUS     current
    DESCRIPTION
           "The remaining lifetime of the entry. 
           If saviObjectsBindingType=static, a value of 2147483647 
           represents infinity."
    ::= { dhcpv4SnoopingStaticBindingEntry 6 }
dhcpv4SnoopingStaticBindingVlanId OBJECT-TYPE
    SYNTAX     Integer32
    MAX-ACCESS read-only
    STATUS     current
    DESCRIPTION
           "VLAN ID that the user belong to."
    ::= { dhcpv4SnoopingStaticBindingEntry 7 }

dhcpv4SnoopingStaticBindingVpls OBJECT-TYPE
    SYNTAX     DisplayString
    MAX-ACCESS read-only
    STATUS     current
    DESCRIPTION
           "Name of the VPLS."
    ::= { dhcpv4SnoopingStaticBindingEntry 8 }

-- DHCPv4 Static Binding Table  

-- DHCPv4 File Table
dhcpv4SnoopingFileConfigTable OBJECT-TYPE
    SYNTAX     SEQUENCE OF Dhcpv4SnoopingFileConfigEntry
    MAX-ACCESS not-accessible
    STATUS     current
    DESCRIPTION
           "The table includes DHCPv4 snooping file server address."
            
    ::= { zxr10dhcpv4Snooping 20 }

dhcpv4SnoopingFileConfigEntry OBJECT-TYPE
    SYNTAX     Dhcpv4SnoopingFileConfigEntry
    MAX-ACCESS not-accessible
    STATUS     current
    DESCRIPTION
           "An entry includes DHCPv4 snooping file address."
    INDEX { 
            dhcpv4SnoopingFileServerType,
            dhcpv4SnoopingFileVrf,
            dhcpv4SnoopingFileURL
           }
    ::= { dhcpv4SnoopingFileConfigTable 1 }

Dhcpv4SnoopingFileConfigEntry ::= 
    SEQUENCE {        
        dhcpv4SnoopingFileServerType        INTEGER,
        dhcpv4SnoopingFileIpv6Flag          Integer32,
        dhcpv4SnoopingFileVrf               DisplayString,
        dhcpv4SnoopingFileURL               DisplayString            
        }

dhcpv4SnoopingFileServerType OBJECT-TYPE
    SYNTAX     INTEGER{
                            tftp(2),
                            ftp(3)
                        }
               
    MAX-ACCESS read-only
    STATUS     current
    DESCRIPTION
           "The type of the server."
    ::= { dhcpv4SnoopingFileConfigEntry 1 }
   
dhcpv4SnoopingFileIpv6Flag OBJECT-TYPE
    SYNTAX     Integer32
               
    MAX-ACCESS read-only
    STATUS     current
    DESCRIPTION
           "The IPv6 address flag."
    ::= { dhcpv4SnoopingFileConfigEntry 2 }   
    
    
dhcpv4SnoopingFileVrf OBJECT-TYPE
    SYNTAX     DisplayString
               
    MAX-ACCESS read-only
    STATUS     current
    DESCRIPTION
           "VRF name."
    ::= { dhcpv4SnoopingFileConfigEntry 3 }       

dhcpv4SnoopingFileURL OBJECT-TYPE
    SYNTAX     DisplayString
               
    MAX-ACCESS read-only
    STATUS     current
    DESCRIPTION
           "Server URL address."
    ::= { dhcpv4SnoopingFileConfigEntry 4 }      

-- DHCPv4 File Table   
   
END
