ZXR10-MDI-MIB DEFINITIONS ::= BEGIN

IMPORTS
    MODULE-IDENTITY, OBJECT-TYPE,
    enterprises, Unsigned32, Counter64, IpAddress
        FROM SNMPv2-SMI    
    DisplayString, RowStatus
        FROM SNMPv2-TC;

zxr10MdiMIB MODULE-IDENTITY
    LAST-UPDATED "201809040000Z"
    ORGANIZATION "ZTE Corporation."
    CONTACT-INFO
           "Xu benchong
           Tel: 025-698109
           E-Mail:xu.benchong@zte.com.cn"
    DESCRIPTION
        "The MIB module to describe the MDI protocol."
    REVISION "201809040000Z"
    DESCRIPTION
        "Initial version of this MIB module."
    ::= { zxr10RosngMIB 168 }

    zte OBJECT IDENTIFIER ::= { enterprises 3902 }
    zxr10 OBJECT IDENTIFIER ::= { zte 3}
    zxr10RosngMIB OBJECT IDENTIFIER ::= { zxr10 6000}


zxr10MdiDetectInstMIB OBJECT IDENTIFIER ::= { zxr10MdiMIB 1 }

--
-- MDI Detection Instance
--

zxr10MdiDetectInstTable OBJECT-TYPE
    SYNTAX  SEQUENCE OF Zxr10MdiDetectInstEntry
    MAX-ACCESS  not-accessible
    STATUS  current
    DESCRIPTION
        "A table to MDI detection."
    ::= { zxr10MdiDetectInstMIB 1 }

zxr10MdiDetectInstEntry OBJECT-TYPE
    SYNTAX Zxr10MdiDetectInstEntry
    MAX-ACCESS  not-accessible
    STATUS  current
    DESCRIPTION
        "An entry to MDI detection."
    INDEX  {
            zxr10MdiDetectInstVrfname,
            zxr10MdiDetectInstSourceAddr,
            zxr10MdiDetectInstGroupAddr }
    ::= { zxr10MdiDetectInstTable 1 }
     
Zxr10MdiDetectInstEntry ::= SEQUENCE {
    zxr10MdiDetectInstVrfname DisplayString,
    zxr10MdiDetectInstSourceAddr IpAddress,
    zxr10MdiDetectInstGroupAddr IpAddress,
    zxr10MdiDetectInstBrType INTEGER,
    zxr10MdiDetectInstCodeRate Unsigned32,
    zxr10MdiDetectInstDtMode INTEGER,
    zxr10MdiDetectInstDtDuration Unsigned32,
    zxr10MdiDetectInstCalPeriod Unsigned32,
    zxr10MdiDetectInstProbePeriod Unsigned32,
    zxr10MdiDetectInstRowStatus RowStatus
}

zxr10MdiDetectInstVrfname OBJECT-TYPE  
    SYNTAX DisplayString (SIZE (0..32))
    MAX-ACCESS  not-accessible
    STATUS  current
    DESCRIPTION
        "VRF name."
    ::= { zxr10MdiDetectInstEntry 1 }

zxr10MdiDetectInstSourceAddr OBJECT-TYPE
    SYNTAX IpAddress
    MAX-ACCESS  not-accessible
    STATUS  current
    DESCRIPTION
        "Unicast source address."
    ::= { zxr10MdiDetectInstEntry 2 }

zxr10MdiDetectInstGroupAddr OBJECT-TYPE
    SYNTAX IpAddress
    MAX-ACCESS  not-accessible
    STATUS  current
    DESCRIPTION
        "Multicast group address."
    ::= { zxr10MdiDetectInstEntry 3 }

zxr10MdiDetectInstBrType OBJECT-TYPE
    SYNTAX INTEGER {vbr(1), cbr(2)}
    MAX-ACCESS  read-create
    STATUS  current
    DESCRIPTION
        "Detection bit rate type."
    ::= { zxr10MdiDetectInstEntry 4 }

zxr10MdiDetectInstCodeRate OBJECT-TYPE
    SYNTAX Unsigned32 (1..1000000)
    MAX-ACCESS  read-create
    STATUS  current
    DESCRIPTION
        "Detection code rate(Kbps)."
    ::= { zxr10MdiDetectInstEntry 5 }

zxr10MdiDetectInstDtMode OBJECT-TYPE
    SYNTAX INTEGER {preActivated(1), asRequired(2)}
    MAX-ACCESS  read-create
    STATUS  current
    DESCRIPTION
        "Detection mode: preActivated or asRequired.
         The preActivated means activation patterns in advance.
         The asRequired means according to the need."
    ::= { zxr10MdiDetectInstEntry 6 }

zxr10MdiDetectInstDtDuration OBJECT-TYPE
    SYNTAX Unsigned32 (10..604800)
    MAX-ACCESS  read-create
    STATUS  current
    DESCRIPTION
        "Detection duration(second)."
    ::= { zxr10MdiDetectInstEntry 7 }

zxr10MdiDetectInstCalPeriod OBJECT-TYPE
    SYNTAX Unsigned32 (1)
    MAX-ACCESS  read-create
    STATUS  current
    DESCRIPTION
        "Detection calculator period(second)."
    ::= { zxr10MdiDetectInstEntry 8 }
    
zxr10MdiDetectInstProbePeriod OBJECT-TYPE
    SYNTAX Unsigned32 (10..900)
    MAX-ACCESS  read-create
    STATUS  current
    DESCRIPTION
        "Detection probe period(second)."
    ::= { zxr10MdiDetectInstEntry 9 }

zxr10MdiDetectInstRowStatus OBJECT-TYPE
    SYNTAX      RowStatus
    MAX-ACCESS  read-create
    STATUS      current
    DESCRIPTION
            "Row status."
    ::= { zxr10MdiDetectInstEntry 100 }


--
-- MDI Detection Performance
--

zxr10MdiDetectPerfmTable OBJECT-TYPE
    SYNTAX  SEQUENCE OF Zxr10MdiDetectPerfmEntry
    MAX-ACCESS  not-accessible
    STATUS  current
    DESCRIPTION
        "A table to MDI detection performance."
    ::= { zxr10MdiDetectInstMIB 2 }

zxr10MdiDetectPerfmEntry OBJECT-TYPE
    SYNTAX Zxr10MdiDetectPerfmEntry
    MAX-ACCESS  not-accessible
    STATUS  current
    DESCRIPTION
        "An entry to MDI detection performance."
    INDEX  { 
            zxr10MdiDetectPerfmVrfName,
            zxr10MdiDetectPerfmSourceAddr,
            zxr10MdiDetectPerfmGroupAddr,
            zxr10MdiDetectPerfmIndex }
    ::= { zxr10MdiDetectPerfmTable 1 }

Zxr10MdiDetectPerfmEntry ::= SEQUENCE {
    zxr10MdiDetectPerfmVrfName DisplayString,
    zxr10MdiDetectPerfmSourceAddr IpAddress,
    zxr10MdiDetectPerfmGroupAddr IpAddress,
    zxr10MdiDetectPerfmIndex Unsigned32,
    zxr10MdiDetectPerfmMlt15m DisplayString,
    zxr10MdiDetectPerfmMlt24h DisplayString,
    zxr10MdiDetectPerfmDfMax DisplayString,
    zxr10MdiDetectPerfmDfMin DisplayString,
    zxr10MdiDetectPerfmDfMean DisplayString,
    zxr10MdiDetectPerfmMlrMax DisplayString,
    zxr10MdiDetectPerfmMlrMin DisplayString,
    zxr10MdiDetectPerfmMlrMean DisplayString    
}

zxr10MdiDetectPerfmVrfName OBJECT-TYPE       
    SYNTAX DisplayString (SIZE (0..32))
    MAX-ACCESS  not-accessible                 
    STATUS  current
    DESCRIPTION
        "VPN Routing/Forwarding instance name."
    ::= { zxr10MdiDetectPerfmEntry 1 }

zxr10MdiDetectPerfmSourceAddr OBJECT-TYPE
    SYNTAX IpAddress
    MAX-ACCESS  not-accessible
    STATUS  current
    DESCRIPTION
        "Unicast source address."
    ::= { zxr10MdiDetectPerfmEntry 2 }
    
zxr10MdiDetectPerfmGroupAddr OBJECT-TYPE
    SYNTAX IpAddress
    MAX-ACCESS  not-accessible
    STATUS  current
    DESCRIPTION
        "Multicast group address."
    ::= { zxr10MdiDetectPerfmEntry 3 }

zxr10MdiDetectPerfmIndex OBJECT-TYPE
    SYNTAX Unsigned32 (1..12)
    MAX-ACCESS  not-accessible
    STATUS  current
    DESCRIPTION
        "Sequence index."
    ::= { zxr10MdiDetectPerfmEntry 4 }

zxr10MdiDetectPerfmMlt15m OBJECT-TYPE
    SYNTAX  DisplayString (SIZE(0..23))
    MAX-ACCESS  read-only
    STATUS  current
    DESCRIPTION
        "The media loss counts in the last fifteen minutes."
    ::= { zxr10MdiDetectPerfmEntry 5 }

zxr10MdiDetectPerfmMlt24h OBJECT-TYPE
    SYNTAX  DisplayString (SIZE(0..23))
    MAX-ACCESS  read-only
    STATUS  current
    DESCRIPTION
        "The media loss counts in the last twenty-four hours."
    ::= { zxr10MdiDetectPerfmEntry 6 }

zxr10MdiDetectPerfmDfMax OBJECT-TYPE
    SYNTAX  DisplayString (SIZE(0..23))
    MAX-ACCESS  read-only
    STATUS  current
    DESCRIPTION
        "The maximum delay factors(ms)."
    ::= { zxr10MdiDetectPerfmEntry 7 }    

zxr10MdiDetectPerfmDfMin OBJECT-TYPE
    SYNTAX  DisplayString (SIZE(0..23))
    MAX-ACCESS  read-only
    STATUS  current
    DESCRIPTION
        "The minimum delay factors(ms)."
    ::= { zxr10MdiDetectPerfmEntry 8 }    

zxr10MdiDetectPerfmDfMean OBJECT-TYPE
    SYNTAX  DisplayString (SIZE(0..23))
    MAX-ACCESS  read-only
    STATUS  current
    DESCRIPTION
        "The average delay factors(ms)."
    ::= { zxr10MdiDetectPerfmEntry 9 }    

zxr10MdiDetectPerfmMlrMax OBJECT-TYPE
    SYNTAX  DisplayString (SIZE(0..23))
    MAX-ACCESS  read-only
    STATUS  current
    DESCRIPTION
        "The maximum media loss rate."
    ::= { zxr10MdiDetectPerfmEntry 10 }    

zxr10MdiDetectPerfmMlrMin OBJECT-TYPE
    SYNTAX  DisplayString (SIZE(0..23))
    MAX-ACCESS  read-only
    STATUS  current
    DESCRIPTION
        "The minimum media loss rate."
    ::= { zxr10MdiDetectPerfmEntry 11 }    

zxr10MdiDetectPerfmMlrMean OBJECT-TYPE
    SYNTAX  DisplayString (SIZE(0..23))
    MAX-ACCESS  read-only
    STATUS  current
    DESCRIPTION
        "The average media loss rate."
    ::= { zxr10MdiDetectPerfmEntry 12 }

END
