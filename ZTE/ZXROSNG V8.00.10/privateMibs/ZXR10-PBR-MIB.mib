ZXR10-PBR-MIB DEFINITIONS ::= BEGIN

IMPORTS
    OBJECT-TYPE, MODULE-IDENTITY, Unsigned32,enterprises
            FROM SNMPv2-SMI
    DisplayString, RowStatus
            FROM SNMPv2-TC;     
            
zxr10PbrMIB MODULE-IDENTITY
                LAST-UPDATED
                "201305240000Z"
                ORGANIZATION
                "ZTE Corporation"
                CONTACT-INFO
                "        Xia wenjuan               
                    Tel:  +86-25-52870000           
                E-Mail: xia.wenjuan1@zte.com.cn 
                "
                DESCRIPTION
                "The MIB module to describe the PBR protocol."
                REVISION
                "201305240000Z" 
                DESCRIPTION
                " Initial version of this MIB module"
                ::= { zxr10RosngMIB 402}
                   
    zte OBJECT IDENTIFIER ::={enterprises 3902}
    zxr10 OBJECT IDENTIFIER ::={zte 3}
    zxr10RosngMIB OBJECT IDENTIFIER ::= { zxr10 6000}
             
    zxr10PbrGlobalObjects  OBJECT IDENTIFIER ::= { zxr10PbrMIB 1 }
    zxr10PbrObjects        OBJECT IDENTIFIER ::= { zxr10PbrMIB 2 }
    zxr10PbrTraps          OBJECT IDENTIFIER ::= { zxr10PbrMIB 3 }
    zxr10PbrConformance    OBJECT IDENTIFIER ::= { zxr10PbrMIB 4 }

-- =============================
-- 1. zxr10PbrGlobalObjects 
-- =============================     
    
    
-- =============================
-- 2. zxr10PbrObjects
-- =============================       
-- =============================
-- 2.1 zxr10PbrIPv4Objects
-- =============================  
zxr10PbrIPv4Objects OBJECT IDENTIFIER ::= { zxr10PbrObjects 1 }
-- =============================
-- 2.1.1 zxr10PbrIPv4GlobalObjects
-- =============================    
zxr10PbrIPv4GlobalObjects  OBJECT IDENTIFIER ::= { zxr10PbrIPv4Objects 1 }
-- =============================
-- 2.1.2 zxr10PbrIPv4Table
-- =============================
zxr10PbrIPv4Table OBJECT-TYPE
        SYNTAX  SEQUENCE OF Zxr10PbrIPv4Entry
        MAX-ACCESS  not-accessible
        STATUS  current
        DESCRIPTION
                "IPv4 Policy Route"
        ::= { zxr10PbrIPv4Objects 2  }

zxr10PbrIPv4Entry OBJECT-TYPE
        SYNTAX   Zxr10PbrIPv4Entry
        MAX-ACCESS  not-accessible
        STATUS  current
        DESCRIPTION
                "IPv4 Policy Route"
        INDEX {zxr10PbrIPv4InterfaceName}
        ::= { zxr10PbrIPv4Table 1 }

Zxr10PbrIPv4Entry ::=
        SEQUENCE {
                zxr10PbrIPv4InterfaceName                    DisplayString,
                zxr10PbrIPv4RouteMapName                     DisplayString,  
                zxr10PbrIPv4RowStatus                        RowStatus                
        }

zxr10PbrIPv4InterfaceName OBJECT-TYPE
        SYNTAX   DisplayString(SIZE(1..31))
        MAX-ACCESS  not-accessible
        STATUS  current
        DESCRIPTION
                "The interface name"
        ::= { zxr10PbrIPv4Entry  1  }

zxr10PbrIPv4RouteMapName OBJECT-TYPE
        SYNTAX   DisplayString(SIZE(1..31))
        MAX-ACCESS  read-create
        STATUS  current
        DESCRIPTION
                "RouteMap name"
        ::= { zxr10PbrIPv4Entry  2  }   
        

zxr10PbrIPv4RowStatus OBJECT-TYPE
        SYNTAX       RowStatus
        MAX-ACCESS   read-create
        STATUS        current
        DESCRIPTION
                "This variable is used to create, modify, and/or
                delete a row in this table. "
        ::= { zxr10PbrIPv4Entry 100 }


-- =============================
-- 2.2 zxr10PbrIPv6Objects
-- =============================  
zxr10PbrIPv6Objects OBJECT IDENTIFIER ::= { zxr10PbrObjects 2 }
-- =============================
-- 2.2.1 zxr10PbrIPv6GlobalObjects
-- =============================    
zxr10PbrIPv6GlobalObjects  OBJECT IDENTIFIER ::= { zxr10PbrIPv6Objects 1 }
-- =============================
-- 2.2.2 zxr10PbrIPv6Table
-- =============================
zxr10PbrIPv6Table OBJECT-TYPE
        SYNTAX  SEQUENCE OF Zxr10PbrIPv6Entry
        MAX-ACCESS  not-accessible
        STATUS  current
        DESCRIPTION
                "IPv6 Policy Route"
        ::= { zxr10PbrIPv6Objects 2  }

zxr10PbrIPv6Entry OBJECT-TYPE
        SYNTAX   Zxr10PbrIPv6Entry
        MAX-ACCESS  not-accessible
        STATUS  current
        DESCRIPTION
                "IPv6 Policy Route"
        INDEX {zxr10PbrIPv6InterfaceName}
        ::= { zxr10PbrIPv6Table 1 }

Zxr10PbrIPv6Entry ::=
        SEQUENCE {
                zxr10PbrIPv6InterfaceName                    DisplayString,
                zxr10PbrIPv6RouteMapName                     DisplayString,
                zxr10PbrIPv6RowStatus                        RowStatus
        }

zxr10PbrIPv6InterfaceName OBJECT-TYPE
        SYNTAX   DisplayString(SIZE(1..31))
        MAX-ACCESS  not-accessible
        STATUS  current
        DESCRIPTION
                "The interface name"
        ::= { zxr10PbrIPv6Entry  1  }

zxr10PbrIPv6RouteMapName OBJECT-TYPE
        SYNTAX   DisplayString(SIZE(1..31))
        MAX-ACCESS  read-create
        STATUS  current
        DESCRIPTION
                "RouteMap name"
        ::= { zxr10PbrIPv6Entry  2  }   
        
zxr10PbrIPv6RowStatus OBJECT-TYPE
        SYNTAX       RowStatus
        MAX-ACCESS   read-create
        STATUS        current
        DESCRIPTION
                "This variable is used to create, modify, and/or
                delete a row in this table. "
        ::= { zxr10PbrIPv6Entry 100 }



-- =============================
--3. zxr10PbrNotifications  
-- =============================   
    
    
-- =============================
--4. zxr10PbrConformance    
-- =============================  
    
END
