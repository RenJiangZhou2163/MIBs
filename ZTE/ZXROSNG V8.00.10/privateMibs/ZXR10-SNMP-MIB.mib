-- *****************************************************************
-- ZXR10-SNMP-MIB.mib
--
-- ZTE Corporation Enterprise Structure of Management Information
--
-- Copyright (c) 2009 by ZTE Corporation
-- All rights reserved.
-- *****************************************************************
--
ZXR10-SNMP-MIB DEFINITIONS ::= BEGIN

    IMPORTS
        RowStatus, DisplayString            FROM SNMPv2-TC
        MODULE-IDENTITY, OBJECT-IDENTITY,
        OBJECT-TYPE, enterprises,
        Integer32                           FROM SNMPv2-SMI
        zxr10RosngMIB                       FROM ZXR10-SMI;

    zxr10SnmpMIB MODULE-IDENTITY
        LAST-UPDATED "201709201500Z"
        ORGANIZATION "ZTE Corporation"
        CONTACT-INFO "ZTE Corporation 
                      Mail: zhu.changyang@zte.com.cn
                      "
        DESCRIPTION  
            "The MIB module to describe the information for SNMP."
        REVISION     "201709201500Z"
        DESCRIPTION  
            "Initial version of this MIB module."
        ::= {zxr10RosngMIB 101} 


    zxr10SnmpSetCmdErrCode  OBJECT-TYPE
        SYNTAX      Integer32
        MAX-ACCESS  read-only
        STATUS      current
        DESCRIPTION 
            "Error code for SNMP set command. When agent executes an SNMP set,
             this variable should be maintained. Value 0 means no error."
        DEFVAL { 0 }
        ::={zxr10SnmpMIB 1}   

END
