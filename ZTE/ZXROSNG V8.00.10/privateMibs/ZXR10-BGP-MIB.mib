--*****************************************************************
--ZXR10-BGP-MIB
--OAM
--2011-8-5 9:35
--
--
--Copyright (c) 1985-2011 by ZTE Corp.
--All rights reserved.
--*****************************************************************



ZXR10-BGP-MIB DEFINITIONS ::= BEGIN

IMPORTS
        MODULE-IDENTITY, OBJECT-TYPE,
        enterprises, Unsigned32, Integer32, IpAddress
                FROM SNMPv2-SMI
        DisplayString, RowStatus
                FROM SNMPv2-TC
        Ipv6Address
                FROM IPV6-TC;

zxr10BgpMIB MODULE-IDENTITY
    LAST-UPDATED "201703300900Z"
    ORGANIZATION "ZTE Corporation"
    CONTACT-INFO
        "ZTE Corporation 
         Nanjing Institute of ZTE Corporation
         
         No.68 Zijinghua Rd. Yuhuatai District, Nanjing, China
         
         Tel: +86-25-52870000"
    DESCRIPTION  
        "ZXR10 T8000 ZXR10FILESYSTEM-MIB"  
        
    REVISION "201703300900Z"
    DESCRIPTION  " add a new value in the value list for these nodes as follows:
               ip_route_bras_pool(24),
               ip_route_ipsec(25)
    "

    REVISION "201605300900Z"
    DESCRIPTION  "Add some nodes:
                zBgpAddrModeLabel,
                zBgpPeerIpv4UniShutDownTrack,
                zBgpPeerShutDownTrack,
    "

    REVISION "201605270900Z"
    DESCRIPTION  "Add a new table :zBgpVpnAddrFamilyHovpnTable"

    REVISION "201605100900Z"
    DESCRIPTION  "Add some nodes:
                zBgpAddrModeIpv4UniDistanceLoc,
                zBgpAddrModeDistanceLoc
    "

    REVISION "201604080900Z"
    DESCRIPTION  "Add some nodes:
                zBgpPeerValidationDisableDest,
                zBgpPeerValidationDisableNh,
        add two new values in the value list for these nodes as follows:
                zBgpAddrModeAddrModeType
                zBgpV4VrfAggregateAddrModeType
                zBgpV6UniAggregateAddrModeType
                zBgpDampAddrModeType
                zBgpRedisAddrModeType
                zBgpV4NetworkAddrModeType
                zBgpV6NetworkAddrModeType
                zBgpAddrModeIpv4VrfmulAddrModeType
                zBgpRedisIpv4VrfmulAddrModeType
                zBgpV4NetworkIpv4VrfmulAddrModeType
                zBgpPeerIpv4UniAddrModeType
                zBgpPeerIpv4UniExtendAddrModeType
                zBgpPeerAddrModeType
                zBgpPeerExtendAddrModeType
                zBgpPeerIpv4VrfmulAddrModeType
                zBgpPeerIpv4VrfmulExtendAddrModeType
                zBgpV4UniAddrModeTypeNew
                zBgpVrfV4AddrModeTypeNew
    "
    REVISION "201603290900Z"
    DESCRIPTION  "Add some nodes:
                zBgpPeerIpv4UniExtendIdleTime,
                zBgpPeerIpv4UniExtendIdleIncr,
                zBgpPeerExtendIdleTime,
                zBgpPeerExtendIdleIncr
    "

    REVISION "201603030900Z"
    DESCRIPTION  "Add some nodes:
                zBgpPeerIpv4UniExtendWaitArp,
                zBgpPeerIpv4UniExtendWaitArpRmp
            add a new value in the value list for these nodes as follows:
                zBgpAddrModeAddrModeType
                zBgpV4VrfAggregateAddrModeType
                zBgpV6UniAggregateAddrModeType
                zBgpDampAddrModeType
                zBgpRedisAddrModeType
                zBgpV4NetworkAddrModeType
                zBgpV6NetworkAddrModeType
                zBgpAddrModeIpv4VrfmulAddrModeType
                zBgpRedisIpv4VrfmulAddrModeType
                zBgpV4NetworkIpv4VrfmulAddrModeType
                zBgpPeerAddrModeType
                zBgpPeerIpv4UniAddrModeType
                zBgpPeerIpv4UniExtendAddrModeType
                zBgpPeerExtendAddrModeType
                zBgpPeerIpv4VrfmulAddrModeType
                zBgpPeerIpv4VrfmulExtendAddrModeType
                zBgpV4UniAddrModeTypeNew
                zBgpVrfV4AddrModeTypeNew
    "

    REVISION "201602250900Z"
    DESCRIPTION  "modify some nodes name:
                zBgpPeerIpv4UniExtendTrackName,
                zBgpPeerIpv4UniExtendTrackRmp,
                zBgpPeerExtendTrackName,
                zBgpPeerExtendTrackRmp
                change to
                zBgpPeerIpv4UniExtendWdTrack,
                zBgpPeerIpv4UniExtendWdRmp,
                zBgpPeerExtendWdTrack,
                zBgpPeerExtendWdRmp
    "

    REVISION "201602010900Z"
    DESCRIPTION  "Add some nodes:
                zBgpPeerIpv4UniExtendTrackName,
                zBgpPeerIpv4UniExtendTrackRmp,
                zBgpPeerExtendTrackName,
                zBgpPeerExtendTrackRmp
    "


    REVISION "201601271100Z"
    DESCRIPTION  "Add zBgpInstanceSelectGlobalNH in ZBgpInstanceEntry"    

    REVISION "201601190900Z"
    DESCRIPTION  "add a new value in the value list for these nodes as follows:
        zBgpAddrModeAddrModeType
        zBgpV4VrfAggregateAddrModeType
        zBgpV6UniAggregateAddrModeType
        zBgpDampAddrModeType
        zBgpRedisAddrModeType
        zBgpV4NetworkAddrModeType
        zBgpV6NetworkAddrModeType
        zBgpAddrModeIpv4VrfmulAddrModeType
        zBgpRedisIpv4VrfmulAddrModeType
        zBgpV4NetworkIpv4VrfmulAddrModeType
        zBgpPeerAddrModeType
        zBgpPeerIpv4UniAddrModeType
        zBgpPeerIpv4UniExtendAddrModeType
        zBgpPeerExtendAddrModeType
        zBgpPeerIpv4VrfmulAddrModeType
        zBgpPeerIpv4VrfmulExtendAddrModeType
        zBgpV4UniAddrModeTypeNew
        zBgpVrfV4AddrModeTypeNew
    "
    REVISION "201512211100Z"
    DESCRIPTION  "Add some nodes:
                zBgpPeerIpv4UniExtendKeyChain,
                zBgpPeerExtendKeyChain,
    "
    REVISION "201511180900Z"
    DESCRIPTION  "Add some nodes:
                zBgpAddrModeIpv4UniRSInterval,
                zBgpAddrModeIpv4UniRSInitial,
                zBgpAddrModeIpv4UniRSMaxWait,
                zBgpAddrModeIpv4UniRSCmdType,
                zBgpAddrModeRSInterval,
                zBgpAddrModeRSInitial,
                zBgpAddrModeRSMaxWait,
                zBgpAddrModeRSCmdType,
                Modify description of zBgpPeerIpv4UniTtlSecurityHops.
    "

    REVISION "201505180900Z"
    DESCRIPTION  "Add some nodes:
                zBgpAddrModeIpv4UniTablePolicy,
                zBgpAddrModeTablePolicy,
                zBgpPeerIpv4UniExtendRplIn,
                zBgpPeerIpv4UniExtendRplOut,
                zBgpPeerExtendRplIn,
                zBgpPeerExtendRplOut,
    "
    REVISION "201504270900Z"
    DESCRIPTION  "modify SYNTAX of zBgpPeerSoo to DisplayString.
    "
    REVISION "201504040900Z"
    DESCRIPTION  "modify description of zBgpVrfV4TrackAdjValueNew and zBgpV4UniTrackAdjValueNew.
    "
    REVISION "201503040900Z"
    DESCRIPTION  "modify type of
                  1.zbgpinstanceTable,
                  2.zBgpAddrModeIpv4UniTable,
                  3.zBgpAddrModeTable,
                  4.zBgpAddrModeIpv4VrfmulTable,
                  5.zBgpPeerIpv4UniTable,
                  6.zBgpPeerIpv4UniExtendTable,
                  7.zBgpPeerTable,
                  8.zBgpPeerExtendTable,
                  9.zBgpPeerIpv4VrfmulTable,
                  10.zBgpPeerIpv4VrfmulExtendTable
    "

    REVISION "201403040900Z"
    DESCRIPTION  "modify type of
                  1.zBgpAddrModeAddrModeType
                  2.zBgpV4VrfAggregateAddrModeType,
                  3.zBgpV6UniAggregateAddrModeType,
                  zBgpDampAddrModeType,
                  zBgpRedisAddrModeType,
                  zBgpV4NetworkAddrModeType
                  zBgpV6NetworkAddrModeType
                  zBgpAddrModeIpv4VrfmulAddrModeType
                  zBgpRedisIpv4VrfmulAddrModeType
                  zBgpV4NetworkIpv4VrfmulAddrModeType
                  zBgpPeerIpv4UniAddrModeType
                  zBgpPeerIpv4UniExtendAddrModeType
                  zBgpPeerAddrModeType
                  zBgpPeerExtendAddrModeType
                  zBgpPeerIpv4VrfmulAddrModeType
                  zBgpPeerIpv4VrfmulExtendAddrModeType
                  zBgpV4UniAddrModeType
                  zBgpVrfV4AddrModeType
                to enumeration.
    "

    REVISION "201307201100Z"
    DESCRIPTION  "Add
                  zBgpV4UniTrackRowStatus,
                  zBgpVrfV4TrackRowStatus
    "

    REVISION "201307041100Z"
    DESCRIPTION  "Add
                  1.zBgpV4UniTrackTable,
                  2.zBgpVrfV4TrackTable
    "

    REVISION "201306241100Z"
    DESCRIPTION  "modify
                  1.zBgpAddrModeIpv4UniTable
                  2.zBgpAddrModeTable,
                  3.zBgpAddrModeIpv4VrfmulTable,
                  add
                  zBgpAddrModeIpv4UniMedUnsign,
                  zBgpAddrModeMedUnsign,
                  zBgpAddrModeIpv4VrfmulMedUnsign
    "

    REVISION "201305221100Z"  
    DESCRIPTION  "modify
                  1.zbgpinstanceTable,
                  2.zBgpAddrModeIpv4UniTable,
                  3.zBgpAddrModeTable,
                  4.zBgpAddrModeIpv4VrfmulTable,
                  5.zBgpPeerIpv4UniTable,
                  6.zBgpPeerIpv4UniExtendTable,
                  7.zBgpPeerTable,
                  8.zBgpPeerExtendTable,
                  9.zBgpPeerIpv4VrfmulTable,
                  10.zBgpPeerIpv4VrfmulExtendTable
    "

    REVISION "200908120000Z"  
    DESCRIPTION  " "
    ::= { zxr10RosngMIB 156 }    

zte             OBJECT IDENTIFIER ::= { enterprises 3902} -- assigned by IANA
zxr10           OBJECT IDENTIFIER ::= { zte 3}
zxr10RosngMIB   OBJECT IDENTIFIER ::= { zxr10 6000 }


--------------------------------------------------------------
--------------------------------------------------------------
--zBgpInstanceTable
--------------------------------------------------------------
zBgpInstanceTable OBJECT-TYPE
        SYNTAX  SEQUENCE OF ZBgpInstanceEntry
        MAX-ACCESS  not-accessible
        STATUS  current
        DESCRIPTION
                "BGP_INSTANCE"
        ::= { zxr10BgpMIB 1  }

zBgpInstanceEntry OBJECT-TYPE
        SYNTAX   ZBgpInstanceEntry
        MAX-ACCESS  not-accessible
        STATUS  current
        DESCRIPTION
                "BGP_INSTANCE"
        INDEX {zBgpInstanceLocalAs }
        ::= { zBgpInstanceTable 1 }

ZBgpInstanceEntry ::=
        SEQUENCE {
                zBgpInstanceLocalAs                               Unsigned32,
                zBgpInstanceCompMed                               Unsigned32,
                zBgpInstanceCtocReflection                        Unsigned32,
                zBgpInstanceClusterId                             Unsigned32,
                zBgpInstanceConfedId                              Unsigned32,
                zBgpInstanceIpv4Unicast                           Unsigned32,
                zBgpInstanceLocalPref                             Unsigned32,
                zBgpInstanceRtFilter                              Unsigned32,
                zBgpInstanceExtCommunityTypeCompatible            Unsigned32,
                zBgpInstanceFastExternalFallover                  Unsigned32,
                zBgpInstanceGracefulRestart                       Unsigned32,
                zBgpInstanceGrRestartTime                         Unsigned32,
                zBgpInstanceGrStalepathTime                       Unsigned32,
                zBgpInstanceGrUpdateDelay                         Unsigned32,
                zBgpInstanceTimersKeepalive                       Unsigned32,
                zBgpInstanceTimersHoldtime                        Unsigned32,
                zBgpInstanceTimersCmdType                         Unsigned32,
                zBgpInstanceClusterIdAddr                         IpAddress,
                zBgpInstanceClusterSet                            Unsigned32,
                zBgpInstanceEnforceFirstAs                        Unsigned32,
                zBgpInstanceSpecialMode                           Unsigned32,
                zBgpInstanceAspathIgnore                          Unsigned32,
                zBgpInstanceRouterIdIgnore                        Unsigned32,
                zBgpInstanceDeterministicMed                      Unsigned32,
                zBgpInstanceAttrDownload                          Unsigned32,
                zBgpInstanceAttrDownloadIpv6                      Unsigned32,
                zBgpInstanceUpdateDelayAlways                     Unsigned32,
                zBgpInstanceconnectDelay                          Unsigned32,
                zBgpInstanceSelectGlobalNH                        INTEGER
        }

zBgpInstanceLocalAs OBJECT-TYPE
        SYNTAX   Unsigned32
        MAX-ACCESS  read-only
        STATUS  current
        DESCRIPTION
                "local_as"
        ::= { zBgpInstanceEntry  1  }

zBgpInstanceCompMed OBJECT-TYPE
        SYNTAX   Unsigned32
        MAX-ACCESS  read-only
        STATUS  current
        DESCRIPTION
                "comp_med"
        ::= { zBgpInstanceEntry  2  }

zBgpInstanceCtocReflection OBJECT-TYPE
        SYNTAX   Unsigned32
        MAX-ACCESS  read-only
        STATUS  current
        DESCRIPTION
                "ctoc_reflection"
        ::= { zBgpInstanceEntry  3  }

zBgpInstanceClusterId OBJECT-TYPE
        SYNTAX   Unsigned32
        MAX-ACCESS  read-only
        STATUS  current
        DESCRIPTION
                "cluster_id"
        ::= { zBgpInstanceEntry  4  }

zBgpInstanceConfedId OBJECT-TYPE
        SYNTAX   Unsigned32
        MAX-ACCESS  read-only
        STATUS  current
        DESCRIPTION
                "confed_id"
        ::= { zBgpInstanceEntry  5  }

zBgpInstanceIpv4Unicast OBJECT-TYPE
        SYNTAX   Unsigned32
        MAX-ACCESS  read-only
        STATUS  current
        DESCRIPTION
                "ipv4_unicast"
        ::= { zBgpInstanceEntry  6  }

zBgpInstanceLocalPref OBJECT-TYPE
        SYNTAX   Unsigned32
        MAX-ACCESS  read-only
        STATUS  current
        DESCRIPTION
                "local_pref"
        ::= { zBgpInstanceEntry  7  }

zBgpInstanceRtFilter OBJECT-TYPE
        SYNTAX   Unsigned32
        MAX-ACCESS  read-only
        STATUS  current
        DESCRIPTION
                "rt_filter"
        ::= { zBgpInstanceEntry  8  }

zBgpInstanceExtCommunityTypeCompatible OBJECT-TYPE
        SYNTAX   Unsigned32
        MAX-ACCESS  read-only
        STATUS  current
        DESCRIPTION
                "ext_community_type_compatible"
        ::= { zBgpInstanceEntry  9  }

zBgpInstanceFastExternalFallover OBJECT-TYPE
        SYNTAX   Unsigned32
        MAX-ACCESS  read-only
        STATUS  current
        DESCRIPTION
                "fast_external_fallover"
        ::= { zBgpInstanceEntry  10  }

zBgpInstanceGracefulRestart OBJECT-TYPE
        SYNTAX   Unsigned32
        MAX-ACCESS  read-only
        STATUS  current
        DESCRIPTION
                "graceful_restart"
        ::= { zBgpInstanceEntry  11  }

zBgpInstanceGrRestartTime OBJECT-TYPE
        SYNTAX   Unsigned32
        MAX-ACCESS  read-only
        STATUS  current
        DESCRIPTION
                "gr_restart_time"
        ::= { zBgpInstanceEntry  12  }

zBgpInstanceGrStalepathTime OBJECT-TYPE
        SYNTAX   Unsigned32
        MAX-ACCESS  read-only
        STATUS  current
        DESCRIPTION
                "gr_stalepath_time"
        ::= { zBgpInstanceEntry  13  }

zBgpInstanceGrUpdateDelay OBJECT-TYPE
        SYNTAX   Unsigned32
        MAX-ACCESS  read-only
        STATUS  current
        DESCRIPTION
                "gr_update_delay"
        ::= { zBgpInstanceEntry  14  }

zBgpInstanceTimersKeepalive OBJECT-TYPE
        SYNTAX   Unsigned32
        MAX-ACCESS  read-only
        STATUS  current
        DESCRIPTION
                "timers_keepalive"
        ::= { zBgpInstanceEntry  15  }

zBgpInstanceTimersHoldtime OBJECT-TYPE
        SYNTAX   Unsigned32
        MAX-ACCESS  read-only
        STATUS  current
        DESCRIPTION
                "timers_holdtime"
        ::= { zBgpInstanceEntry  16  }

zBgpInstanceTimersCmdType OBJECT-TYPE
        SYNTAX   Unsigned32
        MAX-ACCESS  read-only
        STATUS  current
        DESCRIPTION
                "timers_cmd_type"
        ::= { zBgpInstanceEntry  17  }

zBgpInstanceClusterIdAddr OBJECT-TYPE
        SYNTAX   IpAddress
        MAX-ACCESS  read-only
        STATUS  current
        DESCRIPTION
                "cluster_id_addr"
        ::= { zBgpInstanceEntry  18  }

zBgpInstanceClusterSet OBJECT-TYPE
        SYNTAX   Unsigned32
        MAX-ACCESS  read-only
        STATUS  current
        DESCRIPTION
                "cluster_set"
        ::= { zBgpInstanceEntry  19  }

zBgpInstanceEnforceFirstAs OBJECT-TYPE
        SYNTAX   Unsigned32
        MAX-ACCESS  read-only
        STATUS  current
        DESCRIPTION
                "enforce_first_as"
        ::= { zBgpInstanceEntry  20  }

zBgpInstanceSpecialMode OBJECT-TYPE
        SYNTAX   Unsigned32
        MAX-ACCESS  read-only
        STATUS  obsolete
        DESCRIPTION
                "special_mode"
        ::= { zBgpInstanceEntry  21  }

zBgpInstanceAspathIgnore OBJECT-TYPE
        SYNTAX   Unsigned32
        MAX-ACCESS  read-only
        STATUS  current
        DESCRIPTION
                "as_path_ignore (1 enable,0 disable)"
        ::= { zBgpInstanceEntry  22  }

zBgpInstanceRouterIdIgnore OBJECT-TYPE
        SYNTAX   Unsigned32
        MAX-ACCESS  read-only
        STATUS  current
        DESCRIPTION
                "router_id_ignore(1 enable,0 disable)"
        ::= { zBgpInstanceEntry  23  }

zBgpInstanceDeterministicMed OBJECT-TYPE
        SYNTAX   Unsigned32
        MAX-ACCESS  read-only
        STATUS  current
        DESCRIPTION
                "deterministic_med(1 enable,0 disable)"
        ::= { zBgpInstanceEntry  24  }

zBgpInstanceAttrDownload OBJECT-TYPE
        SYNTAX   Unsigned32
        MAX-ACCESS  read-only
        STATUS  current
        DESCRIPTION
                "attribute_download (1 enable,0 disable)"
        ::= { zBgpInstanceEntry  25  }

zBgpInstanceAttrDownloadIpv6 OBJECT-TYPE
        SYNTAX   Unsigned32
        MAX-ACCESS  read-only
        STATUS  current
        DESCRIPTION
                "attribute_download_ipv6(1 enable,0 disable)"
        ::= { zBgpInstanceEntry  26  }

zBgpInstanceUpdateDelayAlways OBJECT-TYPE
        SYNTAX   Unsigned32
        MAX-ACCESS  read-only
        STATUS  current
        DESCRIPTION
                "bgp_update_delay_always"
        ::= { zBgpInstanceEntry  27  }

zBgpInstanceconnectDelay OBJECT-TYPE
        SYNTAX   Unsigned32
        MAX-ACCESS  read-only
        STATUS  current
        DESCRIPTION
                "bgp connect delay time"
        ::= { zBgpInstanceEntry  28  }

zBgpInstanceSelectGlobalNH OBJECT-TYPE
        SYNTAX INTEGER {disable(1),enable(2)}
        MAX-ACCESS  read-only
        STATUS  current
        DESCRIPTION
                "Download global nexthop instand of link-local nexthop"
        ::= { zBgpInstanceEntry  29  }
--------------------------------------------------------------
--------------------------------------------------------------
--zBgpAddrModeIpv4UniTable
--------------------------------------------------------------
zBgpAddrModeIpv4UniTable OBJECT-TYPE
        SYNTAX  SEQUENCE OF ZBgpAddrModeIpv4UniEntry
        MAX-ACCESS  not-accessible
        STATUS  current
        DESCRIPTION
                "BGP_ADDR_MODE_IPV4_UNI"
        ::= { zxr10BgpMIB 2  }

zBgpAddrModeIpv4UniEntry OBJECT-TYPE
        SYNTAX   ZBgpAddrModeIpv4UniEntry
        MAX-ACCESS  not-accessible
        STATUS  current
        DESCRIPTION
                "BGP_ADDR_MODE_IPV4_UNI"
        INDEX {zBgpAddrModeIpv4UniLocalAs }
        ::= { zBgpAddrModeIpv4UniTable 1 }

ZBgpAddrModeIpv4UniEntry ::=
        SEQUENCE {
                zBgpAddrModeIpv4UniLocalAs                        Unsigned32,
                zBgpAddrModeIpv4UniAddrModeType                   INTEGER,
                zBgpAddrModeIpv4UniVrfName                        DisplayString,
                zBgpAddrModeIpv4UniFrr                            Unsigned32,
                zBgpAddrModeIpv4UniRouterId                       Unsigned32,
                zBgpAddrModeIpv4UniDefInfoOriginate               Unsigned32,
                zBgpAddrModeIpv4UniDistanceIbgp                   Unsigned32,
                zBgpAddrModeIpv4UniDistanceEbgp                   Unsigned32,
                zBgpAddrModeIpv4UniMaximumPathsIbgp               Unsigned32,
                zBgpAddrModeIpv4UniMaximumPathsEbgp               Unsigned32,
                zBgpAddrModeIpv4UniSynchronization                Unsigned32,
                zBgpAddrModeIpv4UniTableMap                       DisplayString,
                zBgpAddrModeIpv4UniDefaultMetric                  Integer32,
                zBgpAddrModeIpv4UniRouterIdSet                    Unsigned32,
                zBgpAddrModeIpv4UniVrfConst                       Unsigned32,
                zBgpAddrModeIpv4UniAdvActiveOnly                  Unsigned32,
                zBgpAddrModeIpv4UniMaxPathsEibgp                  Unsigned32,
                zBgpAddrModeIpv4UniRibOnly                        Unsigned32,
                zBgpAddrModeIpv4UniRibOnlyRmp                     DisplayString,
                zBgpAddrModeIpv4UniFrrWtr                         Integer32,
                zBgpAddrModeIpv4UniIgpMedIgnore                   Unsigned32,
                zBgpAddrModeIpv4UniBestExternal                   Unsigned32,
                zBgpAddrModeIpv4UniMedUnsign                      Unsigned32,
                zBgpAddrModeIpv4UniTablePolicy                    DisplayString,
                zBgpAddrModeIpv4UniRSInterval                     Unsigned32,
                zBgpAddrModeIpv4UniRSInitial                      Unsigned32,
                zBgpAddrModeIpv4UniRSMaxWait                      Unsigned32,
                zBgpAddrModeIpv4UniRSCmdType                      Unsigned32,
                zBgpAddrModeIpv4UniDistanceLoc                    Unsigned32
        }

zBgpAddrModeIpv4UniLocalAs OBJECT-TYPE
        SYNTAX   Unsigned32
        MAX-ACCESS  read-only
        STATUS  current
        DESCRIPTION
                "local_as"
        ::= { zBgpAddrModeIpv4UniEntry  1  }

zBgpAddrModeIpv4UniAddrModeType OBJECT-TYPE
        SYNTAX  INTEGER {
                        ipv4_unicast(1)
                    }
        MAX-ACCESS  read-only
        STATUS  current
        DESCRIPTION
                "addr_mode_type"
        ::= { zBgpAddrModeIpv4UniEntry  2  }

zBgpAddrModeIpv4UniVrfName OBJECT-TYPE
        SYNTAX   DisplayString
        MAX-ACCESS  read-only
        STATUS  current
        DESCRIPTION
                "vrf_name"
        ::= { zBgpAddrModeIpv4UniEntry  3  }

zBgpAddrModeIpv4UniFrr OBJECT-TYPE
        SYNTAX   Unsigned32
        MAX-ACCESS  read-only
        STATUS  current
        DESCRIPTION
                "frr"
        ::= { zBgpAddrModeIpv4UniEntry  4  }

zBgpAddrModeIpv4UniRouterId OBJECT-TYPE
        SYNTAX   Unsigned32
        MAX-ACCESS  read-only
        STATUS  current
        DESCRIPTION
                "router_id"
        ::= { zBgpAddrModeIpv4UniEntry  5  }

zBgpAddrModeIpv4UniDefInfoOriginate OBJECT-TYPE
        SYNTAX   Unsigned32
        MAX-ACCESS  read-only
        STATUS  current
        DESCRIPTION
                "def_info_originate"
        ::= { zBgpAddrModeIpv4UniEntry  6  }

zBgpAddrModeIpv4UniDistanceIbgp OBJECT-TYPE
        SYNTAX   Unsigned32
        MAX-ACCESS  read-only
        STATUS  current
        DESCRIPTION
                "distance_ibgp"
        ::= { zBgpAddrModeIpv4UniEntry  7  }

zBgpAddrModeIpv4UniDistanceEbgp OBJECT-TYPE
        SYNTAX   Unsigned32
        MAX-ACCESS  read-only
        STATUS  current
        DESCRIPTION
                "distance_ebgp"
        ::= { zBgpAddrModeIpv4UniEntry  8  }

zBgpAddrModeIpv4UniMaximumPathsIbgp OBJECT-TYPE
        SYNTAX   Unsigned32
        MAX-ACCESS  read-only
        STATUS  current
        DESCRIPTION
                "maximum_paths_ibgp"
        ::= { zBgpAddrModeIpv4UniEntry  9  }

zBgpAddrModeIpv4UniMaximumPathsEbgp OBJECT-TYPE
        SYNTAX   Unsigned32
        MAX-ACCESS  read-only
        STATUS  current
        DESCRIPTION
                "maximum_paths_ebgp"
        ::= { zBgpAddrModeIpv4UniEntry  10  }

zBgpAddrModeIpv4UniSynchronization OBJECT-TYPE
        SYNTAX   Unsigned32
        MAX-ACCESS  read-only
        STATUS  current
        DESCRIPTION
                "synchronization"
        ::= { zBgpAddrModeIpv4UniEntry  11  }

zBgpAddrModeIpv4UniTableMap OBJECT-TYPE
        SYNTAX   DisplayString
        MAX-ACCESS  read-only
        STATUS  current
        DESCRIPTION
                "table_map"
        ::= { zBgpAddrModeIpv4UniEntry  12  }

zBgpAddrModeIpv4UniDefaultMetric OBJECT-TYPE
        SYNTAX   Integer32
        MAX-ACCESS  read-only
        STATUS  current
        DESCRIPTION
                "default_metric"
        ::= { zBgpAddrModeIpv4UniEntry  13  }

zBgpAddrModeIpv4UniRouterIdSet OBJECT-TYPE
        SYNTAX   Unsigned32
        MAX-ACCESS  read-only
        STATUS  current
        DESCRIPTION
                "router_id_set"
        ::= { zBgpAddrModeIpv4UniEntry  14  }

zBgpAddrModeIpv4UniVrfConst OBJECT-TYPE
        SYNTAX   Unsigned32
        MAX-ACCESS  read-only
        STATUS  obsolete
        DESCRIPTION
                "vrf_const"
        ::= { zBgpAddrModeIpv4UniEntry  15  }



zBgpAddrModeIpv4UniAdvActiveOnly OBJECT-TYPE
        SYNTAX   Unsigned32
        MAX-ACCESS  read-only
        STATUS  current
        DESCRIPTION
                "advertise_active_only(1 enable,0 disable)"
        ::= { zBgpAddrModeIpv4UniEntry  16  }

zBgpAddrModeIpv4UniMaxPathsEibgp OBJECT-TYPE
        SYNTAX   Unsigned32
        MAX-ACCESS  read-only
        STATUS  current
        DESCRIPTION
                "maximum_paths_eibgp"
        ::= { zBgpAddrModeIpv4UniEntry  17  }

zBgpAddrModeIpv4UniRibOnly OBJECT-TYPE
        SYNTAX   Unsigned32
        MAX-ACCESS  read-only
        STATUS  current
        DESCRIPTION
                "rib_only;(1 enable,0 disable)"
        ::= { zBgpAddrModeIpv4UniEntry  18  }


zBgpAddrModeIpv4UniRibOnlyRmp OBJECT-TYPE
        SYNTAX   DisplayString
        MAX-ACCESS  read-only
        STATUS  current
        DESCRIPTION
                "rib_only_route_map(route-map name)"
        ::= { zBgpAddrModeIpv4UniEntry  19  }

zBgpAddrModeIpv4UniFrrWtr OBJECT-TYPE
        SYNTAX   Integer32
        MAX-ACCESS  read-only
        STATUS  current
        DESCRIPTION
                "frr_wtr"
        ::= { zBgpAddrModeIpv4UniEntry  20  }

zBgpAddrModeIpv4UniIgpMedIgnore OBJECT-TYPE
        SYNTAX   Unsigned32
        MAX-ACCESS  read-only
        STATUS  current
        DESCRIPTION
                "igpmetric_ignore(1 enable,0 disable)"
        ::= { zBgpAddrModeIpv4UniEntry  21}

zBgpAddrModeIpv4UniBestExternal OBJECT-TYPE
        SYNTAX   Unsigned32
        MAX-ACCESS  read-only
        STATUS  current
        DESCRIPTION
                "best_external(1 enable,0 disable)"
        ::= { zBgpAddrModeIpv4UniEntry  22}

zBgpAddrModeIpv4UniMedUnsign OBJECT-TYPE
        SYNTAX   Unsigned32
        MAX-ACCESS  read-only
        STATUS  current
        DESCRIPTION
                "Unsigned32 default_metric"
        ::= { zBgpAddrModeIpv4UniEntry  23  }

zBgpAddrModeIpv4UniTablePolicy OBJECT-TYPE
        SYNTAX   DisplayString
        MAX-ACCESS  read-only
        STATUS  current
        DESCRIPTION
                "route policy name"
        ::= { zBgpAddrModeIpv4UniEntry  24  }

zBgpAddrModeIpv4UniRSInterval OBJECT-TYPE
        SYNTAX   Unsigned32
        MAX-ACCESS  read-only
        STATUS  current
        DESCRIPTION
                "route scan timer interval wait time(ms)"
        ::= { zBgpAddrModeIpv4UniEntry  25  }

zBgpAddrModeIpv4UniRSInitial OBJECT-TYPE
        SYNTAX   Unsigned32
        MAX-ACCESS  read-only
        STATUS  current
        DESCRIPTION
                "route scan timer initial time(ms)"
        ::= { zBgpAddrModeIpv4UniEntry  26  }

zBgpAddrModeIpv4UniRSMaxWait OBJECT-TYPE
        SYNTAX   Unsigned32
        MAX-ACCESS  read-only
        STATUS  current
        DESCRIPTION
                "route scan timer max wait time(ms)"
        ::= { zBgpAddrModeIpv4UniEntry  27  }

zBgpAddrModeIpv4UniRSCmdType OBJECT-TYPE
        SYNTAX   Unsigned32
        MAX-ACCESS  read-only
        STATUS  current
        DESCRIPTION
                "route scan timer cmd type"
        ::= { zBgpAddrModeIpv4UniEntry  28  }

zBgpAddrModeIpv4UniDistanceLoc OBJECT-TYPE
        SYNTAX   Unsigned32
        MAX-ACCESS  read-only
        STATUS  current
        DESCRIPTION
                "Distance for BGP local routes."
        ::= { zBgpAddrModeIpv4UniEntry  29  }
--------------------------------------------------------------
--------------------------------------------------------------
--zBgpAsWeightTable  bgp as
--------------------------------------------------------------
zBgpAsWeightTable OBJECT-TYPE
        SYNTAX  SEQUENCE OF ZBgpAsWeightEntry
        MAX-ACCESS  not-accessible
        STATUS  obsolete
        DESCRIPTION
                "BGP_AS_WEIGHT"
        ::= { zxr10BgpMIB 3  }

zBgpAsWeightEntry OBJECT-TYPE
        SYNTAX   ZBgpAsWeightEntry
        MAX-ACCESS  not-accessible
        STATUS  obsolete
        DESCRIPTION
                "BGP_AS_WEIGHT"
        INDEX {zBgpAsWeightWeightAs }
        ::= { zBgpAsWeightTable 1 }

ZBgpAsWeightEntry ::=
        SEQUENCE {
                zBgpAsWeightWeightAs                              Unsigned32,
                zBgpAsWeightLocalAs                               Unsigned32,
                zBgpAsWeightWeight                                Unsigned32
        }

zBgpAsWeightWeightAs OBJECT-TYPE
        SYNTAX   Unsigned32
        MAX-ACCESS  read-only
        STATUS  obsolete
        DESCRIPTION
                "weight_as"
        ::= { zBgpAsWeightEntry  1  }

zBgpAsWeightLocalAs OBJECT-TYPE
        SYNTAX   Unsigned32
        MAX-ACCESS  read-only
        STATUS  obsolete
        DESCRIPTION
                "local_as"
        ::= { zBgpAsWeightEntry  2  }

zBgpAsWeightWeight OBJECT-TYPE
        SYNTAX   Unsigned32
        MAX-ACCESS  read-only
        STATUS  obsolete
        DESCRIPTION
                "weight"
        ::= { zBgpAsWeightEntry  3  }



--------------------------------------------------------------
--------------------------------------------------------------
--zBgpConfPeersTable
--------------------------------------------------------------
zBgpConfPeersTable OBJECT-TYPE
        SYNTAX  SEQUENCE OF ZBgpConfPeersEntry
        MAX-ACCESS  not-accessible
        STATUS  obsolete
        DESCRIPTION
                "BGP_CONF_PEERS"
        ::= { zxr10BgpMIB 4  }

zBgpConfPeersEntry OBJECT-TYPE
        SYNTAX   ZBgpConfPeersEntry
        MAX-ACCESS  not-accessible
        STATUS  obsolete
        DESCRIPTION
                "BGP_CONF_PEERS"
        INDEX {zBgpConfPeersConfPeerAs }
        ::= { zBgpConfPeersTable 1 }

ZBgpConfPeersEntry ::=
        SEQUENCE {
                zBgpConfPeersConfPeerAs                           Unsigned32,
                zBgpConfPeersLocalAs                              Unsigned32
        }

zBgpConfPeersConfPeerAs OBJECT-TYPE
        SYNTAX   Unsigned32
        MAX-ACCESS  read-only
        STATUS  obsolete
        DESCRIPTION
                "conf_peer_as"
        ::= { zBgpConfPeersEntry  1  }

zBgpConfPeersLocalAs OBJECT-TYPE
        SYNTAX   Unsigned32
        MAX-ACCESS  read-only
        STATUS  obsolete
        DESCRIPTION
                "local_as"
        ::= { zBgpConfPeersEntry  2  }



--------------------------------------------------------------
--------------------------------------------------------------
--zBgpV4UniAggregateTable
--------------------------------------------------------------
zBgpV4UniAggregateTable OBJECT-TYPE
        SYNTAX  SEQUENCE OF ZBgpV4UniAggregateEntry
        MAX-ACCESS  not-accessible
        STATUS  current
        DESCRIPTION
                "BGP_V4_UNI_AGGREGATE"
        ::= { zxr10BgpMIB 5  }

zBgpV4UniAggregateEntry OBJECT-TYPE
        SYNTAX   ZBgpV4UniAggregateEntry
        MAX-ACCESS  not-accessible
        STATUS  current
        DESCRIPTION
                "BGP_V4_UNI_AGGREGATE"
        INDEX {zBgpV4UniAggregateLocalAs,
               zBgpV4UniAggregateIpAddr,
               zBgpV4UniAggregateIpMask,
               zBgpV4UniAggregateSubnet,
               zBgpV4UniAggregateSubnetIpAddr,
               zBgpV4UniAggregateSubnetIpMask 
        }
        ::= { zBgpV4UniAggregateTable 1 }

ZBgpV4UniAggregateEntry ::=
        SEQUENCE {
                zBgpV4UniAggregateLocalAs                         Unsigned32,
                zBgpV4UniAggregateIpAddr                          IpAddress,
                zBgpV4UniAggregateIpMask                          IpAddress,
                zBgpV4UniAggregateSubnetIpAddr                    IpAddress,
                zBgpV4UniAggregateSubnetIpMask                    IpAddress,
                zBgpV4UniAggregateAddrModeType                    INTEGER,
                zBgpV4UniAggregateVrfName                         DisplayString,
                zBgpV4UniAggregateAsSet                           Unsigned32,
                zBgpV4UniAggregateCount                           Unsigned32,
                zBgpV4UniAggregateStrict                          Unsigned32,
                zBgpV4UniAggregateSummaryOnly                     Unsigned32,
                zBgpV4UniAggregateSubnet                          Unsigned32
        }

zBgpV4UniAggregateLocalAs OBJECT-TYPE
        SYNTAX   Unsigned32
        MAX-ACCESS  read-only
        STATUS  current
        DESCRIPTION
                "local_as"
        ::= { zBgpV4UniAggregateEntry  1  }

zBgpV4UniAggregateIpAddr OBJECT-TYPE
        SYNTAX   IpAddress
        MAX-ACCESS  read-only
        STATUS  current
        DESCRIPTION
                "ip_addr"
        ::= { zBgpV4UniAggregateEntry  2  }

zBgpV4UniAggregateIpMask OBJECT-TYPE
        SYNTAX   IpAddress
        MAX-ACCESS  read-only
        STATUS  current
        DESCRIPTION
                "ip_mask"
        ::= { zBgpV4UniAggregateEntry  3  }

zBgpV4UniAggregateSubnetIpAddr OBJECT-TYPE
        SYNTAX   IpAddress
        MAX-ACCESS  read-only
        STATUS  current
        DESCRIPTION
                "subnet_ip_addr"
        ::= { zBgpV4UniAggregateEntry  4  }

zBgpV4UniAggregateSubnetIpMask OBJECT-TYPE
        SYNTAX   IpAddress
        MAX-ACCESS  read-only
        STATUS  current
        DESCRIPTION
                "subnet_ip_mask"
        ::= { zBgpV4UniAggregateEntry  5  }

zBgpV4UniAggregateAddrModeType OBJECT-TYPE
        SYNTAX   INTEGER  {
                        ipv4_unicast(1)
                    }
        MAX-ACCESS  read-only
        STATUS  current
        DESCRIPTION
                "addr_mode_type"
        ::= { zBgpV4UniAggregateEntry  6  }

zBgpV4UniAggregateVrfName OBJECT-TYPE
        SYNTAX   DisplayString
        MAX-ACCESS  read-only
        STATUS  obsolete
        DESCRIPTION
                "vrf_name"
        ::= { zBgpV4UniAggregateEntry  7  }

zBgpV4UniAggregateAsSet OBJECT-TYPE
        SYNTAX   Unsigned32
        MAX-ACCESS  read-only
        STATUS  current
        DESCRIPTION
                "as_set"
        ::= { zBgpV4UniAggregateEntry  8  }

zBgpV4UniAggregateCount OBJECT-TYPE
        SYNTAX   Unsigned32
        MAX-ACCESS  read-only
        STATUS  current
        DESCRIPTION
                "count"
        ::= { zBgpV4UniAggregateEntry  9  }

zBgpV4UniAggregateStrict OBJECT-TYPE
        SYNTAX   Unsigned32
        MAX-ACCESS  read-only
        STATUS  current
        DESCRIPTION
                "strict"
        ::= { zBgpV4UniAggregateEntry  10  }

zBgpV4UniAggregateSummaryOnly OBJECT-TYPE
        SYNTAX   Unsigned32
        MAX-ACCESS  read-only
        STATUS  current
        DESCRIPTION
                "summary_only"
        ::= { zBgpV4UniAggregateEntry  11  }

zBgpV4UniAggregateSubnet OBJECT-TYPE
        SYNTAX   Unsigned32
        MAX-ACCESS  read-only
        STATUS  current
        DESCRIPTION
                "Subnet"
        ::= { zBgpV4UniAggregateEntry  12  }


--------------------------------------------------------------
--------------------------------------------------------------
--zBgpDampIpv4UniTable
--------------------------------------------------------------
zBgpDampIpv4UniTable OBJECT-TYPE
        SYNTAX  SEQUENCE OF ZBgpDampIpv4UniEntry
        MAX-ACCESS  not-accessible
        STATUS  current
        DESCRIPTION
                "BGP_DAMP_IPV4_UNI"
        ::= { zxr10BgpMIB 6  }

zBgpDampIpv4UniEntry OBJECT-TYPE
        SYNTAX   ZBgpDampIpv4UniEntry
        MAX-ACCESS  not-accessible
        STATUS  current
        DESCRIPTION
                "BGP_DAMP_IPV4_UNI"
        INDEX {zBgpDampIpv4UniLocalAs }
        ::= { zBgpDampIpv4UniTable 1 }

ZBgpDampIpv4UniEntry ::=
        SEQUENCE {
                zBgpDampIpv4UniLocalAs                            Unsigned32,
                zBgpDampIpv4UniAddrModeType                       INTEGER,
                zBgpDampIpv4UniVrfName                            DisplayString,
                zBgpDampIpv4UniDampEnable                         Unsigned32,
                zBgpDampIpv4UniDampRouteMap                       DisplayString,
                zBgpDampIpv4UniDampHalfTime                       Unsigned32,
                zBgpDampIpv4UniDampReuseValue                     Unsigned32,
                zBgpDampIpv4UniDampSuppressValue                  Unsigned32,
                zBgpDampIpv4UniDampMaxSuppress                    Unsigned32
        }

zBgpDampIpv4UniLocalAs OBJECT-TYPE
        SYNTAX   Unsigned32
        MAX-ACCESS  read-only
        STATUS  current
        DESCRIPTION
                "local_as"
        ::= { zBgpDampIpv4UniEntry  1  }

zBgpDampIpv4UniAddrModeType OBJECT-TYPE
        SYNTAX   INTEGER  {
                        ipv4_unicast(1)
                    }
        MAX-ACCESS  read-only
        STATUS  current
        DESCRIPTION
                "addr_mode_type"
        ::= { zBgpDampIpv4UniEntry  2  }

zBgpDampIpv4UniVrfName OBJECT-TYPE
        SYNTAX   DisplayString
        MAX-ACCESS  read-only
        STATUS  obsolete
        DESCRIPTION
                "vrf_name"
        ::= { zBgpDampIpv4UniEntry  3  }

zBgpDampIpv4UniDampEnable OBJECT-TYPE
        SYNTAX   Unsigned32
        MAX-ACCESS  read-only
        STATUS  current
        DESCRIPTION
                "damp_enable"
        ::= { zBgpDampIpv4UniEntry  4  }

zBgpDampIpv4UniDampRouteMap OBJECT-TYPE
        SYNTAX   DisplayString
        MAX-ACCESS  read-only
        STATUS  current
        DESCRIPTION
                "damp_route_map"
        ::= { zBgpDampIpv4UniEntry  5  }

zBgpDampIpv4UniDampHalfTime OBJECT-TYPE
        SYNTAX   Unsigned32
        MAX-ACCESS  read-only
        STATUS  current
        DESCRIPTION
                "damp_half_time"
        ::= { zBgpDampIpv4UniEntry  6  }

zBgpDampIpv4UniDampReuseValue OBJECT-TYPE
        SYNTAX   Unsigned32
        MAX-ACCESS  read-only
        STATUS  current
        DESCRIPTION
                "damp_reuse_value"
        ::= { zBgpDampIpv4UniEntry  7  }

zBgpDampIpv4UniDampSuppressValue OBJECT-TYPE
        SYNTAX   Unsigned32
        MAX-ACCESS  read-only
        STATUS  current
        DESCRIPTION
                "damp_suppress_value"
        ::= { zBgpDampIpv4UniEntry  8  }

zBgpDampIpv4UniDampMaxSuppress OBJECT-TYPE
        SYNTAX   Unsigned32
        MAX-ACCESS  read-only
        STATUS  current
        DESCRIPTION
                "damp_max_suppress"
        ::= { zBgpDampIpv4UniEntry  9  }



--------------------------------------------------------------
--------------------------------------------------------------
--zBgpRedisIpv4UniTable  redistribute
--------------------------------------------------------------
zBgpRedisIpv4UniTable OBJECT-TYPE
        SYNTAX  SEQUENCE OF ZBgpRedisIpv4UniEntry
        MAX-ACCESS  not-accessible
        STATUS  current
        DESCRIPTION
                "BGP_REDIS_IPV4_UNI"
        ::= { zxr10BgpMIB 7  }

zBgpRedisIpv4UniEntry OBJECT-TYPE
        SYNTAX   ZBgpRedisIpv4UniEntry
        MAX-ACCESS  not-accessible
        STATUS  current
        DESCRIPTION
                "BGP_REDIS_IPV4_UNI"
        INDEX {zBgpRedisIpv4UniLocalAs,
               zBgpRedisIpv4UniProtocol,
               zBgpRedisIpv4UniProcessId 
        }
        ::= { zBgpRedisIpv4UniTable 1 }

ZBgpRedisIpv4UniEntry ::=
        SEQUENCE {
                zBgpRedisIpv4UniLocalAs                           Unsigned32,
                zBgpRedisIpv4UniProtocol                          INTEGER,
                zBgpRedisIpv4UniProcessId                         Unsigned32,
                zBgpRedisIpv4UniAddrModeType                      INTEGER,
                zBgpRedisIpv4UniVrfName                           DisplayString,
                zBgpRedisIpv4UniMetric                            Unsigned32,
                zBgpRedisIpv4UniRouteMap                          DisplayString,
                zBgpRedisIpv4UniMetricFlag                        Unsigned32
        }

zBgpRedisIpv4UniLocalAs OBJECT-TYPE
        SYNTAX   Unsigned32
        MAX-ACCESS  read-only
        STATUS  current
        DESCRIPTION
                "local_as"
        ::= { zBgpRedisIpv4UniEntry  1  }

zBgpRedisIpv4UniProtocol OBJECT-TYPE
        SYNTAX   INTEGER {
                        local(1),
                        remote(2),
                        rip(3),
                        isis_level1(4),
                        isis_level2(5),
                        isis_all(6),
                        ospf_ext(7),
                        ospf(8),
                        address(9),
                        ps_busi_addr(10),
                        ps_user_addr(11),
                        nat(12),
                        natpt(13),
                        user_ipaddr(14),
                        user_network(15),
                        ldp(16),
                        user_special(17),
                        slnat64_v4(18),
                        ip_route_se_nat64(19),
                        ip_route_sl_nat64(20),
                        ip_route_aftr(21),
                        ip_route_nd_host(22),
                        ip_route_bras_pool(24),
                        ip_route_ipsec(25)
                 }
        MAX-ACCESS  read-only
        STATUS  current
        DESCRIPTION
                "protocol"
        ::= { zBgpRedisIpv4UniEntry  2  }

zBgpRedisIpv4UniProcessId OBJECT-TYPE
        SYNTAX   Unsigned32
        MAX-ACCESS  read-only
        STATUS  current
        DESCRIPTION
                "process id"
        ::= { zBgpRedisIpv4UniEntry  3  }

zBgpRedisIpv4UniAddrModeType OBJECT-TYPE
        SYNTAX   INTEGER  {
                        ipv4_unicast(1)
                    }
        MAX-ACCESS  read-only
        STATUS  current
        DESCRIPTION
                "addr_mode_type"
        ::= { zBgpRedisIpv4UniEntry  4  }

zBgpRedisIpv4UniVrfName OBJECT-TYPE
        SYNTAX   DisplayString
        MAX-ACCESS  read-only
        STATUS  obsolete
        DESCRIPTION
                "vrf_name"
        ::= { zBgpRedisIpv4UniEntry  5  }

zBgpRedisIpv4UniMetric OBJECT-TYPE
        SYNTAX   Unsigned32
        MAX-ACCESS  read-only
        STATUS  current
        DESCRIPTION
                "metric"
        ::= { zBgpRedisIpv4UniEntry  6  }

zBgpRedisIpv4UniRouteMap OBJECT-TYPE
        SYNTAX   DisplayString
        MAX-ACCESS  read-only
        STATUS  current
        DESCRIPTION
                "route_map"
        ::= { zBgpRedisIpv4UniEntry  7  }

zBgpRedisIpv4UniMetricFlag OBJECT-TYPE
        SYNTAX   Unsigned32
        MAX-ACCESS  read-only
        STATUS  current
        DESCRIPTION
                "metric_flag"
        ::= { zBgpRedisIpv4UniEntry  8  }



--------------------------------------------------------------
--------------------------------------------------------------
--zBgpV4NetworkIpv4UniTable  network
--------------------------------------------------------------
zBgpV4NetworkIpv4UniTable OBJECT-TYPE
        SYNTAX  SEQUENCE OF ZBgpV4NetworkIpv4UniEntry
        MAX-ACCESS  not-accessible
        STATUS  current
        DESCRIPTION
                "BGP_V4_NETWORK_IPV4_UNI"
        ::= { zxr10BgpMIB 8  }

zBgpV4NetworkIpv4UniEntry OBJECT-TYPE
        SYNTAX   ZBgpV4NetworkIpv4UniEntry
        MAX-ACCESS  not-accessible
        STATUS  current
        DESCRIPTION
                "BGP_V4_NETWORK_IPV4_UNI"
        INDEX {zBgpV4NetworkIpv4UniLocalAs,
               zBgpV4NetworkIpv4UniIpAddr,
               zBgpV4NetworkIpv4UniIpMask 
        }
        ::= { zBgpV4NetworkIpv4UniTable 1 }

ZBgpV4NetworkIpv4UniEntry ::=
        SEQUENCE {
                zBgpV4NetworkIpv4UniLocalAs                       Unsigned32,
                zBgpV4NetworkIpv4UniIpAddr                        IpAddress,
                zBgpV4NetworkIpv4UniIpMask                        IpAddress,
                zBgpV4NetworkIpv4UniAddrModeType                  INTEGER,
                zBgpV4NetworkIpv4UniVrfName                       DisplayString,
                zBgpV4NetworkIpv4UniRouteMap                      DisplayString
        }

zBgpV4NetworkIpv4UniLocalAs OBJECT-TYPE
        SYNTAX   Unsigned32
        MAX-ACCESS  read-only
        STATUS  current
        DESCRIPTION
                "local_as"
        ::= { zBgpV4NetworkIpv4UniEntry  1  }

zBgpV4NetworkIpv4UniIpAddr OBJECT-TYPE
        SYNTAX   IpAddress
        MAX-ACCESS  read-only
        STATUS  current
        DESCRIPTION
                "ip_addr"
        ::= { zBgpV4NetworkIpv4UniEntry  2  }

zBgpV4NetworkIpv4UniIpMask OBJECT-TYPE
        SYNTAX   IpAddress
        MAX-ACCESS  read-only
        STATUS  current
        DESCRIPTION
                "ip_mask"
        ::= { zBgpV4NetworkIpv4UniEntry  3  }

zBgpV4NetworkIpv4UniAddrModeType OBJECT-TYPE
        SYNTAX   INTEGER  {
                        ipv4_unicast(1)
                    }
        MAX-ACCESS  read-only
        STATUS  current
        DESCRIPTION
                "addr_mode_type"
        ::= { zBgpV4NetworkIpv4UniEntry  4  }

zBgpV4NetworkIpv4UniVrfName OBJECT-TYPE
        SYNTAX   DisplayString
        MAX-ACCESS  read-only
        STATUS  obsolete
        DESCRIPTION
                "vrf_name"
        ::= { zBgpV4NetworkIpv4UniEntry  5  }

zBgpV4NetworkIpv4UniRouteMap OBJECT-TYPE
        SYNTAX   DisplayString
        MAX-ACCESS  read-only
        STATUS  current
        DESCRIPTION
                "route_map"
        ::= { zBgpV4NetworkIpv4UniEntry  6  }



--------------------------------------------------------------
--------------------------------------------------------------
--zBgpAddrModeTable
--------------------------------------------------------------
zBgpAddrModeTable OBJECT-TYPE
        SYNTAX  SEQUENCE OF ZBgpAddrModeEntry
        MAX-ACCESS  not-accessible
        STATUS  current
        DESCRIPTION
                "BGP_ADDR_MODE"
        ::= { zxr10BgpMIB 9  }

zBgpAddrModeEntry OBJECT-TYPE
        SYNTAX   ZBgpAddrModeEntry
        MAX-ACCESS  not-accessible
        STATUS  current
        DESCRIPTION
                "BGP_ADDR_MODE"
        INDEX {zBgpAddrModeLocalAs,zBgpAddrModeAddrModeType,zBgpAddrModeVrfName}
        ::= { zBgpAddrModeTable 1 }

ZBgpAddrModeEntry ::=
        SEQUENCE {
                zBgpAddrModeLocalAs                               Unsigned32,
                zBgpAddrModeAddrModeType                          INTEGER,
                zBgpAddrModeVrfName                               DisplayString,
                zBgpAddrModeFrr                                   Unsigned32,
                zBgpAddrModeRouterId                              Unsigned32,
                zBgpAddrModeDefInfoOriginate                      Unsigned32,
                zBgpAddrModeDistanceIbgp                          Unsigned32,
                zBgpAddrModeDistanceEbgp                          Unsigned32,
                zBgpAddrModeMaximumPathsIbgp                      Unsigned32,
                zBgpAddrModeMaximumPathsEbgp                      Unsigned32,
                zBgpAddrModeSynchronization                       Unsigned32,
                zBgpAddrModeTableMap                              DisplayString,
                zBgpAddrModeDefaultMetric                         Integer32,
                zBgpAddrModeRouterIdSet                           Unsigned32,
                zBgpAddrModeTemp                                  Unsigned32,
                zBgpAddrModeAdvActiveOnly                         Unsigned32,
                zBgpAddrModeMaxPathsEibgp                         Unsigned32,
                zBgpAddrModeRibOnly                               Unsigned32,
                zBgpAddrModeRibOnlyRmp                            DisplayString,
                zBgpAddrModeFrrWtr                                Integer32,
                zBgpAddrModeEndOfRibTime                          Unsigned32,
                zBgpAddrModeForceRtFilter                         Unsigned32,
                zBgpAddrModeIgpMedIgnore                          Unsigned32,
                zBgpAddrModeBestExternal                          Unsigned32,
                zBgpAddrModeMedUnsign                             Unsigned32,
                zBgpAddrModeTablePolicy                           DisplayString,
                zBgpAddrModeRSInterval                            Unsigned32,
                zBgpAddrModeRSInitial                             Unsigned32,
                zBgpAddrModeRSMaxWait                             Unsigned32,
                zBgpAddrModeRSCmdType                             Unsigned32,
                zBgpAddrModeDistanceLoc                           Unsigned32,
                zBgpAddrModeLabel                                 INTEGER
        }

zBgpAddrModeLocalAs OBJECT-TYPE
        SYNTAX   Unsigned32
        MAX-ACCESS  read-only
        STATUS  current
        DESCRIPTION
                "local_as"
        ::= { zBgpAddrModeEntry  1  }

zBgpAddrModeAddrModeType OBJECT-TYPE
        SYNTAX   INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpAddrModeEntry  2  }

zBgpAddrModeVrfName OBJECT-TYPE
        SYNTAX   DisplayString
        MAX-ACCESS  read-only
        STATUS  current
        DESCRIPTION
                "vrf_name"
        ::= { zBgpAddrModeEntry  3  }

zBgpAddrModeFrr OBJECT-TYPE
        SYNTAX   Unsigned32
        MAX-ACCESS  read-only
        STATUS  current
        DESCRIPTION
                "frr"
        ::= { zBgpAddrModeEntry  4  }

zBgpAddrModeRouterId OBJECT-TYPE
        SYNTAX   Unsigned32
        MAX-ACCESS  read-only
        STATUS  current
        DESCRIPTION
                "router_id"
        ::= { zBgpAddrModeEntry  5  }

zBgpAddrModeDefInfoOriginate OBJECT-TYPE
        SYNTAX   Unsigned32
        MAX-ACCESS  read-only
        STATUS  current
        DESCRIPTION
                "def_info_originate"
        ::= { zBgpAddrModeEntry  6  }

zBgpAddrModeDistanceIbgp OBJECT-TYPE
        SYNTAX   Unsigned32
        MAX-ACCESS  read-only
        STATUS  current
        DESCRIPTION
                "distance_ibgp"
        ::= { zBgpAddrModeEntry  7  }

zBgpAddrModeDistanceEbgp OBJECT-TYPE
        SYNTAX   Unsigned32
        MAX-ACCESS  read-only
        STATUS  current
        DESCRIPTION
                "distance_ebgp"
        ::= { zBgpAddrModeEntry  8  }

zBgpAddrModeMaximumPathsIbgp OBJECT-TYPE
        SYNTAX   Unsigned32
        MAX-ACCESS  read-only
        STATUS  current
        DESCRIPTION
                "maximum_paths_ibgp"
        ::= { zBgpAddrModeEntry  9  }

zBgpAddrModeMaximumPathsEbgp OBJECT-TYPE
        SYNTAX   Unsigned32
        MAX-ACCESS  read-only
        STATUS  current
        DESCRIPTION
                "maximum_paths_ebgp"
        ::= { zBgpAddrModeEntry  10  }

zBgpAddrModeSynchronization OBJECT-TYPE
        SYNTAX   Unsigned32
        MAX-ACCESS  read-only
        STATUS  current
        DESCRIPTION
                "synchronization"
        ::= { zBgpAddrModeEntry  11  }

zBgpAddrModeTableMap OBJECT-TYPE
        SYNTAX   DisplayString
        MAX-ACCESS  read-only
        STATUS  current
        DESCRIPTION
                "table_map"
        ::= { zBgpAddrModeEntry  12  }

zBgpAddrModeDefaultMetric OBJECT-TYPE
        SYNTAX   Integer32
        MAX-ACCESS  read-only
        STATUS  current
        DESCRIPTION
                "default_metric"
        ::= { zBgpAddrModeEntry  13  }

zBgpAddrModeRouterIdSet OBJECT-TYPE
        SYNTAX   Unsigned32
        MAX-ACCESS  read-only
        STATUS  current
        DESCRIPTION
                "router_id_set"
        ::= { zBgpAddrModeEntry  14  }

zBgpAddrModeTemp OBJECT-TYPE
        SYNTAX   Unsigned32
        MAX-ACCESS  read-only
        STATUS  obsolete
        DESCRIPTION
                "temp"
        ::= { zBgpAddrModeEntry  15  }

zBgpAddrModeAdvActiveOnly OBJECT-TYPE
        SYNTAX   Unsigned32
        MAX-ACCESS  read-only
        STATUS  current
        DESCRIPTION
                "advertise_active_only(1 enable,0 disable)"
        ::= { zBgpAddrModeEntry  16  }

zBgpAddrModeMaxPathsEibgp OBJECT-TYPE
        SYNTAX   Unsigned32
        MAX-ACCESS  read-only
        STATUS  current
        DESCRIPTION
                "maximum_paths_eibgp"
        ::= { zBgpAddrModeEntry  17  }

zBgpAddrModeRibOnly OBJECT-TYPE
        SYNTAX   Unsigned32
        MAX-ACCESS  read-only
        STATUS  current
        DESCRIPTION
                "rib_only(1 enable,0 disable)"
        ::= { zBgpAddrModeEntry  18  }
        
zBgpAddrModeRibOnlyRmp OBJECT-TYPE
        SYNTAX   DisplayString
        MAX-ACCESS  read-only
        STATUS  current
        DESCRIPTION
                "rib_only_route_map(route-map name)"
        ::= { zBgpAddrModeEntry  19  }

zBgpAddrModeFrrWtr OBJECT-TYPE
        SYNTAX   Integer32
        MAX-ACCESS  read-only
        STATUS  current
        DESCRIPTION
                "frr_wtr"
        ::= { zBgpAddrModeEntry  20  }

zBgpAddrModeEndOfRibTime OBJECT-TYPE
        SYNTAX   Unsigned32
        MAX-ACCESS  read-only
        STATUS  current
        DESCRIPTION
                "end_of_rib_time"
        ::= { zBgpAddrModeEntry  21  }

zBgpAddrModeForceRtFilter OBJECT-TYPE
        SYNTAX   Unsigned32
        MAX-ACCESS  read-only
        STATUS  current
        DESCRIPTION
                "force_rt_filter(1 enable,0 disable)"
        ::= { zBgpAddrModeEntry  22  }

zBgpAddrModeIgpMedIgnore OBJECT-TYPE
        SYNTAX   Unsigned32
        MAX-ACCESS  read-only
        STATUS  current
        DESCRIPTION
                "igpmetric_ignore(1 enable,0 disable)"
        ::= { zBgpAddrModeEntry  23  }

zBgpAddrModeBestExternal OBJECT-TYPE
        SYNTAX   Unsigned32
        MAX-ACCESS  read-only
        STATUS  current
        DESCRIPTION
                "best_external(1 enable,0 disable)"
        ::= { zBgpAddrModeEntry  24  }

zBgpAddrModeMedUnsign OBJECT-TYPE
        SYNTAX   Unsigned32
        MAX-ACCESS  read-only
        STATUS  current
        DESCRIPTION
                "Unsigned32 default_metric"
        ::= { zBgpAddrModeEntry  25  }

zBgpAddrModeTablePolicy OBJECT-TYPE
        SYNTAX   DisplayString
        MAX-ACCESS  read-only
        STATUS  current
        DESCRIPTION
                "route policy name"
        ::= { zBgpAddrModeEntry  26  }

zBgpAddrModeRSInterval OBJECT-TYPE
        SYNTAX   Unsigned32
        MAX-ACCESS  read-only
        STATUS  current
        DESCRIPTION
                "route scan timer interval wait time(ms)"
        ::= { zBgpAddrModeEntry  27  }

zBgpAddrModeRSInitial  OBJECT-TYPE
        SYNTAX   Unsigned32
        MAX-ACCESS  read-only
        STATUS  current
        DESCRIPTION
                "route scan timer initial time(ms)"
        ::= { zBgpAddrModeEntry  28  }

zBgpAddrModeRSMaxWait OBJECT-TYPE
        SYNTAX   Unsigned32
        MAX-ACCESS  read-only
        STATUS  current
        DESCRIPTION
                "route scan timer max wait time(ms)"
        ::= { zBgpAddrModeEntry  29  }

zBgpAddrModeRSCmdType OBJECT-TYPE
        SYNTAX   Unsigned32
        MAX-ACCESS  read-only
        STATUS  current
        DESCRIPTION
                "route scan timer cmd type"
        ::= { zBgpAddrModeEntry  30  }

zBgpAddrModeDistanceLoc OBJECT-TYPE
        SYNTAX   Unsigned32
        MAX-ACCESS  read-only
        STATUS  current
        DESCRIPTION
                "Distance for BGP local routes."
        ::= { zBgpAddrModeEntry  31  }

zBgpAddrModeLabel OBJECT-TYPE
        SYNTAX   INTEGER  {perVrfByRt(1), perNexthop(2), perPrefix(3), perVrfByRd(4)}
        MAX-ACCESS  read-only
        STATUS  current
        DESCRIPTION
                "Mpls label mode."
        ::= { zBgpAddrModeEntry  32  }
--------------------------------------------------------------
--------------------------------------------------------------
--zBgpV4VrfAggregateTable
--------------------------------------------------------------
zBgpV4VrfAggregateTable OBJECT-TYPE
        SYNTAX  SEQUENCE OF ZBgpV4VrfAggregateEntry
        MAX-ACCESS  not-accessible
        STATUS  current
        DESCRIPTION
                "BGP_V4_VRF_AGGREGATE"
        ::= { zxr10BgpMIB 10  }

zBgpV4VrfAggregateEntry OBJECT-TYPE
        SYNTAX   ZBgpV4VrfAggregateEntry
        MAX-ACCESS  not-accessible
        STATUS  current
        DESCRIPTION
                "BGP_V4_VRF_AGGREGATE"
        INDEX {zBgpV4VrfAggregateLocalAs,
               zBgpV4VrfAggregateAddrModeType,
               zBgpV4VrfAggregateVrfName,
               zBgpV4VrfAggregateIpAddr,
               zBgpV4VrfAggregateIpMask
        }
        ::= { zBgpV4VrfAggregateTable 1 }

ZBgpV4VrfAggregateEntry ::=
        SEQUENCE {
                zBgpV4VrfAggregateLocalAs                         Unsigned32,
                zBgpV4VrfAggregateAddrModeType                    INTEGER,
                zBgpV4VrfAggregateVrfName                         DisplayString,
                zBgpV4VrfAggregateIpAddr                          IpAddress,
                zBgpV4VrfAggregateIpMask                          IpAddress,
                zBgpV4VrfAggregateAsSet                           Unsigned32,
                zBgpV4VrfAggregateSummaryOnly                     Unsigned32,
                zBgpV4VrfAggregateStrict                          Unsigned32,
                zBgpV4VrfAggregateAttributeMap                    DisplayString,
                zBgpV4VrfAggregateSuppressMap                     DisplayString
        }

zBgpV4VrfAggregateLocalAs OBJECT-TYPE
        SYNTAX   Unsigned32
        MAX-ACCESS  read-only
        STATUS  current
        DESCRIPTION
                "local_as"
        ::= { zBgpV4VrfAggregateEntry  1  }

zBgpV4VrfAggregateAddrModeType OBJECT-TYPE
        SYNTAX   INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpV4VrfAggregateEntry  2  }

zBgpV4VrfAggregateVrfName OBJECT-TYPE
        SYNTAX   DisplayString
        MAX-ACCESS  read-only
        STATUS  current
        DESCRIPTION
                "vrf_name"
        ::= { zBgpV4VrfAggregateEntry  3  }

zBgpV4VrfAggregateIpAddr OBJECT-TYPE
        SYNTAX   IpAddress
        MAX-ACCESS  read-only
        STATUS  current
        DESCRIPTION
                "ip_addr"
        ::= { zBgpV4VrfAggregateEntry  4  }

zBgpV4VrfAggregateIpMask OBJECT-TYPE
        SYNTAX   IpAddress
        MAX-ACCESS  read-only
        STATUS  current
        DESCRIPTION
                "ip_mask"
        ::= { zBgpV4VrfAggregateEntry  5  }

zBgpV4VrfAggregateAsSet OBJECT-TYPE
        SYNTAX   Unsigned32
        MAX-ACCESS  read-only
        STATUS  current
        DESCRIPTION
                "as_set"
        ::= { zBgpV4VrfAggregateEntry  6  }

zBgpV4VrfAggregateSummaryOnly OBJECT-TYPE
        SYNTAX   Unsigned32
        MAX-ACCESS  read-only
        STATUS  current
        DESCRIPTION
                "summary_only"
        ::= { zBgpV4VrfAggregateEntry  7  }

zBgpV4VrfAggregateStrict OBJECT-TYPE
        SYNTAX   Unsigned32
        MAX-ACCESS  read-only
        STATUS  current
        DESCRIPTION
                "strict"
        ::= { zBgpV4VrfAggregateEntry  8  }

zBgpV4VrfAggregateAttributeMap OBJECT-TYPE
        SYNTAX   DisplayString
        MAX-ACCESS  read-only
        STATUS  current
        DESCRIPTION
                "attribute_map"
        ::= { zBgpV4VrfAggregateEntry  9  }

zBgpV4VrfAggregateSuppressMap OBJECT-TYPE
        SYNTAX   DisplayString
        MAX-ACCESS  read-only
        STATUS  current
        DESCRIPTION
                "suppress_map"
        ::= { zBgpV4VrfAggregateEntry  10  }



--------------------------------------------------------------
--------------------------------------------------------------
--zBgpV6UniAggregateTable
--------------------------------------------------------------
zBgpV6UniAggregateTable OBJECT-TYPE
        SYNTAX  SEQUENCE OF ZBgpV6UniAggregateEntry
        MAX-ACCESS  not-accessible
        STATUS  current
        DESCRIPTION
                "BGP_V6_UNI_AGGREGATE"
        ::= { zxr10BgpMIB 11  }

zBgpV6UniAggregateEntry OBJECT-TYPE
        SYNTAX   ZBgpV6UniAggregateEntry
        MAX-ACCESS  not-accessible
        STATUS  current
        DESCRIPTION
                "BGP_V6_UNI_AGGREGATE"
        INDEX {zBgpV6UniAggregateLocalAs,
               zBgpV6UniAggregateAddrModeType,
               zBgpV6UniAggregateVrfName,
               zBgpV6UniAggregateIpv6Addr,
               zBgpV6UniAggregateIpv6Mask 
        }
        ::= { zBgpV6UniAggregateTable 1 }

ZBgpV6UniAggregateEntry ::=
        SEQUENCE {
                zBgpV6UniAggregateLocalAs                         Unsigned32,
                zBgpV6UniAggregateAddrModeType                    INTEGER,
                zBgpV6UniAggregateVrfName                         DisplayString,
                zBgpV6UniAggregateIpv6Addr                        DisplayString,
                zBgpV6UniAggregateIpv6Mask                        Unsigned32,
                zBgpV6UniAggregateAsSet                           Unsigned32,
                zBgpV6UniAggregateSummaryOnly                     Unsigned32,
                zBgpV6UniAggregateStrict                          Unsigned32,
                zBgpV6UniAggregateAttributeMap                    DisplayString,
                zBgpV6UniAggregateSuppressMap                     DisplayString
        }

zBgpV6UniAggregateLocalAs OBJECT-TYPE
        SYNTAX   Unsigned32
        MAX-ACCESS  read-only
        STATUS  current
        DESCRIPTION
                "local_as"
        ::= { zBgpV6UniAggregateEntry  1  }

zBgpV6UniAggregateAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpV6UniAggregateEntry  2  }

zBgpV6UniAggregateVrfName OBJECT-TYPE
        SYNTAX   DisplayString
        MAX-ACCESS  read-only
        STATUS  current
        DESCRIPTION
                "vrf_name"
        ::= { zBgpV6UniAggregateEntry  3  }

zBgpV6UniAggregateIpv6Addr OBJECT-TYPE
        SYNTAX   DisplayString
        MAX-ACCESS  read-only
        STATUS  current
        DESCRIPTION
                "ipv6_addr"
        ::= { zBgpV6UniAggregateEntry  4  }

zBgpV6UniAggregateIpv6Mask OBJECT-TYPE
        SYNTAX   Unsigned32
        MAX-ACCESS  read-only
        STATUS  current
        DESCRIPTION
                "ipv6_mask"
        ::= { zBgpV6UniAggregateEntry  5  }

zBgpV6UniAggregateAsSet OBJECT-TYPE
        SYNTAX   Unsigned32
        MAX-ACCESS  read-only
        STATUS  current
        DESCRIPTION
                "as_set"
        ::= { zBgpV6UniAggregateEntry  6  }

zBgpV6UniAggregateSummaryOnly OBJECT-TYPE
        SYNTAX   Unsigned32
        MAX-ACCESS  read-only
        STATUS  current
        DESCRIPTION
                "summary_only"
        ::= { zBgpV6UniAggregateEntry  7  }

zBgpV6UniAggregateStrict OBJECT-TYPE
        SYNTAX   Unsigned32
        MAX-ACCESS  read-only
        STATUS  current
        DESCRIPTION
                "strict"
        ::= { zBgpV6UniAggregateEntry  8  }

zBgpV6UniAggregateAttributeMap OBJECT-TYPE
        SYNTAX   DisplayString
        MAX-ACCESS  read-only
        STATUS  current
        DESCRIPTION
                "attribute_map"
        ::= { zBgpV6UniAggregateEntry  9  }

zBgpV6UniAggregateSuppressMap OBJECT-TYPE
        SYNTAX   DisplayString
        MAX-ACCESS  read-only
        STATUS  current
        DESCRIPTION
                "suppress_map"
        ::= { zBgpV6UniAggregateEntry  10  }



--------------------------------------------------------------
--------------------------------------------------------------
--zBgpDampTable
--------------------------------------------------------------
zBgpDampTable OBJECT-TYPE
        SYNTAX  SEQUENCE OF ZBgpDampEntry
        MAX-ACCESS  not-accessible
        STATUS  current
        DESCRIPTION
                "BGP_DAMP"
        ::= { zxr10BgpMIB 12  }

zBgpDampEntry OBJECT-TYPE
        SYNTAX   ZBgpDampEntry
        MAX-ACCESS  not-accessible
        STATUS  current
        DESCRIPTION
                "BGP_DAMP"
        INDEX {zBgpDampLocalAs,zBgpDampAddrModeType,zBgpDampVrfName }
        ::= { zBgpDampTable 1 }

ZBgpDampEntry ::=
        SEQUENCE {
                zBgpDampLocalAs                                   Unsigned32,
                zBgpDampAddrModeType                              INTEGER,
                zBgpDampVrfName                                   DisplayString,
                zBgpDampDampEnable                                Unsigned32,
                zBgpDampDampRouteMap                              DisplayString,
                zBgpDampDampHalfTime                              Unsigned32,
                zBgpDampDampReuseValue                            Unsigned32,
                zBgpDampDampSuppressValue                         Unsigned32,
                zBgpDampDampMaxSuppress                           Unsigned32
        }

zBgpDampLocalAs OBJECT-TYPE
        SYNTAX   Unsigned32
        MAX-ACCESS  read-only
        STATUS  current
        DESCRIPTION
                "local_as"
        ::= { zBgpDampEntry  1  }

zBgpDampAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpDampEntry  2  }

zBgpDampVrfName OBJECT-TYPE
        SYNTAX   DisplayString
        MAX-ACCESS  read-only
        STATUS  current
        DESCRIPTION
                "vrf_name"
        ::= { zBgpDampEntry  3  }

zBgpDampDampEnable OBJECT-TYPE
        SYNTAX   Unsigned32
        MAX-ACCESS  read-only
        STATUS  current
        DESCRIPTION
                "damp_enable"
        ::= { zBgpDampEntry  4  }

zBgpDampDampRouteMap OBJECT-TYPE
        SYNTAX   DisplayString
        MAX-ACCESS  read-only
        STATUS  current
        DESCRIPTION
                "damp_route_map"
        ::= { zBgpDampEntry  5  }

zBgpDampDampHalfTime OBJECT-TYPE
        SYNTAX   Unsigned32
        MAX-ACCESS  read-only
        STATUS  current
        DESCRIPTION
                "damp_half_time"
        ::= { zBgpDampEntry  6  }

zBgpDampDampReuseValue OBJECT-TYPE
        SYNTAX   Unsigned32
        MAX-ACCESS  read-only
        STATUS  current
        DESCRIPTION
                "damp_reuse_value"
        ::= { zBgpDampEntry  7  }

zBgpDampDampSuppressValue OBJECT-TYPE
        SYNTAX   Unsigned32
        MAX-ACCESS  read-only
        STATUS  current
        DESCRIPTION
                "damp_suppress_value"
        ::= { zBgpDampEntry  8  }

zBgpDampDampMaxSuppress OBJECT-TYPE
        SYNTAX   Unsigned32
        MAX-ACCESS  read-only
        STATUS  current
        DESCRIPTION
                "damp_max_suppress"
        ::= { zBgpDampEntry  9  }



--------------------------------------------------------------
--------------------------------------------------------------
--zBgpRedisTable  redistribute
--------------------------------------------------------------
zBgpRedisTable OBJECT-TYPE
        SYNTAX  SEQUENCE OF ZBgpRedisEntry
        MAX-ACCESS  not-accessible
        STATUS  current
        DESCRIPTION
                "BGP_REDIS"
        ::= { zxr10BgpMIB 13  }

zBgpRedisEntry OBJECT-TYPE
        SYNTAX   ZBgpRedisEntry
        MAX-ACCESS  not-accessible
        STATUS  current
        DESCRIPTION
                "BGP_REDIS"
        INDEX {zBgpRedisLocalAs,
               zBgpRedisAddrModeType,
               zBgpRedisVrfName,
               zBgpRedisProtocol,
               zBgpRedisProcessId 
        }
        ::= { zBgpRedisTable 1 }

ZBgpRedisEntry ::=
        SEQUENCE {
                zBgpRedisLocalAs                                  Unsigned32,
                zBgpRedisAddrModeType                             INTEGER,
                zBgpRedisVrfName                                  DisplayString,
                zBgpRedisProtocol                                 INTEGER,
                zBgpRedisProcessId                                Unsigned32,
                zBgpRedisMetric                                   Unsigned32,
                zBgpRedisRouteMap                                 DisplayString,
                zBgpRedisMetricFlag                               Unsigned32
        }

zBgpRedisLocalAs OBJECT-TYPE
        SYNTAX   Unsigned32
        MAX-ACCESS  read-only
        STATUS  current
        DESCRIPTION
                "local_as"
        ::= { zBgpRedisEntry  1  }

zBgpRedisAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpRedisEntry  2  }

zBgpRedisVrfName OBJECT-TYPE
        SYNTAX   DisplayString
        MAX-ACCESS  read-only
        STATUS  current
        DESCRIPTION
                "vrf_name"
        ::= { zBgpRedisEntry  3  }

zBgpRedisProtocol OBJECT-TYPE
        SYNTAX   INTEGER {
                        local(1),
                        remote(2),
                        rip(3),
                        isis_level1(4),
                        isis_level2(5),
                        isis_all(6),
                        ospf_ext(7),
                        ospf(8),
                        address(9),
                        ps_busi_addr(10),
                        ps_user_addr(11),
                        nat(12),
                        natpt(13),
                        user_ipaddr(14),
                        user_network(15),
                        ldp(16),
                        user_special(17),
                        slnat64_v4(18),
                        ip_route_se_nat64(19),
                        ip_route_sl_nat64(20),
                        ip_route_aftr(21),
                        ip_route_nd_host(22),
                        dhcp_pd(23),
                        ip_route_bras_pool(24),
                        ip_route_ipsec(25)
                 }
        MAX-ACCESS  read-only
        STATUS  current
        DESCRIPTION
                "protocol"
        ::= { zBgpRedisEntry  4  }

zBgpRedisProcessId OBJECT-TYPE
        SYNTAX   Unsigned32
        MAX-ACCESS  read-only
        STATUS  current
        DESCRIPTION
                "process id"
        ::= { zBgpRedisEntry  5  }

zBgpRedisMetric OBJECT-TYPE
        SYNTAX   Unsigned32
        MAX-ACCESS  read-only
        STATUS  current
        DESCRIPTION
                "metric"
        ::= { zBgpRedisEntry  6  }

zBgpRedisRouteMap OBJECT-TYPE
        SYNTAX   DisplayString
        MAX-ACCESS  read-only
        STATUS  current
        DESCRIPTION
                "route_map"
        ::= { zBgpRedisEntry  7  }

zBgpRedisMetricFlag OBJECT-TYPE
        SYNTAX   Unsigned32
        MAX-ACCESS  read-only
        STATUS  current
        DESCRIPTION
                "metric_flag"
        ::= { zBgpRedisEntry  8  }



--------------------------------------------------------------
--------------------------------------------------------------
--zBgpV4NetworkTable  network
--------------------------------------------------------------
zBgpV4NetworkTable OBJECT-TYPE
        SYNTAX  SEQUENCE OF ZBgpV4NetworkEntry
        MAX-ACCESS  not-accessible
        STATUS  current
        DESCRIPTION
                "BGP_V4_NETWORK"
        ::= { zxr10BgpMIB 14  }

zBgpV4NetworkEntry OBJECT-TYPE
        SYNTAX   ZBgpV4NetworkEntry
        MAX-ACCESS  not-accessible
        STATUS  current
        DESCRIPTION
                "BGP_V4_NETWORK"
        INDEX {zBgpV4NetworkLocalAs,
               zBgpV4NetworkAddrModeType,
               zBgpV4NetworkVrfName,
               zBgpV4NetworkIpAddr,
               zBgpV4NetworkIpMask 
        }
        ::= { zBgpV4NetworkTable 1 }

ZBgpV4NetworkEntry ::=
        SEQUENCE {
                zBgpV4NetworkLocalAs                              Unsigned32,
                zBgpV4NetworkAddrModeType                         INTEGER,
                zBgpV4NetworkVrfName                              DisplayString,
                zBgpV4NetworkIpAddr                               IpAddress,
                zBgpV4NetworkIpMask                               IpAddress,
                zBgpV4NetworkRouteMap                             DisplayString
        }

zBgpV4NetworkLocalAs OBJECT-TYPE
        SYNTAX   Unsigned32
        MAX-ACCESS  read-only
        STATUS  current
        DESCRIPTION
                "local_as"
        ::= { zBgpV4NetworkEntry  1  }

zBgpV4NetworkAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpV4NetworkEntry  2  }

zBgpV4NetworkVrfName OBJECT-TYPE
        SYNTAX   DisplayString
        MAX-ACCESS  read-only
        STATUS  current
        DESCRIPTION
                "vrf_name"
        ::= { zBgpV4NetworkEntry  3  }

zBgpV4NetworkIpAddr OBJECT-TYPE
        SYNTAX   IpAddress
        MAX-ACCESS  read-only
        STATUS  current
        DESCRIPTION
                "ip_addr"
        ::= { zBgpV4NetworkEntry  4  }

zBgpV4NetworkIpMask OBJECT-TYPE
        SYNTAX   IpAddress
        MAX-ACCESS  read-only
        STATUS  current
        DESCRIPTION
                "ip_mask"
        ::= { zBgpV4NetworkEntry  5  }

zBgpV4NetworkRouteMap OBJECT-TYPE
        SYNTAX   DisplayString
        MAX-ACCESS  read-only
        STATUS  current
        DESCRIPTION
                "route_map"
        ::= { zBgpV4NetworkEntry  6  }



--------------------------------------------------------------
--------------------------------------------------------------
--zBgpV6NetworkTable  network
--------------------------------------------------------------
zBgpV6NetworkTable OBJECT-TYPE
        SYNTAX  SEQUENCE OF ZBgpV6NetworkEntry
        MAX-ACCESS  not-accessible
        STATUS  current
        DESCRIPTION
                "BGP_V6_NETWORK"
        ::= { zxr10BgpMIB 15  }

zBgpV6NetworkEntry OBJECT-TYPE
        SYNTAX   ZBgpV6NetworkEntry
        MAX-ACCESS  not-accessible
        STATUS  current
        DESCRIPTION
                "BGP_V6_NETWORK"
        INDEX {zBgpV6NetworkLocalAs,
               zBgpV6NetworkAddrModeType,
               zBgpV6NetworkVrfName,
               zBgpV6NetworkIpv6Addr,
               zBgpV6NetworkIpv6Mask 
        }
        ::= { zBgpV6NetworkTable 1 }

ZBgpV6NetworkEntry ::=
        SEQUENCE {
                zBgpV6NetworkLocalAs                              Unsigned32,
                zBgpV6NetworkAddrModeType                         INTEGER,
                zBgpV6NetworkVrfName                              DisplayString,
                zBgpV6NetworkIpv6Addr                             DisplayString,
                zBgpV6NetworkIpv6Mask                             Unsigned32,
                zBgpV6NetworkRouteMap                             DisplayString
        }

zBgpV6NetworkLocalAs OBJECT-TYPE
        SYNTAX   Unsigned32
        MAX-ACCESS  read-only
        STATUS  current
        DESCRIPTION
                "local_as"
        ::= { zBgpV6NetworkEntry  1  }

zBgpV6NetworkAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpV6NetworkEntry  2  }

zBgpV6NetworkVrfName OBJECT-TYPE
        SYNTAX   DisplayString
        MAX-ACCESS  read-only
        STATUS  current
        DESCRIPTION
                "vrf_name"
        ::= { zBgpV6NetworkEntry  3  }

zBgpV6NetworkIpv6Addr OBJECT-TYPE
        SYNTAX   DisplayString
        MAX-ACCESS  read-only
        STATUS  current
        DESCRIPTION
                "ipv6_addr"
        ::= { zBgpV6NetworkEntry  4  }

zBgpV6NetworkIpv6Mask OBJECT-TYPE
        SYNTAX   Unsigned32
        MAX-ACCESS  read-only
        STATUS  current
        DESCRIPTION
                "ipv6_mask"
        ::= { zBgpV6NetworkEntry  5  }

zBgpV6NetworkRouteMap OBJECT-TYPE
        SYNTAX   DisplayString
        MAX-ACCESS  read-only
        STATUS  current
        DESCRIPTION
                "route_map"
        ::= { zBgpV6NetworkEntry  6  }



--------------------------------------------------------------
--------------------------------------------------------------
--zBgpAddrModeIpv4VrfmulTable
--------------------------------------------------------------
zBgpAddrModeIpv4VrfmulTable OBJECT-TYPE
        SYNTAX  SEQUENCE OF ZBgpAddrModeIpv4VrfmulEntry
        MAX-ACCESS  not-accessible
        STATUS  current
        DESCRIPTION
                "BGP_ADDR_MODE_IPV4_VRFMUL"
        ::= { zxr10BgpMIB 16  }

zBgpAddrModeIpv4VrfmulEntry OBJECT-TYPE
        SYNTAX   ZBgpAddrModeIpv4VrfmulEntry
        MAX-ACCESS  not-accessible
        STATUS  current
        DESCRIPTION
                "BGP_ADDR_MODE_IPV4_VRFMUL"
        INDEX {zBgpAddrModeIpv4VrfmulLocalAs,
               zBgpAddrModeIpv4VrfmulAddrModeType,
               zBgpAddrModeIpv4VrfmulVrfName 
        }
        ::= { zBgpAddrModeIpv4VrfmulTable 1 }

ZBgpAddrModeIpv4VrfmulEntry ::=
        SEQUENCE {
                zBgpAddrModeIpv4VrfmulLocalAs                     Unsigned32,
                zBgpAddrModeIpv4VrfmulAddrModeType                INTEGER,
                zBgpAddrModeIpv4VrfmulVrfName                     DisplayString,
                zBgpAddrModeIpv4VrfmulFrr                         Unsigned32,
                zBgpAddrModeIpv4VrfmulRouterId                    Unsigned32,
                zBgpAddrModeIpv4VrfmulDefInfoOriginate            Unsigned32,
                zBgpAddrModeIpv4VrfmulDistanceIbgp                Unsigned32,
                zBgpAddrModeIpv4VrfmulDistanceEbgp                Unsigned32,
                zBgpAddrModeIpv4VrfmulMaximumPathsIbgp            Unsigned32,
                zBgpAddrModeIpv4VrfmulMaximumPathsEbgp            Unsigned32,
                zBgpAddrModeIpv4VrfmulSynchronization             Unsigned32,
                zBgpAddrModeIpv4VrfmulTableMap                    DisplayString,
                zBgpAddrModeIpv4VrfmulDefaultMetric               Integer32,
                zBgpAddrModeIpv4VrfmulRouterIdSet                 Unsigned32,
                zBgpAddrModeIpv4VrfmulTemp                        Unsigned32,
                zBgpAddrModeIpv4VrfmulMedUnsign                   Unsigned32
        }

zBgpAddrModeIpv4VrfmulLocalAs OBJECT-TYPE
        SYNTAX   Unsigned32
        MAX-ACCESS  read-only
        STATUS  current
        DESCRIPTION
                "local_as"
        ::= { zBgpAddrModeIpv4VrfmulEntry  1  }

zBgpAddrModeIpv4VrfmulAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpAddrModeIpv4VrfmulEntry  2  }

zBgpAddrModeIpv4VrfmulVrfName OBJECT-TYPE
        SYNTAX   DisplayString
        MAX-ACCESS  read-only
        STATUS  current
        DESCRIPTION
                "vrf_name"
        ::= { zBgpAddrModeIpv4VrfmulEntry  3  }

zBgpAddrModeIpv4VrfmulFrr OBJECT-TYPE
        SYNTAX   Unsigned32
        MAX-ACCESS  read-only
        STATUS  obsolete
        DESCRIPTION
                "frr"
        ::= { zBgpAddrModeIpv4VrfmulEntry  4  }

zBgpAddrModeIpv4VrfmulRouterId OBJECT-TYPE
        SYNTAX   Unsigned32
        MAX-ACCESS  read-only
        STATUS  obsolete
        DESCRIPTION
                "router_id"
        ::= { zBgpAddrModeIpv4VrfmulEntry  5  }

zBgpAddrModeIpv4VrfmulDefInfoOriginate OBJECT-TYPE
        SYNTAX   Unsigned32
        MAX-ACCESS  read-only
        STATUS  obsolete
        DESCRIPTION
                "def_info_originate"
        ::= { zBgpAddrModeIpv4VrfmulEntry  6  }

zBgpAddrModeIpv4VrfmulDistanceIbgp OBJECT-TYPE
        SYNTAX   Unsigned32
        MAX-ACCESS  read-only
        STATUS  obsolete
        DESCRIPTION
                "distance_ibgp"
        ::= { zBgpAddrModeIpv4VrfmulEntry  7  }

zBgpAddrModeIpv4VrfmulDistanceEbgp OBJECT-TYPE
        SYNTAX   Unsigned32
        MAX-ACCESS  read-only
        STATUS  obsolete
        DESCRIPTION
                "distance_ebgp"
        ::= { zBgpAddrModeIpv4VrfmulEntry  8  }

zBgpAddrModeIpv4VrfmulMaximumPathsIbgp OBJECT-TYPE
        SYNTAX   Unsigned32
        MAX-ACCESS  read-only
        STATUS  obsolete
        DESCRIPTION
                "maximum_paths_ibgp"
        ::= { zBgpAddrModeIpv4VrfmulEntry  9  }

zBgpAddrModeIpv4VrfmulMaximumPathsEbgp OBJECT-TYPE
        SYNTAX   Unsigned32
        MAX-ACCESS  read-only
        STATUS  obsolete
        DESCRIPTION
                "maximum_paths_ebgp"
        ::= { zBgpAddrModeIpv4VrfmulEntry  10  }

zBgpAddrModeIpv4VrfmulSynchronization OBJECT-TYPE
        SYNTAX   Unsigned32
        MAX-ACCESS  read-only
        STATUS  obsolete
        DESCRIPTION
                "synchronization"
        ::= { zBgpAddrModeIpv4VrfmulEntry  11  }

zBgpAddrModeIpv4VrfmulTableMap OBJECT-TYPE
        SYNTAX   DisplayString
        MAX-ACCESS  read-only
        STATUS  obsolete
        DESCRIPTION
                "table_map"
        ::= { zBgpAddrModeIpv4VrfmulEntry  12  }

zBgpAddrModeIpv4VrfmulDefaultMetric OBJECT-TYPE
        SYNTAX   Integer32
        MAX-ACCESS  read-only
        STATUS  obsolete
        DESCRIPTION
                "default_metric"
        ::= { zBgpAddrModeIpv4VrfmulEntry  13  }

zBgpAddrModeIpv4VrfmulRouterIdSet OBJECT-TYPE
        SYNTAX   Unsigned32
        MAX-ACCESS  read-only
        STATUS  obsolete
        DESCRIPTION
                "router_id_set"
        ::= { zBgpAddrModeIpv4VrfmulEntry  14  }

zBgpAddrModeIpv4VrfmulTemp OBJECT-TYPE
        SYNTAX   Unsigned32
        MAX-ACCESS  read-only
        STATUS  obsolete
        DESCRIPTION
                "temp"
        ::= { zBgpAddrModeIpv4VrfmulEntry  15  }

zBgpAddrModeIpv4VrfmulMedUnsign OBJECT-TYPE
        SYNTAX   Unsigned32
        MAX-ACCESS  read-only
        STATUS  obsolete
        DESCRIPTION
                "Unsigned32 default_metric"
        ::= { zBgpAddrModeIpv4VrfmulEntry  16  }

--------------------------------------------------------------
--------------------------------------------------------------
--zBgpRedisIpv4VrfmulTable  redistribute
--------------------------------------------------------------
zBgpRedisIpv4VrfmulTable OBJECT-TYPE
        SYNTAX  SEQUENCE OF ZBgpRedisIpv4VrfmulEntry
        MAX-ACCESS  not-accessible
        STATUS  current
        DESCRIPTION
                "BGP_REDIS_IPV4_VRFMUL"
        ::= { zxr10BgpMIB 17  }

zBgpRedisIpv4VrfmulEntry OBJECT-TYPE
        SYNTAX   ZBgpRedisIpv4VrfmulEntry
        MAX-ACCESS  not-accessible
        STATUS  current
        DESCRIPTION
                "BGP_REDIS_IPV4_VRFMUL"
        INDEX {zBgpRedisIpv4VrfmulLocalAs,
               zBgpRedisIpv4VrfmulAddrModeType,
               zBgpRedisIpv4VrfmulVrfName,
               zBgpRedisIpv4VrfmulProtocol,
               zBgpRedisIpv4VrfmulProcessId 
        }
        ::= { zBgpRedisIpv4VrfmulTable 1 }

ZBgpRedisIpv4VrfmulEntry ::=
        SEQUENCE {
                zBgpRedisIpv4VrfmulLocalAs                        Unsigned32,
                zBgpRedisIpv4VrfmulAddrModeType                   INTEGER,
                zBgpRedisIpv4VrfmulVrfName                        DisplayString,
                zBgpRedisIpv4VrfmulProtocol                       INTEGER,
                zBgpRedisIpv4VrfmulProcessId                      Unsigned32,
                zBgpRedisIpv4VrfmulMetric                         Unsigned32,
                zBgpRedisIpv4VrfmulRouteMap                       DisplayString,
                zBgpRedisIpv4VrfmulMetricFlag                     Unsigned32
        }

zBgpRedisIpv4VrfmulLocalAs OBJECT-TYPE
        SYNTAX   Unsigned32
        MAX-ACCESS  read-only
        STATUS  current
        DESCRIPTION
                "local_as"
        ::= { zBgpRedisIpv4VrfmulEntry  1  }

zBgpRedisIpv4VrfmulAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpRedisIpv4VrfmulEntry  2  }

zBgpRedisIpv4VrfmulVrfName OBJECT-TYPE
        SYNTAX   DisplayString
        MAX-ACCESS  read-only
        STATUS  current
        DESCRIPTION
                "vrf_name"
        ::= { zBgpRedisIpv4VrfmulEntry  3  }

zBgpRedisIpv4VrfmulProtocol OBJECT-TYPE
        SYNTAX   INTEGER {
                        local(1),
                        remote(2),
                        rip(3),
                        isis_level1(4),
                        isis_level2(5),
                        isis_all(6),
                        ospf_ext(7),
                        ospf(8),
                        address(9),
                        ps_busi_addr(10),
                        ps_user_addr(11),
                        nat(12),
                        natpt(13),
                        user_ipaddr(14),
                        user_network(15),
                        ldp(16),
                        user_special(17),
                        slnat64_v4(18),
                        ip_route_se_nat64(19),
                        ip_route_sl_nat64(20),
                        ip_route_aftr(21),
                        ip_route_nd_host(22),
                        ip_route_bras_pool(24),
                        ip_route_ipsec(25)
                 }
        MAX-ACCESS  read-only
        STATUS  current
        DESCRIPTION
                "protocol"
        ::= { zBgpRedisIpv4VrfmulEntry  4  }

zBgpRedisIpv4VrfmulProcessId OBJECT-TYPE
        SYNTAX   Unsigned32
        MAX-ACCESS  read-only
        STATUS  current
        DESCRIPTION
                "process id"
        ::= { zBgpRedisIpv4VrfmulEntry  5  }

zBgpRedisIpv4VrfmulMetric OBJECT-TYPE
        SYNTAX   Unsigned32
        MAX-ACCESS  read-only
        STATUS  current
        DESCRIPTION
                "metric"
        ::= { zBgpRedisIpv4VrfmulEntry  6  }

zBgpRedisIpv4VrfmulRouteMap OBJECT-TYPE
        SYNTAX   DisplayString
        MAX-ACCESS  read-only
        STATUS  current
        DESCRIPTION
                "route_map"
        ::= { zBgpRedisIpv4VrfmulEntry  7  }

zBgpRedisIpv4VrfmulMetricFlag OBJECT-TYPE
        SYNTAX   Unsigned32
        MAX-ACCESS  read-only
        STATUS  current
        DESCRIPTION
                "metric_flag"
        ::= { zBgpRedisIpv4VrfmulEntry  8  }



--------------------------------------------------------------
--------------------------------------------------------------
--zBgpV4NetworkIpv4VrfmulTable  network
--------------------------------------------------------------
zBgpV4NetworkIpv4VrfmulTable OBJECT-TYPE
        SYNTAX  SEQUENCE OF ZBgpV4NetworkIpv4VrfmulEntry
        MAX-ACCESS  not-accessible
        STATUS  current
        DESCRIPTION
                "BGP_V4_NETWORK_IPV4_VRFMUL"
        ::= { zxr10BgpMIB 18  }

zBgpV4NetworkIpv4VrfmulEntry OBJECT-TYPE
        SYNTAX   ZBgpV4NetworkIpv4VrfmulEntry
        MAX-ACCESS  not-accessible
        STATUS  current
        DESCRIPTION
                "BGP_V4_NETWORK_IPV4_VRFMUL"
        INDEX {zBgpV4NetworkIpv4VrfmulLocalAs,
               zBgpV4NetworkIpv4VrfmulAddrModeType,
               zBgpV4NetworkIpv4VrfmulVrfName,
               zBgpV4NetworkIpv4VrfmulIpAddr,
               zBgpV4NetworkIpv4VrfmulIpMask 
        }
        ::= { zBgpV4NetworkIpv4VrfmulTable 1 }

ZBgpV4NetworkIpv4VrfmulEntry ::=
        SEQUENCE {
                zBgpV4NetworkIpv4VrfmulLocalAs                    Unsigned32,
                zBgpV4NetworkIpv4VrfmulAddrModeType               INTEGER,
                zBgpV4NetworkIpv4VrfmulVrfName                    DisplayString,
                zBgpV4NetworkIpv4VrfmulIpAddr                     IpAddress,
                zBgpV4NetworkIpv4VrfmulIpMask                     IpAddress,
                zBgpV4NetworkIpv4VrfmulRouteMap                   DisplayString
        }

zBgpV4NetworkIpv4VrfmulLocalAs OBJECT-TYPE
        SYNTAX   Unsigned32
        MAX-ACCESS  read-only
        STATUS  current
        DESCRIPTION
                "local_as"
        ::= { zBgpV4NetworkIpv4VrfmulEntry  1  }

zBgpV4NetworkIpv4VrfmulAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpV4NetworkIpv4VrfmulEntry  2  }

zBgpV4NetworkIpv4VrfmulVrfName OBJECT-TYPE
        SYNTAX   DisplayString
        MAX-ACCESS  read-only
        STATUS  current
        DESCRIPTION
                "vrf_name"
        ::= { zBgpV4NetworkIpv4VrfmulEntry  3  }

zBgpV4NetworkIpv4VrfmulIpAddr OBJECT-TYPE
        SYNTAX   IpAddress
        MAX-ACCESS  read-only
        STATUS  current
        DESCRIPTION
                "ip_addr"
        ::= { zBgpV4NetworkIpv4VrfmulEntry  4  }

zBgpV4NetworkIpv4VrfmulIpMask OBJECT-TYPE
        SYNTAX   IpAddress
        MAX-ACCESS  read-only
        STATUS  current
        DESCRIPTION
                "ip_mask"
        ::= { zBgpV4NetworkIpv4VrfmulEntry  5  }

zBgpV4NetworkIpv4VrfmulRouteMap OBJECT-TYPE
        SYNTAX   DisplayString
        MAX-ACCESS  read-only
        STATUS  current
        DESCRIPTION
                "route_map"
        ::= { zBgpV4NetworkIpv4VrfmulEntry  6  }



--------------------------------------------------------------
--------------------------------------------------------------
--zBgpPeerIpv4UniTable
--------------------------------------------------------------
zBgpPeerIpv4UniTable OBJECT-TYPE
        SYNTAX  SEQUENCE OF ZBgpPeerIpv4UniEntry
        MAX-ACCESS  not-accessible
        STATUS  current
        DESCRIPTION
                "BGP_PEER_IPV4_UNI"
        ::= { zxr10BgpMIB 19  }

zBgpPeerIpv4UniEntry OBJECT-TYPE
        SYNTAX   ZBgpPeerIpv4UniEntry
        MAX-ACCESS  not-accessible
        STATUS  current
        DESCRIPTION
                "BGP_PEER_IPV4_UNI"
        INDEX {zBgpPeerIpv4UniLocalAs,
               zBgpPeerIpv4UniIpv4Addr,
               zBgpPeerIpv4UniIpv6Addr,
               zBgpPeerIpv4UniNeighborGroup 
        }
        ::= { zBgpPeerIpv4UniTable 1 }

ZBgpPeerIpv4UniEntry ::=
        SEQUENCE {
                zBgpPeerIpv4UniLocalAs                            Unsigned32,
                zBgpPeerIpv4UniIpv4Addr                           IpAddress,
                zBgpPeerIpv4UniIpv6Addr                           DisplayString,
                zBgpPeerIpv4UniNeighborGroup                      DisplayString,
                zBgpPeerIpv4UniAddrModeType                       INTEGER,
                zBgpPeerIpv4UniVrfName                            DisplayString,
                zBgpPeerIpv4UniPeerGroupName                      DisplayString,
                zBgpPeerIpv4UniActivate                           Unsigned32,
                zBgpPeerIpv4UniAdvertisementInterval              Unsigned32,
                zBgpPeerIpv4UniAllowasIn                          Unsigned32,
                zBgpPeerIpv4UniDefaultOriginate                   Unsigned32,
                zBgpPeerIpv4UniDescription                        DisplayString,
                zBgpPeerIpv4UniEbgpMultihop                       Unsigned32,
                zBgpPeerIpv4UniBfd                                Unsigned32,
                zBgpPeerIpv4UniNextHopSelf                        INTEGER,
                zBgpPeerIpv4UniNextHopUnchanged                   Unsigned32,
                zBgpPeerIpv4UniOriginateInterval                  Unsigned32,
                zBgpPeerIpv4UniPassive                            Unsigned32,
                zBgpPeerIpv4UniRemoteAs                           Unsigned32,
                zBgpPeerIpv4UniRemovePrivateAs                    Unsigned32,
                zBgpPeerIpv4UniRouteReflectorClient               Unsigned32,
                zBgpPeerIpv4UniSendCommunity                      Unsigned32,
                zBgpPeerIpv4UniSendMed                            Unsigned32,
                zBgpPeerIpv4UniShutDown                           Unsigned32,
                zBgpPeerIpv4UniUpdateSource                       DisplayString,
                zBgpPeerIpv4UniSendLabel                          Unsigned32,
                zBgpPeerIpv4UniSoftReconfiguration                Unsigned32,
                zBgpPeerIpv4UniChangeUnicastMulticast             Unsigned32,
                zBgpPeerIpv4UniAsOverride                         Unsigned32,
                zBgpPeerIpv4UniJoinPeergroupType                  Unsigned32,
                zBgpPeerIpv4UniAdvMap                             DisplayString,
                zBgpPeerIpv4UniExistMap                           DisplayString,
                zBgpPeerIpv4UniNonExistMap                        DisplayString,
                zBgpPeerIpv4UniAdvMapFlag                         Unsigned32,
                zBgpPeerIpv4UniTtlSecurityHops                    Unsigned32,
                zBgpPeerIpv4UniPeergroupSet                       Unsigned32,
                zBgpPeerIpv4UniGroupConfigCheck                   DisplayString,
                zBgpPeerIpv4UniGroupConfigTempCheck               Unsigned32,
                zBgpPeerIpv4UniMaxasIn                            Unsigned32,
                zBgpPeerIpv4UniUsePeergroupConfig                 DisplayString,
                zBgpPeerIpv4UniSplitUpdgrp                        Unsigned32,
                zBgpPeerIpv4UniWeight                             Unsigned32,
                zBgpPeerIpv4UniAspathLoopchk                      Unsigned32,
                zBgpPeerIpv4UniOrfPrefixFilter                    Unsigned32,
                zBgpPeerIpv4UniOrfPfxFilterCisco                  Unsigned32,
                zBgpPeerIpv4UniConRetryInter                      Unsigned32,
                zBgpPeerIpv4UniShutDownTrack                      DisplayString
        }

zBgpPeerIpv4UniLocalAs OBJECT-TYPE
        SYNTAX   Unsigned32
        MAX-ACCESS  read-only
        STATUS  current
        DESCRIPTION
                "local_as"
        ::= { zBgpPeerIpv4UniEntry  1  }

zBgpPeerIpv4UniIpv4Addr OBJECT-TYPE
        SYNTAX   IpAddress
        MAX-ACCESS  read-only
        STATUS  current
        DESCRIPTION
                "ipv4_addr"
        ::= { zBgpPeerIpv4UniEntry  2  }

zBgpPeerIpv4UniIpv6Addr OBJECT-TYPE
        SYNTAX   DisplayString
        MAX-ACCESS  read-only
        STATUS  current
        DESCRIPTION
                "ipv6_addr"
        ::= { zBgpPeerIpv4UniEntry  3  }

zBgpPeerIpv4UniNeighborGroup OBJECT-TYPE
        SYNTAX   DisplayString
        MAX-ACCESS  read-only
        STATUS  current
        DESCRIPTION
                "neighbor_group"
        ::= { zBgpPeerIpv4UniEntry  4  }

zBgpPeerIpv4UniAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpPeerIpv4UniEntry  5  }

zBgpPeerIpv4UniVrfName OBJECT-TYPE
        SYNTAX   DisplayString
        MAX-ACCESS  read-only
        STATUS  current
        DESCRIPTION
                "vrf_name"
        ::= { zBgpPeerIpv4UniEntry  6  }

zBgpPeerIpv4UniPeerGroupName OBJECT-TYPE
        SYNTAX   DisplayString
        MAX-ACCESS  read-only
        STATUS  current
        DESCRIPTION
                "peer_group_name"
        ::= { zBgpPeerIpv4UniEntry  7  }

zBgpPeerIpv4UniActivate OBJECT-TYPE
        SYNTAX   Unsigned32
        MAX-ACCESS  read-only
        STATUS  current
        DESCRIPTION
                "activate. 0 express disable, 1express enable, 2 express invalid."
        ::= { zBgpPeerIpv4UniEntry  8  }

zBgpPeerIpv4UniAdvertisementInterval OBJECT-TYPE
        SYNTAX   Unsigned32
        MAX-ACCESS  read-only
        STATUS  current
        DESCRIPTION
                "advertisement_interval"
        ::= { zBgpPeerIpv4UniEntry  9  }

zBgpPeerIpv4UniAllowasIn OBJECT-TYPE
        SYNTAX   Unsigned32
        MAX-ACCESS  read-only
        STATUS  current
        DESCRIPTION
                "allowas_in"
        ::= { zBgpPeerIpv4UniEntry  10  }

zBgpPeerIpv4UniDefaultOriginate OBJECT-TYPE
        SYNTAX   Unsigned32
        MAX-ACCESS  read-only
        STATUS  current
        DESCRIPTION
                "default_originate"
        ::= { zBgpPeerIpv4UniEntry  11  }

zBgpPeerIpv4UniDescription OBJECT-TYPE
        SYNTAX   DisplayString
        MAX-ACCESS  read-only
        STATUS  current
        DESCRIPTION
                "description"
        ::= { zBgpPeerIpv4UniEntry  12  }

zBgpPeerIpv4UniEbgpMultihop OBJECT-TYPE
        SYNTAX   Unsigned32
        MAX-ACCESS  read-only
        STATUS  current
        DESCRIPTION
                "ebgp_multihop"
        ::= { zBgpPeerIpv4UniEntry  13  }

zBgpPeerIpv4UniBfd OBJECT-TYPE
        SYNTAX   Unsigned32
        MAX-ACCESS  read-only
        STATUS  current
        DESCRIPTION
                "bfd"
        ::= { zBgpPeerIpv4UniEntry  14  }

zBgpPeerIpv4UniNextHopSelf OBJECT-TYPE
        SYNTAX   INTEGER {
                         invalid(0),--for not configuration
                         nexthopself(1),-- for EBGP peer  
                         nexthopselfall(2)-- for either EBGP or IBGP peer
                         }        
        MAX-ACCESS  read-only
        STATUS  current
        DESCRIPTION
                "next_hop_self"
        ::= { zBgpPeerIpv4UniEntry  15  }

zBgpPeerIpv4UniNextHopUnchanged OBJECT-TYPE
        SYNTAX   Unsigned32
        MAX-ACCESS  read-only
        STATUS  current
        DESCRIPTION
                "next_hop_unchanged"
        ::= { zBgpPeerIpv4UniEntry  16  }

zBgpPeerIpv4UniOriginateInterval OBJECT-TYPE
        SYNTAX   Unsigned32
        MAX-ACCESS  read-only
        STATUS  current
        DESCRIPTION
                "originate_interval"
        ::= { zBgpPeerIpv4UniEntry  17  }

zBgpPeerIpv4UniPassive OBJECT-TYPE
        SYNTAX   Unsigned32
        MAX-ACCESS  read-only
        STATUS  current
        DESCRIPTION
                "passive"
        ::= { zBgpPeerIpv4UniEntry  18  }

zBgpPeerIpv4UniRemoteAs OBJECT-TYPE
        SYNTAX   Unsigned32
        MAX-ACCESS  read-only
        STATUS  current
        DESCRIPTION
                "remote_as"
        ::= { zBgpPeerIpv4UniEntry  19  }

zBgpPeerIpv4UniRemovePrivateAs OBJECT-TYPE
        SYNTAX   Unsigned32
        MAX-ACCESS  read-only
        STATUS  current
        DESCRIPTION
                "remove_private_as"
        ::= { zBgpPeerIpv4UniEntry  20  }

zBgpPeerIpv4UniRouteReflectorClient OBJECT-TYPE
        SYNTAX   Unsigned32
        MAX-ACCESS  read-only
        STATUS  current
        DESCRIPTION
                "route_reflector_client"
        ::= { zBgpPeerIpv4UniEntry  21  }

zBgpPeerIpv4UniSendCommunity OBJECT-TYPE
        SYNTAX   Unsigned32
        MAX-ACCESS  read-only
        STATUS  current
        DESCRIPTION
                "send_community"
        ::= { zBgpPeerIpv4UniEntry  22  }

zBgpPeerIpv4UniSendMed OBJECT-TYPE
        SYNTAX   Unsigned32
        MAX-ACCESS  read-only
        STATUS  current
        DESCRIPTION
                "send_med"
        ::= { zBgpPeerIpv4UniEntry  23  }

zBgpPeerIpv4UniShutDown OBJECT-TYPE
        SYNTAX   Unsigned32
        MAX-ACCESS  read-only
        STATUS  current
        DESCRIPTION
                "shut_down"
        ::= { zBgpPeerIpv4UniEntry  24  }

zBgpPeerIpv4UniUpdateSource OBJECT-TYPE
        SYNTAX   DisplayString
        MAX-ACCESS  read-only
        STATUS  current
        DESCRIPTION
                "update_source"
        ::= { zBgpPeerIpv4UniEntry  25  }

zBgpPeerIpv4UniSendLabel OBJECT-TYPE
        SYNTAX   Unsigned32
        MAX-ACCESS  read-only
        STATUS  current
        DESCRIPTION
                "send_label"
        ::= { zBgpPeerIpv4UniEntry  26  }

zBgpPeerIpv4UniSoftReconfiguration OBJECT-TYPE
        SYNTAX   Unsigned32
        MAX-ACCESS  read-only
        STATUS  current
        DESCRIPTION
                "soft_reconfiguration"
        ::= { zBgpPeerIpv4UniEntry  27  }

zBgpPeerIpv4UniChangeUnicastMulticast OBJECT-TYPE
        SYNTAX   Unsigned32
        MAX-ACCESS  read-only
        STATUS  current
        DESCRIPTION
                "change_unicast_multicast"
        ::= { zBgpPeerIpv4UniEntry  28  }

zBgpPeerIpv4UniAsOverride OBJECT-TYPE
        SYNTAX   Unsigned32
        MAX-ACCESS  read-only
        STATUS  current
        DESCRIPTION
                "as_override"
        ::= { zBgpPeerIpv4UniEntry  29  }

zBgpPeerIpv4UniJoinPeergroupType OBJECT-TYPE
        SYNTAX   Unsigned32
        MAX-ACCESS  read-only
        STATUS  obsolete
        DESCRIPTION
                "join_peergroup_type"
        ::= { zBgpPeerIpv4UniEntry  30  }

zBgpPeerIpv4UniAdvMap OBJECT-TYPE
        SYNTAX   DisplayString
        MAX-ACCESS  read-only
        STATUS  current
        DESCRIPTION
                "adv_map"
        ::= { zBgpPeerIpv4UniEntry  31  }

zBgpPeerIpv4UniExistMap OBJECT-TYPE
        SYNTAX   DisplayString
        MAX-ACCESS  read-only
        STATUS  current
        DESCRIPTION
                "exist_map"
        ::= { zBgpPeerIpv4UniEntry  32  }

zBgpPeerIpv4UniNonExistMap OBJECT-TYPE
        SYNTAX   DisplayString
        MAX-ACCESS  read-only
        STATUS  current
        DESCRIPTION
                "non_exist_map"
        ::= { zBgpPeerIpv4UniEntry  33  }

zBgpPeerIpv4UniAdvMapFlag OBJECT-TYPE
        SYNTAX   Unsigned32
        MAX-ACCESS  read-only
        STATUS  obsolete
        DESCRIPTION
                "adv_map_flag"
        ::= { zBgpPeerIpv4UniEntry  34  }

zBgpPeerIpv4UniTtlSecurityHops OBJECT-TYPE
        SYNTAX   Unsigned32
        MAX-ACCESS  read-only
        STATUS  current
        DESCRIPTION
                "ttl-security-hops"
        ::= { zBgpPeerIpv4UniEntry  35  }

zBgpPeerIpv4UniPeergroupSet OBJECT-TYPE
        SYNTAX   Unsigned32
        MAX-ACCESS  read-only
        STATUS  obsolete
        DESCRIPTION
                "peergroup_set"
        ::= { zBgpPeerIpv4UniEntry  36  }

zBgpPeerIpv4UniGroupConfigCheck OBJECT-TYPE
        SYNTAX   DisplayString
        MAX-ACCESS  read-only
        STATUS  obsolete
        DESCRIPTION
                "group_config_check"
        ::= { zBgpPeerIpv4UniEntry  37  }

zBgpPeerIpv4UniGroupConfigTempCheck OBJECT-TYPE
        SYNTAX   Unsigned32
        MAX-ACCESS  read-only
        STATUS  obsolete
        DESCRIPTION
                "group_config_temp_check"
        ::= { zBgpPeerIpv4UniEntry  38  }

zBgpPeerIpv4UniMaxasIn OBJECT-TYPE
        SYNTAX   Unsigned32
        MAX-ACCESS  read-only
        STATUS  current
        DESCRIPTION
                "maxas_in"
        ::= { zBgpPeerIpv4UniEntry  39  }

zBgpPeerIpv4UniUsePeergroupConfig OBJECT-TYPE
        SYNTAX   DisplayString
        MAX-ACCESS  read-only
        STATUS  obsolete
        DESCRIPTION
                "use_peergroup_config"
        ::= { zBgpPeerIpv4UniEntry  40  }

zBgpPeerIpv4UniSplitUpdgrp OBJECT-TYPE
        SYNTAX   Unsigned32
        MAX-ACCESS  read-only
        STATUS  current
        DESCRIPTION
                "split_updgrp(1 enable,0 disable)"
        ::= { zBgpPeerIpv4UniEntry  41  }

zBgpPeerIpv4UniWeight OBJECT-TYPE
        SYNTAX   Unsigned32
        MAX-ACCESS  read-only
        STATUS  current
        DESCRIPTION
                "weight"
        ::= { zBgpPeerIpv4UniEntry  42  }

zBgpPeerIpv4UniAspathLoopchk OBJECT-TYPE
        SYNTAX   Unsigned32
        MAX-ACCESS  read-only
        STATUS  current
        DESCRIPTION
                "as_path_loopcheck(1 enable,0 disable)"
        ::= { zBgpPeerIpv4UniEntry  43  }

zBgpPeerIpv4UniOrfPrefixFilter OBJECT-TYPE
        SYNTAX   Unsigned32
        MAX-ACCESS  read-only
        STATUS  current
        DESCRIPTION
                "orf_prefix_filter(1 recieve,2 send,3 both)"
        ::= { zBgpPeerIpv4UniEntry  44  }

zBgpPeerIpv4UniOrfPfxFilterCisco OBJECT-TYPE
        SYNTAX   Unsigned32
        MAX-ACCESS  read-only
        STATUS  current
        DESCRIPTION
                "orf_prefix_filter_cisco(1 enable,0 disable)"
        ::= { zBgpPeerIpv4UniEntry  45  }

zBgpPeerIpv4UniConRetryInter OBJECT-TYPE
        SYNTAX   Unsigned32
        MAX-ACCESS  read-only
        STATUS  current
        DESCRIPTION
                "connect_retry_interval"
        ::= { zBgpPeerIpv4UniEntry  46  }

zBgpPeerIpv4UniShutDownTrack OBJECT-TYPE
        SYNTAX   DisplayString
        MAX-ACCESS  read-only
        STATUS  current
        DESCRIPTION
                "Track-group name applies to shutting down neighbor 
                  by track-group.It depends on zBgpPeerIpv4UniShutDown."
        ::= { zBgpPeerIpv4UniEntry  47  }
--------------------------------------------------------------
--------------------------------------------------------------
--zBgpPeerIpv4UniExtendTable
--------------------------------------------------------------
zBgpPeerIpv4UniExtendTable OBJECT-TYPE
        SYNTAX  SEQUENCE OF ZBgpPeerIpv4UniExtendEntry
        MAX-ACCESS  not-accessible
        STATUS  current
        DESCRIPTION
                "BGP_PEER_IPV4_UNI_EXTEND"
        ::= { zxr10BgpMIB 20  }

zBgpPeerIpv4UniExtendEntry OBJECT-TYPE
        SYNTAX   ZBgpPeerIpv4UniExtendEntry
        MAX-ACCESS  not-accessible
        STATUS  current
        DESCRIPTION
                "BGP_PEER_IPV4_UNI_EXTEND"
        INDEX {zBgpPeerIpv4UniExtendLocalAs,
               zBgpPeerIpv4UniExtendIpv4Addr,
               zBgpPeerIpv4UniExtendIpv6Addr,
               zBgpPeerIpv4UniExtendNeighborGroup 
        }
        ::= { zBgpPeerIpv4UniExtendTable 1 }

ZBgpPeerIpv4UniExtendEntry ::=
        SEQUENCE {
                zBgpPeerIpv4UniExtendLocalAs                      Unsigned32,
                zBgpPeerIpv4UniExtendIpv4Addr                     IpAddress,
                zBgpPeerIpv4UniExtendIpv6Addr                     DisplayString,
                zBgpPeerIpv4UniExtendNeighborGroup                DisplayString,
                zBgpPeerIpv4UniExtendAddrModeType                 INTEGER,
                zBgpPeerIpv4UniExtendVrfName                      DisplayString,
                zBgpPeerIpv4UniExtendPeerGroupName                DisplayString,
                zBgpPeerIpv4UniExtendRemoteAs                     Unsigned32,
                zBgpPeerIpv4UniExtendMaxinumPrefix                Unsigned32,
                zBgpPeerIpv4UniExtendMaxinumPrefixThreshold       Unsigned32,
                zBgpPeerIpv4UniExtendMaxinumPrefixRestarttime     Unsigned32,
                zBgpPeerIpv4UniExtendMaxinumPrefixOverAction      Unsigned32,
                zBgpPeerIpv4UniExtendPassword                     DisplayString,
                zBgpPeerIpv4UniExtendPasswordEncrypt              DisplayString,
                zBgpPeerIpv4UniExtendHoldtimeConf                 Unsigned32,
                zBgpPeerIpv4UniExtendKeepaliveConf                Unsigned32,
                zBgpPeerIpv4UniExtendTimersCmdType                Unsigned32,
                zBgpPeerIpv4UniExtendPasswordIsEncrypt            Unsigned32,
                zBgpPeerIpv4UniExtendMaxprefixCmdType             Unsigned32,
                zBgpPeerIpv4UniExtendRouteMapIn                   DisplayString,
                zBgpPeerIpv4UniExtendRouteMapOut                  DisplayString,
                zBgpPeerIpv4UniExtendRoutemapOutFlag              Unsigned32,
                zBgpPeerIpv4UniExtendRoutemapName                 DisplayString,
                zBgpPeerIpv4UniExtendRoutemapInFlag               Unsigned32,
                zBgpPeerIpv4UniExtendPrefixName                   DisplayString,
                zBgpPeerIpv4UniExtendPrefixInFlag                 Unsigned32,
                zBgpPeerIpv4UniExtendPrefixIn                     DisplayString,
                zBgpPeerIpv4UniExtendPrefixOut                    DisplayString,
                zBgpPeerIpv4UniExtendPrefixOutFlag                Unsigned32,
                zBgpPeerIpv4UniExtendPeergroupSet                 Unsigned32,
                zBgpPeerIpv4UniExtendGroupConfigCheck             DisplayString,
                zBgpPeerIpv4UniExtendGroupConfigTempCheck         Unsigned32,
                zBgpPeerIpv4UniExtendPasswordEncrypted            DisplayString,
                zBgpPeerIpv4UniExtendPasswordIsEncrypted          Unsigned32,
                zBgpPeerIpv4UniExtendPasswordIsSet                Unsigned32,
                zBgpPeerIpv4UniExtendUsePeergroupConfig           DisplayString,
                zBgpPeerIpv4UniExtendLocalasCmd                   Unsigned32,
                zBgpPeerIpv4UniExtendLocalasNum                   Unsigned32,
                zBgpPeerIpv4UniExtendLocalasNoPrd                 Unsigned32,
                zBgpPeerIpv4UniExtendLocalasReplc                 Unsigned32,
                zBgpPeerIpv4UniExtendLcoalasDual                  Unsigned32,
                zBgpPeerIpv4UniExtendAddpathsRcv                  Unsigned32,
                zBgpPeerIpv4UniExtendAddpathsSnd                  Unsigned32,
                zBgpPeerIpv4UniExtendAddpathsN                    Unsigned32,
                zBgpPeerIpv4UniExtendAddpathsPrf                  DisplayString,
                zBgpPeerIpv4UniExtendAdvDiversePath               Unsigned32,
                zBgpPeerIpv4UniExtendRplIn                        DisplayString,
                zBgpPeerIpv4UniExtendRplOut                       DisplayString,
                zBgpPeerIpv4UniExtendKeyChain                     DisplayString,
                zBgpPeerIpv4UniExtendWdTrack                      DisplayString,
                zBgpPeerIpv4UniExtendWdRmp                        DisplayString,
                zBgpPeerIpv4UniExtendWaitArp                      Unsigned32,
                zBgpPeerIpv4UniExtendWaitArpRmp                   DisplayString,
                zBgpPeerIpv4UniExtendIdleTime                     Unsigned32,
                zBgpPeerIpv4UniExtendIdleIncr                     Unsigned32
        }

zBgpPeerIpv4UniExtendLocalAs OBJECT-TYPE
        SYNTAX   Unsigned32
        MAX-ACCESS  read-only
        STATUS  current
        DESCRIPTION
                "local_as"
        ::= { zBgpPeerIpv4UniExtendEntry  1  }

zBgpPeerIpv4UniExtendIpv4Addr OBJECT-TYPE
        SYNTAX   IpAddress
        MAX-ACCESS  read-only
        STATUS  current
        DESCRIPTION
                "ipv4_addr"
        ::= { zBgpPeerIpv4UniExtendEntry  2  }

zBgpPeerIpv4UniExtendIpv6Addr OBJECT-TYPE
        SYNTAX   DisplayString
        MAX-ACCESS  read-only
        STATUS  current
        DESCRIPTION
                "ipv6_addr"
        ::= { zBgpPeerIpv4UniExtendEntry  3  }

zBgpPeerIpv4UniExtendNeighborGroup OBJECT-TYPE
        SYNTAX   DisplayString
        MAX-ACCESS  read-only
        STATUS  current
        DESCRIPTION
                "neighbor_group"
        ::= { zBgpPeerIpv4UniExtendEntry  4  }

zBgpPeerIpv4UniExtendAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpPeerIpv4UniExtendEntry  5  }

zBgpPeerIpv4UniExtendVrfName OBJECT-TYPE
        SYNTAX   DisplayString
        MAX-ACCESS  read-only
        STATUS  current
        DESCRIPTION
                "vrf_name"
        ::= { zBgpPeerIpv4UniExtendEntry  6  }

zBgpPeerIpv4UniExtendPeerGroupName OBJECT-TYPE
        SYNTAX   DisplayString
        MAX-ACCESS  read-only
        STATUS  current
        DESCRIPTION
                "peer_group_name"
        ::= { zBgpPeerIpv4UniExtendEntry  7  }

zBgpPeerIpv4UniExtendRemoteAs OBJECT-TYPE
        SYNTAX   Unsigned32
        MAX-ACCESS  read-only
        STATUS  current
        DESCRIPTION
                "remote_as"
        ::= { zBgpPeerIpv4UniExtendEntry  8  }

zBgpPeerIpv4UniExtendMaxinumPrefix OBJECT-TYPE
        SYNTAX   Unsigned32
        MAX-ACCESS  read-only
        STATUS  current
        DESCRIPTION
                "maxinum_prefix"
        ::= { zBgpPeerIpv4UniExtendEntry  9  }

zBgpPeerIpv4UniExtendMaxinumPrefixThreshold OBJECT-TYPE
        SYNTAX   Unsigned32
        MAX-ACCESS  read-only
        STATUS  current
        DESCRIPTION
                "maxinum_prefix_threshold"
        ::= { zBgpPeerIpv4UniExtendEntry  10  }

zBgpPeerIpv4UniExtendMaxinumPrefixRestarttime OBJECT-TYPE
        SYNTAX   Unsigned32
        MAX-ACCESS  read-only
        STATUS  current
        DESCRIPTION
                "maxinum_prefix_restartTime"
        ::= { zBgpPeerIpv4UniExtendEntry  11  }

zBgpPeerIpv4UniExtendMaxinumPrefixOverAction OBJECT-TYPE
        SYNTAX   Unsigned32
        MAX-ACCESS  read-only
        STATUS  current
        DESCRIPTION
                "maxinum_prefix_over_action"
        ::= { zBgpPeerIpv4UniExtendEntry  12  }

zBgpPeerIpv4UniExtendPassword OBJECT-TYPE
        SYNTAX   DisplayString
        MAX-ACCESS  read-only
        STATUS  obsolete
        DESCRIPTION
                "password"
        ::= { zBgpPeerIpv4UniExtendEntry  13  }

zBgpPeerIpv4UniExtendPasswordEncrypt OBJECT-TYPE
        SYNTAX   DisplayString
        MAX-ACCESS  read-only
        STATUS  obsolete
        DESCRIPTION
                "password_encrypt"
        ::= { zBgpPeerIpv4UniExtendEntry  14  }

zBgpPeerIpv4UniExtendHoldtimeConf OBJECT-TYPE
        SYNTAX   Unsigned32
        MAX-ACCESS  read-only
        STATUS  current
        DESCRIPTION
                "holdtime_conf"
        ::= { zBgpPeerIpv4UniExtendEntry  15  }

zBgpPeerIpv4UniExtendKeepaliveConf OBJECT-TYPE
        SYNTAX   Unsigned32
        MAX-ACCESS  read-only
        STATUS  current
        DESCRIPTION
                "keepalive_conf"
        ::= { zBgpPeerIpv4UniExtendEntry  16  }

zBgpPeerIpv4UniExtendTimersCmdType OBJECT-TYPE
        SYNTAX   Unsigned32
        MAX-ACCESS  read-only
        STATUS  obsolete
        DESCRIPTION
                "timers_cmd_type"
        ::= { zBgpPeerIpv4UniExtendEntry  17  }

zBgpPeerIpv4UniExtendPasswordIsEncrypt OBJECT-TYPE
        SYNTAX   Unsigned32
        MAX-ACCESS  read-only
        STATUS  obsolete
        DESCRIPTION
                "password_is_encrypt"
        ::= { zBgpPeerIpv4UniExtendEntry  18  }

zBgpPeerIpv4UniExtendMaxprefixCmdType OBJECT-TYPE
        SYNTAX   Unsigned32
        MAX-ACCESS  read-only
        STATUS  obsolete
        DESCRIPTION
                "maxprefix_cmd_type"
        ::= { zBgpPeerIpv4UniExtendEntry  19  }

zBgpPeerIpv4UniExtendRouteMapIn OBJECT-TYPE
        SYNTAX   DisplayString
        MAX-ACCESS  read-only
        STATUS  current
        DESCRIPTION
                "route_map_in"
        ::= { zBgpPeerIpv4UniExtendEntry  20  }

zBgpPeerIpv4UniExtendRouteMapOut OBJECT-TYPE
        SYNTAX   DisplayString
        MAX-ACCESS  read-only
        STATUS  current
        DESCRIPTION
                "route_map_out"
        ::= { zBgpPeerIpv4UniExtendEntry  21  }

zBgpPeerIpv4UniExtendRoutemapOutFlag OBJECT-TYPE
        SYNTAX   Unsigned32
        MAX-ACCESS  read-only
        STATUS  current
        DESCRIPTION
                "routemap_out_flag"
        ::= { zBgpPeerIpv4UniExtendEntry  22  }

zBgpPeerIpv4UniExtendRoutemapName OBJECT-TYPE
        SYNTAX   DisplayString
        MAX-ACCESS  read-only
        STATUS  obsolete
        DESCRIPTION
                "routemap_name"
        ::= { zBgpPeerIpv4UniExtendEntry  23  }

zBgpPeerIpv4UniExtendRoutemapInFlag OBJECT-TYPE
        SYNTAX   Unsigned32
        MAX-ACCESS  read-only
        STATUS  current
        DESCRIPTION
                "routemap_in_flag"
        ::= { zBgpPeerIpv4UniExtendEntry  24  }

zBgpPeerIpv4UniExtendPrefixName OBJECT-TYPE
        SYNTAX   DisplayString
        MAX-ACCESS  read-only
        STATUS  obsolete
        DESCRIPTION
                "prefix_name"
        ::= { zBgpPeerIpv4UniExtendEntry  25  }

zBgpPeerIpv4UniExtendPrefixInFlag OBJECT-TYPE
        SYNTAX   Unsigned32
        MAX-ACCESS  read-only
        STATUS  current
        DESCRIPTION
                "prefix_in_flag"
        ::= { zBgpPeerIpv4UniExtendEntry  26  }

zBgpPeerIpv4UniExtendPrefixIn OBJECT-TYPE
        SYNTAX   DisplayString
        MAX-ACCESS  read-only
        STATUS  current
        DESCRIPTION
                "prefix_in"
        ::= { zBgpPeerIpv4UniExtendEntry  27  }

zBgpPeerIpv4UniExtendPrefixOut OBJECT-TYPE
        SYNTAX   DisplayString
        MAX-ACCESS  read-only
        STATUS  current
        DESCRIPTION
                "prefix_out"
        ::= { zBgpPeerIpv4UniExtendEntry  28  }

zBgpPeerIpv4UniExtendPrefixOutFlag OBJECT-TYPE
        SYNTAX   Unsigned32
        MAX-ACCESS  read-only
        STATUS  current
        DESCRIPTION
                "prefix_out_flag"
        ::= { zBgpPeerIpv4UniExtendEntry  29  }

zBgpPeerIpv4UniExtendPeergroupSet OBJECT-TYPE
        SYNTAX   Unsigned32
        MAX-ACCESS  read-only
        STATUS  current
        DESCRIPTION
                "peergroup_set"
        ::= { zBgpPeerIpv4UniExtendEntry  30  }

zBgpPeerIpv4UniExtendGroupConfigCheck OBJECT-TYPE
        SYNTAX   DisplayString
        MAX-ACCESS  read-only
        STATUS  obsolete
        DESCRIPTION
                "group_config_check"
        ::= { zBgpPeerIpv4UniExtendEntry  31  }

zBgpPeerIpv4UniExtendGroupConfigTempCheck OBJECT-TYPE
        SYNTAX   Unsigned32
        MAX-ACCESS  read-only
        STATUS  obsolete
        DESCRIPTION
                "group_config_temp_check"
        ::= { zBgpPeerIpv4UniExtendEntry  32  }

zBgpPeerIpv4UniExtendPasswordEncrypted OBJECT-TYPE
        SYNTAX   DisplayString
        MAX-ACCESS  read-only
        STATUS  current
        DESCRIPTION
                "password_encrypted"
        ::= { zBgpPeerIpv4UniExtendEntry  33  }

zBgpPeerIpv4UniExtendPasswordIsEncrypted OBJECT-TYPE
        SYNTAX   Unsigned32
        MAX-ACCESS  read-only
        STATUS  obsolete
        DESCRIPTION
                "password_is_encrypted"
        ::= { zBgpPeerIpv4UniExtendEntry  34  }

zBgpPeerIpv4UniExtendPasswordIsSet OBJECT-TYPE
        SYNTAX   Unsigned32
        MAX-ACCESS  read-only
        STATUS  obsolete
        DESCRIPTION
                "password_is_set"
        ::= { zBgpPeerIpv4UniExtendEntry  35  }

zBgpPeerIpv4UniExtendUsePeergroupConfig OBJECT-TYPE
        SYNTAX   DisplayString
        MAX-ACCESS  read-only
        STATUS  obsolete
        DESCRIPTION
                "use_peergroup_config"
        ::= { zBgpPeerIpv4UniExtendEntry  36  }

zBgpPeerIpv4UniExtendLocalasCmd OBJECT-TYPE
        SYNTAX   Unsigned32
        MAX-ACCESS  read-only
        STATUS  obsolete
        DESCRIPTION
                "localas_cmd_type(1 enable,0 disable)"
        ::= { zBgpPeerIpv4UniExtendEntry  37  }

zBgpPeerIpv4UniExtendLocalasNum OBJECT-TYPE
        SYNTAX   Unsigned32
        MAX-ACCESS  read-only
        STATUS  current
        DESCRIPTION
                "localas_num"
        ::= { zBgpPeerIpv4UniExtendEntry  38  }

zBgpPeerIpv4UniExtendLocalasNoPrd OBJECT-TYPE
        SYNTAX   Unsigned32
        MAX-ACCESS  read-only
        STATUS  current
        DESCRIPTION
                "localas_no_prepend(1 enable,0 disable)"
        ::= { zBgpPeerIpv4UniExtendEntry  39  }

zBgpPeerIpv4UniExtendLocalasReplc OBJECT-TYPE
        SYNTAX   Unsigned32
        MAX-ACCESS  read-only
        STATUS  current
        DESCRIPTION
                "localas_replace_as(1 enable,0 disable)"
        ::= { zBgpPeerIpv4UniExtendEntry  40  }

zBgpPeerIpv4UniExtendLcoalasDual OBJECT-TYPE
        SYNTAX   Unsigned32
        MAX-ACCESS  read-only
        STATUS  current
        DESCRIPTION
                "lcoalas_dual_as(1 enable,0 disable)"
        ::= { zBgpPeerIpv4UniExtendEntry  41  }

zBgpPeerIpv4UniExtendAddpathsRcv OBJECT-TYPE
        SYNTAX   Unsigned32
        MAX-ACCESS  read-only
        STATUS  current
        DESCRIPTION
                "addpaths_receive(1 enable,0 disable)"
        ::= { zBgpPeerIpv4UniExtendEntry  42  }

zBgpPeerIpv4UniExtendAddpathsSnd OBJECT-TYPE
        SYNTAX   Unsigned32
        MAX-ACCESS  read-only
        STATUS  current
        DESCRIPTION
                "addpaths_send(1 enable,0 disable)"
        ::= { zBgpPeerIpv4UniExtendEntry  43  }

zBgpPeerIpv4UniExtendAddpathsN OBJECT-TYPE
        SYNTAX   Unsigned32
        MAX-ACCESS  read-only
        STATUS  current
        DESCRIPTION
                "addpaths number"
        ::= { zBgpPeerIpv4UniExtendEntry  44  }

zBgpPeerIpv4UniExtendAddpathsPrf OBJECT-TYPE
        SYNTAX   DisplayString
        MAX-ACCESS  read-only
        STATUS  current
        DESCRIPTION
                "addpaths_prefix"
        ::= { zBgpPeerIpv4UniExtendEntry  45  }

zBgpPeerIpv4UniExtendAdvDiversePath OBJECT-TYPE
        SYNTAX   Unsigned32
        MAX-ACCESS  read-only
        STATUS  current
        DESCRIPTION
                "adv_diverse_path(1 enable,0 disable)"
        ::= { zBgpPeerIpv4UniExtendEntry  46  }
zBgpPeerIpv4UniExtendRplIn OBJECT-TYPE
        SYNTAX   DisplayString
        MAX-ACCESS  read-only
        STATUS  current
        DESCRIPTION
                "route policy name applied to the inbound routes"
        ::= { zBgpPeerIpv4UniExtendEntry  47  }

zBgpPeerIpv4UniExtendRplOut OBJECT-TYPE
        SYNTAX   DisplayString
        MAX-ACCESS  read-only
        STATUS  current
        DESCRIPTION
                "route policy name applied to the outbound routes"
        ::= { zBgpPeerIpv4UniExtendEntry  48  }

zBgpPeerIpv4UniExtendKeyChain OBJECT-TYPE
        SYNTAX   DisplayString
        MAX-ACCESS  read-only
        STATUS  current
        DESCRIPTION
                "Keychain name associated to peer."
        ::= { zBgpPeerIpv4UniExtendEntry  49  }

zBgpPeerIpv4UniExtendWdTrack OBJECT-TYPE
        SYNTAX   DisplayString
        MAX-ACCESS  read-only
        STATUS  current
        DESCRIPTION
                "track-group name applied to withdraw the routes"
        ::= { zBgpPeerIpv4UniExtendEntry  50  }

zBgpPeerIpv4UniExtendWdRmp OBJECT-TYPE
        SYNTAX   DisplayString
        MAX-ACCESS  read-only
        STATUS  current
        DESCRIPTION
                "route-map name applied to withdraw the routes by track-group"
        ::= { zBgpPeerIpv4UniExtendEntry  51  }

zBgpPeerIpv4UniExtendWaitArp OBJECT-TYPE
        SYNTAX   Unsigned32 {enable(1), disable(2)}
        MAX-ACCESS  read-only
        STATUS  current
        DESCRIPTION
                "wait for controller ARP synchronized event;(1 enable,2 disable)"
        ::= { zBgpPeerIpv4UniExtendEntry  52  }

zBgpPeerIpv4UniExtendWaitArpRmp OBJECT-TYPE
        SYNTAX   DisplayString
        MAX-ACCESS  read-only
        STATUS  current
        DESCRIPTION
                "route-map name applied to waiting for controller ARP synchronized event"
        ::= { zBgpPeerIpv4UniExtendEntry  53  }

zBgpPeerIpv4UniExtendIdleTime OBJECT-TYPE
        SYNTAX   Unsigned32
        MAX-ACCESS  read-only
        STATUS  current
        DESCRIPTION
                "the length of time the peer is held in the idle state"
        ::= { zBgpPeerIpv4UniExtendEntry  54  }

zBgpPeerIpv4UniExtendIdleIncr OBJECT-TYPE
        SYNTAX   Unsigned32 {enable(1), disable(2)}
        MAX-ACCESS  read-only
        STATUS  current
        DESCRIPTION
                "increase idle hold time doubly to maximum 3000(1 enable,2 disable)"
        ::= { zBgpPeerIpv4UniExtendEntry  55  }
--------------------------------------------------------------
--------------------------------------------------------------
--zBgpPeerTable
--------------------------------------------------------------
zBgpPeerTable OBJECT-TYPE
        SYNTAX  SEQUENCE OF ZBgpPeerEntry
        MAX-ACCESS  not-accessible
        STATUS  current
        DESCRIPTION
                "BGP_PEER"
        ::= { zxr10BgpMIB 21  }

zBgpPeerEntry OBJECT-TYPE
        SYNTAX   ZBgpPeerEntry
        MAX-ACCESS  not-accessible
        STATUS  current
        DESCRIPTION
                "BGP_PEER"
        INDEX {zBgpPeerLocalAs,
               zBgpPeerIpv4Addr,
               zBgpPeerIpv6Addr,
               zBgpPeerNeighborGroup,
               zBgpPeerAddrModeType,
               zBgpPeerVrfName 
        }
        ::= { zBgpPeerTable 1 }

ZBgpPeerEntry ::=
        SEQUENCE {
                zBgpPeerLocalAs                                   Unsigned32,
                zBgpPeerIpv4Addr                                  IpAddress,
                zBgpPeerIpv6Addr                                  DisplayString,
                zBgpPeerNeighborGroup                             DisplayString,
                zBgpPeerAddrModeType                              INTEGER,
                zBgpPeerVrfName                                   DisplayString,
                zBgpPeerPeerGroupName                             DisplayString,
                zBgpPeerActivate                                  Unsigned32,
                zBgpPeerAdvertisementInterval                     Unsigned32,
                zBgpPeerAllowasIn                                 Unsigned32,
                zBgpPeerDefaultOriginate                          Unsigned32,
                zBgpPeerDescription                               DisplayString,
                zBgpPeerEbgpMultihop                              Unsigned32,
                zBgpPeerBfd                                       Unsigned32,
                zBgpPeerNextHopSelf                               INTEGER,
                zBgpPeerNextHopUnchanged                          Unsigned32,
                zBgpPeerOriginateInterval                         Unsigned32,
                zBgpPeerPassive                                   Unsigned32,
                zBgpPeerRemoteAs                                  Unsigned32,
                zBgpPeerRemovePrivateAs                           Unsigned32,
                zBgpPeerRouteReflectorClient                      Unsigned32,
                zBgpPeerSendCommunity                             Unsigned32,
                zBgpPeerSendMed                                   Unsigned32,
                zBgpPeerShutDown                                  Unsigned32,
                zBgpPeerUpdateSource                              DisplayString,
                zBgpPeerSendLabel                                 Unsigned32,
                zBgpPeerSoftReconfiguration                       Unsigned32,
                zBgpPeerChangeUnicastMulticast                    Unsigned32,
                zBgpPeerAsOverride                                Unsigned32,
                zBgpPeerJoinPeergroupType                         Unsigned32,
                zBgpPeerAdvMap                                    DisplayString,
                zBgpPeerExistMap                                  DisplayString,
                zBgpPeerNonExistMap                               DisplayString,
                zBgpPeerAdvMapFlag                                Unsigned32,
                zBgpPeerTtlSecurityHops                           Unsigned32,
                zBgpPeerPeergroupSet                              Unsigned32,
                zBgpPeerGroupConfigCheck                          DisplayString,
                zBgpPeerGroupConfigTempCheck                      Unsigned32,
                zBgpPeerMaxasIn                                   Unsigned32,
                zBgpPeerUsePeergroupConfig                        DisplayString,
                zBgpPeerSplitUpdgrp                               Unsigned32,
                zBgpPeerSoo                                       DisplayString,
                zBgpPeerWeight                                    Unsigned32,
                zBgpPeerAspathLoopchk                             Unsigned32,
                zBgpPeerOrfPrefixFilter                           Unsigned32,
                zBgpPeerUpe                                       Unsigned32,
                zBgpPeerUpeReflectNextHopSelf                     Unsigned32,
                zBgpPeerOrfPfxFilterCisco                         Unsigned32,
                zBgpPeerConRetryInter                             Unsigned32,
                zBgpPeerNlriType                                  Unsigned32,
                zBgpPeerValidationDisableDest                     Unsigned32,
                zBgpPeerValidationDisableNh                       Unsigned32,
                zBgpPeerShutDownTrack                             DisplayString
        }

zBgpPeerLocalAs OBJECT-TYPE
        SYNTAX   Unsigned32
        MAX-ACCESS  read-only
        STATUS  current
        DESCRIPTION
                "local_as"
        ::= { zBgpPeerEntry  1  }

zBgpPeerIpv4Addr OBJECT-TYPE
        SYNTAX   IpAddress
        MAX-ACCESS  read-only
        STATUS  current
        DESCRIPTION
                "ipv4_addr"
        ::= { zBgpPeerEntry  2  }

zBgpPeerIpv6Addr OBJECT-TYPE
        SYNTAX   DisplayString
        MAX-ACCESS  read-only
        STATUS  current
        DESCRIPTION
                "ipv6_addr"
        ::= { zBgpPeerEntry  3  }

zBgpPeerNeighborGroup OBJECT-TYPE
        SYNTAX   DisplayString
        MAX-ACCESS  read-only
        STATUS  current
        DESCRIPTION
                "neighbor_group"
        ::= { zBgpPeerEntry  4  }

zBgpPeerAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpPeerEntry  5  }

zBgpPeerVrfName OBJECT-TYPE
        SYNTAX   DisplayString
        MAX-ACCESS  read-only
        STATUS  current
        DESCRIPTION
                "vrf_name"
        ::= { zBgpPeerEntry  6  }

zBgpPeerPeerGroupName OBJECT-TYPE
        SYNTAX   DisplayString
        MAX-ACCESS  read-only
        STATUS  current
        DESCRIPTION
                "peer_group_name"
        ::= { zBgpPeerEntry  7  }

zBgpPeerActivate OBJECT-TYPE
        SYNTAX   Unsigned32
        MAX-ACCESS  read-only
        STATUS  current
        DESCRIPTION
                "activate. 0 express disable, 1express enable, 2 express invalid."
        ::= { zBgpPeerEntry  8  }

zBgpPeerAdvertisementInterval OBJECT-TYPE
        SYNTAX   Unsigned32
        MAX-ACCESS  read-only
        STATUS  current
        DESCRIPTION
                "advertisement_interval"
        ::= { zBgpPeerEntry  9  }

zBgpPeerAllowasIn OBJECT-TYPE
        SYNTAX   Unsigned32
        MAX-ACCESS  read-only
        STATUS  current
        DESCRIPTION
                "allowas_in"
        ::= { zBgpPeerEntry  10  }

zBgpPeerDefaultOriginate OBJECT-TYPE
        SYNTAX   Unsigned32
        MAX-ACCESS  read-only
        STATUS  current
        DESCRIPTION
                "default_originate"
        ::= { zBgpPeerEntry  11  }

zBgpPeerDescription OBJECT-TYPE
        SYNTAX   DisplayString
        MAX-ACCESS  read-only
        STATUS  current
        DESCRIPTION
                "description"
        ::= { zBgpPeerEntry  12  }

zBgpPeerEbgpMultihop OBJECT-TYPE
        SYNTAX   Unsigned32
        MAX-ACCESS  read-only
        STATUS  current
        DESCRIPTION
                "ebgp_multihop"
        ::= { zBgpPeerEntry  13  }

zBgpPeerBfd OBJECT-TYPE
        SYNTAX   Unsigned32
        MAX-ACCESS  read-only
        STATUS  current
        DESCRIPTION
                "bfd"
        ::= { zBgpPeerEntry  14  }

zBgpPeerNextHopSelf OBJECT-TYPE
        SYNTAX   INTEGER {
                         invalid(0),--for not configuration
                         nexthopself(1),-- for EBGP peer  
                         nexthopselfall(2)-- for either EBGP or IBGP peer
                         }    
        MAX-ACCESS  read-only
        STATUS  current
        DESCRIPTION
                "next_hop_self"
        ::= { zBgpPeerEntry  15  }

zBgpPeerNextHopUnchanged OBJECT-TYPE
        SYNTAX   Unsigned32
        MAX-ACCESS  read-only
        STATUS  current
        DESCRIPTION
                "next_hop_unchanged"
        ::= { zBgpPeerEntry  16  }

zBgpPeerOriginateInterval OBJECT-TYPE
        SYNTAX   Unsigned32
        MAX-ACCESS  read-only
        STATUS  current
        DESCRIPTION
                "originate_interval"
        ::= { zBgpPeerEntry  17  }

zBgpPeerPassive OBJECT-TYPE
        SYNTAX   Unsigned32
        MAX-ACCESS  read-only
        STATUS  current
        DESCRIPTION
                "passive"
        ::= { zBgpPeerEntry  18  }

zBgpPeerRemoteAs OBJECT-TYPE
        SYNTAX   Unsigned32
        MAX-ACCESS  read-only
        STATUS  current
        DESCRIPTION
                "remote_as"
        ::= { zBgpPeerEntry  19  }

zBgpPeerRemovePrivateAs OBJECT-TYPE
        SYNTAX   Unsigned32
        MAX-ACCESS  read-only
        STATUS  current
        DESCRIPTION
                "remove_private_as"
        ::= { zBgpPeerEntry  20  }

zBgpPeerRouteReflectorClient OBJECT-TYPE
        SYNTAX   Unsigned32
        MAX-ACCESS  read-only
        STATUS  current
        DESCRIPTION
                "route_reflector_client"
        ::= { zBgpPeerEntry  21  }

zBgpPeerSendCommunity OBJECT-TYPE
        SYNTAX   Unsigned32
        MAX-ACCESS  read-only
        STATUS  current
        DESCRIPTION
                "send_community"
        ::= { zBgpPeerEntry  22  }

zBgpPeerSendMed OBJECT-TYPE
        SYNTAX   Unsigned32
        MAX-ACCESS  read-only
        STATUS  current
        DESCRIPTION
                "send_med"
        ::= { zBgpPeerEntry  23  }

zBgpPeerShutDown OBJECT-TYPE
        SYNTAX   Unsigned32
        MAX-ACCESS  read-only
        STATUS  current
        DESCRIPTION
                "shut_down"
        ::= { zBgpPeerEntry  24  }

zBgpPeerUpdateSource OBJECT-TYPE
        SYNTAX   DisplayString
        MAX-ACCESS  read-only
        STATUS  current
        DESCRIPTION
                "update_source"
        ::= { zBgpPeerEntry  25  }

zBgpPeerSendLabel OBJECT-TYPE
        SYNTAX   Unsigned32
        MAX-ACCESS  read-only
        STATUS  current
        DESCRIPTION
                "send_label"
        ::= { zBgpPeerEntry  26  }

zBgpPeerSoftReconfiguration OBJECT-TYPE
        SYNTAX   Unsigned32
        MAX-ACCESS  read-only
        STATUS  current
        DESCRIPTION
                "soft_reconfiguration"
        ::= { zBgpPeerEntry  27  }

zBgpPeerChangeUnicastMulticast OBJECT-TYPE
        SYNTAX   Unsigned32
        MAX-ACCESS  read-only
        STATUS  current
        DESCRIPTION
                "change_unicast_multicast"
        ::= { zBgpPeerEntry  28  }

zBgpPeerAsOverride OBJECT-TYPE
        SYNTAX   Unsigned32
        MAX-ACCESS  read-only
        STATUS  current
        DESCRIPTION
                "as_override"
        ::= { zBgpPeerEntry  29  }

zBgpPeerJoinPeergroupType OBJECT-TYPE
        SYNTAX   Unsigned32
        MAX-ACCESS  read-only
        STATUS  obsolete
        DESCRIPTION
                "join_peergroup_type"
        ::= { zBgpPeerEntry  30  }

zBgpPeerAdvMap OBJECT-TYPE
        SYNTAX   DisplayString
        MAX-ACCESS  read-only
        STATUS  current
        DESCRIPTION
                "adv_map"
        ::= { zBgpPeerEntry  31  }

zBgpPeerExistMap OBJECT-TYPE
        SYNTAX   DisplayString
        MAX-ACCESS  read-only
        STATUS  current
        DESCRIPTION
                "exist_map"
        ::= { zBgpPeerEntry  32  }

zBgpPeerNonExistMap OBJECT-TYPE
        SYNTAX   DisplayString
        MAX-ACCESS  read-only
        STATUS  current
        DESCRIPTION
                "non_exist_map"
        ::= { zBgpPeerEntry  33  }

zBgpPeerAdvMapFlag OBJECT-TYPE
        SYNTAX   Unsigned32
        MAX-ACCESS  read-only
        STATUS  obsolete
        DESCRIPTION
                "adv_map_flag"
        ::= { zBgpPeerEntry  34  }

zBgpPeerTtlSecurityHops OBJECT-TYPE
        SYNTAX   Unsigned32
        MAX-ACCESS  read-only
        STATUS  current
        DESCRIPTION
                "ttl-security-hops"
        ::= { zBgpPeerEntry  35  }

zBgpPeerPeergroupSet OBJECT-TYPE
        SYNTAX   Unsigned32
        MAX-ACCESS  read-only
        STATUS  current
        DESCRIPTION
                "peergroup_set"
        ::= { zBgpPeerEntry  36  }

zBgpPeerGroupConfigCheck OBJECT-TYPE
        SYNTAX   DisplayString
        MAX-ACCESS  read-only
        STATUS  obsolete
        DESCRIPTION
                "group_config_check"
        ::= { zBgpPeerEntry  37  }

zBgpPeerGroupConfigTempCheck OBJECT-TYPE
        SYNTAX   Unsigned32
        MAX-ACCESS  read-only
        STATUS  obsolete
        DESCRIPTION
                "group_config_temp_check"
        ::= { zBgpPeerEntry  38  }

zBgpPeerMaxasIn OBJECT-TYPE
        SYNTAX   Unsigned32
        MAX-ACCESS  read-only
        STATUS  current
        DESCRIPTION
                "maxas_in"
        ::= { zBgpPeerEntry  39  }

zBgpPeerUsePeergroupConfig OBJECT-TYPE
        SYNTAX   DisplayString
        MAX-ACCESS  read-only
        STATUS  current
        DESCRIPTION
                "use_peergroup_config"
        ::= { zBgpPeerEntry  40  }

zBgpPeerSplitUpdgrp OBJECT-TYPE
        SYNTAX   Unsigned32
        MAX-ACCESS  read-only
        STATUS  current
        DESCRIPTION
                "split_updgrp(1 enable,0 disable)"
        ::= { zBgpPeerEntry  41  }

zBgpPeerSoo OBJECT-TYPE
        SYNTAX   DisplayString
        MAX-ACCESS  read-only
        STATUS  current
        DESCRIPTION
                "soo"
        ::= { zBgpPeerEntry  42  }

zBgpPeerWeight OBJECT-TYPE
        SYNTAX   Unsigned32
        MAX-ACCESS  read-only
        STATUS  current
        DESCRIPTION
                "weight"
        ::= { zBgpPeerEntry  43  }

zBgpPeerAspathLoopchk OBJECT-TYPE
        SYNTAX   Unsigned32
        MAX-ACCESS  read-only
        STATUS  current
        DESCRIPTION
                "as_path_loopcheck(1 enable,0 disable)"
        ::= { zBgpPeerEntry  44  }

zBgpPeerOrfPrefixFilter OBJECT-TYPE
        SYNTAX   Unsigned32
        MAX-ACCESS  read-only
        STATUS  current
        DESCRIPTION
                "orf_prefix_filter(1 recieve,2 send,3 both)"
        ::= { zBgpPeerEntry  45  }

zBgpPeerUpe OBJECT-TYPE
        SYNTAX   Unsigned32
        MAX-ACCESS  read-only
        STATUS  current
        DESCRIPTION
                "upe(1 enable,0 disable)"
        ::= { zBgpPeerEntry  46  }

zBgpPeerUpeReflectNextHopSelf OBJECT-TYPE
        SYNTAX   Unsigned32
        MAX-ACCESS  read-only
        STATUS  current
        DESCRIPTION
                "upe_reflect_next_hop_self(1 enable,0 disable)"
        ::= { zBgpPeerEntry  47  }

zBgpPeerOrfPfxFilterCisco OBJECT-TYPE
        SYNTAX   Unsigned32
        MAX-ACCESS  read-only
        STATUS  current
        DESCRIPTION
                "orf_prefix_filter_cisco(1 enable,0 disable)"
        ::= { zBgpPeerEntry  48  }

zBgpPeerConRetryInter OBJECT-TYPE
        SYNTAX   Unsigned32
        MAX-ACCESS  read-only
        STATUS  current
        DESCRIPTION
                "connect_retry_interval"
        ::= { zBgpPeerEntry  49  }

zBgpPeerNlriType OBJECT-TYPE
        SYNTAX   Unsigned32
        MAX-ACCESS  read-only
        STATUS  current
        DESCRIPTION
                "nlri_type(1 enable,0 disable)"
        ::= { zBgpPeerEntry  50  }

zBgpPeerValidationDisableDest OBJECT-TYPE
        SYNTAX   Unsigned32 {on(1),off(2)}
        MAX-ACCESS  read-only
        STATUS  current
        DESCRIPTION
                "Disable destination validation"
        ::= { zBgpPeerEntry  51  }

zBgpPeerValidationDisableNh OBJECT-TYPE
        SYNTAX   Unsigned32 {on(1),off(2)}
        MAX-ACCESS  read-only
        STATUS  current
        DESCRIPTION
                "Disable nexthop validation"
        ::= { zBgpPeerEntry  52  }

zBgpPeerShutDownTrack OBJECT-TYPE
        SYNTAX   DisplayString
        MAX-ACCESS  read-only
        STATUS  current
        DESCRIPTION
                "Track-group name applies to shutting down neighbor 
                  by track-group.It depends on zBgpPeerShutDown."
        ::= { zBgpPeerEntry  53  }
--------------------------------------------------------------
--------------------------------------------------------------
--zBgpPeerExtendTable
--------------------------------------------------------------
zBgpPeerExtendTable OBJECT-TYPE
        SYNTAX  SEQUENCE OF ZBgpPeerExtendEntry
        MAX-ACCESS  not-accessible
        STATUS  current
        DESCRIPTION
                "BGP_PEER_EXTEND"
        ::= { zxr10BgpMIB 22  }

zBgpPeerExtendEntry OBJECT-TYPE
        SYNTAX   ZBgpPeerExtendEntry
        MAX-ACCESS  not-accessible
        STATUS  current
        DESCRIPTION
                "BGP_PEER_EXTEND"
        INDEX {zBgpPeerExtendLocalAs,
               zBgpPeerExtendIpv4Addr,
               zBgpPeerExtendIpv6Addr,
               zBgpPeerExtendNeighborGroup,
               zBgpPeerExtendAddrModeType,
               zBgpPeerExtendVrfName 
        }
        ::= { zBgpPeerExtendTable 1 }

ZBgpPeerExtendEntry ::=
        SEQUENCE {
                zBgpPeerExtendLocalAs                             Unsigned32,
                zBgpPeerExtendIpv4Addr                            IpAddress,
                zBgpPeerExtendIpv6Addr                            DisplayString,
                zBgpPeerExtendNeighborGroup                       DisplayString,
                zBgpPeerExtendAddrModeType                        INTEGER,
                zBgpPeerExtendVrfName                             DisplayString,
                zBgpPeerExtendPeerGroupName                       DisplayString,
                zBgpPeerExtendRemoteAs                            Unsigned32,
                zBgpPeerExtendMaxinumPrefix                       Unsigned32,
                zBgpPeerExtendMaxinumPrefixThreshold              Unsigned32,
                zBgpPeerExtendMaxinumPrefixRestarttime            Unsigned32,
                zBgpPeerExtendMaxinumPrefixOverAction             Unsigned32,
                zBgpPeerExtendPassword                            DisplayString,
                zBgpPeerExtendPasswordEncrypt                     DisplayString,
                zBgpPeerExtendHoldtimeConf                        Unsigned32,
                zBgpPeerExtendKeepaliveConf                       Unsigned32,
                zBgpPeerExtendTimersCmdType                       Unsigned32,
                zBgpPeerExtendPasswordIsEncrypt                   Unsigned32,
                zBgpPeerExtendMaxprefixCmdType                    Unsigned32,
                zBgpPeerExtendRouteMapIn                          DisplayString,
                zBgpPeerExtendRouteMapOut                         DisplayString,
                zBgpPeerExtendRoutemapOutFlag                     Unsigned32,
                zBgpPeerExtendRoutemapName                        DisplayString,
                zBgpPeerExtendRoutemapInFlag                      Unsigned32,
                zBgpPeerExtendPrefixName                          DisplayString,
                zBgpPeerExtendPrefixInFlag                        Unsigned32,
                zBgpPeerExtendPrefixIn                            DisplayString,
                zBgpPeerExtendPrefixOut                           DisplayString,
                zBgpPeerExtendPrefixOutFlag                       Unsigned32,
                zBgpPeerExtendPeergroupSet                        Unsigned32,
                zBgpPeerExtendGroupConfigCheck                    DisplayString,
                zBgpPeerExtendGroupConfigTempCheck                Unsigned32,
                zBgpPeerExtendPasswordEncrypted                   DisplayString,
                zBgpPeerExtendPasswordIsEncrypted                 Unsigned32,
                zBgpPeerExtendPasswordIsSet                       Unsigned32,
                zBgpPeerExtendUsePeergroupConfig                  DisplayString,
                zBgpPeerExtendLocalasCmd                          Unsigned32,
                zBgpPeerExtendLocalasNum                          Unsigned32,
                zBgpPeerExtendLocalasNoPrd                        Unsigned32,
                zBgpPeerExtendLocalasReplc                        Unsigned32,
                zBgpPeerExtendLcoalasDual                         Unsigned32,
                zBgpPeerExtendAddpathsRcv                         Unsigned32,
                zBgpPeerExtendAddpathsSnd                         Unsigned32,
                zBgpPeerExtendAddpathsN                           Unsigned32,
                zBgpPeerExtendAddpathsPrf                         DisplayString,
                zBgpPeerExtendAdvDiversePath                      Unsigned32,
                zBgpPeerExtendRplIn                               DisplayString,
                zBgpPeerExtendRplOut                              DisplayString,
                zBgpPeerExtendKeyChain                            DisplayString,
                zBgpPeerExtendWdTrack                             DisplayString,
                zBgpPeerExtendWdRmp                               DisplayString,
                zBgpPeerExtendIdleTime                            Unsigned32,
                zBgpPeerExtendIdleIncr                            Unsigned32
        }

zBgpPeerExtendLocalAs OBJECT-TYPE
        SYNTAX   Unsigned32
        MAX-ACCESS  read-only
        STATUS  current
        DESCRIPTION
                "local_as"
        ::= { zBgpPeerExtendEntry  1  }

zBgpPeerExtendIpv4Addr OBJECT-TYPE
        SYNTAX   IpAddress
        MAX-ACCESS  read-only
        STATUS  current
        DESCRIPTION
                "ipv4_addr"
        ::= { zBgpPeerExtendEntry  2  }

zBgpPeerExtendIpv6Addr OBJECT-TYPE
        SYNTAX   DisplayString
        MAX-ACCESS  read-only
        STATUS  current
        DESCRIPTION
                "ipv6_addr"
        ::= { zBgpPeerExtendEntry  3  }

zBgpPeerExtendNeighborGroup OBJECT-TYPE
        SYNTAX   DisplayString
        MAX-ACCESS  read-only
        STATUS  current
        DESCRIPTION
                "neighbor_group"
        ::= { zBgpPeerExtendEntry  4  }

zBgpPeerExtendAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpPeerExtendEntry  5  }

zBgpPeerExtendVrfName OBJECT-TYPE
        SYNTAX   DisplayString
        MAX-ACCESS  read-only
        STATUS  current
        DESCRIPTION
                "vrf_name"
        ::= { zBgpPeerExtendEntry  6  }

zBgpPeerExtendPeerGroupName OBJECT-TYPE
        SYNTAX   DisplayString
        MAX-ACCESS  read-only
        STATUS  current
        DESCRIPTION
                "peer_group_name"
        ::= { zBgpPeerExtendEntry  7  }

zBgpPeerExtendRemoteAs OBJECT-TYPE
        SYNTAX   Unsigned32
        MAX-ACCESS  read-only
        STATUS  current
        DESCRIPTION
                "remote_as"
        ::= { zBgpPeerExtendEntry  8  }

zBgpPeerExtendMaxinumPrefix OBJECT-TYPE
        SYNTAX   Unsigned32
        MAX-ACCESS  read-only
        STATUS  current
        DESCRIPTION
                "maxinum_prefix"
        ::= { zBgpPeerExtendEntry  9  }

zBgpPeerExtendMaxinumPrefixThreshold OBJECT-TYPE
        SYNTAX   Unsigned32
        MAX-ACCESS  read-only
        STATUS  current
        DESCRIPTION
                "maxinum_prefix_threshold"
        ::= { zBgpPeerExtendEntry  10  }

zBgpPeerExtendMaxinumPrefixRestarttime OBJECT-TYPE
        SYNTAX   Unsigned32
        MAX-ACCESS  read-only
        STATUS  current
        DESCRIPTION
                "maxinum_prefix_restartTime"
        ::= { zBgpPeerExtendEntry  11  }

zBgpPeerExtendMaxinumPrefixOverAction OBJECT-TYPE
        SYNTAX   Unsigned32
        MAX-ACCESS  read-only
        STATUS  current
        DESCRIPTION
                "maxinum_prefix_over_action"
        ::= { zBgpPeerExtendEntry  12  }

zBgpPeerExtendPassword OBJECT-TYPE
        SYNTAX   DisplayString
        MAX-ACCESS  read-only
        STATUS  obsolete
        DESCRIPTION
                "password"
        ::= { zBgpPeerExtendEntry  13  }

zBgpPeerExtendPasswordEncrypt OBJECT-TYPE
        SYNTAX   DisplayString
        MAX-ACCESS  read-only
        STATUS  obsolete
        DESCRIPTION
                "password_encrypt"
        ::= { zBgpPeerExtendEntry  14  }

zBgpPeerExtendHoldtimeConf OBJECT-TYPE
        SYNTAX   Unsigned32
        MAX-ACCESS  read-only
        STATUS  current
        DESCRIPTION
                "holdtime_conf"
        ::= { zBgpPeerExtendEntry  15  }

zBgpPeerExtendKeepaliveConf OBJECT-TYPE
        SYNTAX   Unsigned32
        MAX-ACCESS  read-only
        STATUS  current
        DESCRIPTION
                "keepalive_conf"
        ::= { zBgpPeerExtendEntry  16  }

zBgpPeerExtendTimersCmdType OBJECT-TYPE
        SYNTAX   Unsigned32
        MAX-ACCESS  read-only
        STATUS  obsolete
        DESCRIPTION
                "timers_cmd_type"
        ::= { zBgpPeerExtendEntry  17  }

zBgpPeerExtendPasswordIsEncrypt OBJECT-TYPE
        SYNTAX   Unsigned32
        MAX-ACCESS  read-only
        STATUS  obsolete
        DESCRIPTION
                "password_is_encrypt"
        ::= { zBgpPeerExtendEntry  18  }

zBgpPeerExtendMaxprefixCmdType OBJECT-TYPE
        SYNTAX   Unsigned32
        MAX-ACCESS  read-only
        STATUS  obsolete
        DESCRIPTION
                "maxprefix_cmd_type"
        ::= { zBgpPeerExtendEntry  19  }

zBgpPeerExtendRouteMapIn OBJECT-TYPE
        SYNTAX   DisplayString
        MAX-ACCESS  read-only
        STATUS  current
        DESCRIPTION
                "route_map_in"
        ::= { zBgpPeerExtendEntry  20  }

zBgpPeerExtendRouteMapOut OBJECT-TYPE
        SYNTAX   DisplayString
        MAX-ACCESS  read-only
        STATUS  current
        DESCRIPTION
                "route_map_out"
        ::= { zBgpPeerExtendEntry  21  }

zBgpPeerExtendRoutemapOutFlag OBJECT-TYPE
        SYNTAX   Unsigned32
        MAX-ACCESS  read-only
        STATUS  current
        DESCRIPTION
                "routemap_out_flag"
        ::= { zBgpPeerExtendEntry  22  }

zBgpPeerExtendRoutemapName OBJECT-TYPE
        SYNTAX   DisplayString
        MAX-ACCESS  read-only
        STATUS  obsolete
        DESCRIPTION
                "routemap_name"
        ::= { zBgpPeerExtendEntry  23  }

zBgpPeerExtendRoutemapInFlag OBJECT-TYPE
        SYNTAX   Unsigned32
        MAX-ACCESS  read-only
        STATUS  current
        DESCRIPTION
                "routemap_in_flag"
        ::= { zBgpPeerExtendEntry  24  }

zBgpPeerExtendPrefixName OBJECT-TYPE
        SYNTAX   DisplayString
        MAX-ACCESS  read-only
        STATUS  obsolete
        DESCRIPTION
                "prefix_name"
        ::= { zBgpPeerExtendEntry  25  }

zBgpPeerExtendPrefixInFlag OBJECT-TYPE
        SYNTAX   Unsigned32
        MAX-ACCESS  read-only
        STATUS  current
        DESCRIPTION
                "prefix_in_flag"
        ::= { zBgpPeerExtendEntry  26  }

zBgpPeerExtendPrefixIn OBJECT-TYPE
        SYNTAX   DisplayString
        MAX-ACCESS  read-only
        STATUS  current
        DESCRIPTION
                "prefix_in"
        ::= { zBgpPeerExtendEntry  27  }

zBgpPeerExtendPrefixOut OBJECT-TYPE
        SYNTAX   DisplayString
        MAX-ACCESS  read-only
        STATUS  current
        DESCRIPTION
                "prefix_out"
        ::= { zBgpPeerExtendEntry  28  }

zBgpPeerExtendPrefixOutFlag OBJECT-TYPE
        SYNTAX   Unsigned32
        MAX-ACCESS  read-only
        STATUS  current
        DESCRIPTION
                "prefix_out_flag"
        ::= { zBgpPeerExtendEntry  29  }

zBgpPeerExtendPeergroupSet OBJECT-TYPE
        SYNTAX   Unsigned32
        MAX-ACCESS  read-only
        STATUS  current
        DESCRIPTION
                "peergroup_set"
        ::= { zBgpPeerExtendEntry  30  }

zBgpPeerExtendGroupConfigCheck OBJECT-TYPE
        SYNTAX   DisplayString
        MAX-ACCESS  read-only
        STATUS  obsolete
        DESCRIPTION
                "group_config_check"
        ::= { zBgpPeerExtendEntry  31  }

zBgpPeerExtendGroupConfigTempCheck OBJECT-TYPE
        SYNTAX   Unsigned32
        MAX-ACCESS  read-only
        STATUS  obsolete
        DESCRIPTION
                "group_config_temp_check"
        ::= { zBgpPeerExtendEntry  32  }

zBgpPeerExtendPasswordEncrypted OBJECT-TYPE
        SYNTAX   DisplayString
        MAX-ACCESS  read-only
        STATUS  current
        DESCRIPTION
                "password_encrypted"
        ::= { zBgpPeerExtendEntry  33  }

zBgpPeerExtendPasswordIsEncrypted OBJECT-TYPE
        SYNTAX   Unsigned32
        MAX-ACCESS  read-only
        STATUS  obsolete
        DESCRIPTION
                "password_is_encrypted"
        ::= { zBgpPeerExtendEntry  34  }

zBgpPeerExtendPasswordIsSet OBJECT-TYPE
        SYNTAX   Unsigned32
        MAX-ACCESS  read-only
        STATUS  obsolete
        DESCRIPTION
                "password_is_set"
        ::= { zBgpPeerExtendEntry  35  }

zBgpPeerExtendUsePeergroupConfig OBJECT-TYPE
        SYNTAX   DisplayString
        MAX-ACCESS  read-only
        STATUS  obsolete
        DESCRIPTION
                "use_peergroup_config"
        ::= { zBgpPeerExtendEntry  36  }


zBgpPeerExtendLocalasCmd OBJECT-TYPE
        SYNTAX   Unsigned32
        MAX-ACCESS  read-only
        STATUS  obsolete
        DESCRIPTION
                "localas_cmd_type(1 enable,0 disable)"
        ::= { zBgpPeerExtendEntry  37  }

zBgpPeerExtendLocalasNum OBJECT-TYPE
        SYNTAX   Unsigned32
        MAX-ACCESS  read-only
        STATUS  current
        DESCRIPTION
                "localas_num"
        ::= { zBgpPeerExtendEntry  38  }

zBgpPeerExtendLocalasNoPrd OBJECT-TYPE
        SYNTAX   Unsigned32
        MAX-ACCESS  read-only
        STATUS  current
        DESCRIPTION
                "localas_no_prepend(1 enable,0 disable)"
        ::= { zBgpPeerExtendEntry  39  }

zBgpPeerExtendLocalasReplc OBJECT-TYPE
        SYNTAX   Unsigned32
        MAX-ACCESS  read-only
        STATUS  current
        DESCRIPTION
                "localas_replace_as(1 enable,0 disable)"
        ::= { zBgpPeerExtendEntry  40  }

zBgpPeerExtendLcoalasDual OBJECT-TYPE
        SYNTAX   Unsigned32
        MAX-ACCESS  read-only
        STATUS  current
        DESCRIPTION
                "lcoalas_dual_as(1 enable,0 disable)"
        ::= { zBgpPeerExtendEntry  41  }

zBgpPeerExtendAddpathsRcv OBJECT-TYPE
        SYNTAX   Unsigned32
        MAX-ACCESS  read-only
        STATUS  current
        DESCRIPTION
                "addpaths_receive(1 enable,0 disable)"
        ::= { zBgpPeerExtendEntry  42  }

zBgpPeerExtendAddpathsSnd OBJECT-TYPE
        SYNTAX   Unsigned32
        MAX-ACCESS  read-only
        STATUS  current
        DESCRIPTION
                "addpaths_send(1 enable,0 disable)"
        ::= { zBgpPeerExtendEntry  43  }

zBgpPeerExtendAddpathsN OBJECT-TYPE
        SYNTAX   Unsigned32
        MAX-ACCESS  read-only
        STATUS  current
        DESCRIPTION
                "addpathsN"
        ::= { zBgpPeerExtendEntry  44  }

zBgpPeerExtendAddpathsPrf OBJECT-TYPE
        SYNTAX   DisplayString
        MAX-ACCESS  read-only
        STATUS  current
        DESCRIPTION
                "addpaths_prefix"
        ::= { zBgpPeerExtendEntry  45  }

zBgpPeerExtendAdvDiversePath OBJECT-TYPE
        SYNTAX   Unsigned32
        MAX-ACCESS  read-only
        STATUS  current
        DESCRIPTION
                "adv_diverse_path(1 enable,0 disable)"
        ::= { zBgpPeerExtendEntry  46 }
zBgpPeerExtendRplIn OBJECT-TYPE
        SYNTAX   DisplayString
        MAX-ACCESS  read-only
        STATUS  current
        DESCRIPTION
                "route policy name applied to the inbound routes"
        ::= { zBgpPeerExtendEntry  47  }

zBgpPeerExtendRplOut OBJECT-TYPE
        SYNTAX   DisplayString
        MAX-ACCESS  read-only
        STATUS  current
        DESCRIPTION
                "route policy name applied to the outbound routes"
        ::= { zBgpPeerExtendEntry  48 }

zBgpPeerExtendKeyChain OBJECT-TYPE
        SYNTAX   DisplayString
        MAX-ACCESS  read-only
        STATUS  current
        DESCRIPTION
                "Keychain name associated to peer."
        ::= { zBgpPeerExtendEntry  49 }

zBgpPeerExtendWdTrack OBJECT-TYPE
        SYNTAX   DisplayString
        MAX-ACCESS  read-only
        STATUS  current
        DESCRIPTION
                "track-group name applied to withdraw the routes"
        ::= { zBgpPeerExtendEntry  50  }

zBgpPeerExtendWdRmp OBJECT-TYPE
        SYNTAX   DisplayString
        MAX-ACCESS  read-only
        STATUS  current
        DESCRIPTION
                "route-map name applied to withdraw the routes by track-group"
        ::= { zBgpPeerExtendEntry  51  }

zBgpPeerExtendIdleTime OBJECT-TYPE
        SYNTAX   Unsigned32
        MAX-ACCESS  read-only
        STATUS  current
        DESCRIPTION
                "the length of time the peer is held in the idle state"
        ::= { zBgpPeerExtendEntry  52  }

zBgpPeerExtendIdleIncr OBJECT-TYPE
        SYNTAX   Unsigned32 {enable(1), disable(2)}
        MAX-ACCESS  read-only
        STATUS  current
        DESCRIPTION
                "increase idle hold time doubly to maximum 3000(1 enable,2 disable)"
        ::= { zBgpPeerExtendEntry  53  }
--------------------------------------------------------------
--------------------------------------------------------------
--zBgpPeerIpv4VrfmulTable
--------------------------------------------------------------
zBgpPeerIpv4VrfmulTable OBJECT-TYPE
        SYNTAX  SEQUENCE OF ZBgpPeerIpv4VrfmulEntry
        MAX-ACCESS  not-accessible
        STATUS  current
        DESCRIPTION
                "BGP_PEER_IPV4_VRFMUL"
        ::= { zxr10BgpMIB 23  }

zBgpPeerIpv4VrfmulEntry OBJECT-TYPE
        SYNTAX   ZBgpPeerIpv4VrfmulEntry
        MAX-ACCESS  not-accessible
        STATUS  current
        DESCRIPTION
                "BGP_PEER_IPV4_VRFMUL"
        INDEX {zBgpPeerIpv4VrfmulLocalAs,
               zBgpPeerIpv4VrfmulIpv4Addr,
               zBgpPeerIpv4VrfmulIpv6Addr,
               zBgpPeerIpv4VrfmulNeighborGroup,
               zBgpPeerIpv4VrfmulAddrModeType,
               zBgpPeerIpv4VrfmulVrfName 
        }
        ::= { zBgpPeerIpv4VrfmulTable 1 }

ZBgpPeerIpv4VrfmulEntry ::=
        SEQUENCE {
                zBgpPeerIpv4VrfmulLocalAs                         Unsigned32,
                zBgpPeerIpv4VrfmulIpv4Addr                        IpAddress,
                zBgpPeerIpv4VrfmulIpv6Addr                        DisplayString,
                zBgpPeerIpv4VrfmulNeighborGroup                   DisplayString,
                zBgpPeerIpv4VrfmulAddrModeType                    INTEGER,
                zBgpPeerIpv4VrfmulVrfName                         DisplayString,
                zBgpPeerIpv4VrfmulPeerGroupName                   DisplayString,
                zBgpPeerIpv4VrfmulActivate                        Unsigned32,
                zBgpPeerIpv4VrfmulAdvertisementInterval           Unsigned32,
                zBgpPeerIpv4VrfmulAllowasIn                       Unsigned32,
                zBgpPeerIpv4VrfmulDefaultOriginate                Unsigned32,
                zBgpPeerIpv4VrfmulDescription                     DisplayString,
                zBgpPeerIpv4VrfmulEbgpMultihop                    Unsigned32,
                zBgpPeerIpv4VrfmulBfd                             Unsigned32,
                zBgpPeerIpv4VrfmulNextHopSelf                     INTEGER,
                zBgpPeerIpv4VrfmulNextHopUnchanged                Unsigned32,
                zBgpPeerIpv4VrfmulOriginateInterval               Unsigned32,
                zBgpPeerIpv4VrfmulPassive                         Unsigned32,
                zBgpPeerIpv4VrfmulRemoteAs                        Unsigned32,
                zBgpPeerIpv4VrfmulRemovePrivateAs                 Unsigned32,
                zBgpPeerIpv4VrfmulRouteReflectorClient            Unsigned32,
                zBgpPeerIpv4VrfmulSendCommunity                   Unsigned32,
                zBgpPeerIpv4VrfmulSendMed                         Unsigned32,
                zBgpPeerIpv4VrfmulShutDown                        Unsigned32,
                zBgpPeerIpv4VrfmulUpdateSource                    DisplayString,
                zBgpPeerIpv4VrfmulSendLabel                       Unsigned32,
                zBgpPeerIpv4VrfmulSoftReconfiguration             Unsigned32,
                zBgpPeerIpv4VrfmulChangeUnicastMulticast          Unsigned32,
                zBgpPeerIpv4VrfmulAsOverride                      Unsigned32,
                zBgpPeerIpv4VrfmulJoinPeergroupType               Unsigned32,
                zBgpPeerIpv4VrfmulAdvMap                          DisplayString,
                zBgpPeerIpv4VrfmulExistMap                        DisplayString,
                zBgpPeerIpv4VrfmulNonExistMap                     DisplayString,
                zBgpPeerIpv4VrfmulAdvMapFlag                      Unsigned32,
                zBgpPeerIpv4VrfmulTtlSecurityHops                 Unsigned32,
                zBgpPeerIpv4VrfmulPeergroupSet                    Unsigned32,
                zBgpPeerIpv4VrfmulGroupConfigCheck                DisplayString,
                zBgpPeerIpv4VrfmulGroupConfigTempCheck            Unsigned32,
                zBgpPeerIpv4VrfmulMaxasIn                         Unsigned32,
                zBgpPeerIpv4VrfmulUsePeergroupConfig              DisplayString,
                zBgpPeerIpv4VrfmulSplitUpdgrp                     Unsigned32,
                zBgpPeerIpv4VrfmulAspathLoopchk                   Unsigned32
        }

zBgpPeerIpv4VrfmulLocalAs OBJECT-TYPE
        SYNTAX   Unsigned32
        MAX-ACCESS  read-only
        STATUS  current
        DESCRIPTION
                "local_as"
        ::= { zBgpPeerIpv4VrfmulEntry  1  }

zBgpPeerIpv4VrfmulIpv4Addr OBJECT-TYPE
        SYNTAX   IpAddress
        MAX-ACCESS  read-only
        STATUS  current
        DESCRIPTION
                "ipv4_addr"
        ::= { zBgpPeerIpv4VrfmulEntry  2  }

zBgpPeerIpv4VrfmulIpv6Addr OBJECT-TYPE
        SYNTAX   DisplayString
        MAX-ACCESS  read-only
        STATUS  current
        DESCRIPTION
                "ipv6_addr"
        ::= { zBgpPeerIpv4VrfmulEntry  3  }

zBgpPeerIpv4VrfmulNeighborGroup OBJECT-TYPE
        SYNTAX   DisplayString
        MAX-ACCESS  read-only
        STATUS  current
        DESCRIPTION
                "neighbor_group"
        ::= { zBgpPeerIpv4VrfmulEntry  4  }

zBgpPeerIpv4VrfmulAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpPeerIpv4VrfmulEntry  5  }

zBgpPeerIpv4VrfmulVrfName OBJECT-TYPE
        SYNTAX   DisplayString
        MAX-ACCESS  read-only
        STATUS  current
        DESCRIPTION
                "vrf_name"
        ::= { zBgpPeerIpv4VrfmulEntry  6  }

zBgpPeerIpv4VrfmulPeerGroupName OBJECT-TYPE
        SYNTAX   DisplayString
        MAX-ACCESS  read-only
        STATUS  current
        DESCRIPTION
                "peer_group_name"
        ::= { zBgpPeerIpv4VrfmulEntry  7  }

zBgpPeerIpv4VrfmulActivate OBJECT-TYPE
        SYNTAX   Unsigned32
        MAX-ACCESS  read-only
        STATUS  current
        DESCRIPTION
                "activate. 0 express disable, 1express enable, 2 express invalid."
        ::= { zBgpPeerIpv4VrfmulEntry  8  }

zBgpPeerIpv4VrfmulAdvertisementInterval OBJECT-TYPE
        SYNTAX   Unsigned32
        MAX-ACCESS  read-only
        STATUS  obsolete
        DESCRIPTION
                "advertisement_interval"
        ::= { zBgpPeerIpv4VrfmulEntry  9  }

zBgpPeerIpv4VrfmulAllowasIn OBJECT-TYPE
        SYNTAX   Unsigned32
        MAX-ACCESS  read-only
        STATUS  obsolete
        DESCRIPTION
                "allowas_in"
        ::= { zBgpPeerIpv4VrfmulEntry  10  }

zBgpPeerIpv4VrfmulDefaultOriginate OBJECT-TYPE
        SYNTAX   Unsigned32
        MAX-ACCESS  read-only
        STATUS  obsolete
        DESCRIPTION
                "default_originate"
        ::= { zBgpPeerIpv4VrfmulEntry  11  }

zBgpPeerIpv4VrfmulDescription OBJECT-TYPE
        SYNTAX   DisplayString
        MAX-ACCESS  read-only
        STATUS  obsolete
        DESCRIPTION
                "description"
        ::= { zBgpPeerIpv4VrfmulEntry  12  }

zBgpPeerIpv4VrfmulEbgpMultihop OBJECT-TYPE
        SYNTAX   Unsigned32
        MAX-ACCESS  read-only
        STATUS  obsolete
        DESCRIPTION
                "ebgp_multihop"
        ::= { zBgpPeerIpv4VrfmulEntry  13  }

zBgpPeerIpv4VrfmulBfd OBJECT-TYPE
        SYNTAX   Unsigned32
        MAX-ACCESS  read-only
        STATUS  obsolete
        DESCRIPTION
                "bfd"
        ::= { zBgpPeerIpv4VrfmulEntry  14  }

zBgpPeerIpv4VrfmulNextHopSelf OBJECT-TYPE
        SYNTAX   INTEGER {
                         nexthopself(1),-- for EBGP peer  
                         nexthopselfall(2)-- for either EBGP or IBGP peer
                         }    
        MAX-ACCESS  read-only
        STATUS  obsolete
        DESCRIPTION
                "next_hop_self"
        ::= { zBgpPeerIpv4VrfmulEntry  15  }

zBgpPeerIpv4VrfmulNextHopUnchanged OBJECT-TYPE
        SYNTAX   Unsigned32
        MAX-ACCESS  read-only
        STATUS  obsolete
        DESCRIPTION
                "next_hop_unchanged"
        ::= { zBgpPeerIpv4VrfmulEntry  16  }

zBgpPeerIpv4VrfmulOriginateInterval OBJECT-TYPE
        SYNTAX   Unsigned32
        MAX-ACCESS  read-only
        STATUS  obsolete
        DESCRIPTION
                "originate_interval"
        ::= { zBgpPeerIpv4VrfmulEntry  17  }

zBgpPeerIpv4VrfmulPassive OBJECT-TYPE
        SYNTAX   Unsigned32
        MAX-ACCESS  read-only
        STATUS  obsolete
        DESCRIPTION
                "passive"
        ::= { zBgpPeerIpv4VrfmulEntry  18  }

zBgpPeerIpv4VrfmulRemoteAs OBJECT-TYPE
        SYNTAX   Unsigned32
        MAX-ACCESS  read-only
        STATUS  obsolete
        DESCRIPTION
                "remote_as"
        ::= { zBgpPeerIpv4VrfmulEntry  19  }

zBgpPeerIpv4VrfmulRemovePrivateAs OBJECT-TYPE
        SYNTAX   Unsigned32
        MAX-ACCESS  read-only
        STATUS  obsolete
        DESCRIPTION
                "remove_private_as"
        ::= { zBgpPeerIpv4VrfmulEntry  20  }

zBgpPeerIpv4VrfmulRouteReflectorClient OBJECT-TYPE
        SYNTAX   Unsigned32
        MAX-ACCESS  read-only
        STATUS  obsolete
        DESCRIPTION
                "route_reflector_client"
        ::= { zBgpPeerIpv4VrfmulEntry  21  }

zBgpPeerIpv4VrfmulSendCommunity OBJECT-TYPE
        SYNTAX   Unsigned32
        MAX-ACCESS  read-only
        STATUS  obsolete
        DESCRIPTION
                "send_community"
        ::= { zBgpPeerIpv4VrfmulEntry  22  }

zBgpPeerIpv4VrfmulSendMed OBJECT-TYPE
        SYNTAX   Unsigned32
        MAX-ACCESS  read-only
        STATUS  obsolete
        DESCRIPTION
                "send_med"
        ::= { zBgpPeerIpv4VrfmulEntry  23  }

zBgpPeerIpv4VrfmulShutDown OBJECT-TYPE
        SYNTAX   Unsigned32
        MAX-ACCESS  read-only
        STATUS  obsolete
        DESCRIPTION
                "shut_down"
        ::= { zBgpPeerIpv4VrfmulEntry  24  }

zBgpPeerIpv4VrfmulUpdateSource OBJECT-TYPE
        SYNTAX   DisplayString
        MAX-ACCESS  read-only
        STATUS  obsolete
        DESCRIPTION
                "update_source"
        ::= { zBgpPeerIpv4VrfmulEntry  25  }

zBgpPeerIpv4VrfmulSendLabel OBJECT-TYPE
        SYNTAX   Unsigned32
        MAX-ACCESS  read-only
        STATUS  obsolete
        DESCRIPTION
                "send_label"
        ::= { zBgpPeerIpv4VrfmulEntry  26  }

zBgpPeerIpv4VrfmulSoftReconfiguration OBJECT-TYPE
        SYNTAX   Unsigned32
        MAX-ACCESS  read-only
        STATUS  obsolete
        DESCRIPTION
                "soft_reconfiguration"
        ::= { zBgpPeerIpv4VrfmulEntry  27  }

zBgpPeerIpv4VrfmulChangeUnicastMulticast OBJECT-TYPE
        SYNTAX   Unsigned32
        MAX-ACCESS  read-only
        STATUS  obsolete
        DESCRIPTION
                "change_unicast_multicast"
        ::= { zBgpPeerIpv4VrfmulEntry  28  }

zBgpPeerIpv4VrfmulAsOverride OBJECT-TYPE
        SYNTAX   Unsigned32
        MAX-ACCESS  read-only
        STATUS  obsolete
        DESCRIPTION
                "as_override"
        ::= { zBgpPeerIpv4VrfmulEntry  29  }

zBgpPeerIpv4VrfmulJoinPeergroupType OBJECT-TYPE
        SYNTAX   Unsigned32
        MAX-ACCESS  read-only
        STATUS  obsolete
        DESCRIPTION
                "join_peergroup_type"
        ::= { zBgpPeerIpv4VrfmulEntry  30  }

zBgpPeerIpv4VrfmulAdvMap OBJECT-TYPE
        SYNTAX   DisplayString
        MAX-ACCESS  read-only
        STATUS  obsolete
        DESCRIPTION
                "adv_map"
        ::= { zBgpPeerIpv4VrfmulEntry  31  }

zBgpPeerIpv4VrfmulExistMap OBJECT-TYPE
        SYNTAX   DisplayString
        MAX-ACCESS  read-only
        STATUS  obsolete
        DESCRIPTION
                "exist_map"
        ::= { zBgpPeerIpv4VrfmulEntry  32  }

zBgpPeerIpv4VrfmulNonExistMap OBJECT-TYPE
        SYNTAX   DisplayString
        MAX-ACCESS  read-only
        STATUS  obsolete
        DESCRIPTION
                "non_exist_map"
        ::= { zBgpPeerIpv4VrfmulEntry  33  }

zBgpPeerIpv4VrfmulAdvMapFlag OBJECT-TYPE
        SYNTAX   Unsigned32
        MAX-ACCESS  read-only
        STATUS  obsolete
        DESCRIPTION
                "adv_map_flag"
        ::= { zBgpPeerIpv4VrfmulEntry  34  }

zBgpPeerIpv4VrfmulTtlSecurityHops OBJECT-TYPE
        SYNTAX   Unsigned32
        MAX-ACCESS  read-only
        STATUS  obsolete
        DESCRIPTION
                "ttl-security-hops"
        ::= { zBgpPeerIpv4VrfmulEntry  35  }

zBgpPeerIpv4VrfmulPeergroupSet OBJECT-TYPE
        SYNTAX   Unsigned32
        MAX-ACCESS  read-only
        STATUS  obsolete
        DESCRIPTION
                "peergroup_set"
        ::= { zBgpPeerIpv4VrfmulEntry  36  }

zBgpPeerIpv4VrfmulGroupConfigCheck OBJECT-TYPE
        SYNTAX   DisplayString
        MAX-ACCESS  read-only
        STATUS  obsolete
        DESCRIPTION
                "group_config_check"
        ::= { zBgpPeerIpv4VrfmulEntry  37  }

zBgpPeerIpv4VrfmulGroupConfigTempCheck OBJECT-TYPE
        SYNTAX   Unsigned32
        MAX-ACCESS  read-only
        STATUS  obsolete
        DESCRIPTION
                "group_config_temp_check"
        ::= { zBgpPeerIpv4VrfmulEntry  38  }

zBgpPeerIpv4VrfmulMaxasIn OBJECT-TYPE
        SYNTAX   Unsigned32
        MAX-ACCESS  read-only
        STATUS  obsolete
        DESCRIPTION
                "maxas_in"
        ::= { zBgpPeerIpv4VrfmulEntry  39  }

zBgpPeerIpv4VrfmulUsePeergroupConfig OBJECT-TYPE
        SYNTAX   DisplayString
        MAX-ACCESS  read-only
        STATUS  obsolete
        DESCRIPTION
                "use_peergroup_config"
        ::= { zBgpPeerIpv4VrfmulEntry  40  }

zBgpPeerIpv4VrfmulSplitUpdgrp OBJECT-TYPE
        SYNTAX   Unsigned32
        MAX-ACCESS  read-only
        STATUS  current
        DESCRIPTION
                "split_updgrp(1 enable,0 disable)"
        ::= { zBgpPeerIpv4VrfmulEntry  41  }

zBgpPeerIpv4VrfmulAspathLoopchk OBJECT-TYPE
        SYNTAX   Unsigned32
        MAX-ACCESS  read-only
        STATUS  current
        DESCRIPTION
                "as_path_loopcheck(1 enable,0 disable)"
        ::= { zBgpPeerIpv4VrfmulEntry  42  }

--------------------------------------------------------------
--------------------------------------------------------------
--zBgpPeerIpv4VrfmulExtendTable
--------------------------------------------------------------
zBgpPeerIpv4VrfmulExtendTable OBJECT-TYPE
        SYNTAX  SEQUENCE OF ZBgpPeerIpv4VrfmulExtendEntry
        MAX-ACCESS  not-accessible
        STATUS  current
        DESCRIPTION
                "BGP_PEER_IPV4_VRFMUL_EXTEND"
        ::= { zxr10BgpMIB 24  }

zBgpPeerIpv4VrfmulExtendEntry OBJECT-TYPE
        SYNTAX   ZBgpPeerIpv4VrfmulExtendEntry
        MAX-ACCESS  not-accessible
        STATUS  current
        DESCRIPTION
                "BGP_PEER_IPV4_VRFMUL_EXTEND"
        INDEX {zBgpPeerIpv4VrfmulExtendLocalAs,
               zBgpPeerIpv4VrfmulExtendIpv4Addr,
               zBgpPeerIpv4VrfmulExtendIpv6Addr,
               zBgpPeerIpv4VrfmulExtendNeighborGroup,
               zBgpPeerIpv4VrfmulExtendAddrModeType,
               zBgpPeerIpv4VrfmulExtendVrfName 
        }
        ::= { zBgpPeerIpv4VrfmulExtendTable 1 }

ZBgpPeerIpv4VrfmulExtendEntry ::=
        SEQUENCE {
                zBgpPeerIpv4VrfmulExtendLocalAs                   Unsigned32,
                zBgpPeerIpv4VrfmulExtendIpv4Addr                  IpAddress,
                zBgpPeerIpv4VrfmulExtendIpv6Addr                  DisplayString,
                zBgpPeerIpv4VrfmulExtendNeighborGroup             DisplayString,
                zBgpPeerIpv4VrfmulExtendAddrModeType              INTEGER,
                zBgpPeerIpv4VrfmulExtendVrfName                   DisplayString,
                zBgpPeerIpv4VrfmulExtendPeerGroupName             DisplayString,
                zBgpPeerIpv4VrfmulExtendMaxinumPrefix             Unsigned32,
                zBgpPeerIpv4VrfmulExtendMaxinumPrefixThreshold    Unsigned32,
                zBgpPeerIpv4VrfmulExtendMaxinumPrefixRestarttime  Unsigned32,
                zBgpPeerIpv4VrfmulExtendMaxinumPrefixOverAction   Unsigned32,
                zBgpPeerIpv4VrfmulExtendPassword                  DisplayString,
                zBgpPeerIpv4VrfmulExtendPasswordEncrypt           DisplayString,
                zBgpPeerIpv4VrfmulExtendRemoteAs                  Unsigned32,
                zBgpPeerIpv4VrfmulExtendHoldtimeConf              Unsigned32,
                zBgpPeerIpv4VrfmulExtendKeepaliveConf             Unsigned32,
                zBgpPeerIpv4VrfmulExtendTimersCmdType             Unsigned32,
                zBgpPeerIpv4VrfmulExtendPasswordIsEncrypt         Unsigned32,
                zBgpPeerIpv4VrfmulExtendMaxprefixCmdType          Unsigned32,
                zBgpPeerIpv4VrfmulExtendRouteMapIn                DisplayString,
                zBgpPeerIpv4VrfmulExtendRouteMapOut               DisplayString,
                zBgpPeerIpv4VrfmulExtendRoutemapOutFlag           Unsigned32,
                zBgpPeerIpv4VrfmulExtendRoutemapName              DisplayString,
                zBgpPeerIpv4VrfmulExtendRoutemapInFlag            Unsigned32,
                zBgpPeerIpv4VrfmulExtendPrefixName                DisplayString,
                zBgpPeerIpv4VrfmulExtendPrefixInFlag              Unsigned32,
                zBgpPeerIpv4VrfmulExtendPrefixIn                  DisplayString,
                zBgpPeerIpv4VrfmulExtendPrefixOut                 DisplayString,
                zBgpPeerIpv4VrfmulExtendPrefixOutFlag             Unsigned32,
                zBgpPeerIpv4VrfmulExtendPeergroupSet              Unsigned32,
                zBgpPeerIpv4VrfmulExtendGroupConfigCheck          DisplayString,
                zBgpPeerIpv4VrfmulExtendGroupConfigTempCheck      Unsigned32,
                zBgpPeerIpv4VrfmulExtendPasswordEncrypted         DisplayString,
                zBgpPeerIpv4VrfmulExtendPasswordIsEncrypted       Unsigned32,
                zBgpPeerIpv4VrfmulExtendPasswordIsSet             Unsigned32,
                zBgpPeerIpv4VrfmulExtendUsePeergroupConfig        DisplayString
        }

zBgpPeerIpv4VrfmulExtendLocalAs OBJECT-TYPE
        SYNTAX   Unsigned32
        MAX-ACCESS  read-only
        STATUS  current
        DESCRIPTION
                "local_as"
        ::= { zBgpPeerIpv4VrfmulExtendEntry  1  }

zBgpPeerIpv4VrfmulExtendIpv4Addr OBJECT-TYPE
        SYNTAX   IpAddress
        MAX-ACCESS  read-only
        STATUS  current
        DESCRIPTION
                "ipv4_addr"
        ::= { zBgpPeerIpv4VrfmulExtendEntry  2  }

zBgpPeerIpv4VrfmulExtendIpv6Addr OBJECT-TYPE
        SYNTAX   DisplayString
        MAX-ACCESS  read-only
        STATUS  current
        DESCRIPTION
                "ipv6_addr"
        ::= { zBgpPeerIpv4VrfmulExtendEntry  3  }

zBgpPeerIpv4VrfmulExtendNeighborGroup OBJECT-TYPE
        SYNTAX   DisplayString
        MAX-ACCESS  read-only
        STATUS  current
        DESCRIPTION
                "neighbor_group"
        ::= { zBgpPeerIpv4VrfmulExtendEntry  4  }

zBgpPeerIpv4VrfmulExtendAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "addr_mode_type"
        ::= { zBgpPeerIpv4VrfmulExtendEntry  5  }

zBgpPeerIpv4VrfmulExtendVrfName OBJECT-TYPE
        SYNTAX   DisplayString
        MAX-ACCESS  read-only
        STATUS  current
        DESCRIPTION
                "vrf_name"
        ::= { zBgpPeerIpv4VrfmulExtendEntry  6  }

zBgpPeerIpv4VrfmulExtendPeerGroupName OBJECT-TYPE
        SYNTAX   DisplayString
        MAX-ACCESS  read-only
        STATUS  current
        DESCRIPTION
                "peer_group_name"
        ::= { zBgpPeerIpv4VrfmulExtendEntry  7  }

zBgpPeerIpv4VrfmulExtendMaxinumPrefix OBJECT-TYPE
        SYNTAX   Unsigned32
        MAX-ACCESS  read-only
        STATUS  obsolete
        DESCRIPTION
                "maxinum_prefix"
        ::= { zBgpPeerIpv4VrfmulExtendEntry  8  }

zBgpPeerIpv4VrfmulExtendMaxinumPrefixThreshold OBJECT-TYPE
        SYNTAX   Unsigned32
        MAX-ACCESS  read-only
        STATUS  obsolete
        DESCRIPTION
                "maxinum_prefix_threshold"
        ::= { zBgpPeerIpv4VrfmulExtendEntry  9  }

zBgpPeerIpv4VrfmulExtendMaxinumPrefixRestarttime OBJECT-TYPE
        SYNTAX   Unsigned32
        MAX-ACCESS  read-only
        STATUS  obsolete
        DESCRIPTION
                "maxinum_prefix_restartTime"
        ::= { zBgpPeerIpv4VrfmulExtendEntry  10  }

zBgpPeerIpv4VrfmulExtendMaxinumPrefixOverAction OBJECT-TYPE
        SYNTAX   Unsigned32
        MAX-ACCESS  read-only
        STATUS  obsolete
        DESCRIPTION
                "maxinum_prefix_over_action"
        ::= { zBgpPeerIpv4VrfmulExtendEntry  11  }

zBgpPeerIpv4VrfmulExtendPassword OBJECT-TYPE
        SYNTAX   DisplayString
        MAX-ACCESS  read-only
        STATUS  obsolete
        DESCRIPTION
                "password"
        ::= { zBgpPeerIpv4VrfmulExtendEntry  12  }

zBgpPeerIpv4VrfmulExtendPasswordEncrypt OBJECT-TYPE
        SYNTAX   DisplayString
        MAX-ACCESS  read-only
        STATUS  obsolete
        DESCRIPTION
                "password_encrypt"
        ::= { zBgpPeerIpv4VrfmulExtendEntry  13  }

zBgpPeerIpv4VrfmulExtendRemoteAs OBJECT-TYPE
        SYNTAX   Unsigned32
        MAX-ACCESS  read-only
        STATUS  obsolete
        DESCRIPTION
                "remote_as"
        ::= { zBgpPeerIpv4VrfmulExtendEntry  14  }

zBgpPeerIpv4VrfmulExtendHoldtimeConf OBJECT-TYPE
        SYNTAX   Unsigned32
        MAX-ACCESS  read-only
        STATUS  obsolete
        DESCRIPTION
                "holdtime_conf"
        ::= { zBgpPeerIpv4VrfmulExtendEntry  15  }

zBgpPeerIpv4VrfmulExtendKeepaliveConf OBJECT-TYPE
        SYNTAX   Unsigned32
        MAX-ACCESS  read-only
        STATUS  obsolete
        DESCRIPTION
                "keepalive_conf"
        ::= { zBgpPeerIpv4VrfmulExtendEntry  16  }

zBgpPeerIpv4VrfmulExtendTimersCmdType OBJECT-TYPE
        SYNTAX   Unsigned32
        MAX-ACCESS  read-only
        STATUS  obsolete
        DESCRIPTION
                "timers_cmd_type"
        ::= { zBgpPeerIpv4VrfmulExtendEntry  17  }

zBgpPeerIpv4VrfmulExtendPasswordIsEncrypt OBJECT-TYPE
        SYNTAX   Unsigned32
        MAX-ACCESS  read-only
        STATUS  obsolete
        DESCRIPTION
                "password_is_encrypt"
        ::= { zBgpPeerIpv4VrfmulExtendEntry  18  }

zBgpPeerIpv4VrfmulExtendMaxprefixCmdType OBJECT-TYPE
        SYNTAX   Unsigned32
        MAX-ACCESS  read-only
        STATUS  obsolete
        DESCRIPTION
                "maxprefix_cmd_type"
        ::= { zBgpPeerIpv4VrfmulExtendEntry  19  }

zBgpPeerIpv4VrfmulExtendRouteMapIn OBJECT-TYPE
        SYNTAX   DisplayString
        MAX-ACCESS  read-only
        STATUS  obsolete
        DESCRIPTION
                "route_map_in"
        ::= { zBgpPeerIpv4VrfmulExtendEntry  20  }

zBgpPeerIpv4VrfmulExtendRouteMapOut OBJECT-TYPE
        SYNTAX   DisplayString
        MAX-ACCESS  read-only
        STATUS  obsolete
        DESCRIPTION
                "route_map_out"
        ::= { zBgpPeerIpv4VrfmulExtendEntry  21  }

zBgpPeerIpv4VrfmulExtendRoutemapOutFlag OBJECT-TYPE
        SYNTAX   Unsigned32
        MAX-ACCESS  read-only
        STATUS  obsolete
        DESCRIPTION
                "routemap_out_flag"
        ::= { zBgpPeerIpv4VrfmulExtendEntry  22  }

zBgpPeerIpv4VrfmulExtendRoutemapName OBJECT-TYPE
        SYNTAX   DisplayString
        MAX-ACCESS  read-only
        STATUS  obsolete
        DESCRIPTION
                "routemap_name"
        ::= { zBgpPeerIpv4VrfmulExtendEntry  23  }

zBgpPeerIpv4VrfmulExtendRoutemapInFlag OBJECT-TYPE
        SYNTAX   Unsigned32
        MAX-ACCESS  read-only
        STATUS  obsolete
        DESCRIPTION
                "routemap_in_flag"
        ::= { zBgpPeerIpv4VrfmulExtendEntry  24  }

zBgpPeerIpv4VrfmulExtendPrefixName OBJECT-TYPE
        SYNTAX   DisplayString
        MAX-ACCESS  read-only
        STATUS  obsolete
        DESCRIPTION
                "prefix_name"
        ::= { zBgpPeerIpv4VrfmulExtendEntry  25  }

zBgpPeerIpv4VrfmulExtendPrefixInFlag OBJECT-TYPE
        SYNTAX   Unsigned32
        MAX-ACCESS  read-only
        STATUS  obsolete
        DESCRIPTION
                "prefix_in_flag"
        ::= { zBgpPeerIpv4VrfmulExtendEntry  26  }

zBgpPeerIpv4VrfmulExtendPrefixIn OBJECT-TYPE
        SYNTAX   DisplayString
        MAX-ACCESS  read-only
        STATUS  obsolete
        DESCRIPTION
                "prefix_in"
        ::= { zBgpPeerIpv4VrfmulExtendEntry  27  }

zBgpPeerIpv4VrfmulExtendPrefixOut OBJECT-TYPE
        SYNTAX   DisplayString
        MAX-ACCESS  read-only
        STATUS  obsolete
        DESCRIPTION
                "prefix_out"
        ::= { zBgpPeerIpv4VrfmulExtendEntry  28  }

zBgpPeerIpv4VrfmulExtendPrefixOutFlag OBJECT-TYPE
        SYNTAX   Unsigned32
        MAX-ACCESS  read-only
        STATUS  obsolete
        DESCRIPTION
                "prefix_out_flag"
        ::= { zBgpPeerIpv4VrfmulExtendEntry  29  }

zBgpPeerIpv4VrfmulExtendPeergroupSet OBJECT-TYPE
        SYNTAX   Unsigned32
        MAX-ACCESS  read-only
        STATUS  obsolete
        DESCRIPTION
                "peergroup_set"
        ::= { zBgpPeerIpv4VrfmulExtendEntry  30  }

zBgpPeerIpv4VrfmulExtendGroupConfigCheck OBJECT-TYPE
        SYNTAX   DisplayString
        MAX-ACCESS  read-only
        STATUS  obsolete
        DESCRIPTION
                "group_config_check"
        ::= { zBgpPeerIpv4VrfmulExtendEntry  31  }

zBgpPeerIpv4VrfmulExtendGroupConfigTempCheck OBJECT-TYPE
        SYNTAX   Unsigned32
        MAX-ACCESS  read-only
        STATUS  obsolete
        DESCRIPTION
                "group_config_temp_check"
        ::= { zBgpPeerIpv4VrfmulExtendEntry  32  }

zBgpPeerIpv4VrfmulExtendPasswordEncrypted OBJECT-TYPE
        SYNTAX   DisplayString
        MAX-ACCESS  read-only
        STATUS  obsolete
        DESCRIPTION
                "password_encrypted"
        ::= { zBgpPeerIpv4VrfmulExtendEntry  33  }

zBgpPeerIpv4VrfmulExtendPasswordIsEncrypted OBJECT-TYPE
        SYNTAX   Unsigned32
        MAX-ACCESS  read-only
        STATUS  obsolete
        DESCRIPTION
                "password_is_encrypted"
        ::= { zBgpPeerIpv4VrfmulExtendEntry  34  }

zBgpPeerIpv4VrfmulExtendPasswordIsSet OBJECT-TYPE
        SYNTAX   Unsigned32
        MAX-ACCESS  read-only
        STATUS  obsolete
        DESCRIPTION
                "password_is_set"
        ::= { zBgpPeerIpv4VrfmulExtendEntry  35  }

zBgpPeerIpv4VrfmulExtendUsePeergroupConfig OBJECT-TYPE
        SYNTAX   DisplayString
        MAX-ACCESS  read-only
        STATUS  obsolete
        DESCRIPTION
                "use_peergroup_config"
        ::= { zBgpPeerIpv4VrfmulExtendEntry  36  }

--------------------------------------------------------------
--------------------------------------------------------------
--zBgpReleatedVrfV4Table
--------------------------------------------------------------
zBgpReleatedVrfV4Table OBJECT-TYPE
        SYNTAX  SEQUENCE OF ZBgpReleatedVrfV4Entry
        MAX-ACCESS  not-accessible
        STATUS  current
        DESCRIPTION
                "bgp_releated_vrf_v4"
        ::= { zxr10BgpMIB 25  }

zBgpReleatedVrfV4Entry OBJECT-TYPE
        SYNTAX   ZBgpReleatedVrfV4Entry
        MAX-ACCESS  not-accessible
        STATUS  current
        DESCRIPTION
                "bgp_releated_vrf_v4"
        INDEX {zBgpReleatedVrfV4LocalAs,zBgpReleatedVrfV4VrfName }
        ::= { zBgpReleatedVrfV4Table 1 }

ZBgpReleatedVrfV4Entry ::=
        SEQUENCE {
                zBgpReleatedVrfV4LocalAs                          Unsigned32,
                zBgpReleatedVrfV4VrfName                          DisplayString
        }

zBgpReleatedVrfV4LocalAs OBJECT-TYPE
        SYNTAX   Unsigned32
        MAX-ACCESS  read-only
        STATUS  current
        DESCRIPTION
                "local_as"
        ::= { zBgpReleatedVrfV4Entry  1  }

zBgpReleatedVrfV4VrfName OBJECT-TYPE
        SYNTAX   DisplayString
        MAX-ACCESS  read-only
        STATUS  current
        DESCRIPTION
                "vrf_name"
        ::= { zBgpReleatedVrfV4Entry  2  }



--------------------------------------------------------------
--------------------------------------------------------------
--zBgpReleatedVrfV6Table
--------------------------------------------------------------
zBgpReleatedVrfV6Table OBJECT-TYPE
        SYNTAX  SEQUENCE OF ZBgpReleatedVrfV6Entry
        MAX-ACCESS  not-accessible
        STATUS  current
        DESCRIPTION
                "bgp_releated_vrf_v6"
        ::= { zxr10BgpMIB 26  }

zBgpReleatedVrfV6Entry OBJECT-TYPE
        SYNTAX   ZBgpReleatedVrfV6Entry
        MAX-ACCESS  not-accessible
        STATUS  current
        DESCRIPTION
                "bgp_releated_vrf_v6"
        INDEX {zBgpReleatedVrfV6LocalAs,zBgpReleatedVrfV6VrfName }
        ::= { zBgpReleatedVrfV6Table 1 }

ZBgpReleatedVrfV6Entry ::=
        SEQUENCE {
                zBgpReleatedVrfV6LocalAs                          Unsigned32,
                zBgpReleatedVrfV6VrfName                          DisplayString
        }

zBgpReleatedVrfV6LocalAs OBJECT-TYPE
        SYNTAX   Unsigned32
        MAX-ACCESS  read-only
        STATUS  current
        DESCRIPTION
                "local_as"
        ::= { zBgpReleatedVrfV6Entry  1  }

zBgpReleatedVrfV6VrfName OBJECT-TYPE
        SYNTAX   DisplayString
        MAX-ACCESS  read-only
        STATUS  current
        DESCRIPTION
                "vrf_name"
        ::= { zBgpReleatedVrfV6Entry  2  }
--------------------------------------------------------------
--------------------------------------------------------------
--zBgpV4UniTrackTable
--------------------------------------------------------------
zBgpV4UniTrackTable OBJECT-TYPE
        SYNTAX  SEQUENCE OF ZBgpV4UniTrackEntry
        MAX-ACCESS  not-accessible
        STATUS  obsolete
        DESCRIPTION
                "Bgp ipv4 unicast event tracking"
        ::= { zxr10BgpMIB 27  }

zBgpV4UniTrackEntry OBJECT-TYPE
        SYNTAX   ZBgpV4UniTrackEntry
        MAX-ACCESS  not-accessible
        STATUS  obsolete
        DESCRIPTION
                "Bgp ipv4 unicast event tracking"
        INDEX {zBgpV4UniTrackName,zBgpV4UniLocalAs, 
              zBgpV4UniTrackType,zBgpV4UniTrackInterfName}
        ::= { zBgpV4UniTrackTable 1 }

ZBgpV4UniTrackEntry ::=
        SEQUENCE {
                zBgpV4UniTrackName                        DisplayString,
                zBgpV4UniLocalAs                          Unsigned32,
                zBgpV4UniTrackType                        Integer32,
                zBgpV4UniTrackInterfName                  DisplayString,
                zBgpV4UniAddrModeType                     INTEGER, 
                zBgpV4UniTrackAdjValue                    Unsigned32,
                zBgpV4UniTrackRowStatus                   RowStatus
        }
zBgpV4UniTrackName OBJECT-TYPE
        SYNTAX   DisplayString
        MAX-ACCESS  not-accessible
        STATUS  obsolete
        DESCRIPTION
                "Name of track object"
        ::= { zBgpV4UniTrackEntry  1  }

zBgpV4UniLocalAs OBJECT-TYPE
        SYNTAX   Unsigned32
        MAX-ACCESS  not-accessible
        STATUS  obsolete
        DESCRIPTION
                "Autonomous system number (normal or 4 Octets)"
        ::= { zBgpV4UniTrackEntry  2  }
        
 zBgpV4UniTrackType OBJECT-TYPE
        SYNTAX   Integer32
        MAX-ACCESS  not-accessible
        STATUS  obsolete
        DESCRIPTION
                "Configure type of track object"
        ::= { zBgpV4UniTrackEntry  3  } 
         
zBgpV4UniTrackInterfName OBJECT-TYPE
        SYNTAX   DisplayString
        MAX-ACCESS  not-accessible
        STATUS  obsolete
        DESCRIPTION
                "Intreface name"
        ::= { zBgpV4UniTrackEntry  4  } 
                    
zBgpV4UniAddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15)
                    }
        MAX-ACCESS  read-only
        STATUS  obsolete
        DESCRIPTION
                "Address mode type"
        ::= { zBgpV4UniTrackEntry  5  }  

zBgpV4UniTrackAdjValue OBJECT-TYPE
        SYNTAX   Unsigned32
        MAX-ACCESS  read-create
        STATUS  obsolete
        DESCRIPTION
                "Value of adjust-priority"
        ::= { zBgpV4UniTrackEntry  6  }
        
zBgpV4UniTrackRowStatus OBJECT-TYPE
   SYNTAX        RowStatus
   MAX-ACCESS    read-create
   STATUS        obsolete
   DESCRIPTION
       "Row status for this entry."
   ::= { zBgpV4UniTrackEntry 100 }      
        
--------------------------------------------------------------
--------------------------------------------------------------
--zBgpVrfV4TrackTable
--------------------------------------------------------------
zBgpVrfV4TrackTable OBJECT-TYPE
        SYNTAX  SEQUENCE OF ZBgpVrfV4TrackEntry
        MAX-ACCESS  not-accessible
        STATUS  obsolete
        DESCRIPTION
                "bgp vrf ipv4 unicast event tracking"
        ::= { zxr10BgpMIB 28  }

zBgpVrfV4TrackEntry OBJECT-TYPE
        SYNTAX  ZBgpVrfV4TrackEntry
        MAX-ACCESS  not-accessible
        STATUS  obsolete
        DESCRIPTION
                "bgp vrf ipv4 unicast event tracking"
        INDEX {zBgpVrfV4TrackName,zBgpVrfV4LocalAs,
                zBgpVrfV4AddrModeType, zBgpVrfV4Vrfname,
                zBgpVrfV4TrackType,zBgpVrfV4TrackInterfName}
        ::= { zBgpVrfV4TrackTable 1 }

ZBgpVrfV4TrackEntry ::=
        SEQUENCE {
                zBgpVrfV4TrackName                        DisplayString,
                zBgpVrfV4LocalAs                          Unsigned32,
                zBgpVrfV4AddrModeType                     INTEGER,    
                zBgpVrfV4Vrfname                          DisplayString,
                zBgpVrfV4TrackType                        Integer32,
                zBgpVrfV4TrackInterfName                  DisplayString,
                zBgpVrfV4TrackAdjValue                    Unsigned32,
                zBgpVrfV4TrackRowStatus                   RowStatus
        }
zBgpVrfV4TrackName OBJECT-TYPE
        SYNTAX   DisplayString
        MAX-ACCESS  not-accessible
        STATUS  obsolete
        DESCRIPTION
                "Name of track object"
        ::= { zBgpVrfV4TrackEntry  1  }

zBgpVrfV4LocalAs OBJECT-TYPE
        SYNTAX   Unsigned32
        MAX-ACCESS  not-accessible
        STATUS  obsolete
        DESCRIPTION
                "Autonomous system number (normal or 4 Octets)"
        ::= { zBgpVrfV4TrackEntry  2  }
        
zBgpVrfV4AddrModeType OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15)
                    }
        MAX-ACCESS  not-accessible
        STATUS  obsolete
        DESCRIPTION
                "address mode type"
        ::= { zBgpVrfV4TrackEntry  3  }  

zBgpVrfV4Vrfname OBJECT-TYPE
        SYNTAX   DisplayString
        MAX-ACCESS  not-accessible
        STATUS  obsolete
        DESCRIPTION
                "vrf name"
        ::= { zBgpVrfV4TrackEntry  4  }
        
zBgpVrfV4TrackType OBJECT-TYPE
        SYNTAX   Integer32
        MAX-ACCESS  not-accessible
        STATUS  obsolete
        DESCRIPTION
                "track type"
        ::= { zBgpVrfV4TrackEntry  5  }
        
zBgpVrfV4TrackInterfName OBJECT-TYPE
        SYNTAX   DisplayString
        MAX-ACCESS  not-accessible
        STATUS  obsolete
        DESCRIPTION
                "intreface name"
        ::= { zBgpVrfV4TrackEntry  6  }

zBgpVrfV4TrackAdjValue OBJECT-TYPE
        SYNTAX   Unsigned32
        MAX-ACCESS  read-create
        STATUS  obsolete
        DESCRIPTION
                "Value of adjust-priority"
        ::= { zBgpVrfV4TrackEntry  7  }
        
zBgpVrfV4TrackRowStatus OBJECT-TYPE
   SYNTAX        RowStatus
   MAX-ACCESS    read-create
   STATUS        obsolete
   DESCRIPTION
       "Row status for this entry."
   ::= { zBgpVrfV4TrackEntry 100 }

--------------------------------------------------------------
--------------------------------------------------------------
--zBgpAsWeightNewTable  bgp as new
--------------------------------------------------------------
zBgpAsWeightNewTable OBJECT-TYPE
        SYNTAX  SEQUENCE OF ZBgpAsWeightNewEntry
        MAX-ACCESS  not-accessible
        STATUS  current
        DESCRIPTION
                "BGP_AS_WEIGHT"
        ::= { zxr10BgpMIB 29  }

zBgpAsWeightNewEntry OBJECT-TYPE
        SYNTAX   ZBgpAsWeightNewEntry
        MAX-ACCESS  not-accessible
        STATUS  current
        DESCRIPTION
                "BGP_AS_WEIGHT"
        INDEX {
               zBgpAsWeightNewLocalAs, 
               zBgpAsWeightNewWeightAs 
              }
        ::= { zBgpAsWeightNewTable 1 }

ZBgpAsWeightNewEntry ::=
        SEQUENCE {
                zBgpAsWeightNewLocalAs    Unsigned32,
                zBgpAsWeightNewWeightAs   Unsigned32,
                zBgpAsWeightNewWeight     Unsigned32
        }

zBgpAsWeightNewLocalAs OBJECT-TYPE
        SYNTAX   Unsigned32
        MAX-ACCESS  not-accessible
        STATUS  current
        DESCRIPTION
                "local_as"
        ::= { zBgpAsWeightNewEntry  1  }

zBgpAsWeightNewWeightAs OBJECT-TYPE
        SYNTAX   Unsigned32
        MAX-ACCESS  not-accessible
        STATUS  current
        DESCRIPTION
                "weight_as"
        ::= { zBgpAsWeightNewEntry  2  }

zBgpAsWeightNewWeight OBJECT-TYPE
        SYNTAX   Unsigned32
        MAX-ACCESS  read-only
        STATUS  current
        DESCRIPTION
                "weight"
        ::= { zBgpAsWeightNewEntry  3  }

                   
--------------------------------------------------------------
--------------------------------------------------------------
--zBgpConfPeersNewTable                                          
--------------------------------------------------------------
zBgpConfPeersNewTable OBJECT-TYPE                                
        SYNTAX  SEQUENCE OF ZBgpConfPeersNewEntry                
        MAX-ACCESS  not-accessible                            
        STATUS  current                                       
        DESCRIPTION                                           
                "BGP_CONF_PEERS"                              
        ::= { zxr10BgpMIB 30  }                                
                                                              
zBgpConfPeersNewEntry OBJECT-TYPE                                
        SYNTAX   ZBgpConfPeersNewEntry                           
        MAX-ACCESS  not-accessible                            
        STATUS  current                                       
        DESCRIPTION                                           
                "BGP_CONF_PEERS"                              
        INDEX {
               zBgpConfPeersNewLocalAs,
               zBgpConfPeersNewConfPeerAs 
               }                      
        ::= { zBgpConfPeersNewTable 1 }                          
                                                              
ZBgpConfPeersNewEntry ::=                                        
        SEQUENCE {
          zBgpConfPeersNewLocalAs      Unsigned32,  
          zBgpConfPeersNewConfPeerAs   Unsigned32                
        }                                                     

zBgpConfPeersNewLocalAs OBJECT-TYPE
        SYNTAX   Unsigned32
        MAX-ACCESS  not-accessible
        STATUS  current
        DESCRIPTION
                "local_as"
        ::= { zBgpConfPeersNewEntry  1  }
                                                    
zBgpConfPeersNewConfPeerAs OBJECT-TYPE                           
        SYNTAX   Unsigned32                                   
        MAX-ACCESS  read-only                                 
        STATUS  current                                       
        DESCRIPTION                                           
                "conf_peer_as"                                
        ::= { zBgpConfPeersNewEntry  2  }                        

--------------------------------------------------------------
--------------------------------------------------------------
--zBgpV4UniTrackTable
--------------------------------------------------------------
zBgpV4UniTrackNewTable OBJECT-TYPE
        SYNTAX  SEQUENCE OF ZBgpV4UniTrackNewEntry
        MAX-ACCESS  not-accessible
        STATUS  current
        DESCRIPTION
                "Bgp ipv4 unicast event tracking"
        ::= { zxr10BgpMIB 31  }

zBgpV4UniTrackNewEntry OBJECT-TYPE
        SYNTAX   ZBgpV4UniTrackNewEntry
        MAX-ACCESS  not-accessible
        STATUS  current
        DESCRIPTION
                "Bgp ipv4 unicast event tracking"
        INDEX {zBgpV4UniLocalAsNew, 
               zBgpV4UniTrackNameNew,
               zBgpV4UniTrackTypeNew,
               zBgpV4UniTrackInterfNameNew}
        ::= { zBgpV4UniTrackNewTable 1 }

ZBgpV4UniTrackNewEntry ::=
        SEQUENCE {
                zBgpV4UniLocalAsNew                          Unsigned32,
                zBgpV4UniTrackNameNew                        DisplayString,
                zBgpV4UniTrackTypeNew                        Integer32,
                zBgpV4UniTrackInterfNameNew                  DisplayString,
                zBgpV4UniAddrModeTypeNew                     INTEGER, 
                zBgpV4UniTrackAdjValueNew                    Unsigned32,
                zBgpV4UniTrackNewRowStatus                   RowStatus
        }


zBgpV4UniLocalAsNew OBJECT-TYPE
        SYNTAX   Unsigned32
        MAX-ACCESS  not-accessible
        STATUS  current
        DESCRIPTION
                "Autonomous system number (normal or 4 Octets)"
        ::= { zBgpV4UniTrackNewEntry  1  }
        
zBgpV4UniTrackNameNew OBJECT-TYPE
        SYNTAX   DisplayString
        MAX-ACCESS  not-accessible
        STATUS  current
        DESCRIPTION
                "Name of track object"
        ::= { zBgpV4UniTrackNewEntry  2  }

 zBgpV4UniTrackTypeNew OBJECT-TYPE
        SYNTAX   Integer32
        MAX-ACCESS  not-accessible
        STATUS  current
        DESCRIPTION
                "Configure type of track object"
        ::= { zBgpV4UniTrackNewEntry  3  } 
         
zBgpV4UniTrackInterfNameNew OBJECT-TYPE
        SYNTAX   DisplayString
        MAX-ACCESS  not-accessible
        STATUS  current
        DESCRIPTION
                "Intreface name"
        ::= { zBgpV4UniTrackNewEntry  4  } 
                    
zBgpV4UniAddrModeTypeNew OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  read-only
        STATUS  current
        DESCRIPTION
                "Address mode type"
        ::= { zBgpV4UniTrackNewEntry  5  }  

zBgpV4UniTrackAdjValueNew OBJECT-TYPE
        SYNTAX   Unsigned32
        MAX-ACCESS  read-create
        STATUS  current
        DESCRIPTION
                "Value of adjust-priority.If value of zBgpVrfV4TrackTypeNew is 1, range 1-100,
                 else if value of zBgpVrfV4TrackTypeNew is 2, range 0-0."
        ::= { zBgpV4UniTrackNewEntry  6  }
        
zBgpV4UniTrackNewRowStatus OBJECT-TYPE
   SYNTAX        RowStatus
   MAX-ACCESS    read-create
   STATUS        current
   DESCRIPTION
       "Row status for this entry."
   ::= { zBgpV4UniTrackNewEntry 100 }      
        
--------------------------------------------------------------
--------------------------------------------------------------
--zBgpVrfV4TrackTable
--------------------------------------------------------------
zBgpVrfV4TrackNewTable OBJECT-TYPE
        SYNTAX  SEQUENCE OF ZBgpVrfV4TrackNewEntry
        MAX-ACCESS  not-accessible
        STATUS  current
        DESCRIPTION
                "bgp vrf ipv4 unicast event tracking"
        ::= { zxr10BgpMIB 32  }

zBgpVrfV4TrackNewEntry OBJECT-TYPE
        SYNTAX  ZBgpVrfV4TrackNewEntry
        MAX-ACCESS  not-accessible
        STATUS  current
        DESCRIPTION
                "bgp vrf ipv4 unicast event tracking"
        INDEX { zBgpVrfV4LocalAsNew,
                zBgpVrfV4TrackNameNew,
                zBgpVrfV4AddrModeTypeNew, 
                zBgpVrfV4VrfnameNew,
                zBgpVrfV4TrackTypeNew,
                zBgpVrfV4TrackInterfNameNew}
        ::= { zBgpVrfV4TrackNewTable 1 }

ZBgpVrfV4TrackNewEntry ::=
        SEQUENCE {
                zBgpVrfV4LocalAsNew                          Unsigned32,
                zBgpVrfV4TrackNameNew                        DisplayString,
                zBgpVrfV4AddrModeTypeNew                     INTEGER,    
                zBgpVrfV4VrfnameNew                          DisplayString,
                zBgpVrfV4TrackTypeNew                        Integer32,
                zBgpVrfV4TrackInterfNameNew                  DisplayString,
                zBgpVrfV4TrackAdjValueNew                    Unsigned32,
                zBgpVrfV4TrackNewRowStatus                   RowStatus
        }

zBgpVrfV4LocalAsNew OBJECT-TYPE
        SYNTAX   Unsigned32
        MAX-ACCESS  not-accessible
        STATUS  current
        DESCRIPTION
                "Autonomous system number (normal or 4 Octets)"
        ::= { zBgpVrfV4TrackNewEntry  1  }
        
zBgpVrfV4TrackNameNew OBJECT-TYPE
        SYNTAX   DisplayString
        MAX-ACCESS  not-accessible
        STATUS  current
        DESCRIPTION
                "Name of track object"
        ::= { zBgpVrfV4TrackNewEntry  2  }

zBgpVrfV4AddrModeTypeNew OBJECT-TYPE
        SYNTAX  INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  not-accessible
        STATUS  current
        DESCRIPTION
                "address mode type"
        ::= { zBgpVrfV4TrackNewEntry  3  }  

zBgpVrfV4VrfnameNew OBJECT-TYPE
        SYNTAX   DisplayString
        MAX-ACCESS  not-accessible
        STATUS  current
        DESCRIPTION
                "vrf name"
        ::= { zBgpVrfV4TrackNewEntry  4  }
        
zBgpVrfV4TrackTypeNew OBJECT-TYPE
        SYNTAX   Integer32
        MAX-ACCESS  not-accessible
        STATUS  current
        DESCRIPTION
                "track type"
        ::= { zBgpVrfV4TrackNewEntry  5  }
        
zBgpVrfV4TrackInterfNameNew OBJECT-TYPE
        SYNTAX   DisplayString
        MAX-ACCESS  not-accessible
        STATUS  current
        DESCRIPTION
                "intreface name"
        ::= { zBgpVrfV4TrackNewEntry  6  }

zBgpVrfV4TrackAdjValueNew OBJECT-TYPE
        SYNTAX   Unsigned32
        MAX-ACCESS  read-create
        STATUS  current
        DESCRIPTION
                "Value of adjust-priority.If value of zBgpVrfV4TrackTypeNew is 1, range 1-100,
                 else if value of zBgpVrfV4TrackTypeNew is 2, range 0-0."
        ::= { zBgpVrfV4TrackNewEntry  7  }
        
zBgpVrfV4TrackNewRowStatus OBJECT-TYPE
   SYNTAX        RowStatus
   MAX-ACCESS    read-create
   STATUS        current
   DESCRIPTION
       "Row status for this entry."
   ::= { zBgpVrfV4TrackNewEntry 100 }

--------------------------------------------------------------
--------------------------------------------------------------
--zBgpVpnAddrFamilyHovpnTable
--------------------------------------------------------------
zBgpVpnAddrFamilyHovpnTable OBJECT-TYPE
        SYNTAX  SEQUENCE OF ZBgpVpnAddrFamilyHovpnEntry
        MAX-ACCESS  not-accessible
        STATUS  current
        DESCRIPTION
                "HoVPN table for BGP-VPNv4 and BGP-VPNv6 address family."
        ::= { zxr10BgpMIB 33  }

zBgpVpnAddrFamilyHovpnEntry OBJECT-TYPE
        SYNTAX  ZBgpVpnAddrFamilyHovpnEntry
        MAX-ACCESS  not-accessible
        STATUS  current
        DESCRIPTION
                "HoVPN table for BGP-VPNv4 and BGP-VPNv6 address family."
        INDEX { zBgpHovpnLocalAs,
                zBgpHovpnIpv4Addr,
                zBgpHovpnIpv6Addr, 
                zBgpHovpnPeerGroup,
                zBgpHovpnAddrModeType,
                zBgpHovpnAddrVrfName,
                zBgpHovpnVrfName}
        ::= { zBgpVpnAddrFamilyHovpnTable 1 }

ZBgpVpnAddrFamilyHovpnEntry ::=
        SEQUENCE {
                zBgpHovpnLocalAs                          Unsigned32,
                zBgpHovpnIpv4Addr                         IpAddress,
                zBgpHovpnIpv6Addr                         Ipv6Address,    
                zBgpHovpnPeerGroup                        DisplayString,
                zBgpHovpnAddrModeType                     INTEGER,
                zBgpHovpnAddrVrfName                      DisplayString,
                zBgpHovpnVrfName                          DisplayString,
                zBgpHovpnPeerListName                     DisplayString
        }

zBgpHovpnLocalAs OBJECT-TYPE
        SYNTAX   Unsigned32
        MAX-ACCESS  not-accessible
        STATUS  current
        DESCRIPTION
                "Autonomous system number (normal or 4 Octets)."
        ::= { zBgpVpnAddrFamilyHovpnEntry  1  }
        
zBgpHovpnIpv4Addr OBJECT-TYPE
        SYNTAX   IpAddress
        MAX-ACCESS  not-accessible
        STATUS  current
        DESCRIPTION
                "IPv4 peer address."
        ::= { zBgpVpnAddrFamilyHovpnEntry  2  }

zBgpHovpnIpv6Addr OBJECT-TYPE
        SYNTAX  Ipv6Address
        MAX-ACCESS  not-accessible
        STATUS  current
        DESCRIPTION
                "IPv6 peer address."
        ::= { zBgpVpnAddrFamilyHovpnEntry  3  }  

zBgpHovpnPeerGroup OBJECT-TYPE
        SYNTAX   DisplayString (SIZE (0..31))
        MAX-ACCESS  not-accessible
        STATUS  current
        DESCRIPTION
                "Peer group name."
        ::= { zBgpVpnAddrFamilyHovpnEntry  4  }
        
zBgpHovpnAddrModeType OBJECT-TYPE
        SYNTAX   INTEGER  {
                        ipv4_unicast(1),
                        ipv4_multicast(2), 
                        vpnv4(3),
                        ipv4_vrf(4),      
                        ipv6_unicast(5), 
                        ipv6_multicast(6), 
                        vpnv6(7), 
                        ipv6_vrf(8),
                        vpnv4_multicast(9),
                        vpnv4_mcast(10),
                        l2vpn_vpls(11),
                        route_target(12),
                        mdt(13),
                        vpnv6_multicast(14),
                        vpnv6_mcast(15),
                        l2vpn_evpn(16),
                        link_state(17),
                        ipv4_flowspec(18),
                        vpnv4_flowspec(19)
                    }
        MAX-ACCESS  not-accessible
        STATUS  current
        DESCRIPTION
                "Address family type."
        ::= { zBgpVpnAddrFamilyHovpnEntry  5  }
        
zBgpHovpnAddrVrfName OBJECT-TYPE
        SYNTAX   DisplayString (SIZE (0..32))
        MAX-ACCESS  not-accessible
        STATUS  current
        DESCRIPTION
                "The VRF name of VRF address family."
        ::= { zBgpVpnAddrFamilyHovpnEntry  6  }

zBgpHovpnVrfName OBJECT-TYPE
        SYNTAX   DisplayString (SIZE (1..32))
        MAX-ACCESS  not-accessible
        STATUS  current
        DESCRIPTION
                "The specified VRF name."
        ::= { zBgpVpnAddrFamilyHovpnEntry  7  }

zBgpHovpnPeerListName OBJECT-TYPE
        SYNTAX   DisplayString (SIZE (0..31))
        MAX-ACCESS  read-only
        STATUS  current
        DESCRIPTION
                "The peer-list name."
        ::= { zBgpVpnAddrFamilyHovpnEntry  8  }
                                 
END
