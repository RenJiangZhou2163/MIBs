--  ********************************************************
--  $Id: ZXR10-LACP.mib 2006-09-01 01:34:21Z wuxiaoxiang $
--
--  ZXR10-LACP.mib: ZXR10 LACP MIB file
--
--  Sep. 2006, Wu XiaoXiang
--  modify by yuly 155208
--  Copyright(c) 2006 by ZTE Corporation
--  All rights reserved
--
--  ********************************************************

ZXR10-LACP-MIB DEFINITIONS ::= BEGIN

IMPORTS
    MODULE-IDENTITY,
    OBJECT-TYPE,
    Unsigned32,
    enterprises
        FROM SNMPv2-SMI

    TEXTUAL-CONVENTION,    
    MacAddress      
        FROM SNMPv2-TC -- [RFC2579]
                   
     DisplayString
        FROM RFC1213-MIB

     Integer32
        FROM SNMPv2-SMI

   ;   
   
       lacpMIB MODULE-IDENTITY

        LAST-UPDATED "201810300000Z" --2018-10-30 00:00
        
        ORGANIZATION "ZTE Corporation"

        CONTACT-INFO
            "  Yang Zengfang
               Tel : +86-25-15051656440
               E-mail: yang.zengfang@zte.com.cn
            "

        DESCRIPTION
            "This MIB contains managed object definitions for the ZXROSng LACP"

        REVISION "201810300000Z" --2018-10-30 00:00
        DESCRIPTION
            "modify LACPLoadBalanceType:
               add dlbFlowFixed,dlbFlowTimeout,dlbPacket.
            "

        REVISION "201603280000Z" --2016-3-28 00:00
        DESCRIPTION
            "add:  zxr10LacpAggPortDispersion
            "

        REVISION "201512300000Z" --2015-12-30 00:00
        DESCRIPTION
            "modify LACPLoadBalanceType:
               add dstIpDstPort,srcIpSrcPort,srcDstIpSrcDstPort.
            "

        REVISION "201305130000Z" --2013-5-13 00:00
        DESCRIPTION
            "add:  zxr10LacpAggHoldOff 
                   zxr10LacpMclagTable 
                   zxr10LacpEnableMclag                             
            "    
          
        REVISION "201303180000Z" --2013-3-18 00:00
        DESCRIPTION
            "Update version of this MIB module"
        ::= { zxr10 125 } 
     
        
     
   
    zte OBJECT IDENTIFIER ::= { enterprises 3902 }
               
    zxr10 OBJECT IDENTIFIER ::= { zte 3}

        
                  

    lacpMibObjects  OBJECT IDENTIFIER ::= { lacpMIB  1 }


                                        
    LACPMode ::= TEXTUAL-CONVENTION
        STATUS        current
        DESCRIPTION   "LACP Mode"
        SYNTAX        INTEGER
                      {      
                         bondModeOn(0),
                         bondMode8023AD(1)          
                      }
                                    
    LACPLoadBalanceType ::= TEXTUAL-CONVENTION
        STATUS        current
        DESCRIPTION   "LACP Load Balance Type"
        SYNTAX        INTEGER
                      {
                         dstIp(1),
                         dstMac(2),
                         srcDstIp(3),
                         srcDstMac(4),
                         srcIp(5),
                         srcMac(6),
                         srcPort(7),
                         dstPort(8),
                         srcDstPort(9),   
                         perDestination(10),   
                         perPacket(11),   
                         priLabel(12),
                         pubLabel(13),                                       
                         pubPriLabel(14), 
                         vlan(15),
                         macVlan(16),
                         intelligentHash(17),
                         pubSubInterface(18),
                         dstIpDstPort(19),
                         srcIpSrcPort(20),
                         srcDstIpSrcDstPort(21),
                         enhance(24),
                         dlbFlowFixed(25),
                         dlbFlowTimeout(26),
                         dlbPacket(27)
                      }

    LACPPortType ::= TEXTUAL-CONVENTION
        STATUS        current
        DESCRIPTION   "LACP Port Type"
        SYNTAX        INTEGER
                      {
                         passive(1),
                         on(2),
                         active(3)
                      }

    LACPPortTimeoutType ::= TEXTUAL-CONVENTION
        STATUS        current
        DESCRIPTION   "LACP Port Timeout Type"
        SYNTAX        INTEGER
                      {
                         longTime(0),
                         shortTime(1)
                      }      
                      
     LACPAggFastRespondType ::=  TEXTUAL-CONVENTION   
        STATUS        current
        DESCRIPTION   "LACP Fast Respond Type"
        SYNTAX        INTEGER
                      {
                         disable(1),
                         enable(2)
                      }     
                      
     LACPRestoreModeType  ::= TEXTUAL-CONVENTION   
        STATUS        current
        DESCRIPTION   "LACP Restore Mode Type"
        SYNTAX        INTEGER
                      {
                         immediately(1), 
                         revertive(2),
                         nonRevertive(3)                     
                      }   
                      
     LACPPortBackupType  ::= TEXTUAL-CONVENTION   
        STATUS        current
        DESCRIPTION   "LACP Backup Type"
        SYNTAX        INTEGER
                      {
                         disable(1),
                         enable(2)
                      }    
                      
     LACPPortStateType  ::= TEXTUAL-CONVENTION   
        STATUS        current
        DESCRIPTION   "LACP Port State Type"
        SYNTAX        INTEGER
                      {
                         inactive(1),
                         active(2)
                      }                      


     

                                                    
-- groups in lacpMibObjects

      lacpAggregatingPara      OBJECT IDENTIFIER ::= { lacpMibObjects  1 }

      lacpAggregatedPara       OBJECT IDENTIFIER ::= { lacpMibObjects  2 }


---lacpAggregatingPara

      lacpAggregatingTable    OBJECT-TYPE
          SYNTAX            SEQUENCE OF LacpAggregatingEntry
          MAX-ACCESS      not-accessible
          STATUS            current
          DESCRIPTION   "Configure Aggregating Port parameters."
      ::=  { lacpAggregatingPara  1 }

      lacpAggregatingEntry    OBJECT-TYPE
          SYNTAX            LacpAggregatingEntry
          MAX-ACCESS      not-accessible
          STATUS            current
          DESCRIPTION   "Each row index by ifIndex And 
                       contain imformation of Aggregating Port."
            INDEX              {  lacpAggSgIfIndex  }
    ::=  { lacpAggregatingTable 1 }

      LacpAggregatingEntry
      ::=  SEQUENCE
      {
          lacpAggSgIfName                       DisplayString,
          lacpAggMacAddress                     MacAddress,
          lacpAggActorSystemPriority            Unsigned32,
          lacpAggMode                           LACPMode,
          lacpAggLoadBalanceMode                LACPLoadBalanceType,
          lacpAggSubIfIndexName1                DisplayString,
          lacpAggSubIfIndexName2                DisplayString,
          lacpAggSubIfIndexName3                DisplayString,
          lacpAggSubIfIndexName4                DisplayString,
          lacpAggSubIfIndexName5                DisplayString,
          lacpAggSubIfIndexName6                DisplayString,
          lacpAggSubIfIndexName7                DisplayString,
          lacpAggSubIfIndexName8                DisplayString,                                     
          lacpAggMinimumMember                  Unsigned32,
          lacpAggSubIfIndexName9                DisplayString,
          lacpAggSubIfIndexName10               DisplayString,     
          lacpAggSubIfIndexName11               DisplayString,
          lacpAggSubIfIndexName12               DisplayString,
          lacpAggSubIfIndexName13               DisplayString,
          lacpAggSubIfIndexName14               DisplayString,
          lacpAggSubIfIndexName15               DisplayString,
          lacpAggSubIfIndexName16               DisplayString,
          lacpAggSgIfIndex                      Integer32,
          zxr10LacpAggFastRespond               LACPAggFastRespondType,
          zxr10LacpAggActiveLimition            Unsigned32,
          zxr10LacpAggRestoreMode               LACPRestoreModeType,
          zxr10LacpAggRestoreTime               Integer32,
          zxr10LacpAggTimeOut                   Integer32,
          zxr10LacpAggHoldOff                   Integer32,
          zxr10LacpAggEnableMclag               INTEGER,
          zxr10LacpAggPortDispersion            INTEGER
            
      
      }

      lacpAggSgIfName   OBJECT-TYPE
            SYNTAX            DisplayString
            MAX-ACCESS        read-only
            STATUS            current
            DESCRIPTION     "Smartgroup interface name."
      ::=  { lacpAggregatingEntry  1 }

      lacpAggMacAddress   OBJECT-TYPE
            SYNTAX            MacAddress
            MAX-ACCESS        read-only
            STATUS            current
            DESCRIPTION     "Mac address,the LACP module 
                           don't provide the SG interface's MAC !"
      ::=  { lacpAggregatingEntry  2 }

      lacpAggActorSystemPriority   OBJECT-TYPE
            SYNTAX            Unsigned32(1..65535)
            MAX-ACCESS        read-only
            STATUS            current
            DESCRIPTION     "LACP System priority."
      ::=  { lacpAggregatingEntry  3 }

      lacpAggMode   OBJECT-TYPE
            SYNTAX            LACPMode
            MAX-ACCESS        read-only
            STATUS            current
            DESCRIPTION     "Aggregation Type."
      ::=  { lacpAggregatingEntry  4 }

      lacpAggLoadBalanceMode   OBJECT-TYPE
            SYNTAX            LACPLoadBalanceType
            MAX-ACCESS        read-only
            STATUS            current
            DESCRIPTION     "Aggregation Load Balance Type."
      ::=  { lacpAggregatingEntry  5 }
                           
      lacpAggSubIfIndexName1   OBJECT-TYPE
            SYNTAX            DisplayString
            MAX-ACCESS        read-only
            STATUS            obsolete
            DESCRIPTION     "Aggregated Port Name."
      ::=  { lacpAggregatingEntry  7 }

      lacpAggSubIfIndexName2   OBJECT-TYPE
            SYNTAX            DisplayString
            MAX-ACCESS        read-only
            STATUS            obsolete
            DESCRIPTION     "Aggregated Port Name."
      ::=  { lacpAggregatingEntry  8 }

      lacpAggSubIfIndexName3   OBJECT-TYPE
            SYNTAX            DisplayString
            MAX-ACCESS        read-only
            STATUS            obsolete
            DESCRIPTION     "Aggregated Port Name."
      ::=  { lacpAggregatingEntry  9 }

      lacpAggSubIfIndexName4   OBJECT-TYPE
            SYNTAX            DisplayString
            MAX-ACCESS        read-only
            STATUS            obsolete
            DESCRIPTION     "Aggregated Port Name."
      ::=  { lacpAggregatingEntry  10 }

      lacpAggSubIfIndexName5   OBJECT-TYPE
            SYNTAX            DisplayString
            MAX-ACCESS        read-only
            STATUS            obsolete
            DESCRIPTION     "Aggregated Port Name."
      ::=  { lacpAggregatingEntry  11 }

      lacpAggSubIfIndexName6   OBJECT-TYPE
            SYNTAX            DisplayString
            MAX-ACCESS        read-only
            STATUS            obsolete
            DESCRIPTION     "Aggregated Port Name."
      ::=  { lacpAggregatingEntry  12 }

      lacpAggSubIfIndexName7   OBJECT-TYPE
            SYNTAX            DisplayString
            MAX-ACCESS        read-only
            STATUS            obsolete
            DESCRIPTION     "Aggregated Port Name."
      ::=  { lacpAggregatingEntry  13 }

      lacpAggSubIfIndexName8   OBJECT-TYPE
            SYNTAX            DisplayString
            MAX-ACCESS        read-only
            STATUS            obsolete
            DESCRIPTION     "Aggregated Port Name."
      ::=  { lacpAggregatingEntry  14 }   
      
       lacpAggMinimumMember   OBJECT-TYPE
            SYNTAX            Unsigned32(1..32)
            MAX-ACCESS        read-only
            STATUS            current
            DESCRIPTION     "Aggregation Minimum Member Num."
      ::=  { lacpAggregatingEntry  21 }
                           
      lacpAggSubIfIndexName9   OBJECT-TYPE
            SYNTAX            DisplayString
            MAX-ACCESS        read-only
            STATUS            obsolete
            DESCRIPTION     "Aggregated Port Name."
      ::=  { lacpAggregatingEntry  22 }

      lacpAggSubIfIndexName10   OBJECT-TYPE
           SYNTAX            DisplayString
            MAX-ACCESS        read-only
            STATUS            obsolete
            DESCRIPTION     "Aggregated Port Name."
      ::=  { lacpAggregatingEntry  23 }

      lacpAggSubIfIndexName11   OBJECT-TYPE
            SYNTAX            DisplayString
            MAX-ACCESS        read-only
            STATUS            obsolete
            DESCRIPTION     "Aggregated Port Name."
      ::=  { lacpAggregatingEntry  24 }

      lacpAggSubIfIndexName12   OBJECT-TYPE
            SYNTAX            DisplayString
            MAX-ACCESS        read-only
            STATUS            obsolete
            DESCRIPTION     "Aggregated Port Name."
      ::=  { lacpAggregatingEntry  25 }

      lacpAggSubIfIndexName13   OBJECT-TYPE
            SYNTAX            DisplayString
            MAX-ACCESS        read-only
            STATUS            obsolete
            DESCRIPTION     "Aggregated Port Name."
      ::=  { lacpAggregatingEntry  26 }

      lacpAggSubIfIndexName14   OBJECT-TYPE
            SYNTAX            DisplayString
            MAX-ACCESS        read-only
            STATUS            obsolete
            DESCRIPTION     "Aggregated Port Name."
      ::=  { lacpAggregatingEntry  27 }

      lacpAggSubIfIndexName15   OBJECT-TYPE
            SYNTAX            DisplayString
            MAX-ACCESS        read-only
            STATUS            obsolete
            DESCRIPTION     "Aggregated Port Name."
      ::=  { lacpAggregatingEntry  28 }

      lacpAggSubIfIndexName16   OBJECT-TYPE
            SYNTAX            DisplayString
            MAX-ACCESS        read-only
            STATUS            obsolete
            DESCRIPTION     "Aggregated Port Name."
      ::=  { lacpAggregatingEntry  29 }
                
       lacpAggSgIfIndex   OBJECT-TYPE
            SYNTAX            Integer32
            MAX-ACCESS        read-only
            STATUS            current
            DESCRIPTION     "Aggregation Minimum Member Num."  
      ::=  { lacpAggregatingEntry  30 }   
      
      zxr10LacpAggFastRespond   OBJECT-TYPE
            SYNTAX            LACPAggFastRespondType
            MAX-ACCESS        read-only
            STATUS            current
            DESCRIPTION     "Aggregation Fast Respond."
      ::=  { lacpAggregatingEntry  31 }                        
      
      zxr10LacpAggActiveLimition   OBJECT-TYPE
            SYNTAX            Unsigned32(0..32)
            MAX-ACCESS        read-only
            STATUS            current
            DESCRIPTION   "Aggregation Active Limition."
      ::=  { lacpAggregatingEntry  32 }

      zxr10LacpAggRestoreMode   OBJECT-TYPE
            SYNTAX            LACPRestoreModeType
             MAX-ACCESS        read-only
            STATUS            current
            DESCRIPTION     "Aggregation Restore Mode."
      ::=  { lacpAggregatingEntry  33 }       
      
      zxr10LacpAggRestoreTime   OBJECT-TYPE
            SYNTAX            Integer32
             MAX-ACCESS        read-only
            STATUS            current
            DESCRIPTION     "Aggregation Restore Time."
      ::=  { lacpAggregatingEntry  34 }       
           
      zxr10LacpAggTimeOut   OBJECT-TYPE
            SYNTAX            Integer32
             MAX-ACCESS        read-only
            STATUS            current
            DESCRIPTION     "Aggregation TimeOut."
      ::=  { lacpAggregatingEntry  35 }       
      
      zxr10LacpAggHoldOff  OBJECT-TYPE
            SYNTAX            Integer32
             MAX-ACCESS        read-only
            STATUS            current
            DESCRIPTION     "The HoldOff Time of Aggregation."
      ::=  { lacpAggregatingEntry  36 }       
      
      zxr10LacpAggEnableMclag  OBJECT-TYPE
            SYNTAX            INTEGER {enable(1) ,disable(2)}
            MAX-ACCESS        read-only
            STATUS            current
            DESCRIPTION     "The flag whether the Aggregation configed mclag."
      ::=  { lacpAggregatingEntry  37 }

      zxr10LacpAggPortDispersion  OBJECT-TYPE
            SYNTAX            INTEGER {off(1) ,on(2)}
            MAX-ACCESS        read-only
            STATUS            current
            DESCRIPTION     "The port dispersion switch of Aggregation."
      ::=  { lacpAggregatingEntry  38 }



 ---lacpAggregatingPara 
                 
      lacpAggBoundTable  OBJECT-TYPE
          SYNTAX            SEQUENCE OF LacpAggBoundEntry
          MAX-ACCESS        not-accessible
          STATUS            current
          DESCRIPTION      "Aggregating port bound aggregated port."
      ::=  { lacpAggregatingPara  2 }

      lacpAggBoundEntry    OBJECT-TYPE
          SYNTAX            LacpAggBoundEntry
          MAX-ACCESS        not-accessible
          STATUS            current
          DESCRIPTION      "Each row index by smartgroup 
                           port index and aggregated port index."
          INDEX              {  lacpAggBoundSgIfIndex, 
                                 lacpAggBoundPortIfIndex }
    ::=  { lacpAggBoundTable 1 }

      LacpAggBoundEntry
      ::=  SEQUENCE
      {
          lacpAggBoundSgIfIndex       Integer32,
          lacpAggBoundPortIfIndex     Integer32
      }

      lacpAggBoundSgIfIndex   OBJECT-TYPE
            SYNTAX            Integer32
            MAX-ACCESS        read-only
            STATUS            current
            DESCRIPTION     "Smartgroup interface index."
      ::=  { lacpAggBoundEntry  1 }

       lacpAggBoundPortIfIndex   OBJECT-TYPE
            SYNTAX            Integer32
            MAX-ACCESS        read-only
            STATUS            current
            DESCRIPTION     "Aggregated interface index."
      ::=  { lacpAggBoundEntry  2 }   
      
 ---zxr10LacpAggMclagTable

      zxr10LacpAggMclagTable    OBJECT-TYPE
          SYNTAX            SEQUENCE OF Zxr10LacpAggMclagEntry
          MAX-ACCESS      not-accessible
          STATUS            current
          DESCRIPTION   "Configure Aggregating Port mclag parameters."
      ::=  { lacpAggregatingPara  3 }

      zxr10LacpAggMclagEntry    OBJECT-TYPE
          SYNTAX            Zxr10LacpAggMclagEntry
          MAX-ACCESS      not-accessible
          STATUS            current
          DESCRIPTION   "Each row index by ifIndex And contain mclag 
                       imformation of Aggregating Port."
            INDEX              {  zxr10LacpAggMclagSgIndex  }
    ::=  { zxr10LacpAggMclagTable 1 } 
    
      Zxr10LacpAggMclagEntry ::= SEQUENCE {
          zxr10LacpAggMclagSgIndex           Integer32,
          zxr10LacpAggMclagIccpId            Unsigned32,
          zxr10LacpAggMclagRoid              Unsigned32,
          zxr10LacpAggMclagNodeId            Integer32,
          zxr10LacpAggMclagMode              INTEGER,
          zxr10LacpAggMclagRestoreMode       INTEGER,
          zxr10LacpAggMclagRestoreTime       Integer32, 
          zxr10LacpAggMclagPriority          Unsigned32,   
          zxr10LacpAggMclagSysMac            MacAddress,
          zxr10LacpAggMclagSysPri            Unsigned32,
          zxr10LacpAggMclagActorBackup       INTEGER,
          zxr10LacpAggMclagPartnerSysMac     MacAddress,
          zxr10LacpAggMclagPartnerSysPri     Unsigned32,
          zxr10LacpAggMclagPartnerPri        Unsigned32,
          zxr10LacpAggMclagPartnerRoid       Unsigned32,
          zxr10LacpAggMclagPartnerNodeId     Integer32,
          zxr10LacpAggMclagPartnerBackup     INTEGER
                   
      }
      
      zxr10LacpAggMclagSgIndex   OBJECT-TYPE
            SYNTAX            Integer32
            MAX-ACCESS        read-only
            STATUS            current
            DESCRIPTION       "Smartgroup interface index."
      ::=  { zxr10LacpAggMclagEntry  1 }  
      
      zxr10LacpAggMclagIccpId   OBJECT-TYPE
            SYNTAX            Unsigned32
            MAX-ACCESS        read-only
            STATUS            current
            DESCRIPTION       "Mclag Iccp ID binded by each smartgroup."
      ::=  { zxr10LacpAggMclagEntry  2 }  
      
      zxr10LacpAggMclagRoid    OBJECT-TYPE
            SYNTAX            Unsigned32
            MAX-ACCESS        read-only
            STATUS            current
            DESCRIPTION       "Mclag Roid configed by each smartgroup."
      ::=  { zxr10LacpAggMclagEntry  3 }  
      
      zxr10LacpAggMclagNodeId    OBJECT-TYPE
            SYNTAX            Integer32
            MAX-ACCESS        read-only
            STATUS            current
            DESCRIPTION       "Mclag NodeID configed by each smartgroup."
      ::=  { zxr10LacpAggMclagEntry  4 }   
      
      zxr10LacpAggMclagMode    OBJECT-TYPE
            SYNTAX            INTEGER {auto (1) ,master(2),slave(3)}
            MAX-ACCESS        read-only
            STATUS            current
            DESCRIPTION       "Mclag Mode configed by each smartgroup."
      ::=  { zxr10LacpAggMclagEntry  5 } 
      
      zxr10LacpAggMclagRestoreMode    OBJECT-TYPE
            SYNTAX            INTEGER
                              {
                                  immediately(1),
                                  revertive(2),
                                  nonRevertive(3)   
                              }             
            MAX-ACCESS        read-only
            STATUS            current
            DESCRIPTION       "Mclag Restore Mode configed by each smartgroup."
      ::=  { zxr10LacpAggMclagEntry  6 } 

       zxr10LacpAggMclagRestoreTime   OBJECT-TYPE
            SYNTAX            Integer32
            MAX-ACCESS        read-only
            STATUS            current
            DESCRIPTION       "Mclag Restore Time configed by each smartgroup."
      ::=  { zxr10LacpAggMclagEntry  7 } 
      
      zxr10LacpAggMclagPriority    OBJECT-TYPE
            SYNTAX            Unsigned32
            MAX-ACCESS        read-only
            STATUS            current
            DESCRIPTION       "Mclag Priority configed by each smartgroup. "
      ::=  { zxr10LacpAggMclagEntry  8 }   
      
      zxr10LacpAggMclagSysMac    OBJECT-TYPE
            SYNTAX            MacAddress
            MAX-ACCESS        read-only
            STATUS            current
            DESCRIPTION      "Mclag System Mac configed by each smartgroup."
      ::=  { zxr10LacpAggMclagEntry  9 }  
      
      zxr10LacpAggMclagSysPri    OBJECT-TYPE
            SYNTAX            Unsigned32
            MAX-ACCESS        read-only
            STATUS            current
            DESCRIPTION       "Mclag System Priority configed by each smartgroup."
      ::=  { zxr10LacpAggMclagEntry  10 }  
      
      zxr10LacpAggMclagActorBackup    OBJECT-TYPE
            SYNTAX            INTEGER {disable (1) ,enable(2)}
            MAX-ACCESS        read-only
            STATUS            current
            DESCRIPTION       "Mclag Actor Backup configed by each smartgroup."
      ::=  { zxr10LacpAggMclagEntry  11 }   
      
      zxr10LacpAggMclagPartnerSysMac    OBJECT-TYPE
            SYNTAX            MacAddress
            MAX-ACCESS        read-only
            STATUS            current
            DESCRIPTION      "The Partner System Mac of 
                            the smartgroup which configed mclag."
      ::=  { zxr10LacpAggMclagEntry  12 }  
      
      zxr10LacpAggMclagPartnerSysPri    OBJECT-TYPE
            SYNTAX            Unsigned32
            MAX-ACCESS        read-only
            STATUS            current
            DESCRIPTION       "The Mclag Partner System Priority of the 
                              smartgroup which configed mclag."
      ::=  { zxr10LacpAggMclagEntry  13 } 
      
      zxr10LacpAggMclagPartnerPri    OBJECT-TYPE
            SYNTAX            Unsigned32
            MAX-ACCESS        read-only
            STATUS            current
            DESCRIPTION       "The Mclag Partner Priority  of 
                              the smartgroup which configed mclag."
      ::=  { zxr10LacpAggMclagEntry  14 }
      
      zxr10LacpAggMclagPartnerRoid    OBJECT-TYPE
            SYNTAX            Unsigned32
            MAX-ACCESS        read-only
            STATUS            current
            DESCRIPTION       "The Mclag Partner Roid of 
                             the smartgroup which configed mclag."
      ::=  { zxr10LacpAggMclagEntry  15 }  
      
      zxr10LacpAggMclagPartnerNodeId    OBJECT-TYPE
            SYNTAX            Integer32
            MAX-ACCESS        read-only
            STATUS            current
            DESCRIPTION       "The Mclag Partner NodeID of 
                             the smartgroup which configed mclag."
      ::=  { zxr10LacpAggMclagEntry  16 }  
      
      zxr10LacpAggMclagPartnerBackup    OBJECT-TYPE
            SYNTAX            INTEGER {disable (1) ,enable(2)}
            MAX-ACCESS        read-only
            STATUS            current
            DESCRIPTION       "The Mclag Partner Backup of 
                             the smartgroup which configed mclag."
      ::=  { zxr10LacpAggMclagEntry  17 }        
               
      
            
      





---lacpAggregatedPara

      lacpAggregatedTable    OBJECT-TYPE
          SYNTAX            SEQUENCE OF LacpAggregatedEntry
          MAX-ACCESS        not-accessible
          STATUS            current
          DESCRIPTION       "Configure Aggregated Port parameters."
      ::=  { lacpAggregatedPara  1 }

      lacpAggregatedEntry    OBJECT-TYPE
          SYNTAX            LacpAggregatedEntry
          MAX-ACCESS        not-accessible
          STATUS            current
          DESCRIPTION       "Each row index by aggregating and aggregated ifIndex 
                            And contain imformation of Aggregated Port."
            INDEX              {  lacpAggPortIfIndex  }
      ::=  { lacpAggregatedTable 1 }

      LacpAggregatedEntry
      ::=  SEQUENCE
      {
          lacpAggSgId                        Unsigned32,
          lacpAggPortIfName                  DisplayString,
          lacpAggPortMode                    LACPPortType,
          lacpAggPortTimeOut                 LACPPortTimeoutType,
          lacpAggLacpPriority                Unsigned32,
          lacpAggPortActorOperKey            Unsigned32,
          lacpAggPortActorOperState          Unsigned32,
          lacpAggPortPartnerOperKey          Unsigned32,
          lacpAggPortPartnerOperState        Unsigned32,
          lacpAggPortIfIndex                 Integer32,
          zxr10LacpAggPortPartnerPriority    Unsigned32,
          zxr10LacpAggPortBackup             LACPPortBackupType,
          zxr10LacpAggPortState              LACPPortStateType,
          zxr10LacpAggPortTrackName          DisplayString,
          zxr10LacpAggPartnerSysPri          Unsigned32,
          zxr10LacpAggPartnerMacAddress      MacAddress
          
          
          

      }
                                  
      lacpAggSgId   OBJECT-TYPE
            SYNTAX            Unsigned32(1..64)
            MAX-ACCESS        read-only
            STATUS            current
            DESCRIPTION     "Add to smartgroup interface."
      ::=  { lacpAggregatedEntry  1 }

      lacpAggPortIfName   OBJECT-TYPE
            SYNTAX            DisplayString
            MAX-ACCESS        read-only
            STATUS            current
            DESCRIPTION     "Aggregated interface name."
      ::=  { lacpAggregatedEntry  2 }

      lacpAggPortMode   OBJECT-TYPE
            SYNTAX            LACPPortType
            MAX-ACCESS        read-only
            STATUS            current
            DESCRIPTION     "LACP Port Type."
      ::=  { lacpAggregatedEntry  3 }

      lacpAggPortTimeOut   OBJECT-TYPE
            SYNTAX            LACPPortTimeoutType
            MAX-ACCESS        read-only
            STATUS            current
            DESCRIPTION     "LACP Port Timeout."
      ::=  { lacpAggregatedEntry  4 }

      lacpAggLacpPriority   OBJECT-TYPE
            SYNTAX            Unsigned32(1..65535)
            MAX-ACCESS        read-only
            STATUS            current
            DESCRIPTION     "Lacp Priority."
      ::=  { lacpAggregatedEntry  5 }

      lacpAggPortActorOperKey   OBJECT-TYPE
           SYNTAX            Unsigned32
            MAX-ACCESS        read-only
            STATUS            current
            DESCRIPTION     "Lacp Port Operation Key."
      ::=  { lacpAggregatedEntry  6 }

      lacpAggPortActorOperState   OBJECT-TYPE
            SYNTAX            Unsigned32
            MAX-ACCESS        read-only
            STATUS            current
            DESCRIPTION     "Lacp Port Operation Status."
      ::=  { lacpAggregatedEntry  7 }

      lacpAggPortPartnerOperKey   OBJECT-TYPE
            SYNTAX            Unsigned32
            MAX-ACCESS        read-only
            STATUS            current
            DESCRIPTION     "Lacp Partner Operation Key."
      ::=  { lacpAggregatedEntry  8 }

      lacpAggPortPartnerOperState   OBJECT-TYPE
            SYNTAX            Unsigned32 
            MAX-ACCESS        read-only
            STATUS            current
            DESCRIPTION     "Lacp Partner Operation Status."
      ::=  { lacpAggregatedEntry  9 }
                                    
       lacpAggPortIfIndex   OBJECT-TYPE
            SYNTAX            Integer32
            MAX-ACCESS        read-only
            STATUS            current
            DESCRIPTION    "Aggregated interface index."
      ::=  { lacpAggregatedEntry  10 }
                                   
        zxr10LacpAggPortPartnerPriority   OBJECT-TYPE
            SYNTAX            Unsigned32(1..65535)
            MAX-ACCESS        read-only
            STATUS            current
            DESCRIPTION     "Lacp Partner Port Priority."
      ::=  { lacpAggregatedEntry  11 }  
                                          
       zxr10LacpAggPortBackup   OBJECT-TYPE
            SYNTAX            LACPPortBackupType
            MAX-ACCESS        read-only
            STATUS            current
            DESCRIPTION     "Lacp Port Backup."
      ::=  { lacpAggregatedEntry  12 }  
                                          
       zxr10LacpAggPortState   OBJECT-TYPE
            SYNTAX            LACPPortStateType
            MAX-ACCESS        read-only
            STATUS            current
            DESCRIPTION     "Lacp Port Acitive Status."
      ::=  { lacpAggregatedEntry  13 }  
                                          
       zxr10LacpAggPortTrackName   OBJECT-TYPE
            SYNTAX            DisplayString
            MAX-ACCESS        read-only
            STATUS            current
            DESCRIPTION     "Lacp Port Track Name."
      ::=  { lacpAggregatedEntry  14 }    
      
                 
      zxr10LacpAggPartnerSysPri   OBJECT-TYPE
            SYNTAX            Unsigned32(1..65535)
             MAX-ACCESS        read-only
            STATUS            current
            DESCRIPTION     "Lacp Port Partner System Priority."
      ::=  { lacpAggregatedEntry  15 }       
           
      zxr10LacpAggPartnerMacAddress   OBJECT-TYPE
            SYNTAX            MacAddress
             MAX-ACCESS        read-only
            STATUS            current
            DESCRIPTION     "Lacp Port Partner Mac Address."
      ::=  { lacpAggregatedEntry  16 }       
      


      
                                   


END
