--  ************************************************
--  $Id: zxr10-PVLAN-MIB.mib 8 2013-11-05 12:17:08Z xiaguibin $
--
--  zxr10-PVLAN-MIB.mib: ZXR10 PVLAN MIB file
--
--  Mar. 2013, Xia Guibin
--   
--  Copyright(c) 2014 by ZTE Corporaton
--  All rights reservered
--
--  ************************************************
ZXR10-PVLAN-MIB DEFINITIONS ::= BEGIN

IMPORTS
    MODULE-IDENTITY,
    OBJECT-TYPE,
    Integer32,
    enterprises
       FROM SNMPv2-SMI
    DisplayString 
       FROM SNMPv2-TC;
    
    zxr10PVlanMIB MODULE-IDENTITY
        LAST-UPDATED "201311061314Z"  -- 2013-11-06 13:14 
        ORGANIZATION "ZTE Corporation"
        CONTACT-INFO
           "
            Name:  Xia guibin
            Tel:   +86-25-52870000
            Email: xia.guibin@zte.com.cn
           "
        DESCRIPTION
            "The MIB module to describe PVLAN table information." 
        REVISION "201311061314Z"      
        DESCRIPTION   "Initial version of this MIB module"
        ::= { zxr10switch 53 } 

    -- Top level components of this MIB module.
    zte         OBJECT IDENTIFIER ::= { enterprises 3902 }    
    zxr10       OBJECT IDENTIFIER ::= { zte 3 }
    zxr10switch OBJECT IDENTIFIER ::= { zxr10 102 }   
 
    --=======================================================================
    --groups in the ZXR10-PVLAN-MIB
    --======================================================================= 
    zxr10PVlanGlobalObjects   OBJECT IDENTIFIER ::= { zxr10PVlanMIB 1 }
    zxr10PVlanObjects         OBJECT IDENTIFIER ::= { zxr10PVlanMIB 2 }  
    zxr10PVlanNotifications   OBJECT IDENTIFIER ::= { zxr10PVlanMIB 3 }
    zxr10PVlanConformance     OBJECT IDENTIFIER ::= { zxr10PVlanMIB 4 } 
     
    --=======================================================================
    --1. zxr10PVlanGlobalObjects group
    --======================================================================= 
 
    --=======================================================================
    --2. zxr10PVlanObjects group
    --======================================================================= 
    --pvlan isolate port table 
    zxr10PVlanIsolatePortTable  OBJECT-TYPE
        SYNTAX  SEQUENCE OF Zxr10PVlanIsolatePortEntry
        MAX-ACCESS  not-accessible
        STATUS  current
        DESCRIPTION
            "The PVLAN isolate port information table."
        ::= { zxr10PVlanObjects 1 }
        
    zxr10PVlanIsolatePortEntry   OBJECT-TYPE
        SYNTAX  Zxr10PVlanIsolatePortEntry
        MAX-ACCESS  not-accessible
        STATUS  current
        DESCRIPTION
            "The PVLAN isolate port table entry."
        INDEX  { zxr10PVlanIsolateSessionId,
                 zxr10PVlanIsolatePort
               }
        ::= { zxr10PVlanIsolatePortTable 1 }   
        
    Zxr10PVlanIsolatePortEntry ::=
        SEQUENCE {
            zxr10PVlanIsolateSessionId
                Integer32, 
            zxr10PVlanIsolatePort
                DisplayString
            }  
            
    zxr10PVlanIsolateSessionId OBJECT-TYPE
        SYNTAX      Integer32
        MAX-ACCESS  not-accessible
        STATUS      current
        DESCRIPTION
            "The PVLAN session ID."
        ::= { zxr10PVlanIsolatePortEntry 1}
    
    zxr10PVlanIsolatePort OBJECT-TYPE
        SYNTAX   DisplayString(SIZE(1..31))
        MAX-ACCESS  read-only
        STATUS  current
        DESCRIPTION
            "The isolate port name, the max number is 256."
        ::= { zxr10PVlanIsolatePortEntry 2 } 
       
    --pvlan promis port table 
    zxr10PVlanPromisPortTable  OBJECT-TYPE
        SYNTAX  SEQUENCE OF Zxr10PVlanPromisPortEntry
        MAX-ACCESS  not-accessible
        STATUS  current
        DESCRIPTION
            "The PVLAN promis port information table."
        ::= { zxr10PVlanObjects 2 }
        
    zxr10PVlanPromisPortEntry   OBJECT-TYPE
        SYNTAX  Zxr10PVlanPromisPortEntry
        MAX-ACCESS  not-accessible
        STATUS  current
        DESCRIPTION
            "The PVLAN promis port table entry."
        INDEX  { zxr10PVlanPromisSessionId,
                 zxr10PVlanPromisPort
               }
        ::= { zxr10PVlanPromisPortTable 1 }   
        
    Zxr10PVlanPromisPortEntry ::=
        SEQUENCE {
            zxr10PVlanPromisSessionId
                Integer32, 
            zxr10PVlanPromisPort
                DisplayString
            }  
            
    zxr10PVlanPromisSessionId OBJECT-TYPE
        SYNTAX      Integer32
        MAX-ACCESS  not-accessible
        STATUS      current
        DESCRIPTION
            "The PVLAN session ID."
        ::= { zxr10PVlanPromisPortEntry 1}
    
    zxr10PVlanPromisPort OBJECT-TYPE
        SYNTAX   DisplayString(SIZE(1..31))
        MAX-ACCESS  read-only
        STATUS  current
        DESCRIPTION
            "The promis port name, the max number is 4."
        ::= { zxr10PVlanPromisPortEntry 2 } 
        
    --pvlan community port table 
    zxr10PVlanCommunityPortTable  OBJECT-TYPE
        SYNTAX  SEQUENCE OF Zxr10PVlanCommunityPortEntry
        MAX-ACCESS  not-accessible
        STATUS  current
        DESCRIPTION
            "The PVLAN community port information table."
        ::= { zxr10PVlanObjects 3 }
        
    zxr10PVlanCommunityPortEntry   OBJECT-TYPE
        SYNTAX  Zxr10PVlanCommunityPortEntry
        MAX-ACCESS  not-accessible
        STATUS  current
        DESCRIPTION
            "The PVLAN community port table entry."
        INDEX  { zxr10PVlanCommunitySessionId,
                 zxr10PVlanCommunityPort
               }
        ::= { zxr10PVlanCommunityPortTable 1 }   
        
    Zxr10PVlanCommunityPortEntry ::=
        SEQUENCE {
            zxr10PVlanCommunitySessionId
                Integer32, 
            zxr10PVlanCommunityPort
                DisplayString
            }  
            
    zxr10PVlanCommunitySessionId OBJECT-TYPE
        SYNTAX      Integer32
        MAX-ACCESS  not-accessible
        STATUS      current
        DESCRIPTION
            "The PVLAN session ID."
        ::= { zxr10PVlanCommunityPortEntry 1}
    
    zxr10PVlanCommunityPort OBJECT-TYPE
        SYNTAX      DisplayString(SIZE(1..31))
        MAX-ACCESS  read-only
        STATUS      current
        DESCRIPTION
            "The community port name, the max number is 16."
        ::= { zxr10PVlanCommunityPortEntry 2 } 
        
    --pvlan vlan bitmap table 
    zxr10PVlanVlanBitmapTable  OBJECT-TYPE
        SYNTAX  SEQUENCE OF Zxr10PVlanVlanBitmapEntry
        MAX-ACCESS  not-accessible
        STATUS  current
        DESCRIPTION
            "The PVLAN vlan bitmap information table."
        ::= { zxr10PVlanObjects 4 }
        
    zxr10PVlanVlanBitmapEntry   OBJECT-TYPE
        SYNTAX  Zxr10PVlanVlanBitmapEntry
        MAX-ACCESS  not-accessible
        STATUS  current
        DESCRIPTION
            "The PVLAN vlan bitmap table entry."
        INDEX  { zxr10PVlanVlanSessionId,
                 zxr10PVlanVlanBitmap
               }
        ::= { zxr10PVlanVlanBitmapTable 1 }   
        
    Zxr10PVlanVlanBitmapEntry ::=
        SEQUENCE {
            zxr10PVlanVlanSessionId
                Integer32, 
            zxr10PVlanVlanBitmap
                OCTET STRING
            }  
            
    zxr10PVlanVlanSessionId OBJECT-TYPE
        SYNTAX      Integer32
        MAX-ACCESS  not-accessible
        STATUS      current
        DESCRIPTION
            "The PVLAN session ID."
        ::= { zxr10PVlanVlanBitmapEntry 1}
    
    zxr10PVlanVlanBitmap OBJECT-TYPE
        SYNTAX   OCTET STRING (SIZE(0..512))
        MAX-ACCESS  read-only
        STATUS  current
        DESCRIPTION
            "The vlan bitmap infomation(1-4094)."
        ::= { zxr10PVlanVlanBitmapEntry 2 }
    --=======================================================================
    --3. zxr10PVlanNotifications group
    --======================================================================= 
 
    --=======================================================================
    --4. zxr10PVlanConformance group
    --======================================================================= 
    
           

     
        
END
