ZXR10-P2MP-TE-MIB DEFINITIONS ::= BEGIN

IMPORTS
    OBJECT-TYPE, MODULE-IDENTITY, Unsigned32,Integer32,IpAddress
            FROM SNMPv2-SMI
    MacAddress, DisplayString, RowStatus, TruthValue, TimeTicks
            FROM SNMPv2-TC
    zxr10RosngMIB
            FROM ZXR10-SMI;

    zxr10P2mpTeMIB MODULE-IDENTITY
                LAST-UPDATED
                "201601291000Z"
                ORGANIZATION
                "ZTE Corporation"
                CONTACT-INFO
                "ZTE Corporation
                 Nanjing Institute of ZTE Corporation
                 No.68 Zijinghua Rd. Yuhuatai District, Nanjing, China
                 Tel: +86-25-52870000 "
                DESCRIPTION
                "P2MP TE"
                REVISION
                  "201601291000Z"
                DESCRIPTION
                  "Modify the range of zxr10P2mpTeLocTnnlCfgMinTxInter, The old min value is 10,The new min value is 3.
                   Modify the range of zxr10P2mpTeLocTnnlCfgMinRxInter, The old min value is 10,The new min value is 3."
                REVISION
                  "201512031000Z"
                DESCRIPTION
                  "Add the leaf bfd of zxr10P2mpTeLocTnnlCfgTable.
                   Add the leaf MinTxInter of zxr10P2mpTeLocTnnlCfgTable.
                   Add the leaf MinRxInter of zxr10P2mpTeLocTnnlCfgTable.
                   Add the leaf Mult of zxr10P2mpTeLocTnnlCfgTable.
                   Add the leaf e2e of zxr10P2mpTeLocTnnlCfgTable."
                REVISION
                  "201508061000Z"
                DESCRIPTION
                  "Modify the range of zxr10P2mpTeLeafTnnlCfgRootTnnlID,The old value is 65535,The new value is 200.
                   Modify the range of zxr10P2mpTeLocTnnlName,The old value is 0,The new value is 1.
                   Modify the range of zxr10P2mpTeLeafTnnlName,The old value is 0,The new value is 1.
                   Modify the description of zxr10P2mpTeHopRowStatus and zxr10P2mpTeHopStorageType.
                   Modify the MAX-ACCESS of zxr10P2mpTeFrrBackupTunnelIndex,zxr10P2mpTeFrrProtectedIfName,zxr10P2mpTeFrrInnerLabel,and zxr10P2mpTeFrrStatus."
                REVISION
                  "201507101000Z"
                DESCRIPTION
                  "Add a new field zxr10P2mpTeLocTnnlCfgEscapepath in Zxr10P2mpTeLocTnnlCfgEntry."
                REVISION
                  "201502101000Z"
                DESCRIPTION
                  "Modify the range and MAX-ACCESS field of zxr10P2mpTeLocTnnlCfgBandwith in zxr10P2mpTeLocTnnlCfgEntry.
                   Modify the MAX-ACCESS field of zxr10P2mpTeLocTnnlCfgSetupprio in zxr10P2mpTeLocTnnlCfgEntry.
                   Modify the MAX-ACCESS field of zxr10P2mpTeLocTnnlCfgHoldprio in zxr10P2mpTeLocTnnlCfgEntry.
                   Modify the range and MAX-ACCESS field of zxr10P2mpTeLocTnnlCfgResvStyle in zxr10P2mpTeLocTnnlCfgEntry.
                   Modify the MAX-ACCESS field of zxr10P2mpTeLspResvStyle in zxr10P2mpTeLspEntry.
                   Add new table zxr10P2mpTeDsteCfgTable."
                REVISION
                  "201402171000Z"
                DESCRIPTION
                "Modify the range of destlist name,The old value is 20,The new value is 16."
                REVISION
                  "201401211000Z"
                DESCRIPTION
                "Add zxr10P2mpTeFrrDBTable for frr of mtunnel."
                REVISION
                  "201308291700Z"
                DESCRIPTION
                  "Add some new fields for crankback of mtunnel."
                REVISION
                "201306070000Z"
                DESCRIPTION
                "ADD P2MP TE MIB"
                ::= { zxr10RosngMIB 205}

                -- 1.3.6.1.4.1.3902.3.6000.205.1
                zxr10P2mpTeGlobalObjects OBJECT IDENTIFIER ::= { zxr10P2mpTeMIB 1 }
                -- 1.3.6.1.4.1.3902.3.6000.205.2
                zxr10P2mpTeObjects OBJECT IDENTIFIER ::= { zxr10P2mpTeMIB 2}
                -- 1.3.6.1.4.1.3902.3.6000.205.3
                zxr10P2mpTeTraps OBJECT IDENTIFIER ::= { zxr10P2mpTeMIB 3 }
                -- 1.3.6.1.4.1.3902.3.6000.205.4
                zxr10P2mpTeConformance OBJECT IDENTIFIER ::= { zxr10P2mpTeMIB 4 }



-- =============================
--2. zxr10P2mpTeObjects
-- =============================
-- =======================================
--2.1. zxr10P2mpTeLocTnnlCfgTable
-- =======================================
-- 1.3.6.1.4.1.3902.3.6000.205.2.1
zxr10P2mpTeLocTnnlCfgTable OBJECT-TYPE
    SYNTAX      SEQUENCE OF Zxr10P2mpTeLocTnnlCfgEntry
    MAX-ACCESS  not-accessible
    STATUS      current
    DESCRIPTION
            ""
    ::= { zxr10P2mpTeObjects 1 }

-- 1.3.6.1.4.1.3902.3.6000.205.2.1.1
zxr10P2mpTeLocTnnlCfgEntry OBJECT-TYPE
    SYNTAX      Zxr10P2mpTeLocTnnlCfgEntry
    MAX-ACCESS  not-accessible
    STATUS      current
    DESCRIPTION
            ""
    INDEX   { zxr10P2mpTeLocTnnlCfgName }
    ::= { zxr10P2mpTeLocTnnlCfgTable 1 }

Zxr10P2mpTeLocTnnlCfgEntry ::=
    SEQUENCE {
        zxr10P2mpTeLocTnnlCfgName                     DisplayString,
        zxr10P2mpTeLocTnnlCfgIndex                    Integer32,
        zxr10P2mpTeLocTnnlCfgDestLType                INTEGER,
        zxr10P2mpTeLocTnnlCfgDestLName                DisplayString,
        zxr10P2mpTeLocTnnlCfgDestLID                  Integer32,
        zxr10P2mpTeLocTnnlCfgIntegrity                TruthValue,
        zxr10P2mpTeLocTnnlCfgRRO                      TruthValue,
        zxr10P2mpTeLocTnnlCfgBandwith                 Unsigned32,
        zxr10P2mpTeLocTnnlCfgSetupprio                Integer32,
        zxr10P2mpTeLocTnnlCfgHoldprio                 Integer32,
        zxr10P2mpTeLocTnnlCfgResvStyle                INTEGER,
        zxr10P2mpTeLocTnnlCfgReopEnable               TruthValue,
        zxr10P2mpTeLocTnnlCfgCrkBackMode              INTEGER,
        zxr10P2mpTeLocTnnlCfgFrrEnable                TruthValue,
        zxr10P2mpTeLocTnnlCfgEscapepath               TruthValue,
        zxr10P2mpTeLocTnnlCfgBfd                      TruthValue,
        zxr10P2mpTeLocTnnlCfgMinTxInter               Unsigned32,
        zxr10P2mpTeLocTnnlCfgMinRxInter               Unsigned32,
        zxr10P2mpTeLocTnnlCfgMult                     Integer32,
        zxr10P2mpTeLocTnnlCfgE2E                      TruthValue,
        zxr10P2mpTeLocTnnlCfgRowStatus                RowStatus
    }

-- 1.3.6.1.4.1.3902.3.6000.205.2.1.1.1
zxr10P2mpTeLocTnnlCfgName OBJECT-TYPE
    SYNTAX      DisplayString(SIZE(1..32))
    MAX-ACCESS  not-accessible
    STATUS      current
    DESCRIPTION
            "P2mp Local tunnel Name ."
    ::= { zxr10P2mpTeLocTnnlCfgEntry 1 }

-- 1.3.6.1.4.1.3902.3.6000.205.2.1.1.2
zxr10P2mpTeLocTnnlCfgIndex OBJECT-TYPE
    SYNTAX      Integer32(1..65535)
    MAX-ACCESS  read-only
    STATUS      current
    DESCRIPTION
            "P2mp Local tunnel Index."
    ::= { zxr10P2mpTeLocTnnlCfgEntry 2 }

-- 1.3.6.1.4.1.3902.3.6000.205.2.1.1.3
zxr10P2mpTeLocTnnlCfgDestLType OBJECT-TYPE
    SYNTAX      INTEGER{name(1),identifier(2)}
    MAX-ACCESS  read-create
    STATUS      current
    DESCRIPTION
            "The destlist type of P2mp Local tunnel  ."
    ::= { zxr10P2mpTeLocTnnlCfgEntry 3 }

-- 1.3.6.1.4.1.3902.3.6000.205.2.1.1.4
zxr10P2mpTeLocTnnlCfgDestLName OBJECT-TYPE
    SYNTAX      DisplayString(SIZE(1..16))
    MAX-ACCESS  read-create
    STATUS      current
    DESCRIPTION
            "The destlist type of P2mp Local tunnel is Name."
    ::= { zxr10P2mpTeLocTnnlCfgEntry 4 }

-- 1.3.6.1.4.1.3902.3.6000.205.2.1.1.5
zxr10P2mpTeLocTnnlCfgDestLID OBJECT-TYPE
    SYNTAX      Integer32(1..65535)
    MAX-ACCESS  read-create
    STATUS      current
    DESCRIPTION
            "The destlist type of P2mp Local tunnel is Id."
    ::= { zxr10P2mpTeLocTnnlCfgEntry 5 }

-- 1.3.6.1.4.1.3902.3.6000.205.2.1.1.6
zxr10P2mpTeLocTnnlCfgIntegrity OBJECT-TYPE
    SYNTAX      TruthValue
    MAX-ACCESS  read-create
    STATUS      current
    DESCRIPTION
            "P2mp Local tunnel is configed Integrity ."
    ::= { zxr10P2mpTeLocTnnlCfgEntry 6 }

-- 1.3.6.1.4.1.3902.3.6000.205.2.1.1.7
zxr10P2mpTeLocTnnlCfgRRO   OBJECT-TYPE
    SYNTAX      TruthValue
    MAX-ACCESS  read-create
    STATUS      current
    DESCRIPTION
            "P2mp Local tunnel is configed Integrity RRO."
    ::= { zxr10P2mpTeLocTnnlCfgEntry 7 }

-- 1.3.6.1.4.1.3902.3.6000.205.2.1.1.8
zxr10P2mpTeLocTnnlCfgBandwith   OBJECT-TYPE
    SYNTAX      Unsigned32(1..4294967295)
    MAX-ACCESS  read-create
    STATUS      current
    DESCRIPTION
            "The total bandwith of P2mp Local tunnel ."
    ::= { zxr10P2mpTeLocTnnlCfgEntry 8 }

-- 1.3.6.1.4.1.3902.3.6000.205.2.1.1.9
zxr10P2mpTeLocTnnlCfgSetupprio   OBJECT-TYPE
    SYNTAX      Integer32(0..7)
    MAX-ACCESS  read-create
    STATUS      current
    DESCRIPTION
            "The Setupprio of P2mp Local tunnel ."
    ::= { zxr10P2mpTeLocTnnlCfgEntry 9 }

-- 1.3.6.1.4.1.3902.3.6000.205.2.1.1.10
zxr10P2mpTeLocTnnlCfgHoldprio   OBJECT-TYPE
    SYNTAX      Integer32(0..7)
    MAX-ACCESS  read-create
    STATUS      current
    DESCRIPTION
            "The Holdprio of P2mp Local tunnel ."
    ::= { zxr10P2mpTeLocTnnlCfgEntry 10 }

-- 1.3.6.1.4.1.3902.3.6000.205.2.1.1.11
zxr10P2mpTeLocTnnlCfgResvStyle   OBJECT-TYPE
    SYNTAX      INTEGER{se(1),ff(2)}
    MAX-ACCESS  read-create
    STATUS      current
    DESCRIPTION
            "The ResvStyle of P2mp Local tunnel ."
    ::= { zxr10P2mpTeLocTnnlCfgEntry 11 }

-- 1.3.6.1.4.1.3902.3.6000.205.2.1.1.12
zxr10P2mpTeLocTnnlCfgReopEnable   OBJECT-TYPE
    SYNTAX      TruthValue
    MAX-ACCESS  read-create
    STATUS      current
    DESCRIPTION
            "The ReopEnable of P2mp Local tunnel ."
    ::= { zxr10P2mpTeLocTnnlCfgEntry 12 }

-- 1.3.6.1.4.1.3902.3.6000.205.2.1.1.13
zxr10P2mpTeLocTnnlCfgCrkBackMode   OBJECT-TYPE
    SYNTAX      INTEGER{endtoend(1),disabled(2)}
    MAX-ACCESS  read-create
    STATUS      current
    DESCRIPTION
            "The CrankbackMode of P2mp Local tunnel ."
    ::= { zxr10P2mpTeLocTnnlCfgEntry 13 }

-- 1.3.6.1.4.1.3902.3.6000.205.2.1.1.14
zxr10P2mpTeLocTnnlCfgFrrEnable   OBJECT-TYPE
    SYNTAX      TruthValue
    MAX-ACCESS  read-create
    STATUS      current
    DESCRIPTION
            "The Frr of P2mp Local tunnel ."
    ::= { zxr10P2mpTeLocTnnlCfgEntry 14 }

-- 1.3.6.1.4.1.3902.3.6000.205.2.1.1.15
zxr10P2mpTeLocTnnlCfgEscapepath   OBJECT-TYPE
    SYNTAX      TruthValue
    MAX-ACCESS  read-create
    STATUS      current
    DESCRIPTION
            "The Escapepath of P2mp Local tunnel ."
    ::= { zxr10P2mpTeLocTnnlCfgEntry 15 }

-- 1.3.6.1.4.1.3902.3.6000.205.2.1.1.16
zxr10P2mpTeLocTnnlCfgBfd   OBJECT-TYPE
    SYNTAX      TruthValue
    MAX-ACCESS  read-create
    STATUS      current
    DESCRIPTION
            "The bfd enable of P2mp Local tunnel ."
    ::= { zxr10P2mpTeLocTnnlCfgEntry 16 }

-- 1.3.6.1.4.1.3902.3.6000.205.2.1.1.17
zxr10P2mpTeLocTnnlCfgMinTxInter   OBJECT-TYPE
    SYNTAX      Unsigned32(3..990)
    MAX-ACCESS  read-create
    STATUS      current
    DESCRIPTION
            "The bfd MinTxInterval of P2mp Local tunnel ."
    ::= { zxr10P2mpTeLocTnnlCfgEntry 17 }

-- 1.3.6.1.4.1.3902.3.6000.205.2.1.1.18
zxr10P2mpTeLocTnnlCfgMinRxInter   OBJECT-TYPE
    SYNTAX      Unsigned32(3..990)
    MAX-ACCESS  read-create
    STATUS      current
    DESCRIPTION
            "The bfd MinRxInterval of P2mp Local tunnel ."
    ::= { zxr10P2mpTeLocTnnlCfgEntry 18 }

-- 1.3.6.1.4.1.3902.3.6000.205.2.1.1.19
zxr10P2mpTeLocTnnlCfgMult   OBJECT-TYPE
    SYNTAX      Integer32(3..50)
    MAX-ACCESS  read-create
    STATUS      current
    DESCRIPTION
            "The bfd multiplier of P2mp Local tunnel ."
    ::= { zxr10P2mpTeLocTnnlCfgEntry 19 }

-- 1.3.6.1.4.1.3902.3.6000.205.2.1.1.20
zxr10P2mpTeLocTnnlCfgE2E   OBJECT-TYPE
    SYNTAX      TruthValue
    MAX-ACCESS  read-create
    STATUS      current
    DESCRIPTION
            "The e2e enable of P2mp Local tunnel ."
    ::= { zxr10P2mpTeLocTnnlCfgEntry 20 }


-- 1.3.6.1.4.1.3902.3.6000.205.2.1.1.100
zxr10P2mpTeLocTnnlCfgRowStatus OBJECT-TYPE
    SYNTAX      RowStatus
    MAX-ACCESS  read-create
    STATUS      current
    DESCRIPTION
            "Row status"
    ::= { zxr10P2mpTeLocTnnlCfgEntry 100 }

-- =======================================
--2.2. zxr10P2mpTeLeafTnnlCfgTable
-- =======================================
-- 1.3.6.1.4.1.3902.3.6000.205.2.2
zxr10P2mpTeLeafTnnlCfgTable OBJECT-TYPE
    SYNTAX      SEQUENCE OF Zxr10P2mpTeLeafTnnlCfgEntry
    MAX-ACCESS  not-accessible
    STATUS      current
    DESCRIPTION
            ""
    ::= { zxr10P2mpTeObjects 2 }

-- 1.3.6.1.4.1.3902.3.6000.205.2.2.1
zxr10P2mpTeLeafTnnlCfgEntry OBJECT-TYPE
    SYNTAX      Zxr10P2mpTeLeafTnnlCfgEntry
    MAX-ACCESS  not-accessible
    STATUS      current
    DESCRIPTION
            ""
    INDEX   { zxr10P2mpTeLeafTnnlCfgName }
    ::= { zxr10P2mpTeLeafTnnlCfgTable 1 }

Zxr10P2mpTeLeafTnnlCfgEntry ::=
    SEQUENCE {
        zxr10P2mpTeLeafTnnlCfgName                     DisplayString,
        zxr10P2mpTeLeafTnnlCfgIndex                    Integer32,
        zxr10P2mpTeLeafTnnlCfgRootAddr                 IpAddress,
        zxr10P2mpTeLeafTnnlCfgRootTnnlID               Integer32,
        zxr10P2mpTeLeafTnnlCfgRootP2mpID               Unsigned32,
        zxr10P2mpTeLeafTnnlCfgRowStatus                RowStatus

    }

-- 1.3.6.1.4.1.3902.3.6000.205.2.2.1.1
zxr10P2mpTeLeafTnnlCfgName OBJECT-TYPE
    SYNTAX      DisplayString(SIZE(1..32))
    MAX-ACCESS  not-accessible
    STATUS      current
    DESCRIPTION
            "P2mp Leaf Tunnel Name."
    ::= { zxr10P2mpTeLeafTnnlCfgEntry 1 }

-- 1.3.6.1.4.1.3902.3.6000.205.2.2.1.2
zxr10P2mpTeLeafTnnlCfgIndex OBJECT-TYPE
    SYNTAX      Integer32(1..65535)
    MAX-ACCESS  read-only
    STATUS      current
    DESCRIPTION
            "P2mp Leaf Tunnel index."
    ::= { zxr10P2mpTeLeafTnnlCfgEntry 2 }

-- 1.3.6.1.4.1.3902.3.6000.205.2.2.1.3
zxr10P2mpTeLeafTnnlCfgRootAddr OBJECT-TYPE
    SYNTAX      IpAddress
    MAX-ACCESS  read-create
    STATUS      current
    DESCRIPTION
            "The IngressId of P2mp Leaf Tunnel."
    ::= { zxr10P2mpTeLeafTnnlCfgEntry 3 }

-- 1.3.6.1.4.1.3902.3.6000.205.2.2.1.4
zxr10P2mpTeLeafTnnlCfgRootTnnlID OBJECT-TYPE
    SYNTAX      Integer32(1..65535)
    MAX-ACCESS  read-create
    STATUS      current
    DESCRIPTION
            "The Index of P2mp Leaf Tunnel."
    ::= { zxr10P2mpTeLeafTnnlCfgEntry 4 }

-- 1.3.6.1.4.1.3902.3.6000.205.2.2.1.5
zxr10P2mpTeLeafTnnlCfgRootP2mpID OBJECT-TYPE
    SYNTAX      Unsigned32(1..4294967295)
    MAX-ACCESS  read-create
    STATUS      current
    DESCRIPTION
            "The P2mpId of P2mp Leaf Tunnel."
    ::= { zxr10P2mpTeLeafTnnlCfgEntry 5 }

-- 1.3.6.1.4.1.3902.3.6000.205.2.2.1.100
zxr10P2mpTeLeafTnnlCfgRowStatus OBJECT-TYPE
    SYNTAX      RowStatus
    MAX-ACCESS  read-create
    STATUS      current
    DESCRIPTION
            "RowStatus."
    ::= { zxr10P2mpTeLeafTnnlCfgEntry 100 }

--*************************************************************************
--  zxr10P2mpTeDsteCfgTable
--*************************************************************************
--1.3.6.1.4.1.3902.3.6000.205.2.3
zxr10P2mpTeDsteCfgTable OBJECT-TYPE
    SYNTAX      SEQUENCE OF Zxr10P2mpTeDsteCfgEntry
    MAX-ACCESS  not-accessible
    STATUS      current
    DESCRIPTION
            ""
    ::= { zxr10P2mpTeObjects 3 }
--1.3.6.1.4.1.3902.3.6000.205.2.3.1
zxr10P2mpTeDsteCfgEntry OBJECT-TYPE
    SYNTAX      Zxr10P2mpTeDsteCfgEntry
    MAX-ACCESS  not-accessible
    STATUS      current
    DESCRIPTION
            ""
    INDEX   { zxr10P2mpTeDsteCfgTunnelName,zxr10P2mpTeDsteCfgClassType }
    ::= { zxr10P2mpTeDsteCfgTable 1 }

Zxr10P2mpTeDsteCfgEntry ::=
    SEQUENCE {
        zxr10P2mpTeDsteCfgTunnelName        DisplayString,
        zxr10P2mpTeDsteCfgClassType         Unsigned32,
        zxr10P2mpTeDsteCfgBandwidth         Unsigned32,
        zxr10P2mpTeDsteCfgRowStatus         RowStatus
    }
--1.3.6.1.4.1.3902.3.6000.205.2.3.1.1
zxr10P2mpTeDsteCfgTunnelName OBJECT-TYPE
    SYNTAX      DisplayString(SIZE(0..31))
    MAX-ACCESS  not-accessible
    STATUS      current
    DESCRIPTION
            "The canonical name assigned to the tunnel. This name can be used
            to refer to the tunnel on the LSR's console port.If
            mplsTETunnelIsIf is set to true then the ifName of the interface
            corresponding to this tunnel should have a value equal to
            mplsTETunnelName. Also see the description of ifName in RFC 2863."
    ::= { zxr10P2mpTeDsteCfgEntry 1 }
--1.3.6.1.4.1.3902.3.6000.205.2.3.1.2
zxr10P2mpTeDsteCfgClassType OBJECT-TYPE
    SYNTAX      Unsigned32(0..7)
    MAX-ACCESS  not-accessible
    STATUS      current
    DESCRIPTION
            "The dste class type of this tunnel."
    ::= { zxr10P2mpTeDsteCfgEntry 2 }
--1.3.6.1.4.1.3902.3.6000.205.2.3.1.3
zxr10P2mpTeDsteCfgBandwidth OBJECT-TYPE
    SYNTAX      Unsigned32(1..4294967295)
    MAX-ACCESS  read-create
    STATUS      current
    DESCRIPTION
            "The dste bandwidth of this tunnel."
    ::= { zxr10P2mpTeDsteCfgEntry 3 }
--1.3.6.1.4.1.3902.3.6000.205.2.3.1.100
zxr10P2mpTeDsteCfgRowStatus OBJECT-TYPE
    SYNTAX      RowStatus
    MAX-ACCESS  read-create
    STATUS      current
    DESCRIPTION
            "Row status."
    ::= { zxr10P2mpTeDsteCfgEntry 100 }

-- =======================================
--2.4. zxr10P2mpTeDestLNameCfgTable
-- =======================================
-- 1.3.6.1.4.1.3902.3.6000.205.2.4
zxr10P2mpTeDestLNameCfgTable OBJECT-TYPE
    SYNTAX      SEQUENCE OF Zxr10P2mpTeDestLNameCfgEntry
    MAX-ACCESS  not-accessible
    STATUS      current
    DESCRIPTION
            ""
    ::= { zxr10P2mpTeObjects 4 }

-- 1.3.6.1.4.1.3902.3.6000.205.2.4.1
zxr10P2mpTeDestLNameCfgEntry OBJECT-TYPE
    SYNTAX      Zxr10P2mpTeDestLNameCfgEntry
    MAX-ACCESS  not-accessible
    STATUS      current
    DESCRIPTION
            ""
    INDEX   { zxr10P2mpTeDestLNameCfgName}
    ::= { zxr10P2mpTeDestLNameCfgTable 1 }

Zxr10P2mpTeDestLNameCfgEntry ::=
    SEQUENCE {
        zxr10P2mpTeDestLNameCfgName                      DisplayString,
        zxr10P2mpTeDestLNameCfgRowStatus                 RowStatus
    }

-- 1.3.6.1.4.1.3902.3.6000.205.2.4.1.1
zxr10P2mpTeDestLNameCfgName OBJECT-TYPE
    SYNTAX      DisplayString(SIZE(1..16))
    MAX-ACCESS  not-accessible
    STATUS      current
    DESCRIPTION
            "The Name of destlist."
    ::= { zxr10P2mpTeDestLNameCfgEntry 1 }

-- 1.3.6.1.4.1.3902.3.6000.205.2.4.1.100
zxr10P2mpTeDestLNameCfgRowStatus OBJECT-TYPE
    SYNTAX      RowStatus
    MAX-ACCESS  read-create
    STATUS      current
    DESCRIPTION
            "row status."
    ::= { zxr10P2mpTeDestLNameCfgEntry 100 }


-- =======================================
--2.5. zxr10P2mpTeDestLIDCfgTable
-- =======================================
-- 1.3.6.1.4.1.3902.3.6000.205.2.5
zxr10P2mpTeDestLIDCfgTable OBJECT-TYPE
    SYNTAX      SEQUENCE OF Zxr10P2mpTeDestLIDCfgEntry
    MAX-ACCESS  not-accessible
    STATUS      current
    DESCRIPTION
            ""
    ::= { zxr10P2mpTeObjects 5 }

-- 1.3.6.1.4.1.3902.3.6000.205.2.5.1
zxr10P2mpTeDestLIDCfgEntry OBJECT-TYPE
    SYNTAX      Zxr10P2mpTeDestLIDCfgEntry
    MAX-ACCESS  not-accessible
    STATUS      current
    DESCRIPTION
            ""
    INDEX   { zxr10P2mpTeDestLIDCfgDestLID}
    ::= { zxr10P2mpTeDestLIDCfgTable 1 }

Zxr10P2mpTeDestLIDCfgEntry ::=
    SEQUENCE {
        zxr10P2mpTeDestLIDCfgDestLID               Unsigned32,
        zxr10P2mpTeDestLIDCfgRowStatus                RowStatus
    }

-- 1.3.6.1.4.1.3902.3.6000.205.2.5.1.1
zxr10P2mpTeDestLIDCfgDestLID OBJECT-TYPE
    SYNTAX      Unsigned32(0..4294967295)
    MAX-ACCESS  not-accessible
    STATUS      current
    DESCRIPTION
            "The id of destlist."
    ::= { zxr10P2mpTeDestLIDCfgEntry 1 }

-- 1.3.6.1.4.1.3902.3.6000.205.2.5.1.100
zxr10P2mpTeDestLIDCfgRowStatus OBJECT-TYPE
    SYNTAX      RowStatus
    MAX-ACCESS  read-create
    STATUS      current
    DESCRIPTION
            "row status."
    ::= { zxr10P2mpTeDestLIDCfgEntry 100 }

-- =======================================
--2.6. zxr10P2mpTeDstNameCfgTable
-- =======================================
-- 1.3.6.1.4.1.3902.3.6000.205.2.6
zxr10P2mpTeDstNameCfgTable OBJECT-TYPE
    SYNTAX      SEQUENCE OF Zxr10P2mpTeDstNameCfgEntry
    MAX-ACCESS  not-accessible
    STATUS      current
    DESCRIPTION
            ""
    ::= { zxr10P2mpTeObjects 6 }

-- 1.3.6.1.4.1.3902.3.6000.205.2.6.1
zxr10P2mpTeDstNameCfgEntry OBJECT-TYPE
    SYNTAX      Zxr10P2mpTeDstNameCfgEntry
    MAX-ACCESS  not-accessible
    STATUS      current
    DESCRIPTION
            ""
    INDEX   { zxr10P2mpTeDstNameCfgName,
              zxr10P2mpTeDstNameCfgDestAddr}
    ::= { zxr10P2mpTeDstNameCfgTable 1 }

Zxr10P2mpTeDstNameCfgEntry ::=
    SEQUENCE {
        zxr10P2mpTeDstNameCfgName                             DisplayString,
        zxr10P2mpTeDstNameCfgDestAddr                         IpAddress,
        zxr10P2mpTeDstNameCfgPathOptNum                       Integer32,
        zxr10P2mpTeDstNameCfgPathType                         INTEGER,
        zxr10P2mpTeDstNameCfgExpPathName                      DisplayString,
        zxr10P2mpTeDstNameCfgExpPathID                        Integer32,
        zxr10P2mpTeDstNameCfgRowStatus                        RowStatus
    }

-- 1.3.6.1.4.1.3902.3.6000.205.2.6.1.1
zxr10P2mpTeDstNameCfgName OBJECT-TYPE
    SYNTAX      DisplayString(SIZE(1..16))
    MAX-ACCESS  not-accessible
    STATUS      current
    DESCRIPTION
            "The Name of destlist."
    ::= { zxr10P2mpTeDstNameCfgEntry 1 }

-- 1.3.6.1.4.1.3902.3.6000.205.2.6.1.2
zxr10P2mpTeDstNameCfgDestAddr OBJECT-TYPE
    SYNTAX      IpAddress
    MAX-ACCESS  not-accessible
    STATUS      current
    DESCRIPTION
            "The destination address of destlistname."
    ::= { zxr10P2mpTeDstNameCfgEntry 2 }

-- 1.3.6.1.4.1.3902.3.6000.205.2.6.1.3
zxr10P2mpTeDstNameCfgPathOptNum OBJECT-TYPE
    SYNTAX      Integer32(1..16)
    MAX-ACCESS  read-create
    STATUS      current
    DESCRIPTION
            "The destination address of destlistname."
    ::= { zxr10P2mpTeDstNameCfgEntry 3 }

-- 1.3.6.1.4.1.3902.3.6000.205.2.6.1.4
zxr10P2mpTeDstNameCfgPathType OBJECT-TYPE
    SYNTAX      INTEGER{explicitName(1),explicitId(2),dynamic(3)}
    MAX-ACCESS  read-create
    STATUS      current
    DESCRIPTION
            "The pathtype of destname."
    ::= { zxr10P2mpTeDstNameCfgEntry 4 }

-- 1.3.6.1.4.1.3902.3.6000.205.2.6.1.5
zxr10P2mpTeDstNameCfgExpPathName OBJECT-TYPE
    SYNTAX      DisplayString(SIZE(1..64))
    MAX-ACCESS  read-create
    STATUS      current
    DESCRIPTION
            "The explicit pathname of destname."
    ::= { zxr10P2mpTeDstNameCfgEntry 5 }

-- 1.3.6.1.4.1.3902.3.6000.205.2.6.1.6
zxr10P2mpTeDstNameCfgExpPathID OBJECT-TYPE
    SYNTAX      Integer32(0..65535)
    MAX-ACCESS  read-create
    STATUS      current
    DESCRIPTION
            "The explicit pathid of destname."
    ::= { zxr10P2mpTeDstNameCfgEntry 6 }

-- 1.3.6.1.4.1.3902.3.6000.205.2.6.1.100
zxr10P2mpTeDstNameCfgRowStatus OBJECT-TYPE
    SYNTAX      RowStatus
    MAX-ACCESS  read-create
    STATUS      current
    DESCRIPTION
            "Row status."
    ::= { zxr10P2mpTeDstNameCfgEntry 100 }


-- =======================================
--2.7. zxr10P2mpTeDstIDCfgTable
-- =======================================
-- 1.3.6.1.4.1.3902.3.6000.205.2.7
zxr10P2mpTeDstIDCfgTable OBJECT-TYPE
    SYNTAX      SEQUENCE OF Zxr10P2mpTeDstIDCfgEntry
    MAX-ACCESS  not-accessible
    STATUS      current
    DESCRIPTION
            ""
    ::= { zxr10P2mpTeObjects 7 }

-- 1.3.6.1.4.1.3902.3.6000.205.2.7.1
zxr10P2mpTeDstIDCfgEntry OBJECT-TYPE
    SYNTAX      Zxr10P2mpTeDstIDCfgEntry
    MAX-ACCESS  not-accessible
    STATUS      current
    DESCRIPTION
            ""
    INDEX   { zxr10P2mpTeDstIDCfgDestLID,
              zxr10P2mpTeDstIDCfgDestAddr}
    ::= { zxr10P2mpTeDstIDCfgTable 1 }

Zxr10P2mpTeDstIDCfgEntry ::=
    SEQUENCE {
        zxr10P2mpTeDstIDCfgDestLID                           Unsigned32,
        zxr10P2mpTeDstIDCfgDestAddr                          IpAddress,
        zxr10P2mpTeDstIDCfgPathOptNum                        Integer32,
        zxr10P2mpTeDstIDCfgPathType                          INTEGER,
        zxr10P2mpTeDstIDCfgExpPathName                       DisplayString,
        zxr10P2mpTeDstIDCfgExpPathID                         Integer32,
        zxr10P2mpTeDstIDCfgRowStatus                         RowStatus
    }

-- 1.3.6.1.4.1.3902.3.6000.205.2.7.1.1
zxr10P2mpTeDstIDCfgDestLID OBJECT-TYPE
    SYNTAX      Unsigned32
    MAX-ACCESS  not-accessible
    STATUS      current
    DESCRIPTION
            "The id of destlist."
    ::= { zxr10P2mpTeDstIDCfgEntry 1 }

-- 1.3.6.1.4.1.3902.3.6000.205.2.7.1.2
zxr10P2mpTeDstIDCfgDestAddr OBJECT-TYPE
    SYNTAX      IpAddress
    MAX-ACCESS  not-accessible
    STATUS      current
    DESCRIPTION
            "The destination address of destid."
    ::= { zxr10P2mpTeDstIDCfgEntry 2 }

-- 1.3.6.1.4.1.3902.3.6000.205.2.7.1.3
zxr10P2mpTeDstIDCfgPathOptNum OBJECT-TYPE
    SYNTAX      Integer32(1..16)
    MAX-ACCESS  read-create
    STATUS      current
    DESCRIPTION
            "The pathopt num of destid."
    ::= { zxr10P2mpTeDstIDCfgEntry 3 }

-- 1.3.6.1.4.1.3902.3.6000.205.2.7.1.4
zxr10P2mpTeDstIDCfgPathType OBJECT-TYPE
    SYNTAX      INTEGER{explicitName(1),explicitId(2),dynamic(3)}
    MAX-ACCESS  read-create
    STATUS      current
    DESCRIPTION
            "The pathtype of destid."
    ::= { zxr10P2mpTeDstIDCfgEntry 4 }

-- 1.3.6.1.4.1.3902.3.6000.205.2.7.1.5
zxr10P2mpTeDstIDCfgExpPathName OBJECT-TYPE
    SYNTAX      DisplayString(SIZE(1..64))
    MAX-ACCESS  read-create
    STATUS      current
    DESCRIPTION
            "The explicitpathname of destlistid."
    ::= { zxr10P2mpTeDstIDCfgEntry 5 }

-- 1.3.6.1.4.1.3902.3.6000.205.2.7.1.6
zxr10P2mpTeDstIDCfgExpPathID OBJECT-TYPE
    SYNTAX      Integer32(0..65535)
    MAX-ACCESS  read-create
    STATUS      current
    DESCRIPTION
            "The expicit pathid of destid."
    ::= { zxr10P2mpTeDstIDCfgEntry 6 }

-- 1.3.6.1.4.1.3902.3.6000.205.2.7.1.100
zxr10P2mpTeDstIDCfgRowStatus OBJECT-TYPE
    SYNTAX      RowStatus
    MAX-ACCESS  read-create
    STATUS      current
    DESCRIPTION
            "Row status."
    ::= { zxr10P2mpTeDstIDCfgEntry 100 }

-- =======================================
--2.8. zxr10P2mpTeLocTnnlTable
-- =======================================
-- 1.3.6.1.4.1.3902.3.6000.205.2.8
zxr10P2mpTeLocTnnlTable OBJECT-TYPE
    SYNTAX      SEQUENCE OF Zxr10P2mpTeLocTnnlEntry
    MAX-ACCESS  not-accessible
    STATUS      current
    DESCRIPTION
            ""
    ::= { zxr10P2mpTeObjects 8 }

-- 1.3.6.1.4.1.3902.3.6000.205.2.8.1
zxr10P2mpTeLocTnnlEntry OBJECT-TYPE
    SYNTAX      Zxr10P2mpTeLocTnnlEntry
    MAX-ACCESS  not-accessible
    STATUS      current
    DESCRIPTION
            ""
    INDEX   { zxr10P2mpTeLocTnnlIndex }
    ::= { zxr10P2mpTeLocTnnlTable 1 }

Zxr10P2mpTeLocTnnlEntry ::=
    SEQUENCE {
        zxr10P2mpTeLocTnnlIndex                     Integer32,
        zxr10P2mpTeLocTnnlName                      DisplayString,
        zxr10P2mpTeLocTnnlP2mpID                    Unsigned32,
        zxr10P2mpTeLocTnnlInuseLspID                Integer32,
        zxr10P2mpTeLocTnnlCreationTime              TimeTicks,
        zxr10P2mpTeLocTnnlUpTime                    TimeTicks,
        zxr10P2mpTeLocTnnlOperStatus                INTEGER,
        zxr10P2mpTeLocTnnlAdminStatus               INTEGER
    }

-- 1.3.6.1.4.1.3902.3.6000.205.2.8.1.1
zxr10P2mpTeLocTnnlIndex OBJECT-TYPE
    SYNTAX      Integer32(1..65535)
    MAX-ACCESS  not-accessible
    STATUS      current
    DESCRIPTION
            "P2mp Local tunnel Index."
    ::= { zxr10P2mpTeLocTnnlEntry 1 }

-- 1.3.6.1.4.1.3902.3.6000.205.2.8.1.2
zxr10P2mpTeLocTnnlName OBJECT-TYPE
    SYNTAX      DisplayString(SIZE(1..32))
    MAX-ACCESS  read-only
    STATUS      current
    DESCRIPTION
            "P2mp Local tunnel Name ."
    ::= { zxr10P2mpTeLocTnnlEntry 2 }

-- 1.3.6.1.4.1.3902.3.6000.205.2.8.1.3
zxr10P2mpTeLocTnnlP2mpID OBJECT-TYPE
    SYNTAX      Unsigned32(1..4294967295)
    MAX-ACCESS  read-only
    STATUS      current
    DESCRIPTION
            "The p2mpid of P2mp Local tunnel  ."
    ::= { zxr10P2mpTeLocTnnlEntry 3 }

-- 1.3.6.1.4.1.3902.3.6000.205.2.8.1.4
zxr10P2mpTeLocTnnlInuseLspID    OBJECT-TYPE
    SYNTAX      Integer32(0..65535)
    MAX-ACCESS  read-only
    STATUS      current
    DESCRIPTION
            "The inuselspid of P2mp Local tunnel ."
    ::= { zxr10P2mpTeLocTnnlEntry 4 }

-- 1.3.6.1.4.1.3902.3.6000.205.2.8.1.5
zxr10P2mpTeLocTnnlCreationTime   OBJECT-TYPE
    SYNTAX      TimeTicks
    MAX-ACCESS  read-only
    STATUS      current
    DESCRIPTION
            "The creationtime of P2mp Local tunnel."
    ::= { zxr10P2mpTeLocTnnlEntry 5 }

-- 1.3.6.1.4.1.3902.3.6000.205.2.8.1.6
zxr10P2mpTeLocTnnlUpTime   OBJECT-TYPE
    SYNTAX      TimeTicks
    MAX-ACCESS  read-only
    STATUS      current
    DESCRIPTION
            "The uptime of P2mp Local tunnel."
    ::= { zxr10P2mpTeLocTnnlEntry 6 }

-- 1.3.6.1.4.1.3902.3.6000.205.2.8.1.7
zxr10P2mpTeLocTnnlOperStatus   OBJECT-TYPE
    SYNTAX      INTEGER{ up(1),
                         down(2)
                         }
    MAX-ACCESS  read-only
    STATUS      current
    DESCRIPTION
            "The operstatus of P2mp Local tunnel ."
    ::= { zxr10P2mpTeLocTnnlEntry 7 }

-- 1.3.6.1.4.1.3902.3.6000.205.2.8.1.8
zxr10P2mpTeLocTnnlAdminStatus   OBJECT-TYPE
    SYNTAX      INTEGER{ up(1),
                         down(2)
                         }
    MAX-ACCESS  read-only
    STATUS      current
    DESCRIPTION
            "The adminstatus of P2mp Local tunnel ."
    ::= { zxr10P2mpTeLocTnnlEntry 8 }

-- =======================================
--2.9. zxr10P2mpTeLeafTnnlTable
-- =======================================
-- 1.3.6.1.4.1.3902.3.6000.205.2.9
zxr10P2mpTeLeafTnnlTable OBJECT-TYPE
    SYNTAX      SEQUENCE OF Zxr10P2mpTeLeafTnnlEntry
    MAX-ACCESS  not-accessible
    STATUS      current
    DESCRIPTION
            ""
    ::= { zxr10P2mpTeObjects 9 }

-- 1.3.6.1.4.1.3902.3.6000.205.2.9.1
zxr10P2mpTeLeafTnnlEntry OBJECT-TYPE
    SYNTAX      Zxr10P2mpTeLeafTnnlEntry
    MAX-ACCESS  not-accessible
    STATUS      current
    DESCRIPTION
            ""
    INDEX   { zxr10P2mpTeLeafTnnlIndex }
    ::= { zxr10P2mpTeLeafTnnlTable 1 }

Zxr10P2mpTeLeafTnnlEntry ::=
    SEQUENCE {
        zxr10P2mpTeLeafTnnlIndex                  Integer32,
        zxr10P2mpTeLeafTnnlName                   DisplayString,
        zxr10P2mpTeLeafTnnlOperStatus             INTEGER
    }

-- 1.3.6.1.4.1.3902.3.6000.205.2.9.1.1
zxr10P2mpTeLeafTnnlIndex OBJECT-TYPE
    SYNTAX      Integer32(1..65535)
    MAX-ACCESS  not-accessible
    STATUS      current
    DESCRIPTION
            "P2mp Leaf tunnel Index."
    ::= { zxr10P2mpTeLeafTnnlEntry 1 }

-- 1.3.6.1.4.1.3902.3.6000.205.2.9.1.2
zxr10P2mpTeLeafTnnlName OBJECT-TYPE
    SYNTAX      DisplayString(SIZE(1..32))
    MAX-ACCESS  read-only
    STATUS      current
    DESCRIPTION
            "P2mp Leaf tunnel Name ."
    ::= { zxr10P2mpTeLeafTnnlEntry 2 }

-- 1.3.6.1.4.1.3902.3.6000.205.2.9.1.3
zxr10P2mpTeLeafTnnlOperStatus   OBJECT-TYPE
    SYNTAX      INTEGER{ up(1),
                         down(2)
                         }
    MAX-ACCESS  read-only
    STATUS      current
    DESCRIPTION
            "The operstatus of P2mp root tunnel ."
    ::= { zxr10P2mpTeLeafTnnlEntry 3 }


-- =======================================
--2.10. zxr10P2mpTeLspTable
-- =======================================
-- 1.3.6.1.4.1.3902.3.6000.205.2.10
zxr10P2mpTeLspTable OBJECT-TYPE
    SYNTAX      SEQUENCE OF Zxr10P2mpTeLspEntry
    MAX-ACCESS  not-accessible
    STATUS      current
    DESCRIPTION
            ""
    ::= { zxr10P2mpTeObjects 10 }

-- 1.3.6.1.4.1.3902.3.6000.205.2.10.1
zxr10P2mpTeLspEntry OBJECT-TYPE
    SYNTAX      Zxr10P2mpTeLspEntry
    MAX-ACCESS  not-accessible
    STATUS      current
    DESCRIPTION
            ""
    INDEX   { zxr10P2mpTeLspTnnlIndex,
              zxr10P2mpTeLspP2mpID,
              zxr10P2mpTeLspLSPID,
              zxr10P2mpTeLspIngressID,
              zxr10P2mpTeLspPrevHop}
    ::= { zxr10P2mpTeLspTable 1 }

Zxr10P2mpTeLspEntry ::=
    SEQUENCE {
        zxr10P2mpTeLspTnnlIndex                   Integer32,
        zxr10P2mpTeLspP2mpID                      Unsigned32,
        zxr10P2mpTeLspLSPID                       Integer32,
        zxr10P2mpTeLspIngressID                   IpAddress,
        zxr10P2mpTeLspPrevHop                     IpAddress,
        zxr10P2mpTeLspBandwith                    Unsigned32,
        zxr10P2mpTeLspSetupprio                   Integer32,
        zxr10P2mpTeLspHoldprio                    Integer32,
        zxr10P2mpTeLspIntegrity                   TruthValue,
        zxr10P2mpTeLspRRO                         TruthValue,
        zxr10P2mpTeLspResvStyle                   INTEGER,
        zxr10P2mpTeLspRole                        INTEGER,
        zxr10P2mpTeLspCreationTime                TimeTicks,
        zxr10P2mpTeLspOperStatus                  INTEGER,
        zxr10P2mpTeLspCrkbackMode                 INTEGER
    }

-- 1.3.6.1.4.1.3902.3.6000.205.2.10.1.1
zxr10P2mpTeLspTnnlIndex OBJECT-TYPE
    SYNTAX      Integer32(1..65535)
    MAX-ACCESS  not-accessible
    STATUS      current
    DESCRIPTION
            "P2mp Te Lsp Name ."
    ::= { zxr10P2mpTeLspEntry 1 }

-- 1.3.6.1.4.1.3902.3.6000.205.2.10.1.2
zxr10P2mpTeLspP2mpID OBJECT-TYPE
    SYNTAX      Unsigned32(1..4294967295)
    MAX-ACCESS  not-accessible
    STATUS      current
    DESCRIPTION
            "P2mp Te Lsp P2mpId ."
    ::= { zxr10P2mpTeLspEntry 2 }

-- 1.3.6.1.4.1.3902.3.6000.205.2.10.1.3
zxr10P2mpTeLspLSPID OBJECT-TYPE
    SYNTAX      Integer32(0..65535)
    MAX-ACCESS  not-accessible
    STATUS      current
    DESCRIPTION
            "P2mp Te Lsp Index."
    ::= { zxr10P2mpTeLspEntry 3 }

-- 1.3.6.1.4.1.3902.3.6000.205.2.10.1.4
zxr10P2mpTeLspIngressID OBJECT-TYPE
    SYNTAX      IpAddress
    MAX-ACCESS  not-accessible
    STATUS      current
    DESCRIPTION
            "P2mp Te Lsp IngressId."
    ::= { zxr10P2mpTeLspEntry 4 }

-- 1.3.6.1.4.1.3902.3.6000.205.2.10.1.5
zxr10P2mpTeLspPrevHop OBJECT-TYPE
    SYNTAX      IpAddress
    MAX-ACCESS  not-accessible
    STATUS      current
    DESCRIPTION
            "P2mp Te Lsp PrevHop."
    ::= { zxr10P2mpTeLspEntry 5 }

-- 1.3.6.1.4.1.3902.3.6000.205.2.10.1.6
zxr10P2mpTeLspBandwith OBJECT-TYPE
    SYNTAX      Unsigned32(0..4294967295)
    MAX-ACCESS  read-only
    STATUS      current
    DESCRIPTION
            "P2mp Te Lsp Bandwith."
    ::= { zxr10P2mpTeLspEntry 6 }

-- 1.3.6.1.4.1.3902.3.6000.205.2.10.1.7
zxr10P2mpTeLspSetupprio OBJECT-TYPE
    SYNTAX      Integer32(0..7)
    MAX-ACCESS  read-only
    STATUS      current
    DESCRIPTION
            "P2mp Te Lsp Setupprio."
    ::= { zxr10P2mpTeLspEntry 7 }

-- 1.3.6.1.4.1.3902.3.6000.205.2.10.1.8
zxr10P2mpTeLspHoldprio OBJECT-TYPE
    SYNTAX      Integer32(0..7)
    MAX-ACCESS  read-only
    STATUS      current
    DESCRIPTION
            "P2mp Te Lsp Holdprio."
    ::= { zxr10P2mpTeLspEntry 8 }

-- 1.3.6.1.4.1.3902.3.6000.205.2.10.1.9
zxr10P2mpTeLspIntegrity OBJECT-TYPE
    SYNTAX      TruthValue
    MAX-ACCESS  read-only
    STATUS      current
    DESCRIPTION
            "P2mp Te Lsp Integrity."
    ::= { zxr10P2mpTeLspEntry 9 }

-- 1.3.6.1.4.1.3902.3.6000.205.2.10.1.10
zxr10P2mpTeLspRRO OBJECT-TYPE
    SYNTAX      TruthValue
    MAX-ACCESS  read-only
    STATUS      current
    DESCRIPTION
            "P2mp Te Lsp RRO."
    ::= { zxr10P2mpTeLspEntry 10 }

-- 1.3.6.1.4.1.3902.3.6000.205.2.10.1.11
zxr10P2mpTeLspResvStyle OBJECT-TYPE
    SYNTAX      INTEGER {
                         se(1),
                         ff(2)
                         }
    MAX-ACCESS  read-only
    STATUS      current
    DESCRIPTION
            "P2mp Te Lsp RevStyle."
    ::= { zxr10P2mpTeLspEntry 11 }

-- 1.3.6.1.4.1.3902.3.6000.205.2.10.1.12
zxr10P2mpTeLspRole OBJECT-TYPE
    SYNTAX      INTEGER {
                         notBranch(1),
                         branch(2),
                         bud(3)
                         }
    MAX-ACCESS  read-only
    STATUS      current
    DESCRIPTION
            "P2mp Te Lsp Role."
    ::= { zxr10P2mpTeLspEntry 12 }

-- 1.3.6.1.4.1.3902.3.6000.205.2.10.1.13
zxr10P2mpTeLspCreationTime OBJECT-TYPE
    SYNTAX      TimeTicks
    MAX-ACCESS  read-only
    STATUS      current
    DESCRIPTION
            "P2mp Te Lsp CreationTime."
    ::= { zxr10P2mpTeLspEntry 13 }

-- 1.3.6.1.4.1.3902.3.6000.205.2.10.1.14
zxr10P2mpTeLspOperStatus   OBJECT-TYPE
    SYNTAX      INTEGER{ up(1),
                         down(2)
                         }
    MAX-ACCESS  read-only
    STATUS      current
    DESCRIPTION
            "The operstatus of P2mp Te lsp ."
    ::= { zxr10P2mpTeLspEntry 14 }

-- 1.3.6.1.4.1.3902.3.6000.205.2.10.1.15
zxr10P2mpTeLspCrkbackMode   OBJECT-TYPE
    SYNTAX      INTEGER{endtoend(1), disabled(2)}
    MAX-ACCESS  read-only
    STATUS      current
    DESCRIPTION
            "The CrankbackMode of P2mp Te lsp ."
    ::= { zxr10P2mpTeLspEntry 15 }
-- =======================================
--2.11. zxr10P2mpTeSLspTable
-- =======================================
-- 1.3.6.1.4.1.3902.3.6000.205.2.11
zxr10P2mpTeSLspTable OBJECT-TYPE
    SYNTAX      SEQUENCE OF Zxr10P2mpTeSLspEntry
    MAX-ACCESS  not-accessible
    STATUS      current
    DESCRIPTION
            ""
    ::= { zxr10P2mpTeObjects 11 }

-- 1.3.6.1.4.1.3902.3.6000.205.2.11.1
zxr10P2mpTeSLspEntry OBJECT-TYPE
    SYNTAX      Zxr10P2mpTeSLspEntry
    MAX-ACCESS  not-accessible
    STATUS      current
    DESCRIPTION
            ""
    INDEX   { zxr10P2mpTeSLspTnnlIndex,
              zxr10P2mpTeSLspP2mpID,
              zxr10P2mpTeSLspLspID,
              zxr10P2mpTeSLspIngressAddr,
              zxr10P2mpTeSLspDestAddr,
              zxr10P2mpTeSLspPrevHop}
    ::= { zxr10P2mpTeSLspTable 1 }

Zxr10P2mpTeSLspEntry ::=
    SEQUENCE {
        zxr10P2mpTeSLspTnnlIndex                  Integer32,
        zxr10P2mpTeSLspP2mpID                     Unsigned32,
        zxr10P2mpTeSLspLspID                      Integer32,
        zxr10P2mpTeSLspIngressAddr                IpAddress,
        zxr10P2mpTeSLspDestAddr                   IpAddress,
        zxr10P2mpTeSLspPrevHop                    IpAddress,
        zxr10P2mpTeSLspInLabel                    Unsigned32,
        zxr10P2mpTeSLspOutLabel                   Unsigned32,
        zxr10P2mpTeSLspInIfName                   DisplayString,
        zxr10P2mpTeSLspOutIfName                  DisplayString,
        zxr10P2mpTeSLspSrcSubGrpOrigType          INTEGER,
        zxr10P2mpTeSLspSrcSubGrpOrigin            IpAddress,
        zxr10P2mpTeSLspSrcSubGrpID                Unsigned32,
        zxr10P2mpTeSLspSubGrpOrigType             INTEGER,
        zxr10P2mpTeSLspSubGrpOrig                 IpAddress,
        zxr10P2mpTeSLspSubGrpID                   Unsigned32,
        zxr10P2mpTeSLspHopIndex                   Unsigned32,
        zxr10P2mpTeSLspChopIndex                  Unsigned32,
        zxr10P2mpTeSLspARhopIndex                 Unsigned32,
        zxr10P2mpTeSLspRole                       INTEGER,
        zxr10P2mpTeSLspCreationTime               TimeTicks,
        zxr10P2mpTeSLspUpTime                     TimeTicks,
        zxr10P2mpTeSLspOperStatus                 INTEGER
    }

-- 1.3.6.1.4.1.3902.3.6000.205.2.11.1
zxr10P2mpTeSLspTnnlIndex OBJECT-TYPE
    SYNTAX      Integer32(1..65535)
    MAX-ACCESS  not-accessible
    STATUS      current
    DESCRIPTION
            "P2mp Te SubLsp TunnelIndex ."
    ::= { zxr10P2mpTeSLspEntry 1 }

-- 1.3.6.1.4.1.3902.3.6000.205.2.11.2
zxr10P2mpTeSLspP2mpID OBJECT-TYPE
    SYNTAX      Unsigned32(1..4294967295)
    MAX-ACCESS  not-accessible
    STATUS      current
    DESCRIPTION
            "P2mp Te SubLsp P2mpId ."
    ::= { zxr10P2mpTeSLspEntry 2 }

-- 1.3.6.1.4.1.3902.3.6000.205.2.11.3
zxr10P2mpTeSLspLspID OBJECT-TYPE
    SYNTAX      Integer32(0..65535)
    MAX-ACCESS  not-accessible
    STATUS      current
    DESCRIPTION
            "P2mp Te SubLsp LSPId."
    ::= { zxr10P2mpTeSLspEntry 3 }

-- 1.3.6.1.4.1.3902.3.6000.205.2.11.4
zxr10P2mpTeSLspIngressAddr OBJECT-TYPE
    SYNTAX      IpAddress
    MAX-ACCESS  not-accessible
    STATUS      current
    DESCRIPTION
            "P2mp Te SubLsp IngressAddr."
    ::= { zxr10P2mpTeSLspEntry 4 }

-- 1.3.6.1.4.1.3902.3.6000.205.2.11.5
zxr10P2mpTeSLspDestAddr OBJECT-TYPE
    SYNTAX      IpAddress
    MAX-ACCESS  not-accessible
    STATUS      current
    DESCRIPTION
            "P2mp Te SubLsp DestAddr ."
    ::= { zxr10P2mpTeSLspEntry 5 }

-- 1.3.6.1.4.1.3902.3.6000.205.2.11.6
zxr10P2mpTeSLspPrevHop OBJECT-TYPE
    SYNTAX      IpAddress
    MAX-ACCESS  not-accessible
    STATUS      current
    DESCRIPTION
            "P2mp Te SubLsp PrevHop ."
    ::= { zxr10P2mpTeSLspEntry 6 }

-- 1.3.6.1.4.1.3902.3.6000.205.2.11.7
zxr10P2mpTeSLspInLabel OBJECT-TYPE
    SYNTAX      Unsigned32(0..4294967295)
    MAX-ACCESS  read-only
    STATUS      current
    DESCRIPTION
            "P2mp Te SubLsp InLabel."
    ::= { zxr10P2mpTeSLspEntry 7 }

-- 1.3.6.1.4.1.3902.3.6000.205.2.11.8
zxr10P2mpTeSLspOutLabel OBJECT-TYPE
    SYNTAX      Unsigned32(0..4294967295)
    MAX-ACCESS  read-only
    STATUS      current
    DESCRIPTION
            "P2mp Te SubLsp OutLabel."
    ::= { zxr10P2mpTeSLspEntry 8 }

-- 1.3.6.1.4.1.3902.3.6000.205.2.11.9
zxr10P2mpTeSLspInIfName OBJECT-TYPE
    SYNTAX      DisplayString(SIZE(0..32))
    MAX-ACCESS  read-only
    STATUS      current
    DESCRIPTION
            "P2mp Te SubLsp InIfName."
    ::= { zxr10P2mpTeSLspEntry 9 }

-- 1.3.6.1.4.1.3902.3.6000.205.2.11.10
zxr10P2mpTeSLspOutIfName OBJECT-TYPE
    SYNTAX      DisplayString(SIZE(0..32))
    MAX-ACCESS  read-only
    STATUS      current
    DESCRIPTION
            "P2mp Te SubLsp OutIfName."
    ::= { zxr10P2mpTeSLspEntry 10 }

-- 1.3.6.1.4.1.3902.3.6000.205.2.11.11
zxr10P2mpTeSLspSrcSubGrpOrigType OBJECT-TYPE
    SYNTAX      INTEGER {
                                ipv4(1),
                                ipv6(2)
                                }
    MAX-ACCESS  read-only
    STATUS      current
    DESCRIPTION
            "P2mp Te SubLsp Src SubGroupOriginType."
    ::= { zxr10P2mpTeSLspEntry 11 }

-- 1.3.6.1.4.1.3902.3.6000.205.2.11.12
zxr10P2mpTeSLspSrcSubGrpOrigin OBJECT-TYPE
    SYNTAX      IpAddress
    MAX-ACCESS  read-only
    STATUS      current
    DESCRIPTION
            "P2mp Te SubLsp Src SubGroupOrigin."
    ::= { zxr10P2mpTeSLspEntry 12 }

-- 1.3.6.1.4.1.3902.3.6000.205.2.11.13
zxr10P2mpTeSLspSrcSubGrpID OBJECT-TYPE
    SYNTAX      Unsigned32(0..65535)
    MAX-ACCESS  read-only
    STATUS      current
    DESCRIPTION
            "P2mp Te SubLsp Src SubGroupID."
    ::= { zxr10P2mpTeSLspEntry 13 }

-- 1.3.6.1.4.1.3902.3.6000.205.2.11.14
zxr10P2mpTeSLspSubGrpOrigType OBJECT-TYPE
    SYNTAX      INTEGER {
                                ipv4(1),
                                ipv6(2)
                                }
    MAX-ACCESS  read-only
    STATUS      current
    DESCRIPTION
            "P2mp Te SubLsp SubGroupOriginType."
    ::= { zxr10P2mpTeSLspEntry 14 }

-- 1.3.6.1.4.1.3902.3.6000.205.2.11.15
zxr10P2mpTeSLspSubGrpOrig OBJECT-TYPE
    SYNTAX      IpAddress
    MAX-ACCESS  read-only
    STATUS      current
    DESCRIPTION
            "P2mp Te SubLsp SubGroupOrigin."
    ::= { zxr10P2mpTeSLspEntry 15 }

-- 1.3.6.1.4.1.3902.3.6000.205.2.11.16
zxr10P2mpTeSLspSubGrpID OBJECT-TYPE
    SYNTAX      Unsigned32(0..65535)
    MAX-ACCESS  read-only
    STATUS      current
    DESCRIPTION
            "P2mp Te SubLsp SubGroupID."
    ::= { zxr10P2mpTeSLspEntry 16 }

-- 1.3.6.1.4.1.3902.3.6000.205.2.11.17
zxr10P2mpTeSLspHopIndex    OBJECT-TYPE
    SYNTAX      Unsigned32(0..4294967295)
    MAX-ACCESS  read-only
    STATUS      current
    DESCRIPTION
            "P2mp Te SubLsp hopindex."
    ::= { zxr10P2mpTeSLspEntry 17 }

-- 1.3.6.1.4.1.3902.3.6000.205.2.11.18
zxr10P2mpTeSLspChopIndex    OBJECT-TYPE
    SYNTAX      Unsigned32(0..4294967295)
    MAX-ACCESS  read-only
    STATUS      current
    DESCRIPTION
            "P2mp Te SubLsp chopindex."
    ::= { zxr10P2mpTeSLspEntry 18 }

-- 1.3.6.1.4.1.3902.3.6000.205.2.11.19
zxr10P2mpTeSLspARhopIndex    OBJECT-TYPE
    SYNTAX      Unsigned32(0..4294967295)
    MAX-ACCESS  read-only
    STATUS      current
    DESCRIPTION
            "P2mp Te SubLsp arhopindex."
    ::= { zxr10P2mpTeSLspEntry 19 }

-- 1.3.6.1.4.1.3902.3.6000.205.2.11.20
zxr10P2mpTeSLspRole    OBJECT-TYPE
    SYNTAX   INTEGER {
                 root(1),
                         transit(2),
                         leaf(3)
                         }
    MAX-ACCESS  read-only
    STATUS      current
    DESCRIPTION
            "P2mp Te SubLsp UpTime."
    ::= { zxr10P2mpTeSLspEntry 20 }

-- 1.3.6.1.4.1.3902.3.6000.205.2.11.21
zxr10P2mpTeSLspCreationTime OBJECT-TYPE
    SYNTAX      TimeTicks
    MAX-ACCESS  read-only
    STATUS      current
    DESCRIPTION
            "P2mp Te SubLsp CreationTime."
    ::= { zxr10P2mpTeSLspEntry 21 }

-- 1.3.6.1.4.1.3902.3.6000.205.2.11.22
zxr10P2mpTeSLspUpTime    OBJECT-TYPE
    SYNTAX      TimeTicks
    MAX-ACCESS  read-only
    STATUS      current
    DESCRIPTION
            "P2mp Te SubLsp UpTime."
    ::= { zxr10P2mpTeSLspEntry 22 }

-- 1.3.6.1.4.1.3902.3.6000.205.2.11.23
zxr10P2mpTeSLspOperStatus OBJECT-TYPE
    SYNTAX      INTEGER{ up(1),
                         down(2)
                         }
    MAX-ACCESS  read-only
    STATUS      current
    DESCRIPTION
            "P2mp Te SubLsp OperStatus."
    ::= { zxr10P2mpTeSLspEntry 23 }



-- =======================================
--2.12. zxr10P2mpTeHopTable
-- =======================================
-- 1.3.6.1.4.1.3902.3.6000.205.2.12
zxr10P2mpTeHopTable OBJECT-TYPE
    SYNTAX      SEQUENCE OF Zxr10P2mpTeHopEntry
    MAX-ACCESS  not-accessible
    STATUS      current
    DESCRIPTION
            ""
    ::= { zxr10P2mpTeObjects 12 }

-- 1.3.6.1.4.1.3902.3.6000.205.2.12.1
zxr10P2mpTeHopEntry OBJECT-TYPE
    SYNTAX      Zxr10P2mpTeHopEntry
    MAX-ACCESS  not-accessible
    STATUS      current
    DESCRIPTION
            ""
    INDEX   { zxr10P2mpTeHopListIndex,
              zxr10P2mpTeHopPathOptionIndex,
              zxr10P2mpTeHopIndex}
    ::= { zxr10P2mpTeHopTable 1 }

Zxr10P2mpTeHopEntry ::=
    SEQUENCE {
        zxr10P2mpTeHopListIndex                             Unsigned32,
        zxr10P2mpTeHopPathOptionIndex                       Integer32,
        zxr10P2mpTeHopIndex                                 Integer32,
        zxr10P2mpTeHopAddrType                              INTEGER,
        zxr10P2mpTeHopIpAddr                                IpAddress,
        zxr10P2mpTeHopIpPrefixLen                           Unsigned32,
        zxr10P2mpTeHopAsNumber                              Unsigned32,
        zxr10P2mpTeHopAddrUnnum                             Unsigned32,
        zxr10P2mpTeHopLspID                                 Unsigned32,
        zxr10P2mpTeHopType                                  INTEGER,
        zxr10P2mpTeHopInclude                               TruthValue,
        zxr10P2mpTeHopPathOptionName                        DisplayString,
        zxr10P2mpTeHopEntryPathComp                         INTEGER,
        zxr10P2mpTeHopRowStatus                             INTEGER,
        zxr10P2mpTeHopStorageType                           INTEGER

    }

-- 1.3.6.1.4.1.3902.3.6000.205.2.12.1.1
zxr10P2mpTeHopListIndex OBJECT-TYPE
    SYNTAX      Unsigned32
    MAX-ACCESS  not-accessible
    STATUS      current
    DESCRIPTION
        "Primary index into this table identifying a
        particular explicit route object."
    ::= { zxr10P2mpTeHopEntry 1 }

-- 1.3.6.1.4.1.3902.3.6000.205.2.12.1.2
zxr10P2mpTeHopPathOptionIndex OBJECT-TYPE
    SYNTAX  Integer32
    MAX-ACCESS  not-accessible
    STATUS      current
    DESCRIPTION
        "Secondary index into this table identifying a
        particular group of hops representing a particular
        configured path. This is otherwise known as a path
        option."
    ::= { zxr10P2mpTeHopEntry 2 }

-- 1.3.6.1.4.1.3902.3.6000.205.2.12.1.3
zxr10P2mpTeHopIndex OBJECT-TYPE
    SYNTAX      Integer32
    MAX-ACCESS  not-accessible
    STATUS      current
    DESCRIPTION
        "Tertiary index into this table identifying a particular hop."
    ::= { zxr10P2mpTeHopEntry 3 }

-- 1.3.6.1.4.1.3902.3.6000.205.2.12.1.4
zxr10P2mpTeHopAddrType OBJECT-TYPE
    SYNTAX      INTEGER{
                        ipv4(1),
                        ipv6(2),
                        asnumber(3),
                        unnum(4),
                        lspid(5)
                        }
    MAX-ACCESS  read-only
    STATUS      current
    DESCRIPTION
        "The Hop Address Type of this tunnel hop."
    ::= { zxr10P2mpTeHopEntry 4 }

-- 1.3.6.1.4.1.3902.3.6000.205.2.12.1.5
zxr10P2mpTeHopIpAddr OBJECT-TYPE
    SYNTAX      IpAddress
    MAX-ACCESS  read-only
    STATUS      current
    DESCRIPTION
        "The Tunnel Hop Address for this tunnel hop."
    ::= { zxr10P2mpTeHopEntry 5 }

-- 1.3.6.1.4.1.3902.3.6000.205.2.12.1.6
zxr10P2mpTeHopIpPrefixLen OBJECT-TYPE
    SYNTAX      Unsigned32
    MAX-ACCESS  read-only
    STATUS      current
    DESCRIPTION
        "If zxr10P2mpTeHopAddrType is set to ipv4(1) or
         ipv6(2), then this value will contain an
         appropriate prefix length for the IP address in
         object zxr10P2mpTeHopIpAddr. Otherwise this value
         is irrelevant and should be ignored. "
    ::= { zxr10P2mpTeHopEntry 6 }

-- 1.3.6.1.4.1.3902.3.6000.205.2.12.1.7
zxr10P2mpTeHopAsNumber OBJECT-TYPE
     SYNTAX     Unsigned32
     MAX-ACCESS read-only
     STATUS     current
     DESCRIPTION
         "If zxr10P2mpTeHopAddrType is set to asnumber(3), then
         this value will contain the AS number of this hop.
         Otherwise the agent should set this object to zerolength
         string and the manager should ignore this."
     ::= { zxr10P2mpTeHopEntry 7 }

-- 1.3.6.1.4.1.3902.3.6000.205.2.12.1.8
zxr10P2mpTeHopAddrUnnum OBJECT-TYPE
    SYNTAX      Unsigned32
    MAX-ACCESS  read-only
    STATUS      current
    DESCRIPTION
        "If zxr10P2mpTeHopAddrType is set to unnum(4), then
        this value will contain the interface identifier of
        the unnumbered interface for this hop. This object
        should be used in conjunction with
        zxr10P2mpTeHopIpAddr which would contain the LSR
        Router ID in this case. Otherwise the agent should
        set this object to zero-length string and the
        manager should ignore this."
    ::= { zxr10P2mpTeHopEntry 8 }

-- 1.3.6.1.4.1.3902.3.6000.205.2.12.1.9
zxr10P2mpTeHopLspID OBJECT-TYPE
    SYNTAX      Unsigned32
    MAX-ACCESS  read-only
    STATUS      current
    DESCRIPTION
        "If zxr10P2mpTeHopAddrType is set to lspid(5), then
        this value will contain the LSPID of a tunnel of
        this hop. The present tunnel being configured is
        tunneled through this hop (using label stacking).
        This object is otherwise insignificant and should
        contain a value of 0 to indicate this fact."
    ::= { zxr10P2mpTeHopEntry 9 }

-- 1.3.6.1.4.1.3902.3.6000.205.2.12.1.10
zxr10P2mpTeHopType OBJECT-TYPE
    SYNTAX      INTEGER{
                            strict(1),
                            loose(2)
                            }

    MAX-ACCESS  read-only
    STATUS      current
    DESCRIPTION
        "Denotes whether this tunnel hop is routed in a
         strict or loose fashion. The value of this object
         has no meaning if the zxr10P2mpTeHopInclude object
         is set to false."
    ::= { zxr10P2mpTeHopEntry 10 }

-- 1.3.6.1.4.1.3902.3.6000.205.2.12.1.11
zxr10P2mpTeHopInclude OBJECT-TYPE
    SYNTAX      TruthValue
    MAX-ACCESS  read-only
    STATUS      current
    DESCRIPTION
        "If this value is set to true, then this indicates
        that this hop must be included in the tunnel's
        path. If this value is set to 'false', then this hoph
        must be avoided when calculating the path for this
        tunnel. The default value of this object is 'true',
        so that by default all indicated hops are included
        in the CSPF path computation. If this object is set
        to 'false' the value of zxr10P2mpTeHopType should be
        ignored."
    ::= { zxr10P2mpTeHopEntry 11 }

-- 1.3.6.1.4.1.3902.3.6000.205.2.12.1.12
zxr10P2mpTeHopPathOptionName OBJECT-TYPE
     SYNTAX     DisplayString(SIZE(1..64))
     MAX-ACCESS read-only
     STATUS     current
     DESCRIPTION
     "The description of this series of hops as they
     relate to the specified path option. The
     value of this object SHOULD be the same for
     each hop in the series that comprises a
     path option."
     ::= { zxr10P2mpTeHopEntry 12 }

-- 1.3.6.1.4.1.3902.3.6000.205.2.12.1.13
zxr10P2mpTeHopEntryPathComp    OBJECT-TYPE
    SYNTAX        INTEGER {
                            dynamic(1), -- CSPF computed
                            explicit(2) -- strict hop
                            }

    MAX-ACCESS  read-only
    STATUS      current
    DESCRIPTION
         "If this value is set to dynamic, then the user
         should only specify the source and destination of
         the path and expect that the CSPF will calculate
         the remainder of the path. If this value is set to
         explicit, the user should specify the entire path
         for the tunnel to take. This path may contain
         strict or loose hops. Each hop along a specific
         path SHOULD have this object set to the same value."
    ::= { zxr10P2mpTeHopEntry 13 }

-- 1.3.6.1.4.1.3902.3.6000.205.2.12.1.100
zxr10P2mpTeHopRowStatus OBJECT-TYPE
    SYNTAX      INTEGER {active(1),
                            notInService(2),
                            notReady(3),
                            createAndGo(4),
                            createAndWait(5),
                            destroy(6)}
    MAX-ACCESS  read-only
    STATUS      current
    DESCRIPTION
        "Row status."
    ::= { zxr10P2mpTeHopEntry 100 }

-- 1.3.6.1.4.1.3902.3.6000.205.2.12.1.101
zxr10P2mpTeHopStorageType OBJECT-TYPE
    SYNTAX     INTEGER {other(1),
                        volatile(2),
                        nonVolatile(3),
                        permanent(4),
                        readOnly(5)}
    MAX-ACCESS read-only
    STATUS     current
    DESCRIPTION
        "The storage type for this Hop entry."
    DEFVAL { volatile }
    ::= { zxr10P2mpTeHopEntry 101 }

-- =======================================
--2.13. zxr10P2mpTeCHopTable
-- =======================================
-- 1.3.6.1.4.1.3902.3.6000.205.2.13
zxr10P2mpTeCHopTable OBJECT-TYPE
    SYNTAX      SEQUENCE OF Zxr10P2mpTeCHopEntry
    MAX-ACCESS  not-accessible
    STATUS      current
    DESCRIPTION
            ""
    ::= { zxr10P2mpTeObjects 13 }

-- 1.3.6.1.4.1.3902.3.6000.205.2.13.1
zxr10P2mpTeCHopEntry OBJECT-TYPE
    SYNTAX      Zxr10P2mpTeCHopEntry
    MAX-ACCESS  not-accessible
    STATUS      current
    DESCRIPTION
            ""
    INDEX   { zxr10P2mpTeCHopListIndex,zxr10P2mpTeCHopIndex }
    ::= { zxr10P2mpTeCHopTable 1 }

Zxr10P2mpTeCHopEntry ::=
    SEQUENCE {
    zxr10P2mpTeCHopListIndex                      Unsigned32,
    zxr10P2mpTeCHopIndex                          Unsigned32,
    zxr10P2mpTeCHopAddrType                       INTEGER,
    zxr10P2mpTeCHopIpAddr                         IpAddress,
    zxr10P2mpTeCHopIpPrefixLen                    Unsigned32,
    zxr10P2mpTeCHopAsNumber                       Unsigned32,
    zxr10P2mpTeCHopAddrUnnum                      Unsigned32,
    zxr10P2mpTeCHopLspID                          Unsigned32,
    zxr10P2mpTeCHopType                           INTEGER
    }

-- 1.3.6.1.4.1.3902.3.6000.205.2.13.1.1
zxr10P2mpTeCHopListIndex OBJECT-TYPE
    SYNTAX      Unsigned32(0..4294967295)
    MAX-ACCESS  not-accessible
    STATUS      current
    DESCRIPTION
            "Primary index into this table identifying a
    particular computed hop list."
    ::= { zxr10P2mpTeCHopEntry 1 }

-- 1.3.6.1.4.1.3902.3.6000.205.2.13.1.2
zxr10P2mpTeCHopIndex OBJECT-TYPE
    SYNTAX      Unsigned32(0..4294967295)
    MAX-ACCESS  not-accessible
    STATUS      current
    DESCRIPTION
            "Secondary index into this table identifying the
    particular hop."
    ::= { zxr10P2mpTeCHopEntry 2 }

-- 1.3.6.1.4.1.3902.3.6000.205.2.13.1.3
zxr10P2mpTeCHopAddrType   OBJECT-TYPE
    SYNTAX      INTEGER {
                        ipv4(1),
                        ipv6(2),
                        asnumber(3),
                        unnum(4),
                        lspid(5)}
    MAX-ACCESS  read-only
    STATUS      current
    DESCRIPTION
            "The Hop Address Type of this tunnel hop.
    Note that lspid(5) is a valid option only
    for tunnels signaled via CRLDP."
    ::= { zxr10P2mpTeCHopEntry 3 }

-- 1.3.6.1.4.1.3902.3.6000.205.2.13.1.4
zxr10P2mpTeCHopIpAddr   OBJECT-TYPE
    SYNTAX      IpAddress
    MAX-ACCESS  read-only
    STATUS      current
    DESCRIPTION
            "The Tunnel Hop Address for this tunnel hop.
    The type of this address is determined by the
    value of the corresponding zxr10r10MplsTunnelCHopAddrType.
    If zxr10r10MplsTunnelCHopAddrType is set to unnum(4), then
    this value will contain the LSR Router ID of the
    unnumbered interface. Otherwise the agent should
    set this object to the zero-length string and the
    manager SHOULD ignore this object."
    ::= { zxr10P2mpTeCHopEntry 4 }

-- 1.3.6.1.4.1.3902.3.6000.205.2.13.1.5
zxr10P2mpTeCHopIpPrefixLen   OBJECT-TYPE
    SYNTAX      Unsigned32(0..4294967295)
    MAX-ACCESS  read-only
    STATUS      current
    DESCRIPTION
            "If zxr10P2mpTeCHopAddrType is set to ipv4(1) or
    ipv6(2), then this value will contain an
    appropriate prefix length for the IP address in
    object zxr10P2mpTeCHopIpAddr. Otherwise this value
    is irrelevant and should be ignored."
    ::= { zxr10P2mpTeCHopEntry 5 }

-- 1.3.6.1.4.1.3902.3.6000.205.2.13.1.6
zxr10P2mpTeCHopAsNumber   OBJECT-TYPE
    SYNTAX      Unsigned32(0..4294967295)
    MAX-ACCESS  read-only
    STATUS      current
    DESCRIPTION
            "If zxr10P2mpTeCHopAddrType is set to asnumber(3),
    then this value will contain the AS number of this
    hop. Otherwise the agent should set this object to
    zero-length string and the manager should ignore
    this."
    ::= { zxr10P2mpTeCHopEntry 6 }

-- 1.3.6.1.4.1.3902.3.6000.205.2.13.1.7
zxr10P2mpTeCHopAddrUnnum   OBJECT-TYPE
    SYNTAX      Unsigned32(0..4294967295)
    MAX-ACCESS  read-only
    STATUS      current
    DESCRIPTION
            "If zxr10P2mpTeCHopAddrType is set to unnum(4), then
    this value will contain the unnumbered interface
    identifier of this hop. This object should be used
    in conjunction with zxr10P2mpTeCHopIpAddr which
    would contain the LSR Router ID in this case.
    Otherwise the agent should set this object to zerolength
    string and the manager should ignore this."
    ::= { zxr10P2mpTeCHopEntry 7 }

-- 1.3.6.1.4.1.3902.3.6000.205.2.13.1.8
zxr10P2mpTeCHopLspID   OBJECT-TYPE
    SYNTAX      Unsigned32(0..4294967295)
    MAX-ACCESS  read-only
    STATUS      current
    DESCRIPTION
            "If zxr10P2mpTeCHopAddrType is set to lspid(5), then
    his value will contain the LSP ID of this hop.
    his object is otherwise insignificant and should
    contain a value of 0 to indicate this fact."
    ::= { zxr10P2mpTeCHopEntry 8 }

-- 1.3.6.1.4.1.3902.3.6000.205.2.13.1.9
zxr10P2mpTeCHopType   OBJECT-TYPE
    SYNTAX      INTEGER {
                 strict(1),
                         loose(2),
                         routerid(3)}

    MAX-ACCESS  read-only
    STATUS      current
    DESCRIPTION
            "Denotes whether this is tunnel hop is routed in a
    strict or loose fashion."
    ::= { zxr10P2mpTeCHopEntry 9 }

-- =======================================
--2.14. zxr10P2mpTeARHopTable
-- =======================================
-- 1.3.6.1.4.1.3902.3.6000.205.2.14
zxr10P2mpTeARHopTable OBJECT-TYPE
    SYNTAX      SEQUENCE OF Zxr10P2mpTeARHopEntry
    MAX-ACCESS  not-accessible
    STATUS      current
    DESCRIPTION
            ""
    ::= { zxr10P2mpTeObjects 14 }

-- 1.3.6.1.4.1.3902.3.6000.205.2.14.1
zxr10P2mpTeARHopEntry OBJECT-TYPE
    SYNTAX      Zxr10P2mpTeARHopEntry
    MAX-ACCESS  not-accessible
    STATUS      current
    DESCRIPTION
            ""
    INDEX   { zxr10P2mpTeARHopListIndex,zxr10P2mpTeARHopIndex }
    ::= { zxr10P2mpTeARHopTable 1 }

Zxr10P2mpTeARHopEntry ::=
    SEQUENCE {
    zxr10P2mpTeARHopListIndex                     Unsigned32,
    zxr10P2mpTeARHopIndex                         Unsigned32,
    zxr10P2mpTeARHopAddrType                      INTEGER,
    zxr10P2mpTeARHopIpAddr                        IpAddress,
    zxr10P2mpTeARHopAddrUnnum                     Unsigned32,
    zxr10P2mpTeARHopLspID                         Unsigned32
    }

-- 1.3.6.1.4.1.3902.3.6000.205.2.14.1.1
zxr10P2mpTeARHopListIndex OBJECT-TYPE
    SYNTAX      Unsigned32(0..4294967295)
    MAX-ACCESS  not-accessible
    STATUS      current
    DESCRIPTION
            "Primary index into this table identifying a
    particular recorded hop list."
    ::= { zxr10P2mpTeARHopEntry 1 }

-- 1.3.6.1.4.1.3902.3.6000.205.2.14.1.2
zxr10P2mpTeARHopIndex OBJECT-TYPE
    SYNTAX      Unsigned32(0..4294967295)
    MAX-ACCESS  not-accessible
    STATUS      current
    DESCRIPTION
            "Secondary index into this table identifying the
    particular hop."
    ::= { zxr10P2mpTeARHopEntry 2 }

-- 1.3.6.1.4.1.3902.3.6000.205.2.14.1.3
zxr10P2mpTeARHopAddrType OBJECT-TYPE
    SYNTAX       INTEGER {
                        ipv4(1),
                        ipv6(2),
                        asnumber(3),
                        unnum(4),
                        lspid(5)}
    MAX-ACCESS  read-only
    STATUS      current
    DESCRIPTION
            "The Hop Address Type of this tunnel hop.
    ote that lspid(5) is a valid option only
    for tunnels signaled via CRLDP."
    ::= { zxr10P2mpTeARHopEntry 3 }

-- 1.3.6.1.4.1.3902.3.6000.205.2.14.1.4
zxr10P2mpTeARHopIpAddr OBJECT-TYPE
    SYNTAX      IpAddress
    MAX-ACCESS  read-only
    STATUS      current
    DESCRIPTION
            "The Tunnel Hop Address for this tunnel hop.
    The type of this address is determined by the
    value of the corresponding zxr10r10MplsTunnelARHopAddrType.
    If zxr10P2mpTeARHopAddrType is set to unnum(4),
    then this value contains the LSR Router ID of the
    unnumbered interface. Otherwise the agent SHOULD
    set this object to the zero-length string and the
    manager should ignore this object.
"
    ::= { zxr10P2mpTeARHopEntry 4 }

-- 1.3.6.1.4.1.3902.3.6000.205.2.14.1.5
zxr10P2mpTeARHopAddrUnnum OBJECT-TYPE
    SYNTAX      Unsigned32(0..4294967295)
    MAX-ACCESS  read-only
    STATUS      current
    DESCRIPTION
            "If zxr10P2mpTeARHopAddrType is set to unnum(4), then
    this value will contain the interface identifier of
    the unnumbered interface for this hop. This object
    should be used in conjunction with
    zxr10P2mpTeARHopIpAddr which would contain the LSR
    Router ID in this case. Otherwise the agent should
    set this object to zero-length string and the
    manager should ignore this.
"
    ::= { zxr10P2mpTeARHopEntry 5 }

-- 1.3.6.1.4.1.3902.3.6000.205.2.14.1.6
zxr10P2mpTeARHopLspID OBJECT-TYPE
    SYNTAX      Unsigned32(0..4294967295)
    MAX-ACCESS  read-only
    STATUS      current
    DESCRIPTION
            "If zxr10P2mpTeARHopAddrType is set to lspid(5), then
    this value will contain the LSP ID of this hop.
    This object is otherwise insignificant and should
    contain a value of 0 to indicate this fact."
    ::= { zxr10P2mpTeARHopEntry 6 }

-- =======================================
--2.15. zxr10P2mpTeFrrDBTable
-- =======================================
-- 1.3.6.1.4.1.3902.3.6000.205.2.15
zxr10P2mpTeFrrDBTable OBJECT-TYPE
    SYNTAX      SEQUENCE OF Zxr10P2mpTeFrrDBEntry
    MAX-ACCESS  not-accessible
    STATUS      current
    DESCRIPTION
            ""
    ::= { zxr10P2mpTeObjects 15 }

-- 1.3.6.1.4.1.3902.3.6000.205.2.15.1
zxr10P2mpTeFrrDBEntry OBJECT-TYPE
    SYNTAX      Zxr10P2mpTeFrrDBEntry
    MAX-ACCESS  not-accessible
    STATUS      current
    DESCRIPTION
            ""
    INDEX   { zxr10P2mpTeFrrProtectedIfIndex,
              zxr10P2mpTeFrrPriTunnelIndex,
              zxr10P2mpTeFrrPriTunnelP2mpID,
              zxr10P2mpTeFrrPriTunnelIngressID,
              zxr10P2mpTeFrrPriTunnelLspID,
              zxr10P2mpTeFrrPriTunnelPrevHop,
              zxr10P2mpTeFrrPriTunnelNextHop}
    ::= { zxr10P2mpTeFrrDBTable 1 }

Zxr10P2mpTeFrrDBEntry ::=
    SEQUENCE {
        zxr10P2mpTeFrrProtectedIfIndex                  Unsigned32,
        zxr10P2mpTeFrrPriTunnelIndex                    Integer32,
        zxr10P2mpTeFrrPriTunnelP2mpID                   Unsigned32,
        zxr10P2mpTeFrrPriTunnelIngressID                IpAddress,
        zxr10P2mpTeFrrPriTunnelLspID                    Integer32,
        zxr10P2mpTeFrrPriTunnelPrevHop                  IpAddress,
        zxr10P2mpTeFrrPriTunnelNextHop                  IpAddress,
        zxr10P2mpTeFrrBackupTunnelIndex                 Integer32,
        zxr10P2mpTeFrrProtectedIfName                   DisplayString,
        zxr10P2mpTeFrrInnerLabel                        Unsigned32,
        zxr10P2mpTeFrrStatus                            INTEGER
    }

-- 1.3.6.1.4.1.3902.3.6000.205.2.15.1.1
zxr10P2mpTeFrrProtectedIfIndex OBJECT-TYPE
    SYNTAX      Unsigned32(1..4294967295)
    MAX-ACCESS  not-accessible
    STATUS      current
    DESCRIPTION
            "P2MP TE FRR Protected Interface Index."
    ::= { zxr10P2mpTeFrrDBEntry 1 }

-- 1.3.6.1.4.1.3902.3.6000.205.2.15.1.2
zxr10P2mpTeFrrPriTunnelIndex OBJECT-TYPE
    SYNTAX      Integer32(1..65535)
    MAX-ACCESS  not-accessible
    STATUS      current
    DESCRIPTION
            "P2MP TE FRR Primary Tunnel Index."
    ::= { zxr10P2mpTeFrrDBEntry 2 }

-- 1.3.6.1.4.1.3902.3.6000.205.2.15.1.3
zxr10P2mpTeFrrPriTunnelP2mpID OBJECT-TYPE
    SYNTAX      Unsigned32(1..4294967295)
    MAX-ACCESS  not-accessible
    STATUS      current
    DESCRIPTION
            "P2MP TE FRR Primary Tunnel P2MP ID."
    ::= { zxr10P2mpTeFrrDBEntry 3 }

-- 1.3.6.1.4.1.3902.3.6000.205.2.15.1.4
zxr10P2mpTeFrrPriTunnelIngressID OBJECT-TYPE
    SYNTAX      IpAddress
    MAX-ACCESS  not-accessible
    STATUS      current
    DESCRIPTION
            "P2MP TE FRR Primary Tunnel IngressID."
    ::= { zxr10P2mpTeFrrDBEntry 4 }

-- 1.3.6.1.4.1.3902.3.6000.205.2.15.1.5
zxr10P2mpTeFrrPriTunnelLspID OBJECT-TYPE
    SYNTAX      Integer32(1..65535)
    MAX-ACCESS  not-accessible
    STATUS      current
    DESCRIPTION
            "P2MP TE FRR Primary Tunnel LspId."
    ::= { zxr10P2mpTeFrrDBEntry 5 }

-- 1.3.6.1.4.1.3902.3.6000.205.2.15.1.6
zxr10P2mpTeFrrPriTunnelPrevHop OBJECT-TYPE
    SYNTAX      IpAddress
    MAX-ACCESS  not-accessible
    STATUS      current
    DESCRIPTION
            "P2MP TE FRR Primary Tunnel PrevHop."
    ::= { zxr10P2mpTeFrrDBEntry 6 }

-- 1.3.6.1.4.1.3902.3.6000.205.2.15.1.7
zxr10P2mpTeFrrPriTunnelNextHop OBJECT-TYPE
    SYNTAX      IpAddress
    MAX-ACCESS  not-accessible
    STATUS      current
    DESCRIPTION
            "P2MP TE FRR Primary Tunnel NextHop."
    ::= { zxr10P2mpTeFrrDBEntry 7 }

-- 1.3.6.1.4.1.3902.3.6000.205.2.15.1.8
zxr10P2mpTeFrrBackupTunnelIndex OBJECT-TYPE
    SYNTAX      Integer32(1..65535)
    MAX-ACCESS  read-only
    STATUS      current
    DESCRIPTION
            "P2MP TE FRR Backup tunnel index."
    ::= { zxr10P2mpTeFrrDBEntry 8 }

-- 1.3.6.1.4.1.3902.3.6000.205.2.15.1.9
zxr10P2mpTeFrrProtectedIfName OBJECT-TYPE
    SYNTAX      DisplayString(SIZE(1..32))
    MAX-ACCESS  read-only
    STATUS      current
    DESCRIPTION
            "P2MP TE FRR Protected Interface Name."
    ::= { zxr10P2mpTeFrrDBEntry 9 }

-- 1.3.6.1.4.1.3902.3.6000.205.2.15.1.10
zxr10P2mpTeFrrInnerLabel OBJECT-TYPE
    SYNTAX      Unsigned32(1..4294967295)
    MAX-ACCESS  read-only
    STATUS      current
    DESCRIPTION
            "P2MP TE FRR Inner Label."
    ::= { zxr10P2mpTeFrrDBEntry 10 }

-- 1.3.6.1.4.1.3902.3.6000.205.2.15.1.11
zxr10P2mpTeFrrStatus OBJECT-TYPE
    SYNTAX      INTEGER{ready(1),active(2)}
    MAX-ACCESS  read-only
    STATUS      current
    DESCRIPTION
            "P2MP TE FRR Status."
    ::= { zxr10P2mpTeFrrDBEntry 11 }





END

--
-- ZXROSNG-P2MP-TE-MIB.mib
--
