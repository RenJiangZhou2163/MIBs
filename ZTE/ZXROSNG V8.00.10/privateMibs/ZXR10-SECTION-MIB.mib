ZXR10-SECTION-MIB DEFINITIONS ::= BEGIN

IMPORTS
    OBJECT-TYPE, MODULE-IDENTITY, Unsigned32,enterprises
            FROM SNMPv2-SMI
    DisplayString, RowStatus
            FROM SNMPv2-TC;     
            
zxr10SectionMIB MODULE-IDENTITY
                LAST-UPDATED
                "201305310000Z"
                ORGANIZATION
                "ZTE Corporation"
                CONTACT-INFO
                "        Xia wenjuan               
                    Tel:  +86-25-52870000           
                E-Mail: xia.wenjuan1@zte.com.cn 
                "
                DESCRIPTION
                "The MIB module to describe the section."
                REVISION
                "201305310000Z" 
                DESCRIPTION
                " Initial version of this MIB module"
                ::= { zxr10RosngMIB 506}
                   
    zte OBJECT IDENTIFIER ::={enterprises 3902}
    zxr10 OBJECT IDENTIFIER ::={zte 3}
    zxr10RosngMIB OBJECT IDENTIFIER ::= { zxr10 6000}
             
    zxr10SectionGlobalObjects  OBJECT IDENTIFIER ::= { zxr10SectionMIB 1 }
    zxr10SectionObjects        OBJECT IDENTIFIER ::= { zxr10SectionMIB 2 }
    zxr10SectionTraps          OBJECT IDENTIFIER ::= { zxr10SectionMIB 3 }
    zxr10SectionConformance    OBJECT IDENTIFIER ::= { zxr10SectionMIB 4 }

-- =============================
-- 1. zxr10SectionGlobalObjects 
-- =============================     
    
    
-- =============================
-- 2. zxr10SectionObjects
-- =============================       
-- =============================
-- 2.1 zxr10SectionListObjects
-- =============================  
zxr10SectionListObjects OBJECT IDENTIFIER ::= { zxr10SectionObjects 1 }
-- =============================
-- 2.1.1 zxr10SectionListGlobalObjects
-- =============================    
zxr10SectionListGlobalObjects  OBJECT IDENTIFIER ::= { zxr10SectionListObjects 1 }
-- =============================
-- 2.1.2 zxr10SectionListConfigTable
-- =============================
zxr10SectionListConfigTable OBJECT-TYPE
        SYNTAX  SEQUENCE OF Zxr10SectionListConfigEntry
        MAX-ACCESS  not-accessible
        STATUS  current
        DESCRIPTION
                "Section list config  table"
        ::= { zxr10SectionListObjects 2  }

zxr10SectionListConfigEntry OBJECT-TYPE
        SYNTAX   Zxr10SectionListConfigEntry
        MAX-ACCESS  not-accessible
        STATUS  current
        DESCRIPTION
                ""
        INDEX {zxr10SectionListConfigListId}
        ::= { zxr10SectionListConfigTable 1 }

Zxr10SectionListConfigEntry ::=
        SEQUENCE {
                zxr10SectionListConfigListId          Unsigned32,
                zxr10SectionListConfigMasterId        Unsigned32,
                zxr10SectionListConfigRowStatus       RowStatus             
        }

zxr10SectionListConfigListId OBJECT-TYPE
        SYNTAX   Unsigned32
        MAX-ACCESS  not-accessible
        STATUS  current
        DESCRIPTION
                "The number of this section list"
        ::= { zxr10SectionListConfigEntry  1  }

zxr10SectionListConfigMasterId OBJECT-TYPE
        SYNTAX   Unsigned32
        MAX-ACCESS  read-create
        STATUS  current
        DESCRIPTION
                "The master section of this section list"
        ::= { zxr10SectionListConfigEntry  2  }  
 
zxr10SectionListConfigRowStatus OBJECT-TYPE
        SYNTAX       RowStatus
        MAX-ACCESS   read-create
        STATUS        current
        DESCRIPTION
                "This variable is used to create, modify, and/or
                delete a row in this table. "
        ::= { zxr10SectionListConfigEntry 100 }
       
-- =============================
-- 2.1.3 zxr10SectionListSlaveTable
-- =============================
zxr10SectionListSlaveTable OBJECT-TYPE
        SYNTAX  SEQUENCE OF Zxr10SectionListSlaveEntry
        MAX-ACCESS  not-accessible
        STATUS  current
        DESCRIPTION
                "Section list slave table"
        ::= { zxr10SectionListObjects 3  }

zxr10SectionListSlaveEntry OBJECT-TYPE
        SYNTAX   Zxr10SectionListSlaveEntry
        MAX-ACCESS  not-accessible
        STATUS  current
        DESCRIPTION
                "to do"
        INDEX {zxr10SectionListSlaveListId,zxr10SectionListSlaveSlaveId}
        ::= { zxr10SectionListSlaveTable 1 }

Zxr10SectionListSlaveEntry ::=
        SEQUENCE {
                zxr10SectionListSlaveListId          Unsigned32,
                zxr10SectionListSlaveSlaveId         Unsigned32,   
                zxr10SectionListSlaveRowStatus       RowStatus               
        }

zxr10SectionListSlaveListId OBJECT-TYPE
        SYNTAX   Unsigned32
        MAX-ACCESS  not-accessible
        STATUS  current
        DESCRIPTION
                "The number of this section list"
        ::= { zxr10SectionListSlaveEntry  1  }

zxr10SectionListSlaveSlaveId OBJECT-TYPE
        SYNTAX   Unsigned32
        MAX-ACCESS  not-accessible
        STATUS  current
        DESCRIPTION
                "The slave section of this section list"
        ::= { zxr10SectionListSlaveEntry  2  }

zxr10SectionListSlaveRowStatus OBJECT-TYPE
        SYNTAX       RowStatus
        MAX-ACCESS   read-create
        STATUS        current
        DESCRIPTION
                "This variable is used to create, modify, and/or
                delete a row in this table. "
        ::= { zxr10SectionListSlaveEntry 100 }

-- =============================
--3. zxr10PbrNotifications  
-- =============================   
    
    
-- =============================
--4. zxr10PbrConformance    
-- =============================  
    
END
