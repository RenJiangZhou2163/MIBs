-- ******************************************************************
-- IEEE P802.1ag(TM) CFM MIB
-- ******************************************************************
ZXR10-CFM-MIB DEFINITIONS ::= BEGIN


IMPORTS
    MODULE-IDENTITY,
    OBJECT-TYPE,
    Integer32,
    Counter32,
    Unsigned32
        FROM SNMPv2-SMI --[RFC2578]

    TEXTUAL-CONVENTION,
    RowStatus,
    TruthValue,
    MacAddress,
    DisplayString
        FROM SNMPv2-TC --[RFC2579]

    zxr10
        FROM ZXR10-SMI;




    zxr10cfmMIB MODULE-IDENTITY
        LAST-UPDATED "201904191000Z" -- 2019-04-19
        ORGANIZATION "IEEE 802.1 Working Group"
        CONTACT-INFO
            "WG-URL: http://grouper.ieee.org/groups/802/1/index.html
            WG-EMail: stds-802-1@ieee.org
            Contact: David Elie-Dit-Cosaque
            Alcatel North America
            3400 W. Plano Pkwy.
            Plano, TX 75075, USA
            E-mail: david.elie_dit_cosaque@alcatel.com
            Contact: Norman Finn
            Cisco Systems
            170 W. Tasman Drive
            SJ-03/2/2
            San Jose, CA 95134, USA
            E-mail: nfinn@cisco.com
            "
        DESCRIPTION
            "Connectivity Fault Management module for managing IEEE 802.1ag"        
        REVISION "201904191000Z" -- 2019-04-19
        DESCRIPTION
             "modify: modify the attribute of MAX-ACCESS on 
             dot1agCfmPwMipPortName from not-accessible to read-only."
        REVISION "201710191000Z" -- 2017-10-19
        DESCRIPTION
             "modify: modify size list of dot1agCfmMepCcmLtmPriority."
        REVISION "201308291000Z" -- 2013-08-29
        DESCRIPTION
             "add: dot1agCfmMepDLMCountOamFlag,
             dot1agCfmMepLMMCountOamFlag"
        REVISION "201306251000Z" -- 2013-06-25
        DESCRIPTION
             "modify: dot1agCfmMepLMMInterval,
             dot1agCfmMepLMMRequireTime,
             dot1agCfmMepDMMInterval,
             dot1agCfmMepDMMRequireTime,
             dot1agCfmMepDMMFrameSize,
             dot1agCfmMep1DMInterval,
             dot1agCfmMep1DMRequireTime,
             dot1agCfmMep1DMFrameSize,
             dot1agCfmMepProcDMMInterval,
             dot1agCfmMepProcDMMFrameSize,
             dot1agCfmMepProc1DMInterval,
             dot1agCfmMepProc1DMFrameSize,
             dot1agCfmMepAISInterval,
             dot1agCfmMepLCKInterval,
             dot1agCfmMepDbDaly,
             dot1agCfmMepDbDalyChg,
             dot1agCfmMepDbProcDaly,
             dot1agCfmMepDbProcDalyChg"
        REVISION "201306131000Z" -- 2013-06-13
        DESCRIPTION
             "modify: Dot1agCfmMaintAssocNameType"
        REVISION "201305231000Z" -- 2013-05-23
        DESCRIPTION
             "modify: Dot1agCfmMaintDomainName,Dot1agCfmMaintAssocName"
        REVISION "201303251000Z" -- 2013-03-25
        DESCRIPTION
             "Included in ITU-T Y.1731."
        REVISION "200701240000Z" -- 2007-01-24
        DESCRIPTION
            "Included in IEEE P802.1ag Draft 8."
        ::= { zxr10 120 }


    dot1agMIBObjects OBJECT IDENTIFIER ::= { zxr10cfmMIB 1 }
-- ******************************************************************
-- Groups in the CFM MIB Module
-- ******************************************************************
    dot1agCfmMd OBJECT IDENTIFIER ::= { dot1agMIBObjects 1 }
    dot1agCfmMa OBJECT IDENTIFIER ::= { dot1agMIBObjects 2 }
    dot1agCfmMep OBJECT IDENTIFIER ::= { dot1agMIBObjects 3 }
    dot1agCfmGloPara OBJECT IDENTIFIER ::= { dot1agMIBObjects 4 }
    dot1agCfmPwMip OBJECT IDENTIFIER ::= { dot1agMIBObjects 5 }
-- ******************************************************************
-- Textual conventions InterfaceIndex,InterfaceIndexOrZero FROM IF-MIB [RFC2863]
-- ******************************************************************
    InterfaceIndexOrZero ::= TEXTUAL-CONVENTION
        DISPLAY-HINT "d"
        STATUS       current
        DESCRIPTION
            "This textual convention is an extension of the
            InterfaceIndex convention.  The latter defines a
            greater than zero value used to identify an interface
            or interface sub-layer in the managed system.  This
            extension permits the additional value of zero.  the
            value zero is object-specific and must therefore be
            defined as part of the description of any object which
            uses this syntax.  Examples of the usage of zero might
            include situations where interface was unknown, or
            when none or all interfaces need to be referenced."
        SYNTAX       Integer32 (0..2147483647)


-- ******************************************************************
-- Textual conventions
--                  LldpChassisId,
--                  LldpChassisIdSubtype,
--                  LldpPortId,
--                  LldpPortIdSubtype FROM LLDP-MIB  [IEEExxx]
-- ******************************************************************


-- ******************************************************************
-- Textual conventions        VlanIdOrNone, VlanId FROM Q-BRIDGE-MIB  [RFC4363]
-- ******************************************************************
    VlanIdOrNone ::= TEXTUAL-CONVENTION
        DISPLAY-HINT "d"
        STATUS       current
        DESCRIPTION
            "The VLAN-ID that uniquely identifies a specific VLAN,
            or no VLAN.  The special value of zero is used to
            indicate that no VLAN-ID is present or used.  This can
            be used in any situation where an object or a table entry
            must refer either to a specific VLAN, or to no VLAN.

            Note that a MIB object that is defined using this
            TEXTUAL-CONVENTION should clarify the meaning of
            'no VLAN' (i.e., the special value 0)."
        SYNTAX       Integer32 (0 | 1..4094)


    VlanId ::= TEXTUAL-CONVENTION
        DISPLAY-HINT "d"
        STATUS      current
        DESCRIPTION
            "The VLAN-ID that uniquely identifies a VLAN.  This
            is the 12-bit VLAN-ID used in the VLAN Tag header.
            The range is defined by the REFERENCEd specification."
        REFERENCE
            "IEEE Std 802.1Q 2003 Edition, Virtual Bridged Local Area Networks."
        SYNTAX      Integer32 (1..4094)

-- ******************************************************************
-- Textual conventions
-- ******************************************************************
    Dot1agCfmMaintDomainNameType ::= TEXTUAL-CONVENTION
        STATUS current
        DESCRIPTION
            "A value that represents a type (and thereby the format)
            of a Dot1agCfmMaintDomainName. The value can be one of
            the following:
            ieeeReserved(0) Reserved for definition by IEEE 802.1
            recommend to not use zero unless
            absolutely needed.
            none(1) No format specified, usually because
            there is not (yet) a Maintenance
            Domain Name. In this case, a zero
            length OCTET STRING for the Domain
            Name field is acceptable.
            dnsLikeName(2) Domain Name like string, globally unique
            text string derived from a DNS name.
            macAddrAndUint(3) MAC address + 2-octet (unsigned) integer.
            charString(4) RFC2579 DisplayString, except that the
            character codes 0-31 (decimal) are not
            used.
            ieeeReserved(xx) Reserved for definition by IEEE 802.1
            xx values can be [5..31] and [64..255]
            ituReserved(xx) Reserved for definition by ITU-T Y.1731
            xx values range from [32..63]To
            support future extensions, the Dot1agCfmMaintDomainNameType
            textual convention SHOULD NOT be sub-typed in object type
            definitions. It MAY be sub-typed in compliance statements in
            order to require only a subset of these address types for a
            compliant implementation.
            Implementations must ensure that Dot1agCfmMaintDomainNameType
            objects and any dependent objects (e.g.,
            Dot1agCfmMaintDomainName objects) are consistent. An
            inconsistentValue error must be generated if an attempt to
            change an Dot1agCfmMaintDomainNameType object would, for
            example, lead to an undefined Dot1agCfmMaintDomainName value.
            In particular,
            Dot1agCfmMaintDomainNameType/Dot1agCfmMaintDomainName pairs
            must be changed together if the nameType changes.
            "
        REFERENCE
            "802.1ag clause 21.6.5, Table 21-19"
        SYNTAX INTEGER {
            none (1),
            dnsLikeName (2),
            macAddressAndUint (3),
            charString (4)
            }

    Dot1agCfmMaintDomainName ::= TEXTUAL-CONVENTION
        STATUS current
        DESCRIPTION
            "Denotes a generic Maintenance Domain Name.A Dot1agC
            fmMaintDomainName value is always interpreted within
            the context of a Dot1agCfmMaintDomainNameType value. Every
            usage of the Dot1agCfmMaintDomainName textual convention is
            required to specify the Dot1agCfmMaintDomainNameType object
            that provides the context. It is suggested that the
            Dot1agCfmMaintDomainNameType object be logically registered
            before the object(s) that use the Dot1agCfmMaintDomainName
            textual convention, if they appear in the same logical row.
            The value of a Dot1agCfmMaintDomainName object must always
            be consistent with the value of the associated
            Dot1agCfmMaintDomainNameType object. Attempts to set
            an Dot1agCfmMaintDomainName object to a value inconsistent
            with the associated Dot1agCfmMaintDomainNameType must fail
            with an inconsistentValue error.
            When this textual convention is used as the syntax of an
            index object, there may be issues with the limit of 128
            sub-identifiers specified in SMIv2, IETF STD 58. In this
            case, the object definition MUST include a 'SIZE' clause
            to limit the number of potential instance sub-identifiers;
            otherwise the applicable constraints MUST be stated in
            the appropriate conceptual row DESCRIPTION clauses, or
            in the surrounding documentation if there is no single
            DESCRIPTION clause that is appropriate.
            A value of none(1) in the associated
            Dot1agCfmMaintDomainNameType object means that no Maintenance
            Domain name is present, and the contents of the
            Dot1agCfmMaintDomainName object are meaningless.
            See the DESCRIPTION of the Dot1agCfmMaintAssocNameType
            TEXTUAL-CONVENTION for a discussion of the length limits on
            the Maintenance Domain name and Maintenance Association name.
            "
        REFERENCE
           "802.1ag clause 21.6.5"
        SYNTAX OCTET STRING (SIZE(1..43))

    Dot1agCfmMaintAssocNameType ::= TEXTUAL-CONVENTION
    STATUS current
    DESCRIPTION
        "A value that represents a type (and thereby the format)
        of a Dot1agCfmMaintAssocName. The value can be one of
        the following:
        ieeeReserved(0) Reserved for definition by IEEE 802.1
        recommend to not use zero unless
        absolutely needed.
        primaryVid(1) Primary VLAN ID.
        12 bits represented in a 2-octet integer:
        - 4 least significant bits of the first
        byte contains the 4 most significant
        bits of the 12 bits primary VID
        - second byte contains the 8 least
        significant bits of the primary VID
        0 1 2 3 4 5 6 7 8
        +-+-+-+-+-+-+-+-+
        |0 0 0 0| (MSB) |
        +-+-+-+-+-+-+-+-+
        | VID LSB |
        +-+-+-+-+-+-+-+-+
        charString(2) RFC2579 DisplayString, except that the
        character codes 0-31 (decimal) are not
        used. (1..45) octets
        unsignedInt16 (3) 2-octet integer/big endian
        rfc2865VpnId(4) RFC 2685 VPN ID
        3 octet VPN authority Organizationally
        Unique Identifier followed by 4 octet VPN
        index identifying VPN according to the OUI:
        0 1 2 3 4 5 6 7 8
        +-+-+-+-+-+-+-+-+
        | VPN OUI (MSB) |
        +-+-+-+-+-+-+-+-+
        | VPN OUI |
        +-+-+-+-+-+-+-+-+
        | VPN OUI (LSB) |
        +-+-+-+-+-+-+-+-+
        |VPN Index (MSB)|
        +-+-+-+-+-+-+-+-+
        | VPN Index |
        +-+-+-+-+-+-+-+-+
        | VPN Index |
        +-+-+-+-+-+-+-+-+
        |VPN Index (LSB)|
        +-+-+-+-+-+-+-+-+
        iccString(32) ICC-based string. It consists of two subfields:
        the ITU carrier code (ICC) followed by a unique MEG ID code (UMC).
        The ITU Carrier Code consists of 1 6 left-justified characters,
        alphabetic, or leading alphabetic with trailing numeric. The UMC
        code immediately follows the ICC and shall consist of 7-12 characters, 
        with trailing NULLs, completing the 13-character MEG ID Value.
        The UMC shall be a matter for the organization to which the ICC
        has been assigned, provided that uniqueness is guaranteed. 
        ieeeReserved(xx) Reserved for definition by IEEE 802.1
        xx values can be [5..31] and [64..255]
        ituReserved(xx) Reserved for definition by ITU-T Y.1731
        xx values range from [33..63]
        To support future extensions, the Dot1agCfmMaintAssocNameType
        textual convention SHOULD NOT be sub-typed in object type
        definitions. It MAY be sub-typed in compliance statements in
        order to require only a subset of these address types for a
        compliant implementation.
        Implementations must ensure that Dot1agCfmMaintAssocNameType
        objects and any dependent objects (e.g.,
        Dot1agCfmMaintAssocName objects) are consistent. An
        inconsistentValue error must be generated if an attempt to
        change an Dot1agCfmMaintAssocNameType object would, for
        example, lead to an undefined Dot1agCfmMaintAssocName value.
        In particular,
        Dot1agCfmMaintAssocNameType/Dot1agCfmMaintAssocName pairs
        must be changed together if the nameType changes.
        The Maintenance Domain name and Maintenance Association name,
        when put together into the CCM PDU, MUST total 48 octets or
        less. If the Dot1agCfmMaintDomainNameType object contains
        none(1), then the Dot1agCfmMaintAssocName object MUST be
        45 octets or less in length. Otherwise, the length of
        the Dot1agCfmMaintDomainName object plus the length of the
        Dot1agCfmMaintAssocName object, added together, MUST total
        less than or equal to 44 octets.
        "
    REFERENCE
        "802.1ag clause 21.6.5.4, Table 21-20"
    SYNTAX INTEGER {
        primaryVid (1),
        charString (2),
        unsignedInt16 (3),
        rfc2865VpnId (4),
        iccString (32)
        }

    Dot1agCfmMaintAssocName ::= TEXTUAL-CONVENTION
        STATUS current
        DESCRIPTION
            "Denotes a generic Maintenance Association Name. It is the
            part of the Maintenance Association Identifier which is
            unique within the Maintenance Domain Name and is appended
            to the Maintenance Domain Name to form the Maintenance
            Association Identifier (MAID).
            A Dot1agCfmMaintAssocName value is always interpreted within
            the context of a Dot1agCfmMaintAssocNameType value. Every
            usage of the Dot1agCfmMaintAssocName textual convention is
            required to specify the Dot1agCfmMaintAssocNameType object
            that provides the context. It is suggested that the
            Dot1agCfmMaintAssocNameType object be logically registered
            before the object(s) that use the Dot1agCfmMaintAssocName
            textual convention, if they appear in the same logical row.
            The value of a Dot1agCfmMaintAssocName object must
            always be consistent with the value of the associated
            Dot1agCfmMaintAssocNameType object. Attempts to set
            an Dot1agCfmMaintAssocName object to a value inconsistent
            with the associated Dot1agCfmMaintAssocNameType must fail
            with an inconsistentValue error.
            When this textual convention is used as the syntax of an
            index object, there may be issues with the limit of 128
            sub-identifiers specified in SMIv2, IETF STD 58. In this
            case, the object definition MUST include a 'SIZE' clause
            to limit the number of potential instance sub-identifiers;
            otherwise the applicable constraints MUST be stated in
            the appropriate conceptual row DESCRIPTION clauses, or
            in the surrounding documentation if there is no single
            DESCRIPTION clause that is appropriate.
            "
        REFERENCE
            "802.1ag clauses 21.6.5.4, 21.6.5.5, 21.6.5.6"
        SYNTAX OCTET STRING (SIZE(1..45))

    Dot1agCfmMDLevel ::= TEXTUAL-CONVENTION
        DISPLAY-HINT "d"
        STATUS current
        DESCRIPTION
            "Integer identifying the Maintenance Domain Level (MD Level).
            Higher numbers correspond to higher Maintenance Domains,
            those with the greatest physical reach, with the highest
            values for customers' CFM PDUs. Lower numbers correspond
            to lower Maintenance Domains, those with more limited
            physical reach, with the lowest values for CFM PDUs
            protecting single bridges or physical links.
            "
        REFERENCE
            "802.1ag clauses 18.3, 21.4.1"
        SYNTAX Integer32 (0..7)

    Dot1agCfmMpDirection ::= TEXTUAL-CONVENTION
        STATUS current
        DESCRIPTION
            "Indicates the direction in which the Maintenance
            association (MEP or MIP) faces on the bridge port:
            down(1) Sends Continuity Check Messages away from the
            MAC Relay Entity.
            up(2) Sends Continuity Check Messages towards the
            MAC Relay Entity.
            "
        REFERENCE
            "802.1ag clauses 12.14.6.3.2:c"
        SYNTAX INTEGER {
            down (1),
            up (2)
            }

    Dot1agCfmHighestDefectPri ::= TEXTUAL-CONVENTION
        STATUS current
        DESCRIPTION
            "An enumerated value, equal to the contents of the variable
            highestDefect (20.33.9 and Table 20-1), indicating the
            highest-priority defect that has been present since the MEP
            Fault Notification Generator State Machine was last in the
            FNG_RESET state, either:
            none(0) no defects since FNG_RESET
            defRDICCM(1) DefRDICCM
            defMACstatus(2) DefMACstatus
            defRemoteCCM(3) DefRemoteCCM
            defErrorCCM(4) DefErrorCCM
            defXconCCM(5) DefXconCCM
            The value 0 is used for no defects so that additional higher
            priority values can be added, if needed, at a later time, and
            so that these values correspond with those in
            Dot1agCfmLowestAlarmPri.
            "
        REFERENCE
            "802.1ag clause 20.1.2, 12.14.7.7.2:c and 20.33.9"
        SYNTAX INTEGER {
            none (0),
            defRDICCM (1),
            defMACstatus (2),
            defRemoteCCM (3),
            defErrorCCM (4),
            defXconCCM (5)
            }

    Dot1agCfmLowestAlarmPri ::= TEXTUAL-CONVENTION
        STATUS current
        DESCRIPTION
            "An integer value specifying the lowest priority defect
            that is allowed to generate a Fault Alarm (20.9.5), either:
            allDef(1) DefRDICCM, DefMACstatus, DefRemoteCCM,
            DefErrorCCM, and DefXconCCM;
            macRemErrXcon(2) Only DefMACstatus, DefRemoteCCM,
            DefErrorCCM, and DefXconCCM (default);
            remErrXcon(3) Only DefRemoteCCM, DefErrorCCM,
            and DefXconCCM;
            errXcon(4) Only DefErrorCCM and DefXconCCM;
            xcon(5) Only DefXconCCM; or
            noXcon(6) No defects DefXcon or lower are to be
            reported;
            "
        REFERENCE
            "802.1ag clause 12.14.7.1.3:k and 20.9.5"
        SYNTAX INTEGER {
            allDef (1),
            macRemErrXcon (2),
            remErrXcon (3),
            errXcon (4),
            xcon (5),
            noXcon (6)
            }

    Dot1agCfmSessionId ::= TEXTUAL-CONVENTION
        DISPLAY-HINT "d"
        STATUS current
        DESCRIPTION
            "Maintenance association End Point Identifier (MEPID): A small
            integer, unique over a given Maintenance Association,
            identifying a specific MEP.
            "
        REFERENCE
            "802.1ag clauses 3.19 and 19.2.1"
        SYNTAX Unsigned32 (1..8191)

    Dot1agCfmMhfCreation ::= TEXTUAL-CONVENTION
        STATUS current
        DESCRIPTION
            "Indicates if the Management Entity can create MHFs.
            The valid values are:
            defMHFnone(1) No MHFs can be created for this VID.
            defMHFdefault(2) MHFs can be created on this VID on any
            Bridge port through which this VID can
            pass.
            defMHFexplicit(3) MHFs can be created for this VID only on
            Bridge ports through which this VID can
            pass, and only if a MEP is created at some
            lower MD Level.
            defMHFdefer(4) The creation of MHFs is determined by the
            corresponding Maintenance Domain variable
            (dot1agCfmMaMhfCreation).
            "
        REFERENCE
            "802.1ag clause 12.14.5.1.3:c and 22.2.3"
        SYNTAX INTEGER {
            defMHFnone (1),
            defMHFdefault (2),
            defMHFexplicit (3),
            defMHFdefer (4)
            }

    Dot1agCfmIdPermission ::= TEXTUAL-CONVENTION
        STATUS current
        DESCRIPTION
            "Indicates what, if anything, is to be included in the Sender
            ID TLV transmitted in CCMs, LBMs, LTMs, and LTRs. The valid
            values are:
            sendIdNone(1) The Sender ID TLV is not to be sent.
            sendIdChassis(2) The Chassis ID Length, Chassis ID
            Subtype, and Chassis ID fields of the
            Sender ID TLV are to be sent.
            sendIdManage(3) The Management Address Length and
            Management Address of the Sender ID TLV
            are to be sent.
            sendIdChassisManage(4) The Chassis ID Length, Chassis ID
            Subtype, Chassis ID, Management Address
            Length and Management Address fields are
            all to be sent.
            sendIdDefer(5) The contents of the Sender ID TLV are
            determined by the corresponding
            Maintenance Domain variable
            (dot1agCfmMaIdPermission).
            "
        REFERENCE
            "802.1ag clause 12.14.6.1.3:d and 21.5.3"
        SYNTAX INTEGER {
            sendIdNone (1),
            sendIdChassis (2),
            sendIdManage (3),
            sendIdChassisManage (4),
            sendIdDefer (5)
            }

    Dot1agCfmCcmInterval ::= TEXTUAL-CONVENTION
        STATUS current
        DESCRIPTION
            "Indicates the interval at which CCMs are sent by a MEP.
            The possible values are:
            intervalInvalid(0) No CCMs are sent (disabled).
            interval300Hz(1) CCMs are sent every 3 1/3 milliseconds
            (300Hz).
            interval10ms(2) CCMs are sent every 10 milliseconds.
            interval100ms(3) CCMs are sent every 100 milliseconds.
            interval1s(4) CCMs are sent every 1 second.
            interval10s(5) CCMs are sent every 10 seconds.
            interval1min(6) CCMs are sent every minute.
            interval10min(7) CCMs are sent every 10 minutes.
            Note: enumerations start at zero to match the 'CCM Interval
            field' protocol field.
            "
        REFERENCE
            "802.1ag clauses 12.14.6.1.3:e, 20.8.1 and 21.6.1.3"
        SYNTAX INTEGER {
            intervalInvalid (0),
            interval300Hz (1),
            interval10ms (2),
            interval100ms (3),
            interval1s (4),
            interval10s (5),
            interval1min (6),
            interval10min (7)
            }

    Dot1agCfmFngState ::= TEXTUAL-CONVENTION
        STATUS current
        DESCRIPTION
            "Indicates the diferent states of the MEP Fault Notification
            Generator State Machine.
            fngReset(1) No defect has been present since the
            dot1agCfmMepFngResetTime timer
            expired, or since the state machine
            was last reset.
            fngDefect(2) A defect is present, but not for a
            long enough time to be reported
            (dot1agCfmMepFngAlarmTime).
            fngReportDefect(3) A momentary state during which the
            defect is reported by sending a
            dot1agCfmFaultAlarm notification,
            if that action is enabled.
            fngDefectReported(4) A defect is present, and some defect
            has been reported.
            fngDefectClearing(5) No defect is present, but the
            dot1agCfmMepFngResetTime timer has
            not yet expired.
            "
        REFERENCE
            "802.1ag clause 12.14.7.1.3:f and 20.35"
        SYNTAX INTEGER {
            fngReset (1),
            fngDefect (2),
            fngReportDefect (3),
            fngDefectReported (4),
            fngDefectClearing (5)
            }

    Dot1agCfmRelayActionFieldValue ::= TEXTUAL-CONVENTION
        STATUS current
        DESCRIPTION
            "Possible values the Relay action field can take."
        REFERENCE
            "802.1ag clauses 12.14.7.5.3:g, 20.36.2.5, 21.9.5, and Table 21-27"
        SYNTAX INTEGER {
            rlyHit (1),
            rlyFdb (2),
            rlyMpdb (3)
            }

    Dot1agCfmIngressActionFieldValue ::= TEXTUAL-CONVENTION
        STATUS current
        DESCRIPTION
            "Possible values returned in the ingress action field."
        REFERENCE
            "802.1ag clauses 12.14.7.5.3:g, 20.36.2.6, 21.9.8.1, and
            Table 21-30
            "
        SYNTAX INTEGER {
            ingOk (1),
            ingDown (2),
            ingBlocked (3),
            ingVid (4)
            }

    Dot1agCfmEgressActionFieldValue ::= TEXTUAL-CONVENTION
        STATUS current
        DESCRIPTION
            "Possible values returned in the egress action field"
        REFERENCE
            "802.1ag clauses 12.14.7.5.3:o, 20.36.2.10, 21.9.9.1, and
            Table 21-32"
        SYNTAX INTEGER {
            egrOK (1),
            egrDown (2),
            egrBlocked (3),
            egrVid (4)
            }

    Dot1afCfmIndexIntegerNextFree ::= TEXTUAL-CONVENTION
        DISPLAY-HINT "d"
        STATUS current
        DESCRIPTION
            "An integer which may be used as a new Index in a table.
            The special value of 0 indicates that no more new entries can
            be created in the relevant table.
            When a MIB is used for configuration, an object with this
            SYNTAX always contains a legal value (if non-zero) for an
            index that is not currently used in the relevant table. The
            Command Generator (Network Management Application) reads this
            variable and uses the (non-zero) value read when creating a
            new row with an SNMP SET. When the SET is performed, the
            Command Responder (agent) must determine whether the value is
            indeed still unused; Two Network Management Applications may
            attempt to create a row (configuration entry) simultaneously
            and use the same value. If it is currently unused, the SET
            succeeds and the Command Responder (agent) changes the value
            of this object, according to an implementation-specific
            algorithm. If the value is in use, however, the SET fails.
            The Network Management Application must then re-read this
            variable to obtain a new usable value.
            An OBJECT-TYPE definition using this SYNTAX MUST specify the
            relevant table for which the object is providing this
            functionality.
            "
        SYNTAX Unsigned32 (0..4294967295)

    Dot1agCfmMepDefects ::= TEXTUAL-CONVENTION
        STATUS current
        DESCRIPTION
            "A MEP can detect and report a number of defects, and multiple
            defects can be present at the same time. These defects are:
            bDefRDICCM(1) A remote MEP is reported the RDI bit in its
            last CCM.
            bDefMACstatus(2) Either some remote MEP is reporting its
            Interface Status TLV as not isUp, or all remote
            MEPs are reporting a Port Status TLV that
            contains some value other than psUp.
            bDefRemoteCCM(3) The MEP is not receiving valid CCMs from at
            least one of the remote MEPs.
            bDefErrorCCM(4) The MEP has received at least one invalid CCM
            whose CCM Interval has not yet timed out.
            bDefXconCCM(5) The MEP has received at least one CCM from
            either another MAID or a lower MD Level whose
            CCM Interval has not yet timed out.
            "
        REFERENCE
            "802.1ag clauses 12.14.7.1.3:o, 12.14.7.1.3:p, 12.14.7.1.3:q,
            12.14.7.1.3:r, and 12.14.7.1.3:s."
        SYNTAX BITS {
            bDefInvalid(0),
            bDefRDICCM(1),
            bDefMACstatus(2),
            bDefRemoteCCM(3),
            bDefErrorCCM(4),
            bDefXconCCM(5)
            }

    Dot1agCfmLbrTransId ::= TEXTUAL-CONVENTION
        DISPLAY-HINT "d"
        STATUS current
        DESCRIPTION
            "Sequence number/transaction identifier received in
            a Loopback Reply."
        SYNTAX Unsigned32 (1..4294967295)

    Dot1agCfmClientLevel ::= TEXTUAL-CONVENTION
        DISPLAY-HINT "d"
        STATUS current
        DESCRIPTION
            "Value equal to MD Level. "
        SYNTAX Unsigned32 (0..7)


-- ******************************************************************
-- The Maintenance Domain Managed Object. This group contains all
-- the MIB objects used to maintain Maintenance Domains.
-- ******************************************************************
    dot1agCfmMdTableNextIndex OBJECT-TYPE
        SYNTAX Dot1afCfmIndexIntegerNextFree
        MAX-ACCESS read-only
        STATUS current
        DESCRIPTION
            "This object contains an unused value for dot1agCfmMdIndex in
            the dot1agCfmMdTable, or a zero to indicate that none exist.
            "
        ::= { dot1agCfmMd 1 }
-- ******************************************************************
-- The Maintenance Domain Table
-- ******************************************************************
    dot1agCfmMdTable OBJECT-TYPE
        SYNTAX SEQUENCE OF Dot1agCfmMdEntry
        MAX-ACCESS not-accessible
        STATUS current
        DESCRIPTION
            "The Maintenance Domain table. Each row in the table
            represents a different Maintenance Domain.
            A Maintenance Domain is described in 802.1ag (3.22) as the
            network or the part of the network for which faults in
            connectivity are to be managed. The boundary of a Maintenance
            Domain is defined by a set of DSAPs, each of which can become
            a point of connectivity to a service instance.
            "
        REFERENCE
            "802.1ag clauses 3.22 and 18.1"
        ::= { dot1agCfmMd 2 }

    dot1agCfmMdEntry OBJECT-TYPE
        SYNTAX Dot1agCfmMdEntry
        MAX-ACCESS not-accessible
        STATUS current
        DESCRIPTION
            "The Maintenance Domain table entry. This entry is not lost
            upon reboot. It is backed up by stable storage.
            "
        INDEX {dot1agCfmMdIndex }
        ::= { dot1agCfmMdTable 1 }

        
    Dot1agCfmMdEntry ::= SEQUENCE {
        dot1agCfmMdIndex Unsigned32,
        dot1agCfmMdFormat Dot1agCfmMaintDomainNameType,
        dot1agCfmMdName Dot1agCfmMaintDomainName,
        dot1agCfmMdMdLevel Dot1agCfmMDLevel,
        dot1agCfmMdMhfCreation Dot1agCfmMhfCreation,
        dot1agCfmMdMhfIdPermission Dot1agCfmIdPermission,
        dot1agCfmMdMaTableNextIndex Dot1afCfmIndexIntegerNextFree,
        dot1agCfmMdRowStatus RowStatus
        }

    dot1agCfmMdIndex OBJECT-TYPE
        SYNTAX Unsigned32(1..16)
        MAX-ACCESS not-accessible
        STATUS current
        DESCRIPTION
            "The index to the Maintenance Domain table.
            dot1agCfmMdTableNextIndex needs to be inspected to find an
            available index for row-creation.
            Referential integrity is required i.e. the index needs to be
            persistent upon a reboot or restart of a device. The index
            can never be reused for other Maintenance Domain. The index
            value should keep increasing up to the time that they wrap
            around. This is to facilitate access control based on OID.
            "
        ::= { dot1agCfmMdEntry 1 }

    dot1agCfmMdFormat OBJECT-TYPE
        SYNTAX Dot1agCfmMaintDomainNameType
        MAX-ACCESS read-only
        STATUS current
        DESCRIPTION
            "The type (and thereby format) of the Maintenance Domain Name."
        REFERENCE
            "802.1ag clause 21.6.5.1"
        DEFVAL { charString }
        ::= { dot1agCfmMdEntry 2 }

    dot1agCfmMdName OBJECT-TYPE
        SYNTAX Dot1agCfmMaintDomainName
        MAX-ACCESS read-only
        STATUS current
        DESCRIPTION
            "The Maintenance Domain name. The type/format of this object
            is determined by the value of the dot1agCfmMdNameType object.
            Each Maintenance Domain has unique name amongst all those
            used or available to a service provider or operator. It
            facilitates easy identification of administrative
            responsibility for each Maintenance Domain.
            Clause 3.24 defines a Maintenance Domain name as the
            identifier, unique over the domain for which CFM is to
            protect against accidental concatenation of Service
            Instances, of a particular Maintenance Domain.
            "
        REFERENCE
            "802.1ag clauses 3.24, 12.14.5, and 21.6.5.3"
        DEFVAL { "DEFAULT" }
        ::= { dot1agCfmMdEntry 3 }

    dot1agCfmMdMdLevel OBJECT-TYPE
        SYNTAX Dot1agCfmMDLevel
        MAX-ACCESS read-only
        STATUS current
        DESCRIPTION
            "The Maintenance Domain Level."
        REFERENCE
            "802.1ag clause 12.14.5.1.3:b"
        DEFVAL { 0 }
        ::= { dot1agCfmMdEntry 4 }

    dot1agCfmMdMhfCreation OBJECT-TYPE
        SYNTAX Dot1agCfmMhfCreation
        MAX-ACCESS read-only
        STATUS current
        DESCRIPTION
            "Enumerated value indicating whether the management entity can
            create MHFs (MIP Half Function) for this Maintenance Domain.
            "
        REFERENCE
            "802.1ag clause 12.14.5.1.3:c"
        DEFVAL { defMHFnone }
        ::= { dot1agCfmMdEntry 5 }

    dot1agCfmMdMhfIdPermission OBJECT-TYPE
        SYNTAX Dot1agCfmIdPermission
        MAX-ACCESS read-only
        STATUS current
        DESCRIPTION
            "Enumerated value indicating what, if anything, is to be
            included in the Sender ID TLV (21.5.3) transmitted by MPs
            configured in this Maintenance Domain. Since, in this
            variable, there is no encompassing Maintenance Domain, the
            value sendIdDefer takes the meaning of sendIdChassisManage.
            "
        REFERENCE
            "802.1ag clause 12.14.5.1.3:d"
        DEFVAL { sendIdNone }
        ::= { dot1agCfmMdEntry 6 }

    dot1agCfmMdMaTableNextIndex OBJECT-TYPE
        SYNTAX Dot1afCfmIndexIntegerNextFree
        MAX-ACCESS read-only
        STATUS current
        DESCRIPTION
            "Value to be used as the index of the MA table entries for
            this Maintenance Domain when the management entity wants to
            create a new row in the MA table.
            "
        ::= { dot1agCfmMdEntry 7 }

    dot1agCfmMdRowStatus OBJECT-TYPE
        SYNTAX RowStatus
        MAX-ACCESS read-only
        STATUS current
        DESCRIPTION
            "The status of the row.
            The writable columns in a row can not be changed if the row
            is active. All columns must have a valid value before a row
            can be activated.
            "
        ::= { dot1agCfmMdEntry 8 }

-- ******************************************************************
-- The Maintenance Association Object. This group contains all the
-- MIB objects used to read, create, modify, and delete Maintenance
-- Associations in the MIB.
-- ******************************************************************
-- ******************************************************************
-- The Maintenance Association (MA) Table
-- ******************************************************************
    dot1agCfmMaTable OBJECT-TYPE
        SYNTAX SEQUENCE OF Dot1agCfmMaEntry
        MAX-ACCESS not-accessible
        STATUS current
        DESCRIPTION
            "The Maintenance Association table. Each row in the table
            represents an MA. An MA is a set of MEPs, each configured
            with a single service instance.
            Creation of a Service Instance establishes a connectionless
            association among the selected DSAPs. Configuring a
            Maintenance association End Point (MEP) at each of the
            DSAPs creates a Maintenance Association (MA) to monitor
            that connectionless connectivity. The MA is identified by a
            Short MA Name that is unique within the Maintenance Domain
            and chosen to facilitate easy identification of the Service
            Instance. Together, the Maintenance Domain Name and the
            Short MA Name form the Maintenance Association Identifier
            (MAID) that is carried in CFM Messages to identify
            incorrect connectivity among Service Instances. A small
            integer, the Maintenance association End Point Identifier
            (MEPID), identifies each MEP among those configured on a
            single MA (802.1ag clauses 3.17 and 18.2).
            This table uses two indices, first index is the index of the
            Maintenance Domain table.
            The writable objects in this table need to be persistent
            upon reboot or restart of a device.
            "
        REFERENCE
            "802.1ag clause 18.2"
        ::= { dot1agCfmMa 1 }

    dot1agCfmMaEntry OBJECT-TYPE
        SYNTAX Dot1agCfmMaEntry
        MAX-ACCESS not-accessible
        STATUS current
        DESCRIPTION
            "The MA table entry."
        INDEX {dot1agCfmMdIndex, dot1agCfmMaIndex }
        ::= { dot1agCfmMaTable 1 }

    Dot1agCfmMaEntry ::= SEQUENCE {
        dot1agCfmMaIndex Unsigned32,
        dot1agCfmMaPrimaryVlanId VlanIdOrNone,
        dot1agCfmMaFormat Dot1agCfmMaintAssocNameType,
        dot1agCfmMaName Dot1agCfmMaintAssocName,
        dot1agCfmMaMhfCreation Dot1agCfmMhfCreation,
        dot1agCfmMaCompIdPermission Dot1agCfmIdPermission,
        dot1agCfmMaCcmInterval Dot1agCfmCcmInterval,
        dot1agCfmMaRowStatus RowStatus
        }

    dot1agCfmMaIndex OBJECT-TYPE
        SYNTAX Unsigned32(1..32)
        MAX-ACCESS not-accessible
        STATUS current
        DESCRIPTION
            "Index of the MA table dot1agCfmMdMaTableNextIndex needs to
            be inspected to find an available index for row-creation.
            "
        ::= { dot1agCfmMaEntry 1 }

    dot1agCfmMaPrimaryVlanId OBJECT-TYPE
        SYNTAX VlanIdOrNone
        MAX-ACCESS read-only
        STATUS current
        DESCRIPTION
            "The Primary VLAN ID with which the Maintenance Association is
            associated, or 0 if the MA is not attached to any VID. If
            the MA is associated with more than one VID, the
            dot1agCfmVlanTable lists them.
            "
        REFERENCE
            "802.1ag clause 12.14.6.1.3:b"
        ::= { dot1agCfmMaEntry 2 }

    dot1agCfmMaFormat OBJECT-TYPE
        SYNTAX Dot1agCfmMaintAssocNameType
        MAX-ACCESS read-only
        STATUS current
        DESCRIPTION
            "The type (and thereby format) of the Maintenance Association Name."
        REFERENCE
            "802.1ag clauses 21.6.5.4"
        ::= { dot1agCfmMaEntry 3 }

    dot1agCfmMaName OBJECT-TYPE
        SYNTAX Dot1agCfmMaintAssocName
        MAX-ACCESS read-only
        STATUS current
        DESCRIPTION
            "The Short Maintenance Association name. The type/format of
            this object is determined by the value of the
            dot1agCfmMaNameType object.
            "
        REFERENCE
            "802.1ag clauses 21.6.5.6, and Table 21-20"
        ::= { dot1agCfmMaEntry 4 }

    dot1agCfmMaMhfCreation OBJECT-TYPE
        SYNTAX Dot1agCfmMhfCreation
        MAX-ACCESS read-only
        STATUS current
        DESCRIPTION
            "Indicates if the Management entity can create MHFs (MIP Half
            Function) for this MA.
            "
        REFERENCE
            "802.1ag clause 12.14.6.1.3:c"
        DEFVAL { defMHFdefer }
        ::= { dot1agCfmMaEntry 5 }

    dot1agCfmMaCompIdPermission OBJECT-TYPE
        SYNTAX Dot1agCfmIdPermission
        MAX-ACCESS read-only
        STATUS current
        DESCRIPTION
            "Enumerated value indicating what, if anything, is to be
            included in the Sender ID TLV (21.5.3) transmitted by MPs
            configured in this MA.
            "
        REFERENCE
            "802.1ag clause 12.14.6.1.3:d"
        DEFVAL { sendIdDefer }
        ::= { dot1agCfmMaEntry 6 }

    dot1agCfmMaCcmInterval OBJECT-TYPE
        SYNTAX Dot1agCfmCcmInterval
        MAX-ACCESS read-only
        STATUS current
        DESCRIPTION
            "Interval between CCM transmissions to be used by all MEPs
            in the MA.
            "
        REFERENCE
            "802.1ag clause 12.14.6.1.3:e"
        DEFVAL { interval1s }
        ::= { dot1agCfmMaEntry 7 }

    dot1agCfmMaRowStatus OBJECT-TYPE
        SYNTAX RowStatus
        MAX-ACCESS read-only
        STATUS current
        DESCRIPTION
            "The status of the row.
            The writable columns in a row can not be changed if the row
            is active. All columns must have a valid value before a row
            can be activated.
            "
        ::= { dot1agCfmMaEntry 8 }


-- ******************************************************************
-- The list of known Vlanlist for a given MA
-- ******************************************************************
    dot1agCfmMaVlanListTable OBJECT-TYPE
        SYNTAX SEQUENCE OF Dot1agCfmMaVlanListEntry
        MAX-ACCESS not-accessible
        STATUS current
        DESCRIPTION
            "List of Vlan. "
        ::= { dot1agCfmMa 2 }

    dot1agCfmMaVlanListEntry OBJECT-TYPE
        SYNTAX Dot1agCfmMaVlanListEntry
        MAX-ACCESS not-accessible
        STATUS current
        DESCRIPTION
            "The known Vlan table entry."
        INDEX {dot1agCfmMdIndex,
               dot1agCfmMaIndex,
               dot1agCfmMaVlanListIdentifier
               }
        ::= { dot1agCfmMaVlanListTable 1 }

    Dot1agCfmMaVlanListEntry ::= SEQUENCE {
        dot1agCfmMaVlanListIdentifier VlanId,
        dot1agCfmMaVlanListRowStatus RowStatus
        }

    dot1agCfmMaVlanListIdentifier OBJECT-TYPE
        SYNTAX VlanId
        MAX-ACCESS not-accessible
        STATUS current
        DESCRIPTION
            "VlanId"
        ::= { dot1agCfmMaVlanListEntry 1 }

    dot1agCfmMaVlanListRowStatus OBJECT-TYPE
        SYNTAX RowStatus
        MAX-ACCESS read-only
        STATUS current
        DESCRIPTION
            "The status of the row. Read SNMPv2-TC (RFC1903) for an
            explanation of the possible values this object can take.
            "
        ::= { dot1agCfmMaVlanListEntry 2 }

-- ******************************************************************
-- The list of known MEPs for a given MA
-- ******************************************************************
    dot1agCfmMaMepListTable OBJECT-TYPE
        SYNTAX SEQUENCE OF Dot1agCfmMaMepListEntry
        MAX-ACCESS not-accessible
        STATUS current
        DESCRIPTION
            "List of MEPIDs (in any bridge) that belong to the same MA.
            Clause 12.14.6.1.3 specifies that a list of MEPIDs in all
            bridges in that MA, but since SNMP SMI does not allow to
            state in a MIB that an object in a table is an array, the
            information has to be stored in another table with two
            indices, being the first index, the index of the table that
            contains the list or array.
            "
        REFERENCE
            "802.1ag clause 12.14.6.1.3:g"
        ::= { dot1agCfmMa 3 }

    dot1agCfmMaMepListEntry OBJECT-TYPE
        SYNTAX Dot1agCfmMaMepListEntry
        MAX-ACCESS not-accessible
        STATUS current
        DESCRIPTION
            "The known MEPS table entry."
        INDEX {dot1agCfmMdIndex,
               dot1agCfmMaIndex,
               dot1agCfmMaMepListSessionId
               }
        ::= { dot1agCfmMaMepListTable 1 }

    Dot1agCfmMaMepListEntry ::= SEQUENCE {
        dot1agCfmMaMepListSessionId Dot1agCfmSessionId,
        dot1agCfmMaMepListRowStatus RowStatus
        }

    dot1agCfmMaMepListSessionId OBJECT-TYPE
        SYNTAX Dot1agCfmSessionId
        MAX-ACCESS not-accessible
        STATUS current
        DESCRIPTION
            "MEPID"
        REFERENCE
            "802.1ag clause 12.14.6.1.3:g"
        ::= { dot1agCfmMaMepListEntry 1 }

    dot1agCfmMaMepListRowStatus OBJECT-TYPE
        SYNTAX RowStatus
        MAX-ACCESS read-only
        STATUS current
        DESCRIPTION
            "The status of the row. Read SNMPv2-TC (RFC1903) for an
            explanation of the possible values this object can take.
            "
        ::= { dot1agCfmMaMepListEntry 2 }




-- ******************************************************************
-- The MEP Object. This object represents a Maintenance End
-- Point as described in 802.1ag document.
-- ******************************************************************
-- ******************************************************************
-- The MEP Table
-- ******************************************************************
    dot1agCfmMepTable OBJECT-TYPE
    SYNTAX SEQUENCE OF Dot1agCfmMepEntry
    MAX-ACCESS not-accessible
    STATUS current
    DESCRIPTION
        "The Maintenance Association End Point (MEP) table.
        Each row in the table represents a different MEP. A MEP is
        an actively managed CFM entity, associated with a specific
        DSAP of a Service Instance, which can generate and receive
        CFM PDUs and track any responses. It is an end point of a
        single Maintenance Association, and is an endpoint of a
        separate Maintenance Entity for each of the other MEPs in
        the same Maintenance Association (802.1ag clause 3.18).
        This table uses three indices. The first two indices are the
        indices of the Maintenance Domain and MA tables, the reason
        being that a MEP is always related to an MA and Maintenance
        Domain.
        The Transmit Loopback table. Entries in this table are
        created/removed at the same time than entries in the MEP
        table are created/removed.
        The MEP table also stores all the managed objects for sending
        LBM and LTM.
        *LBM Managed objects
        LBM Managed objects in the MEP table
        enables the management entity to initiate
        transmission of Loopback messages. It will signal the MEP
        that it should transmit some number of Loopback messages
        and detect the detection (or lack thereof) of the
        corresponding Loopback messages.
        Steps to use entries in this table:
        1) Wait for dot1agCfmMepTransmitLbmStatus value to be
        'ready'. To do this do this sequence:
        a. an SNMP GET for both SnmpSetSerialNo and
        dot1agCfmMepTransmitLbmStatus objects (in same SNMP
        PDU).
        b. Check if value for dot1agCfmMepTransmitLbmStatus is
        'ready'
        - if not, wait x seconds, go to step a above.
        - if yes, save the value of SnmpSetSerialNo and go
        to step 2) below
        2) Change dot1agCfmMepTransmitLbmStatus value from 'ready' to
        'notReady' to ensure no other management entity will use
        the service. In order to not disturb a possible other NMS
        do this by sending an SNMP SET for both SnmpSetSerialNo
        and dot1agCfmMepTransmitLbmStatus objects (in same SNMP
        PDU, and make sure SNmpSetSerialNo is the first varBind).
        For the SnmpSetSerialNo varBind, use the value that you
        obtained in step 1)a.. This ensures that two cooperating
        NMSes will not step on each others toes.
        3) Setup the different data to be sent (number of messages,
        optional TLVs,...).
        4) Record the current values of dot1agCfmMepLbrIn,
        dot1agCfmMepLbrInOutOfOrder, and dot1agCfmMepLbrBadMsdu.
        6) Change dot1agCfmMepTransmitLbmStatus value from 'notReady'
        to 'transmit' to initiate transmission of Loopback
        messages.
        7) Check the value of dot1agCfmMepTransmitLbmResultOK to
        find out if the operation was successfully initiated or
        not.
        8) Monitor the value of dot1agCfmMepTransmitLbmMessages.
        When it reaches 0, the last LBM has been transmitted.
        Wait an additional 5 seconds to ensure that all LBRs have
        been returned.
        9) Compare dot1agCfmMepLbrIn, dot1agCfmMepLbrInOutOfOrder,
        and dot1agCfmMepLbrBadMsdu to their old values from step
        4, above, to get the results of the test.
        10) Change the dot1agCfmMepTransmitLbmStatus value back to
        'ready' to allow other management entities to use the
        table.
        *LTM Managed objects
        The LTM Managed objects in the MEP table are used in a manner
        similar to that described for LBM transmission, above. Upon
        successfully initiating the transmission, the variables
        dot1agCfmMepTransmitLtmSeqNumber and
        dot1agCfmMepTransmitLtmEgressIdentifier return the information
        required to recover the results of the LTM from the
        dot1agCfmLtrTable.
        "
    REFERENCE
        "802.1ag clauses 12.14.7 and 19.2"
    ::= { dot1agCfmMep 1 }

    dot1agCfmMepEntry OBJECT-TYPE
        SYNTAX Dot1agCfmMepEntry
        MAX-ACCESS not-accessible
        STATUS current
        DESCRIPTION
            "The MEP table entry"
        INDEX {dot1agCfmMdIndex,
               dot1agCfmMaIndex,
               dot1agCfmSessionId
            }
        ::= { dot1agCfmMepTable 1 }

    Dot1agCfmMepEntry ::= SEQUENCE {
        dot1agCfmSessionId Dot1agCfmSessionId,
        dot1agCfmMepIfIndex InterfaceIndexOrZero,
        dot1agCfmMepDirection Dot1agCfmMpDirection,
        dot1agCfmMepPrimaryVid Unsigned32,
        dot1agCfmMepActive TruthValue,
        dot1agCfmMepFngState Dot1agCfmFngState,
        dot1agCfmMepCciEnabled TruthValue,
        dot1agCfmMepCcmLtmPriority Unsigned32,
        dot1agCfmMepMacAddress MacAddress,
        dot1agCfmMepLowPrDef Dot1agCfmLowestAlarmPri,
        dot1agCfmMepHighestPrDefect Dot1agCfmHighestDefectPri,
        dot1agCfmMepDefects Dot1agCfmMepDefects,
        dot1agCfmMepCciSentCcms Counter32,
        dot1agCfmMepId Unsigned32,
        dot1agCfmMepPortName DisplayString,
        dot1agCfmMepLbrIn Counter32,
        dot1agCfmMepLbrInOutOfOrder Counter32,
        dot1agCfmMepLbrBadMsdu Counter32,
        dot1agCfmMepLtmNextSeqNumber Unsigned32,
        dot1agCfmMepUnexpLtrIn Counter32,
        dot1agCfmMepLbrOut Counter32,
        dot1agCfmMepRowStatus RowStatus,
-- updated 2008-8-19
        dot1agCfmMepCcCheckFlag TruthValue,
        dot1agCfmMepclientLevel Dot1agCfmClientLevel,
        dot1agCfmMepAISEnableFlag TruthValue, 
        dot1agCfmMepLCKEnableFlag TruthValue,
        dot1agCfmMepNearLost Counter32, 
        dot1agCfmMepFarLost Counter32,
        dot1agCfmMepDaly Counter32,
        dot1agCfmMepDalyChg Counter32,
        dot1agCfmMepDLMEnableFlag TruthValue,
        dot1agCfmMepLMMEnableFlag TruthValue,
        dot1agCfmMepDMMEnableFlag TruthValue,
        dot1agCfmMep1DMEnableFlag TruthValue,
        dot1agCfmMepProcDMMEnableFlag TruthValue,
        dot1agCfmMepProc1DMEnableFlag TruthValue,
        dot1agCfmMepLMMRMepId Unsigned32,
        dot1agCfmMepLMMInterval Unsigned32,
        dot1agCfmMepLMMRequireTime Unsigned32,
        dot1agCfmMepDMMRMepId Unsigned32,
        dot1agCfmMepDMMInterval Unsigned32,
        dot1agCfmMepDMMRequireTime Unsigned32,
        dot1agCfmMepDMMFrameSize Unsigned32,
        dot1agCfmMep1DMRMepId Unsigned32,
        dot1agCfmMep1DMInterval Unsigned32,
        dot1agCfmMep1DMRequireTime Unsigned32,
        dot1agCfmMep1DMFrameSize Unsigned32,
        dot1agCfmMepProcDMMRMepId Unsigned32,
        dot1agCfmMepProcDMMInterval Unsigned32,
        dot1agCfmMepProcDMMFrameSize Unsigned32,
        dot1agCfmMepProc1DMRMepId Unsigned32,
        dot1agCfmMepProc1DMInterval Unsigned32,
        dot1agCfmMepProc1DMFrameSize Unsigned32,
        dot1agCfmMepAISInterval Unsigned32,
        dot1agCfmMepLCKInterval Unsigned32,
        dot1agCfmMepDLMCountOamFlag TruthValue,
        dot1agCfmMepLMMCountOamFlag TruthValue
        }

    dot1agCfmSessionId OBJECT-TYPE
        SYNTAX Dot1agCfmSessionId
        MAX-ACCESS not-accessible
        STATUS current
        DESCRIPTION
            "Integer that is unique among all the MEPs in the same MA.
            Other definition is: a small integer, unique over a given
            Maintenance Association, identifying a specific Maintenance
            association End Point (3.19).
            MEP Identifier is also known as the MEPID.
            "
        REFERENCE
            "802.1ag clauses 3.19, 19.2 and 12.14.7"
        ::= { dot1agCfmMepEntry 1 }

    dot1agCfmMepIfIndex OBJECT-TYPE
        SYNTAX InterfaceIndexOrZero
        MAX-ACCESS read-only
        STATUS current
        DESCRIPTION
            "This object is the interface index of the interface either a
            bridge port, or an aggregated IEEE 802.1 link within a bridge
            port, to which the MEP is attached.
            Upon a restart of the system, the system SHALL, if necessary,
            change the value of this variable so that it indexes the
            entry in the interface table with the same value of ifAlias
            that it indexed before the system restart. If no such
            entry exists, then the system SHALL set this variable to 0.
            "
        REFERENCE
            "802.1ag clause 12.14.7.1.3:b"
        ::= { dot1agCfmMepEntry 2 }

    dot1agCfmMepDirection OBJECT-TYPE
        SYNTAX Dot1agCfmMpDirection
        MAX-ACCESS read-only
        STATUS current
        DESCRIPTION
            "The direction in which the MEP faces on the Bridge port."
        REFERENCE
            "802.1ag clauses 12.14.7.1.3:c and 19.2"
        ::= { dot1agCfmMepEntry 3 }

    dot1agCfmMepPrimaryVid OBJECT-TYPE
        SYNTAX Unsigned32(0..4095)
        MAX-ACCESS read-only
        STATUS current
        DESCRIPTION
            "An integer indicating the Primary VID of the MEP, always
            one of the VIDs assigned to the MEP's MA. The value 0
            indicates that either the Primary VID is that of the
            MEP's MA, or that the MEP's MA is associated with no VID."
        REFERENCE
            "802.1ag clauses 12.14.7.1.3:d"
        DEFVAL { 0 }
        ::= { dot1agCfmMepEntry 4 }

    dot1agCfmMepActive OBJECT-TYPE
        SYNTAX TruthValue
        MAX-ACCESS read-only
        STATUS current
        DESCRIPTION
            "Administrative state of the MEP
            A Boolean indicating the administrative state of the MEP.
            True indicates that the MEP is to function normally, and
            false that it is to cease functioning."
        REFERENCE
            "802.1ag clauses 12.14.7.1.3:e and 20.9.1"
        DEFVAL { false }
        ::= { dot1agCfmMepEntry 5 }

    dot1agCfmMepFngState OBJECT-TYPE
        SYNTAX Dot1agCfmFngState
        MAX-ACCESS read-only
        STATUS current
        DESCRIPTION
            "Current state of the MEP Fault Notification Generator
            State Machine.
            "
        REFERENCE
            "802.1ag clauses 12.14.7.1.3:f and 20.35"
        DEFVAL { fngReset }
        ::= { dot1agCfmMepEntry 6 }

    dot1agCfmMepCciEnabled OBJECT-TYPE
        SYNTAX TruthValue
        MAX-ACCESS read-only
        STATUS current
        DESCRIPTION
            "If set to true, the MEP will generate CCM messages."
        REFERENCE
            "802.1ag clauses 12.14.7.1.3:g and 20.10.1"
        DEFVAL { false }
        ::= { dot1agCfmMepEntry 7 }

    dot1agCfmMepCcmLtmPriority OBJECT-TYPE
        SYNTAX Unsigned32 (0..7 | 255)
        MAX-ACCESS read-only
        STATUS current
        DESCRIPTION
            "The priority value for CCMs and LTMs transmitted by the MEP.
            Default Value in the highest priority value allowed to pass
            through the bridge port for any of this MEPs VIDs.
            The management entity can obtain the default value for this
            variable from the priority regeneration table by extracting the
            highest priority value in this table on this MEPs bridge port.
            (1 is lowest, then 2, then 0, then 3-7, 255 is an invalid value).
            "
        REFERENCE
            "802.1ag clause 12.14.7.1.3:h"
        ::= { dot1agCfmMepEntry 8 }

    dot1agCfmMepMacAddress OBJECT-TYPE
        SYNTAX MacAddress
        MAX-ACCESS read-only
        STATUS current
        DESCRIPTION
            "MAC address of the MEP."
        REFERENCE
            "802.1ag clause 12.14.7.1.3:i and 19.4"
        ::= { dot1agCfmMepEntry 9 }

    dot1agCfmMepLowPrDef OBJECT-TYPE
        SYNTAX Dot1agCfmLowestAlarmPri
        MAX-ACCESS read-only
        STATUS current
        DESCRIPTION
            "An integer value specifying the lowest priority defect
            that is allowed to generate fault alarm.
            "
        REFERENCE
            "802.1ag clause 12.14.7.1.3:k and 20.9.5 and Table 20-1"
        DEFVAL { macRemErrXcon }
        ::= { dot1agCfmMepEntry 10}

    dot1agCfmMepHighestPrDefect OBJECT-TYPE
        SYNTAX Dot1agCfmHighestDefectPri
        MAX-ACCESS read-only
        STATUS current
        DESCRIPTION
            "The highest priority defect that has been present since the
            MEPs Fault Notification Generator State Machine was last in
            the FNG_RESET state.
            "
        REFERENCE
            "802.1ag clause 12.14.7.1.3:n 20.33.9 and Table 21-1"
        ::= { dot1agCfmMepEntry 11 } 

    dot1agCfmMepDefects OBJECT-TYPE
        SYNTAX Dot1agCfmMepDefects
        MAX-ACCESS read-only
        STATUS current
        DESCRIPTION
            "A vector of Boolean error conditions from Table 20-1, any of
            which may be true:
            DefRDICCM(1)
            DefMACstatus(2)
            DefRemoteCCM(3)
            DefErrorCCM(4)
            DefXconCCM(5)
            "
        REFERENCE
            "802.1ag clauses 12.14.7.1.3:o, 12.14.7.1.3:p, 12.14.7.1.3:q,
            12.14.7.1.3:r, 12.14.7.1.3:s, 20.21.3, 20.23.3, 20.33.5,
            20.33.6, 20.33.7."
        ::= { dot1agCfmMepEntry 12 } 

    dot1agCfmMepCciSentCcms OBJECT-TYPE
        SYNTAX Counter32
        MAX-ACCESS read-only
        STATUS current
        DESCRIPTION
            "Total number of Continuity Check messages transmitted."
        REFERENCE
            "802.1ag clauses 12.14.7.1.3:w and 20.10.2"
        ::= { dot1agCfmMepEntry 13 } 

    dot1agCfmMepId OBJECT-TYPE
        SYNTAX Unsigned32
        MAX-ACCESS read-only
        STATUS current
        DESCRIPTION
            "Integer that is unique among all the MEPs in the same MA.
            Other definition is: a small integer, unique over a given
            Maintenance Association, identifying a specific Maintenance
            association End Point (3.18).
            MEP Identifier is also known as the MEPID.
            "
        REFERENCE
            "802.1ag clauses 3.18, 19.2 and 12.14.7"
        ::= { dot1agCfmMepEntry 14 } 

    dot1agCfmMepPortName OBJECT-TYPE
        SYNTAX DisplayString
        MAX-ACCESS read-only
        STATUS current
        DESCRIPTION
            "Name of interface on which mep reside."
        REFERENCE
            "802.1ag clause 12.14.7.1.3:b"
        ::= { dot1agCfmMepEntry 19 } 

    dot1agCfmMepLbrIn OBJECT-TYPE
        SYNTAX Counter32
        MAX-ACCESS read-only
        STATUS current
        DESCRIPTION
            "Total number of valid, in-order Loopback Replies received."
        REFERENCE
            "802.1ag clause 12.14.7.1.3:y and 20.31.1"
        ::= { dot1agCfmMepEntry 20 }

    dot1agCfmMepLbrInOutOfOrder OBJECT-TYPE
        SYNTAX Counter32
        MAX-ACCESS read-only
        STATUS current
        DESCRIPTION
            "The total number of valid, out-of-order Loopback Replies
            received.
            "
        REFERENCE
            "802.1ag clause 12.14.7.1.3:z and 20.31.1"
        ::= { dot1agCfmMepEntry 21 }

    dot1agCfmMepLbrBadMsdu OBJECT-TYPE
        SYNTAX Counter32
        MAX-ACCESS read-only
        STATUS current
        DESCRIPTION
            "(optional) The total number of LBRs received whose
            mac_service_data_unit did not match (except for the OpCode)
            that of the corresponding LBM (20.2.3).
            "
        REFERENCE
            "802.1ag clause 12.14.7.1.3:aa 20.2.3"
        ::= { dot1agCfmMepEntry 22}

    dot1agCfmMepLtmNextSeqNumber OBJECT-TYPE
        SYNTAX Unsigned32
        MAX-ACCESS read-only
        STATUS current
        DESCRIPTION
            "Next transaction identifier/sequence number to be sent in a
            Linktrace message. This sequence number can be zero because
            it wraps around.
            "
        REFERENCE
            "802.1ag clause 12.14.7.1.3:ab and 20.36.1"
        ::= { dot1agCfmMepEntry 23 }

    dot1agCfmMepUnexpLtrIn OBJECT-TYPE
        SYNTAX Counter32
        MAX-ACCESS read-only
        STATUS current
        DESCRIPTION
            "The total number of unexpected LTRs received (20.39.1)."
        REFERENCE
            "802.1ag clause 12.14.7.1.3:ac 20.39.1"
        ::= { dot1agCfmMepEntry 24 }

    dot1agCfmMepLbrOut OBJECT-TYPE
        SYNTAX Counter32
        MAX-ACCESS read-only
        STATUS current
        DESCRIPTION
            "Total number of Loopback Replies transmitted."
        REFERENCE
            "802.1ag clause 12.14.7.1.3:ad and 20.26.2"
        ::= { dot1agCfmMepEntry 25 } 

    dot1agCfmMepRowStatus OBJECT-TYPE
        SYNTAX RowStatus
        MAX-ACCESS read-only
        STATUS current
        DESCRIPTION
            "The status of the row.
            The writable columns in a row can not be changed if the row
            is active. All columns must have a valid value before a row
            can be activated.
            "
        ::= { dot1agCfmMepEntry 26 } 

-- update
    dot1agCfmMepCcCheckFlag OBJECT-TYPE
        SYNTAX TruthValue
        MAX-ACCESS read-only
        STATUS current
        DESCRIPTION
            "Mep cc check flag"
        DEFVAL { false }
        ::= { dot1agCfmMepEntry 27 }

    dot1agCfmMepclientLevel OBJECT-TYPE
        SYNTAX Dot1agCfmClientLevel
        MAX-ACCESS read-only
        STATUS current
        DESCRIPTION
            "ClientLevel: Mep Client-Level"
        ::= { dot1agCfmMepEntry 29 }

    dot1agCfmMepAISEnableFlag OBJECT-TYPE
        SYNTAX TruthValue
        MAX-ACCESS read-only
        STATUS current
        DESCRIPTION
            "AIS enable state"
        DEFVAL { false }
        ::= { dot1agCfmMepEntry 30 }

    dot1agCfmMepLCKEnableFlag OBJECT-TYPE
        SYNTAX TruthValue
        MAX-ACCESS read-only
        STATUS current
        DESCRIPTION
            "LCK enable state"
        DEFVAL { false }
        ::= { dot1agCfmMepEntry 31 } 

    dot1agCfmMepNearLost OBJECT-TYPE             --obsolete
        SYNTAX Counter32
        MAX-ACCESS read-only
        STATUS obsolete
        DESCRIPTION
            "Local loss rate "
        ::= { dot1agCfmMepEntry 36 } 
    dot1agCfmMepFarLost OBJECT-TYPE               --obsolete
        SYNTAX Counter32
        MAX-ACCESS read-only
        STATUS obsolete
        DESCRIPTION
            "Remote loss rate "
        ::= { dot1agCfmMepEntry 37 } 
--dm info
    dot1agCfmMepDaly OBJECT-TYPE                  --obsolete
        SYNTAX Counter32
        MAX-ACCESS read-only
        STATUS obsolete
        DESCRIPTION
            "Time delay "
        ::= { dot1agCfmMepEntry 38 } 
    dot1agCfmMepDalyChg OBJECT-TYPE                --obsolete
        SYNTAX Counter32
        MAX-ACCESS read-only
        STATUS obsolete
        DESCRIPTION
            "Time delay change "
        ::= { dot1agCfmMepEntry 40 }

-- LM info
    dot1agCfmMepDLMEnableFlag OBJECT-TYPE
        SYNTAX TruthValue
        MAX-ACCESS read-only
        STATUS current
        DESCRIPTION
            "DLM enable state"
        DEFVAL { false }
        ::= { dot1agCfmMepEntry  41} 

    dot1agCfmMepLMMEnableFlag OBJECT-TYPE
        SYNTAX TruthValue
        MAX-ACCESS read-only
        STATUS current
        DESCRIPTION
            "LMM enable state"
        DEFVAL { false }
        ::= { dot1agCfmMepEntry  42} 

    dot1agCfmMepDMMEnableFlag OBJECT-TYPE
        SYNTAX TruthValue
        MAX-ACCESS read-only
        STATUS current
        DESCRIPTION
            "DMM enable state"
        DEFVAL { false }
        ::= { dot1agCfmMepEntry  43} 

--jyt add 0518 for ITU 1731
    dot1agCfmMep1DMEnableFlag OBJECT-TYPE
        SYNTAX TruthValue
        MAX-ACCESS read-only
        STATUS current
        DESCRIPTION
            "1DM enable state"
        DEFVAL { false }
        ::= { dot1agCfmMepEntry  44} 

--zcy add 20130306 for ROSNG33
    dot1agCfmMepProcDMMEnableFlag OBJECT-TYPE
        SYNTAX TruthValue
        MAX-ACCESS read-only
        STATUS current
        DESCRIPTION
            "Proactive DMM enable state."
        DEFVAL { false }
        ::= { dot1agCfmMepEntry 45 }

    dot1agCfmMepProc1DMEnableFlag OBJECT-TYPE
        SYNTAX TruthValue
        MAX-ACCESS read-only
        STATUS current
        DESCRIPTION
            "Proactive 1DM enable state."
        DEFVAL { false }
        ::= { dot1agCfmMepEntry 46 }

    dot1agCfmMepLMMRMepId OBJECT-TYPE
        SYNTAX Unsigned32
        MAX-ACCESS read-only
        STATUS current
        DESCRIPTION
            "Maintenance association End Point Identifier of a remote MEP
            whose information from the MEP Database is to be returned.
            "
        ::= { dot1agCfmMepEntry 47 }

    dot1agCfmMepLMMInterval OBJECT-TYPE
        SYNTAX Unsigned32
        UNITS "seconds"
        MAX-ACCESS read-only
        STATUS current
        DESCRIPTION
            "Interval between LMM transmissions to be used by the MEP."
        DEFVAL { 1 }
        ::= { dot1agCfmMepEntry 48 }

    dot1agCfmMepLMMRequireTime OBJECT-TYPE
        SYNTAX Unsigned32
        UNITS "seconds"
        MAX-ACCESS read-only
        STATUS current
        DESCRIPTION
            "Require time of LMM function."
        ::= { dot1agCfmMepEntry 49 }

    dot1agCfmMepDMMRMepId OBJECT-TYPE
        SYNTAX Unsigned32
        MAX-ACCESS read-only
        STATUS current
        DESCRIPTION
            "Maintenance association End Point Identifier of a remote MEP
            whose information from the MEP Database is to be returned.
            "
        ::= { dot1agCfmMepEntry 50 }

    dot1agCfmMepDMMInterval OBJECT-TYPE
        SYNTAX Unsigned32
        UNITS "seconds"
        MAX-ACCESS read-only
        STATUS current
        DESCRIPTION
            "Interval between DMM transmissions to be used by the MEP."
        DEFVAL { 1 }
        ::= { dot1agCfmMepEntry 51 }

    dot1agCfmMepDMMRequireTime OBJECT-TYPE
        SYNTAX Unsigned32
        UNITS "seconds"
        MAX-ACCESS read-only
        STATUS current
        DESCRIPTION
            "Require time of DMM function."
        ::= { dot1agCfmMepEntry 52 }

    dot1agCfmMepDMMFrameSize OBJECT-TYPE
        SYNTAX Unsigned32
        UNITS "bytes"
        MAX-ACCESS read-only
        STATUS current
        DESCRIPTION
            "Frame size of DMM."
        DEFVAL { 64 }
        ::= { dot1agCfmMepEntry 53 }

    dot1agCfmMep1DMRMepId OBJECT-TYPE
        SYNTAX Unsigned32
        MAX-ACCESS read-only
        STATUS current
        DESCRIPTION
            "Maintenance association End Point Identifier of a remote MEP
            whose information from the MEP Database is to be returned.
            "
        ::= { dot1agCfmMepEntry 54 }

    dot1agCfmMep1DMInterval OBJECT-TYPE
        SYNTAX Unsigned32
        UNITS "seconds"
        MAX-ACCESS read-only
        STATUS current
        DESCRIPTION
            "Interval between 1DM transmissions to be used by the MEP."
        DEFVAL { 1 }
        ::= { dot1agCfmMepEntry 55 }

    dot1agCfmMep1DMRequireTime OBJECT-TYPE
        SYNTAX Unsigned32
        UNITS "seconds"
        MAX-ACCESS read-only
        STATUS current
        DESCRIPTION
            "Require time of 1DM function."
        ::= { dot1agCfmMepEntry 56 }

    dot1agCfmMep1DMFrameSize OBJECT-TYPE
        SYNTAX Unsigned32
        UNITS "bytes"
        MAX-ACCESS read-only
        STATUS current
        DESCRIPTION
            "Frame size of 1DM."
        DEFVAL { 64 }
        ::= { dot1agCfmMepEntry 57 }

    dot1agCfmMepProcDMMRMepId OBJECT-TYPE
        SYNTAX Unsigned32
        MAX-ACCESS read-only
        STATUS current
        DESCRIPTION
            "Maintenance association End Point Identifier of a remote MEP
            whose information from the MEP Database is to be returned.
            "
        ::= { dot1agCfmMepEntry 58 }

    dot1agCfmMepProcDMMInterval OBJECT-TYPE
        SYNTAX Unsigned32
        UNITS "seconds"
        MAX-ACCESS read-only
        STATUS current
        DESCRIPTION
            "Interval between DMM transmissions to be used by the MEP."
        DEFVAL { 1 }
        ::= { dot1agCfmMepEntry 59 }

    dot1agCfmMepProcDMMFrameSize OBJECT-TYPE
        SYNTAX Unsigned32
        UNITS "bytes"
        MAX-ACCESS read-only
        STATUS current
        DESCRIPTION
            "Frame size of DMM."
        DEFVAL { 64 }
        ::= { dot1agCfmMepEntry 60 }

    dot1agCfmMepProc1DMRMepId OBJECT-TYPE
        SYNTAX Unsigned32
        MAX-ACCESS read-only
        STATUS current
        DESCRIPTION
            "Maintenance association End Point Identifier of a remote MEP
            whose information from the MEP Database is to be returned.
            "
        ::= { dot1agCfmMepEntry 61 }

    dot1agCfmMepProc1DMInterval OBJECT-TYPE
        SYNTAX Unsigned32
        UNITS "seconds"
        MAX-ACCESS read-only
        STATUS current
        DESCRIPTION
            "Interval between 1DM transmissions to be used by the MEP."
        DEFVAL { 1 }
        ::= { dot1agCfmMepEntry 62 }

    dot1agCfmMepProc1DMFrameSize OBJECT-TYPE
        SYNTAX Unsigned32
        UNITS "bytes"
        MAX-ACCESS read-only
        STATUS current
        DESCRIPTION
            "Frame size of 1DM."
        DEFVAL { 64 }
        ::= { dot1agCfmMepEntry 63 }

    dot1agCfmMepAISInterval OBJECT-TYPE
        SYNTAX Unsigned32
        UNITS "seconds"
        MAX-ACCESS read-only
        STATUS current
        DESCRIPTION
            "Interval between AIS transmissions to be used by the MEP."
        DEFVAL { 1 }
        ::= { dot1agCfmMepEntry 64 }

    dot1agCfmMepLCKInterval OBJECT-TYPE
        SYNTAX Unsigned32
        UNITS "seconds"
        MAX-ACCESS read-only
        STATUS current
        DESCRIPTION
            "Interval between LCK transmissions to be used by the MEP."
        DEFVAL { 1 }
        ::= { dot1agCfmMepEntry 65 }

    dot1agCfmMepDLMCountOamFlag OBJECT-TYPE
        SYNTAX TruthValue
        MAX-ACCESS read-only
        STATUS current
        DESCRIPTION
            "Transmit and receive counters do not count the OAM frames
            transmitted or received by the MEP at the MEP's MEG Level
            normally. This flag set true provide rules of countting OAM
            frames at the MEP's MEG Level as below:
            A. For single-ended ETH-LM, both counters do not need to
            count on-demand OAM frames for ETH-LB, ETH-LT, ETH-LM,
            ETH-DM, and ETH-Test. Instead, proactive OAM frames for
            ETH-CC and ETH-APS need to be counted. For dual-ended
            ETH-LM, the counters do not need to count on-demand OAM
            frames for ETH-LB, ETH-LT, ETH-LM, ETH-DM, and ETH-Test
            and proactive OAM frames for ETH-CC. However, proactive
            OAM frames for ETH-APS need to be counted.
            B. As OAM frames for ETH-AIS and ETH-LCK are only sent in
            the defect conditions where the result of loss measurements
            is invalid, it is unnecessary to count these frames.
            "
        DEFVAL { false }
        ::= { dot1agCfmMepEntry 66 }

    dot1agCfmMepLMMCountOamFlag OBJECT-TYPE
        SYNTAX TruthValue
        MAX-ACCESS read-only
        STATUS current
        DESCRIPTION
            "Transmit and receive counters do not count the OAM frames
            transmitted or received by the MEP at the MEP's MEG Level
            normally. This flag set true provide rules of countting OAM
            frames at the MEP's MEG Level as below:
            A. For single-ended ETH-LM, both counters do not need to
            count on-demand OAM frames for ETH-LB, ETH-LT, ETH-LM,
            ETH-DM, and ETH-Test. Instead, proactive OAM frames for
            ETH-CC and ETH-APS need to be counted. For dual-ended
            ETH-LM, the counters do not need to count on-demand OAM
            frames for ETH-LB, ETH-LT, ETH-LM, ETH-DM, and ETH-Test
            and proactive OAM frames for ETH-CC. However, proactive
            OAM frames for ETH-APS need to be counted.
            B. As OAM frames for ETH-AIS and ETH-LCK are only sent in
            the defect conditions where the result of loss measurements
            is invalid, it is unnecessary to count these frames.
            "
        DEFVAL { false }
        ::= { dot1agCfmMepEntry 67 }


-- ******************************************************************
-- The Linktrace Reply Table
-- ******************************************************************
    dot1agCfmLtrTable OBJECT-TYPE
        SYNTAX SEQUENCE OF Dot1agCfmLtrEntry
        MAX-ACCESS not-accessible
        STATUS current
        DESCRIPTION
            "This table extends the MEP table and contains a list of
            Linktrace replies received by a specific MEP in response to
            a linktrace message.
            SNMP SMI does not allow to state in a MIB that an object in
            a table is an array. The solution is to take the index (or
            indices) of the first table and add one or more indices.
            "
        REFERENCE
            "802.1ag clause 12.14.7.5"
        ::= { dot1agCfmMep 2 }

    dot1agCfmLtrEntry OBJECT-TYPE
        SYNTAX Dot1agCfmLtrEntry
        MAX-ACCESS not-accessible
        STATUS current
        DESCRIPTION
            "The Linktrace Reply table entry."
        INDEX {
            dot1agCfmMdIndex,
            dot1agCfmMaIndex,
            dot1agCfmMepId,
            dot1agCfmLtrSeqNumber,
            dot1agCfmLtrReceiveOrder
            }
        ::= { dot1agCfmLtrTable 1 }

    Dot1agCfmLtrEntry ::= SEQUENCE {
        dot1agCfmLtrSeqNumber Unsigned32,
        dot1agCfmLtrReceiveOrder Unsigned32,
        dot1agCfmLtrTtl Unsigned32,
        dot1agCfmLtrForwarded TruthValue,
        dot1agCfmLtrTerminalMep TruthValue,
        dot1agCfmLtrLastEgressIdentifier OCTET STRING,
        dot1agCfmLtrNextEgressIdentifier OCTET STRING,
        dot1agCfmLtrRelay Dot1agCfmRelayActionFieldValue,
        dot1agCfmLtrIngress Dot1agCfmIngressActionFieldValue,
        dot1agCfmLtrIngressMac MacAddress,
        dot1agCfmLtrEgress Dot1agCfmEgressActionFieldValue,
        dot1agCfmLtrEgressMac MacAddress
        }

    dot1agCfmLtrSeqNumber OBJECT-TYPE
        SYNTAX Unsigned32 (0..4294967295)
        MAX-ACCESS not-accessible
        STATUS current
        DESCRIPTION
            "Transaction identifier/Sequence number returned by a previous
            transmit linktrace message command, indicating which LTM's
            response is going to be returned.
            "
        REFERENCE
            "802.1ag clause 12.14.7.5.2:b"
        ::= { dot1agCfmLtrEntry 1}

    dot1agCfmLtrReceiveOrder OBJECT-TYPE
        SYNTAX Unsigned32(1..4294967295)
        MAX-ACCESS not-accessible
        STATUS current
        DESCRIPTION
            "An index to distinguish among multiple LTRs with the same LTR
            Transaction Identifier field value.  dot1agCfmLtrReceiveOrder
            are assigned sequentially from 1, in the order that the
            Linktrace Initiator received the LTRs.
            "
        REFERENCE
            "802.1ag clause 12.14.7.5.2:c"
        ::= { dot1agCfmLtrEntry 2 }

    dot1agCfmLtrTtl OBJECT-TYPE
        SYNTAX Unsigned32 (0..255)
        MAX-ACCESS read-only
        STATUS current
        DESCRIPTION
            "TTL field value for a returned LTR."
        REFERENCE
            "802.1ag clause 12.14.7.5 and 20.36.2.2"
        ::= { dot1agCfmLtrEntry 3 }

    dot1agCfmLtrForwarded OBJECT-TYPE
        SYNTAX TruthValue
        MAX-ACCESS read-only
        STATUS current
        DESCRIPTION
            "Indicates if a LTM was forwarded by the responding MP, as
            returned in the 'FwdYes' flag of the flags field.
            "
        REFERENCE
            "802.1ag clauses 12.14.7.5.3:c and 20.36.2.1"
        ::= { dot1agCfmLtrEntry 4 }

    dot1agCfmLtrTerminalMep OBJECT-TYPE
        SYNTAX TruthValue
        MAX-ACCESS read-only
        STATUS current
        DESCRIPTION
            "A boolean value stating whether the forwarded LTM reached a
            MEP enclosing its MA, as returned in the Terminal MEP flag of
            the Flags field.
            "
        REFERENCE
            "802.1ag clauses 12.14.7.5.3:d and 20.36.2.1"
        ::= { dot1agCfmLtrEntry 5 }

    dot1agCfmLtrLastEgressIdentifier OBJECT-TYPE
        SYNTAX OCTET STRING (SIZE(8))
        MAX-ACCESS read-only
        STATUS current
        DESCRIPTION
            "An octet field holding the Last Egress Identifier returned
            in the LTR Egress Identifier TLV of the LTR.
            The Last Egress Identifier identifies the MEP Linktrace
            Initiator that originated, or the Linktrace Responder that
            forwarded, the LTM to which this LTR is the response. This
            is the same value as the Egress Identifier TLV of that LTM.
            "
        REFERENCE
            "802.1ag clauses 12.14.7.5.3:e and 20.36.2.3"
        ::= { dot1agCfmLtrEntry 6 }

    dot1agCfmLtrNextEgressIdentifier OBJECT-TYPE
        SYNTAX OCTET STRING (SIZE(8))
        MAX-ACCESS read-only
        STATUS current
        DESCRIPTION
            "An octet field holding the Next Egress Identifier returned
            in the LTR Egress Identifier TLV of the LTR. The Next Egress
            Identifier Identifies the Linktrace Responder that
            transmitted this LTR, and can forward the LTM to the next
            hop. This is the same value as the Egress Identifier TLV of
            the forwarded LTM, if any. If the FwdYes bit of the Flags
            field is false, the contents of this field are undefined,
            i.e. any value can be transmitted, and the field is ignored
            by the receiver.
            "
        REFERENCE
            "802.1ag clauses 12.14.7.5.3:f and 20.36.2.4"
        ::= { dot1agCfmLtrEntry 7 }

    dot1agCfmLtrRelay OBJECT-TYPE
        SYNTAX Dot1agCfmRelayActionFieldValue
        MAX-ACCESS read-only
        STATUS current
        DESCRIPTION
            "Value returned in the Relay Action field."
        REFERENCE
            "802.1ag clauses 12.14.7.5.3:g and 20.36.2.5"
        ::= { dot1agCfmLtrEntry 8 }

    dot1agCfmLtrIngress OBJECT-TYPE
        SYNTAX Dot1agCfmIngressActionFieldValue
        MAX-ACCESS read-only
        STATUS current
        DESCRIPTION
            "The value returned in the Ingress Action Field of the LTM."
        REFERENCE
            "802.1ag clauses 12.14.7.5.3:k and 20.36.2.6"
        ::= { dot1agCfmLtrEntry 9 }

    dot1agCfmLtrIngressMac OBJECT-TYPE
        SYNTAX MacAddress
        MAX-ACCESS read-only
        STATUS current
        DESCRIPTION
            "MAC address returned in the ingress MAC address field."
        REFERENCE
            "802.1ag clauses 12.14.7.5.3:l and 20.36.2.7"
        ::= { dot1agCfmLtrEntry 10 }

    dot1agCfmLtrEgress OBJECT-TYPE
        SYNTAX Dot1agCfmEgressActionFieldValue
        MAX-ACCESS read-only
        STATUS current
        DESCRIPTION
            "The value returned in the Egress Action Field of the LTM."
        REFERENCE
            "802.1ag clauses 12.14.7.5.3:o and 20.36.2.10"
        ::= { dot1agCfmLtrEntry 11 }

    dot1agCfmLtrEgressMac OBJECT-TYPE
        SYNTAX MacAddress
        MAX-ACCESS read-only
        STATUS current
        DESCRIPTION
            "MAC address returned in the egress MAC address field."
        REFERENCE
            "802.1ag clauses 12.14.7.5.3:p and 20.36.2.11"
        ::= { dot1agCfmLtrEntry 12 }


-- ******************************************************************
-- The RMEP Database Table
-- ******************************************************************
    dot1agCfmMepDbTable OBJECT-TYPE
        SYNTAX SEQUENCE OF Dot1agCfmMepDbEntry
        MAX-ACCESS not-accessible
        STATUS current
        DESCRIPTION
            "The MEP Database. A database, maintained by every MEP, that
            maintains received information about other MEPs in the
            Maintenance Domain.
            The SMI does not allow to state in a MIB that an object in
            a table is an array. The solution is to take the index (or
            indices) of the first table and add one or more indices.
            "
        REFERENCE
            "802.1ag clause 19.2.15"
        ::= { dot1agCfmMep 3 }

    dot1agCfmMepDbEntry OBJECT-TYPE
        SYNTAX Dot1agCfmMepDbEntry
        MAX-ACCESS not-accessible
        STATUS current
        DESCRIPTION
            "The MEP Database table entry."
        INDEX {dot1agCfmMdIndex,
               dot1agCfmMaIndex,
               dot1agCfmMepDbRSessionId
               }
        ::= { dot1agCfmMepDbTable 1 }

    Dot1agCfmMepDbEntry ::= SEQUENCE {
        dot1agCfmMepDbRSessionId Dot1agCfmSessionId,
        dot1agCfmMepDbMacAddress MacAddress,
        dot1agCfmMepDbRdi TruthValue,
        dot1agCfmMepDbNearLost Counter32, 
        dot1agCfmMepDbFarLost Counter32, 
        dot1agCfmMepDbDaly Counter32,
        dot1agCfmMepDbDalyChg Counter32,
        dot1agCfmMepDbProcDaly Counter32,
        dot1agCfmMepDbProcDalyChg Counter32
        }

    dot1agCfmMepDbRSessionId OBJECT-TYPE
        SYNTAX Dot1agCfmSessionId
        MAX-ACCESS not-accessible
        STATUS current
        DESCRIPTION
            "Maintenance association End Point Identifier of a remote MEP
            whose information from the MEP Database is to be returned.
            "
        REFERENCE
            "802.1ag clause 12.14.7.6.2:b"
        ::= { dot1agCfmMepDbEntry 1 }

    dot1agCfmMepDbMacAddress OBJECT-TYPE
        SYNTAX MacAddress
        MAX-ACCESS read-only
        STATUS current
        DESCRIPTION
            "The MAC address of the remote MEP."
        REFERENCE
            "802.1ag clause 12.14.7.6.3:d and 20.19.7"
        ::= { dot1agCfmMepDbEntry 2 }

    dot1agCfmMepDbRdi OBJECT-TYPE
        SYNTAX TruthValue
        MAX-ACCESS read-only
        STATUS current
        DESCRIPTION
            "State of the RDI bit in the last received CCM (true for
            RDI=1), or false if none has been received.
            "
        REFERENCE
            "802.1ag clauses 12.14.7.6.3:e and 20.19.2"
        ::= { dot1agCfmMepDbEntry 3 } 

    dot1agCfmMepDbNearLost OBJECT-TYPE
        SYNTAX Counter32
        MAX-ACCESS read-only
        STATUS current
        DESCRIPTION
            "Local loss rate "
        ::= { dot1agCfmMepDbEntry 4 } 

    dot1agCfmMepDbFarLost OBJECT-TYPE
        SYNTAX Counter32
        MAX-ACCESS read-only
        STATUS current
        DESCRIPTION
            "Remote loss rate "
        ::= { dot1agCfmMepDbEntry 5 } 

--dm info
    dot1agCfmMepDbDaly OBJECT-TYPE
        SYNTAX Counter32
        UNITS "nanoseconds"
        MAX-ACCESS read-only
        STATUS current
        DESCRIPTION
            "Time delay."
        ::= { dot1agCfmMepDbEntry 6 } 

    dot1agCfmMepDbDalyChg OBJECT-TYPE
        SYNTAX Counter32
        UNITS "nanoseconds"
        MAX-ACCESS read-only
        STATUS current
        DESCRIPTION
            "Time delay change."
        ::= { dot1agCfmMepDbEntry 7 } 

    dot1agCfmMepDbProcDaly OBJECT-TYPE
        SYNTAX Counter32
        UNITS "nanoseconds"
        MAX-ACCESS read-only
        STATUS current
        DESCRIPTION
            "Proactive time delay."
        ::= { dot1agCfmMepDbEntry 8 } 

    dot1agCfmMepDbProcDalyChg OBJECT-TYPE
        SYNTAX Counter32
        UNITS "nanoseconds"
        MAX-ACCESS read-only
        STATUS current
        DESCRIPTION
            "Proactive time delay change."
        ::= { dot1agCfmMepDbEntry 9 }


-- ******************************************************************
-- The LBR Database 
-- ******************************************************************
    dot1agCfmLbrInfo OBJECT IDENTIFIER ::= { dot1agCfmMep 4 }

    dot1agCfmLbrTransId OBJECT-TYPE
        SYNTAX Dot1agCfmLbrTransId
        MAX-ACCESS read-only
        STATUS current
        DESCRIPTION
            "Loopback Reply state"
        ::= { dot1agCfmLbrInfo 1 }

    dot1agCfmLbrPrintInfo OBJECT-TYPE
        SYNTAX DisplayString
        MAX-ACCESS read-only
        STATUS current
        DESCRIPTION
            "Loopback Reply state"
        ::= { dot1agCfmLbrInfo 2 }


-- ******************************************************************
-- The MIP Database Table 
-- ******************************************************************
    dot1agCfmMipTable OBJECT-TYPE
        SYNTAX SEQUENCE OF Dot1agCfmMipEntry
        MAX-ACCESS not-accessible
        STATUS current
        DESCRIPTION
            "MIP Table"
        REFERENCE
            "802.1ag clauses 12.14.7 and 19.2"
        ::= { dot1agCfmMep 5 }

    dot1agCfmMipEntry OBJECT-TYPE
        SYNTAX Dot1agCfmMipEntry
        MAX-ACCESS not-accessible
        STATUS current
        DESCRIPTION
            "The MIP table entry"
        INDEX {dot1agCfmMdIndex,
               dot1agCfmMaIndex,
               dot1agCfmMipSessionId
               }
        ::= { dot1agCfmMipTable 1 }

    Dot1agCfmMipEntry ::= SEQUENCE {
        dot1agCfmMipSessionId Unsigned32,
        dot1agCfmMipPortName DisplayString
        }

    dot1agCfmMipSessionId OBJECT-TYPE
        SYNTAX Unsigned32
        MAX-ACCESS read-only
        STATUS current
        DESCRIPTION
            "Session Id"
        ::= { dot1agCfmMipEntry 1 }

    dot1agCfmMipPortName OBJECT-TYPE
        SYNTAX DisplayString
        MAX-ACCESS read-only
        STATUS current
        DESCRIPTION
            "Mip Port Name"
        REFERENCE
            "802.1ag clause 12.14.7.1.3:b"
        ::= { dot1agCfmMipEntry 3 }


-- ******************************************************************
-- The GloPara Database 
-- ******************************************************************
    dot1agCfmGlobalIsEnable OBJECT-TYPE
        SYNTAX TruthValue
        MAX-ACCESS read-only
        STATUS current
        DESCRIPTION
            "CFM global state"
        ::= { dot1agCfmGloPara 1 }


-- ******************************************************************
-- The PW MIP Database Table 
-- ******************************************************************
    dot1agCfmPwMipTable OBJECT-TYPE
        SYNTAX SEQUENCE OF Dot1agCfmPwMipEntry
        MAX-ACCESS not-accessible
        STATUS current
        DESCRIPTION
            "PW MIP Table"
        ::= { dot1agCfmPwMip 1 }

    dot1agCfmPwMipEntry OBJECT-TYPE
        SYNTAX Dot1agCfmPwMipEntry
        MAX-ACCESS not-accessible
        STATUS current
        DESCRIPTION
            "The PW MIP table entry"
        INDEX { dot1agCfmPwMipPortName }
        ::= { dot1agCfmPwMipTable 1 }

    Dot1agCfmPwMipEntry ::= SEQUENCE {
        dot1agCfmPwMipPortName DisplayString,
        dot1agCfmPwMipLevel Unsigned32
        }

    dot1agCfmPwMipPortName OBJECT-TYPE
        SYNTAX DisplayString
        MAX-ACCESS read-only
        STATUS current
        DESCRIPTION
            "PW MIP port name"
        ::= { dot1agCfmPwMipEntry 1 }

    dot1agCfmPwMipLevel OBJECT-TYPE
        SYNTAX Unsigned32
        MAX-ACCESS read-only
        STATUS current
        DESCRIPTION
            "PW MIP level"
        ::= { dot1agCfmPwMipEntry 2 }

END
