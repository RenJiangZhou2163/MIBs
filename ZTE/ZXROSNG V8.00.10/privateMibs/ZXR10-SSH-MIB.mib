ZXR10-SSH-MIB DEFINITIONS ::= BEGIN

IMPORTS
        MODULE-IDENTITY, OBJECT-TYPE,
        enterprises, Unsigned32
                FROM SNMPv2-SMI;
    
    zxr10SSHMIB MODULE-IDENTITY
        LAST-UPDATED "201710251420Z"
        ORGANIZATION "ZTE Corporation"
        CONTACT-INFO
            "Chen wenbo
             Tel: +86-25-52870000 
             E-Mail: chen.wenbo@zte.com.cn"
        
        DESCRIPTION
            "The MIB module to describe the information for SSH"
             
        REVISION "201710251420Z"
        DESCRIPTION
            "Change MAX-ACCESS from read-only to read-write"
            
        REVISION "201405080000Z"  -- 2014-05-08 11:00
        DESCRIPTION
            " Initial version of this MIB module."

        ::= { zxr10RosngMIB 53 } 
               
    zte OBJECT IDENTIFIER ::= { enterprises 3902 }
    zxr10 OBJECT IDENTIFIER ::= { zte 3}
    zxr10RosngMIB OBJECT IDENTIFIER ::= { zxr10 6000}
        
    zxr10SSHGlobalObjects  OBJECT IDENTIFIER ::= { zxr10SSHMIB 1 }

    zxr10SSHServerState OBJECT-TYPE 
        SYNTAX   INTEGER
                  {
                     disable(1),
                     enable(2)
                  }
        MAX-ACCESS    read-write 
        STATUS        current 
        DESCRIPTION
           "SSH server state, disable(1), or enable(2)"  
        DEFVAL        {disable}
        ::= { zxr10SSHGlobalObjects 1 }
    
    zxr10SSHServerListenPort OBJECT-TYPE
        SYNTAX    Unsigned32(22|49152..65535)
        MAX-ACCESS  read-write
        STATUS  current
        DESCRIPTION
            "SSH listening port when SSH server is enable. "
        DEFVAL     {22}
        ::= { zxr10SSHGlobalObjects 2 }
                                           
    zxr10SSHServerVersion OBJECT-TYPE 
        SYNTAX   INTEGER
                  {
                     sshv1(1),
                     sshv2(2)
                  }   
        MAX-ACCESS    read-write 
        STATUS        current 
        DESCRIPTION
           "SSH server version, SSHv1(1) or SSHv2(2)"  
        DEFVAL        {sshv2}
        ::= { zxr10SSHGlobalObjects 3 }

    END
