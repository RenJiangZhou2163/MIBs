ZXR10-VRRP-EXT-MIB DEFINITIONS ::= BEGIN

 IMPORTS
     MODULE-IDENTITY, OBJECT-TYPE,
     NOTIFICATION-TYPE, Counter32,
     Integer32, enterprises
        FROM SNMPv2-SMI
     TEXTUAL-CONVENTION, RowStatus,
     MacAddress, TruthValue, TimeStamp, DisplayString
        FROM SNMPv2-TC
     MODULE-COMPLIANCE, OBJECT-GROUP,
     NOTIFICATION-GROUP
        FROM SNMPv2-CONF
     InetAddressType, InetAddress
        FROM INET-ADDRESS-MIB
     ifIndex
        FROM RFC1213-MIB;
     

 vrrpExtMIB  MODULE-IDENTITY
     LAST-UPDATED    "201502061424Z"
    ORGANIZATION    "ZTE Corporation."
    CONTACT-INFO
        "       Zhao yanhua
        Tel:    +86-25-52870000
        E-Mail: zhao.yanhua3@zte.com.cn
        "
     DESCRIPTION
         "This MIB describes objects used for managing Virtual Router
          Redundancy Protocol (VRRP) routers.
          This MIB Module is a supplement to the VRRP-MIB [RFC2787]."
     REVISION        "201502061424Z"
     DESCRIPTION
        "add:       zxr10VrrpOperPrimaryVIPType
                    zxr10VrrpOperPrimaryVIPAddr
        "     
     REVISION        "201311160223Z"
     DESCRIPTION
        "add:       zxr10VrrpVFCfgObjects
                    zxr10VrrpVFOperObjects
                    zxr10VrrpVFTrackManages
                    zxr10VrrpOperState
                    zxr10VrrpOperRunPriority
        "     
     REVISION        "201305021110Z"
     DESCRIPTION
        "modify:   add UNITS for
                   zxr10VrrpOperPreemptDelay
                   zxr10VrrpOperReloadDelay
                   zxr10VrrpOperStateLastChangeTime
                   zxr10VrrpOperMasterAdverInterval
                   zxr10VrrpOperMasterDownInterval                       
                   delete DisplayString ::= OCTET STRING,imports it                   
                   delete hyphen for enumerated label of vrrpTrackState               
        "
     REVISION        "201304251110Z"
     DESCRIPTION
        "modify:    below nodes modified from read-write to read-only
                    zxr10VrrpOperTimerLearnMode
                    zxr10VrrpOperPreemptMode
                    zxr10VrrpOperPreemptDelay
                    zxr10VrrpOperPrivateAdvInterval
                    zxr10VrrpOperVersion
                    zxr10VrrpOperCfgPriority
                    zxr10VrrpOperAcceptMode
                    zxr10VrrpOperBackupRouteMode
                    zxr10VrrpOperCheckTtlMode
                    zxr10VrrpOperOutInterface1
                    zxr10VrrpOperOutInterface2
                    zxr10VrrpOperOutInterface3
                    zxr10VrrpOperReloadDelay
                    zxr10VrrpOperPktSendMode         
        "
     REVISION        "201304151110Z"
     DESCRIPTION
        "modify:    fix tool check problems
                    DESCRIPTION of vrrpExtMIB 
                    rename the 4th object of vrrpExtMIBCompliance
                    DESCRIPTION of zxr10VrrpExtOperEntry
        "
     REVISION        "201303191130Z"
     DESCRIPTION
        "add:       zxr10VrrpTrackInterPolicy
                    zxr10VrrpExtOperTable
        "
     REVISION "201004170000Z" 
     DESCRIPTION "Initial version as published in RFC 2787."
     ::= { zxr10 108}
     
     zte OBJECT IDENTIFIER ::= { enterprises 3902 }
     zxr10 OBJECT IDENTIFIER ::= { zte 3}

-- *******************************************************************
--  Textual Conventions
-- *******************************************************************

 VrId ::= TEXTUAL-CONVENTION
     STATUS       current
     DESCRIPTION
         "A number which, along with an interface index (ifIndex),
         serves to uniquely identify a virtual router on a given VRRP
         router. A set of one or more associated addresses is assigned
         to a VRID."
     SYNTAX      Integer32 (1..255)

-- *******************************************************************
--  VRRP MIB Groups
-- *******************************************************************

 vrrpTrackManages         OBJECT IDENTIFIER ::= { vrrpExtMIB 1 }
 vrrpGroupManages         OBJECT IDENTIFIER ::= { vrrpExtMIB 2 }
 vrrpExtConformance       OBJECT IDENTIFIER ::= { vrrpExtMIB 3 }
 zxr10VrrpExtOperObjects  OBJECT IDENTIFIER ::= { vrrpExtMIB 4 }
 zxr10VrrpVFCfgObjects    OBJECT IDENTIFIER ::= { vrrpExtMIB 5 }
 zxr10VrrpVFOperObjects   OBJECT IDENTIFIER ::= { vrrpExtMIB 6 }
 zxr10VrrpVFTrackManages  OBJECT IDENTIFIER ::= { vrrpExtMIB 7 }

-- *******************************************************************
--  Start of MIB objects
-- *******************************************************************

-- *******************************************************************
--  VRRP Track Interface Table
-- *******************************************************************

 vrrpTrackInterTable OBJECT-TYPE
     SYNTAX       SEQUENCE OF VrrpTrackInterEntry
     MAX-ACCESS   not-accessible
     STATUS       current
     DESCRIPTION
         "Tracking interface table for a VRRP router which consists of a
          sequence (i.e., one or more conceptual rows) of
          'VrrpTrackInterEntry' items."
     ::= { vrrpTrackManages 1 }

 vrrpTrackInterEntry OBJECT-TYPE
     SYNTAX       VrrpTrackInterEntry
     MAX-ACCESS   not-accessible
     STATUS       current
     DESCRIPTION
         "An entry in the vrrpTrackInterTable containing the tracking
          characteristics of a virtual router. On a VRRP router,
          a given virtual router is identified by a combination
          of the IF index and VRID. Rows in the table cannot be modified."
     INDEX  {
                vrrpTrackInterStandByIfIdx,
                vrrpTrackInterVrid,
                vrrpTrackInterIfIdx
            }
     ::= { vrrpTrackInterTable 1 }

 VrrpTrackInterEntry ::=
     SEQUENCE {
         vrrpTrackInterState
             INTEGER,
         vrrpTrackInterPriReduce
             Integer32,         
         vrrpTrackInterOperRowStatus
             RowStatus,
         vrrpTrackInterStandByIfIdx
             Integer32,
         vrrpTrackInterVrid
             VrId,         
         vrrpTrackInterIfIdx
            Integer32,
        zxr10VrrpTrackInterPolicy
            INTEGER
 }
 
 vrrpTrackInterState OBJECT-TYPE
    SYNTAX          INTEGER
                    {
         up(1),
         down(2)
     }
     MAX-ACCESS   read-only
     STATUS       current

     DESCRIPTION
         "The current state of the tracked interface. This object has
         two defined values:
           - `up', which indicates the protocol status of the tracked interface.
           - `down', which indicates the protocol status of the tracked interface."
      ::= { vrrpTrackInterEntry 1 }
 
 vrrpTrackInterPriReduce OBJECT-TYPE
     SYNTAX       Integer32 (0..254)
     MAX-ACCESS   read-only
     STATUS       current
     DESCRIPTION
         "This object specifies the priority to be reduced when 
          the tracked interface is down.
         A priority of '0', indicates not set the reduced priority."
     DEFVAL { 10 }
     ::= { vrrpTrackInterEntry 2 }

 vrrpTrackInterOperRowStatus OBJECT-TYPE
     SYNTAX       RowStatus
     MAX-ACCESS   read-only
     STATUS       current
     DESCRIPTION
         "The row status variable, used in accordance to installation
         and removal conventions for conceptual rows. The rowstatus of
         a currently active row in the VrrpTrackInterTable is constrained
         by the tracking state of the corresponding virtual router.
         When `VrrpTrackInterOperRowStatus' is set to active(1), no other
         objects in the conceptual row. 

         To create a row in this table, a manager sets this object
         to either createAndGo(4) or createAndWait(5). Until instances
         of all corresponding columns are appropriately configured,
        the value of the corresponding instance of the
        `VrrpTrackInterOperRowStatus' column will be read as notReady(3).

         In particular, a newly created row cannot be made active(1)
        until (minimally) the corresponding instance of `VrrpTrackInterVrid'
        has been set and there is at least one active row in the
        `VrrpTrackInterTable' tracking a interface for the virtual router."
     ::= { vrrpTrackInterEntry 3 }

 vrrpTrackInterStandByIfIdx OBJECT-TYPE
     SYNTAX       Integer32
     MAX-ACCESS   not-accessible
     STATUS       current
     DESCRIPTION
         "The interface index of VRRP groups."
     ::= { vrrpTrackInterEntry 4 }
     
 vrrpTrackInterVrid OBJECT-TYPE
     SYNTAX       VrId
     MAX-ACCESS   not-accessible
     STATUS       current
     DESCRIPTION
        "This object contains the Virtual Router Identifier (VRID) of the
        tracked interface."
     ::= { vrrpTrackInterEntry 5 }

 vrrpTrackInterIfIdx OBJECT-TYPE
     SYNTAX       Integer32
     MAX-ACCESS   not-accessible
     STATUS       current
     DESCRIPTION
         "The index of the tracked interface."
     ::= { vrrpTrackInterEntry 6 }  

zxr10VrrpTrackInterPolicy OBJECT-TYPE
    SYNTAX          INTEGER { priorityDecrement(1), rapidDown(2) }
    MAX-ACCESS      read-only
    STATUS          current
    DESCRIPTION
        "The policy of tracking interface."
    ::= { vrrpTrackInterEntry 7 }

-- *******************************************************************
--  VRRP Track Table
-- *******************************************************************

 vrrpTrackTable OBJECT-TYPE
     SYNTAX       SEQUENCE OF VrrpTrackEntry
     MAX-ACCESS   not-accessible
     STATUS       current
     DESCRIPTION
         "The table of VRRP track associated with this virtual router."
     ::= { vrrpTrackManages 2 }

 vrrpTrackEntry OBJECT-TYPE
     SYNTAX       VrrpTrackEntry
     MAX-ACCESS   not-accessible
     STATUS       current
     DESCRIPTION
         "An entry in the table contains an VRRP track that is
         associated with a virtual router. The number of rows for
         a given ifIndex and VrId will equal the number of VRRP track
         associated by the virtual router.

         Rows in the table cannot be modified."
     INDEX    { ifIndex, VrId, vrrpTrackName }
     ::= { vrrpTrackTable 1 }

 VrrpTrackEntry ::=
     SEQUENCE {         
         vrrpTrackType
             INTEGER,
         vrrpDetectType
             DisplayString,
         vrrpPolicyType
             INTEGER,
         vrrpTrackPriReduce
             Integer32,
         vrrpTrackState
             INTEGER,         
         vrrpTrackOperRowStatus
             RowStatus,
         vrrpTrackName
             DisplayString,
         vrrpTrackVrid
             VrId,
         vrrpTrackStandByIfIdx
             Integer32    
 }
      
 vrrpTrackType OBJECT-TYPE
     SYNTAX INTEGER {
         object(1),
         group(2)
     }
     MAX-ACCESS   read-only
     STATUS       current
     DESCRIPTION
         "The type of tracking for a virtual router."
     ::= { vrrpTrackEntry 1 }
     
 vrrpDetectType OBJECT-TYPE
     SYNTAX       DisplayString
     MAX-ACCESS   read-only
     STATUS       current
     DESCRIPTION
         "The type of VRRP track detect for a virtual router."
     ::= { vrrpTrackEntry 2 }
     
 vrrpPolicyType OBJECT-TYPE
     SYNTAX INTEGER {
         normal(1),
         link(2),
         peer(3)
     }
     MAX-ACCESS   read-only
     STATUS       current
     DESCRIPTION
         "The type of VRRP track policy for a virtual router."
     ::= { vrrpTrackEntry 3 }
     
 vrrpTrackPriReduce OBJECT-TYPE
     SYNTAX       Integer32
     MAX-ACCESS   read-only
     STATUS       current
     DESCRIPTION
         "The assigned reduced priority when VRRP track down for a virtual
         router."
     ::= { vrrpTrackEntry 4 }
 
 vrrpTrackState OBJECT-TYPE
    SYNTAX INTEGER {
         up(1),
         localdown(2),
         transdown(3),
         localsd(4),
         transsd(5),
         unknown(6)
     }     
     MAX-ACCESS   read-only
     STATUS       current
     DESCRIPTION
         "The VRRP track state for a virtual router."
     ::= { vrrpTrackEntry 5 }
     
 vrrpTrackOperRowStatus OBJECT-TYPE
     SYNTAX       RowStatus
     MAX-ACCESS   read-only
     STATUS       current
     DESCRIPTION
         "The row status variable, used in accordance to installation
         and removal conventions for conceptual rows. The rowstatus of
         a currently active row in the vrrpTrackTable is constrained
         by the tracking state of the corresponding virtual router.
         When `vrrpTrackOperRowStatus' is set to active(1), no other
         objects in the conceptual row.

         To create a row in this table, a manager sets this object
         to either createAndGo(4) or createAndWait(5). Until instances
         of all corresponding columns are appropriately configured,
         the value of the corresponding instance of the `vrrpTrackOperRowStatus'
         column will be read as notReady(3).

         In particular, a newly created row cannot be made active(1)
         until (minimally) the corresponding instance of
         `VrrpTrackName' has been set and there is at least one active
         row in the `VrrpTrackTable'."
     ::= { vrrpTrackEntry 6 }
     
 vrrpTrackName OBJECT-TYPE
     SYNTAX       DisplayString
     MAX-ACCESS   not-accessible
     STATUS       current
     DESCRIPTION
         "The name of VRRP track for a virtual router."
     ::= { vrrpTrackEntry 7 }
     
 vrrpTrackVrid OBJECT-TYPE
     SYNTAX       VrId
     MAX-ACCESS   not-accessible
     STATUS       current
     DESCRIPTION
         "This object contains the Virtual Router Identifier (VRID) of the
         VRRP track."
     ::= { vrrpTrackEntry 8 }

 vrrpTrackStandByIfIdx OBJECT-TYPE
     SYNTAX       Integer32
     MAX-ACCESS   not-accessible
     STATUS       current
     DESCRIPTION
         "The interface index of VRRP groups."
     ::= { vrrpTrackEntry 9 } 

-- *******************************************************************
--  VRRP Group Manages
-- *******************************************************************

-- *******************************************************************
--  VRRP Group Manage Table
-- *******************************************************************

 vrrpManageCfgTable OBJECT-TYPE
     SYNTAX       SEQUENCE OF VrrpManageCfgEntry
     MAX-ACCESS   not-accessible
     STATUS       current
     DESCRIPTION
         "Table of virtual router manage."
     ::= { vrrpGroupManages 1 }

 vrrpManageCfgEntry OBJECT-TYPE
     SYNTAX       VrrpManageCfgEntry
     MAX-ACCESS   not-accessible
     STATUS       current
     DESCRIPTION
         "An entry in the table, containing manage information
         about a given virtual router."
     INDEX    { mVrrpCfgIfIndex, mVrrpCfgVRID }
     ::= { vrrpManageCfgTable 1 }

 VrrpManageCfgEntry ::=
     SEQUENCE {
         mCfgOperRowStatus
             RowStatus,
         mVrrpCfgIfIndex
             Integer32,
         mVrrpCfgVRID
             Integer32                  
     }
     
 mCfgOperRowStatus OBJECT-TYPE
     SYNTAX       RowStatus
     MAX-ACCESS   read-only
     STATUS       current
     DESCRIPTION
         "The row status variable, used according to installation
         and removal conventions for conceptual rows. Setting this
         object to active(1) or createAndGo(4) results in the
         addition of an associated address for a virtual router.
         Destroying the entry or setting it to notInService(2)
         removes the manage info from the virtual router.
         The use of other values is implementation-dependent."
     ::= { vrrpManageCfgEntry 1 }
     
 mVrrpCfgIfIndex OBJECT-TYPE
     SYNTAX       Integer32
     MAX-ACCESS   not-accessible
     STATUS       current
     DESCRIPTION
         "The interface index of manage VRRP groups."
     ::= { vrrpManageCfgEntry 2 }
     
 mVrrpCfgVRID OBJECT-TYPE
     SYNTAX       Integer32
     MAX-ACCESS   not-accessible
     STATUS       current
     DESCRIPTION
         "The vrid of the manage VRRP groups."
     ::= { vrrpManageCfgEntry 3 } 
 
-- *******************************************************************
--  VRRP Group Member Table
-- *******************************************************************

 vrrpMemberCfgTable OBJECT-TYPE
     SYNTAX       SEQUENCE OF VrrpMemberCfgEntry
     MAX-ACCESS   not-accessible
     STATUS       current
     DESCRIPTION
         "The member table of the VRRP manage group."
     ::= { vrrpGroupManages 2 }

 vrrpMemberCfgEntry OBJECT-TYPE
     SYNTAX       VrrpMemberCfgEntry
     MAX-ACCESS   not-accessible
     STATUS       current
     DESCRIPTION
         "An entry in the table, containing member information
         about a given virtual router manage group."
     INDEX    { memberIfIndex, memberVRID, mVrrpIfIndex, mVrrpVRID }
     ::= { vrrpMemberCfgTable 1 }

 VrrpMemberCfgEntry ::=
     SEQUENCE {
         cfgOperRowStatus
             RowStatus,
         memberIfIndex
             Integer32,
         memberVRID
             Integer32,
         mVrrpIfIndex
             Integer32,
         mVrrpVRID
             Integer32         
     }
     
 cfgOperRowStatus OBJECT-TYPE
     SYNTAX       RowStatus
     MAX-ACCESS   read-only
     STATUS       current
     DESCRIPTION
         "The row status variable, used according to installation
         and removal conventions for conceptual rows. Setting this
         object to active(1) or createAndGo(4) results in the
         addition of a member group for a virtual router manage group.
         Destroying the entry or setting it to notInService(2)
         removes the member group from the virtual router manage group.
         The use of other values is implementation-dependent."
     ::= { vrrpMemberCfgEntry 1 }
     
 memberIfIndex OBJECT-TYPE
     SYNTAX       Integer32
     MAX-ACCESS   not-accessible
     STATUS       current
     DESCRIPTION
         "The member interface index of virtual router manage group."
     ::= { vrrpMemberCfgEntry 2 }
     
 memberVRID OBJECT-TYPE
     SYNTAX       Integer32
     MAX-ACCESS   not-accessible
     STATUS       current
     DESCRIPTION
         "The member vrid of virtual router manage group"
     ::= { vrrpMemberCfgEntry 3 }
     
 mVrrpIfIndex OBJECT-TYPE
     SYNTAX       Integer32
     MAX-ACCESS   not-accessible
     STATUS       current
     DESCRIPTION
         "The interface index of the virtual router manage group."
     ::= { vrrpMemberCfgEntry 4 }   
     
 mVrrpVRID OBJECT-TYPE
     SYNTAX       Integer32
     MAX-ACCESS   not-accessible
     STATUS       current
     DESCRIPTION
         "The vrid of the virtual router manage group."
     ::= { vrrpMemberCfgEntry 5 }    

-- *******************************************************************
--   Trap Definitions
-- *******************************************************************
 
-- *******************************************************************
--  Conformance Information
-- *******************************************************************

 vrrpExtMIBCompliances  OBJECT IDENTIFIER ::= { vrrpExtConformance 1 }
 vrrpExtMIBGroups       OBJECT IDENTIFIER ::= { vrrpExtConformance 2 }

-- ...................................................................
-- Compliance Statements
-- ...................................................................

 vrrpExtMIBCompliance MODULE-COMPLIANCE
     STATUS current
     DESCRIPTION
        "The core compliance statement for all VRRP implementations."
     MODULE -- this module
     MANDATORY-GROUPS  {
         vrrpExtendTrackInterGroup,
         vrrpExtendTrackGroup,
         vrrpManageCfgGroup,
         vrrpMemberCfgGroup
     }

     ::= { vrrpExtMIBCompliances 1 }

-- ...................................................................
-- Conformance Groups
-- ...................................................................

 vrrpExtendTrackInterGroup  OBJECT-GROUP
     OBJECTS  {
         vrrpTrackInterState,
         vrrpTrackInterPriReduce,
         vrrpTrackInterOperRowStatus
         }
     STATUS current
     DESCRIPTION
        "Conformance group for VRRP track interface operations."
     ::= { vrrpExtMIBGroups 1 }

 vrrpExtendTrackGroup  OBJECT-GROUP
     OBJECTS  {         
         vrrpTrackType,
         vrrpDetectType,
         vrrpPolicyType,
         vrrpTrackPriReduce,
         vrrpTrackState,
         vrrpTrackOperRowStatus
         }
     STATUS current
     DESCRIPTION
        "Conformance group for VRRP tracking operations."
     ::= { vrrpExtMIBGroups 2 }

 vrrpManageCfgGroup  OBJECT-GROUP
     OBJECTS  {
         mCfgOperRowStatus         
         }
     STATUS current
     DESCRIPTION
        "Conformance group for VRRP manage operations."
     ::= { vrrpExtMIBGroups 3 }
 
 vrrpMemberCfgGroup  OBJECT-GROUP
     OBJECTS  {
         cfgOperRowStatus         
         }
     STATUS current
     DESCRIPTION
        "Conformance group for VRRP member operations."
     ::= { vrrpExtMIBGroups 4 }

-- *******************************************************************
--  VRRP Extend Operations Table
-- *******************************************************************

zxr10VrrpExtOperTable OBJECT-TYPE
    SYNTAX       SEQUENCE OF Zxr10VrrpExtOperEntry
    MAX-ACCESS   not-accessible
    STATUS       current
    DESCRIPTION
        "Extend operations table for a VRRP router which consists
        of a sequence (i.e., one or more conceptual rows) of
        'zxr10VrrpExtOperEntry' items."

    ::= { zxr10VrrpExtOperObjects 1 }

zxr10VrrpExtOperEntry OBJECT-TYPE
    SYNTAX       Zxr10VrrpExtOperEntry
    MAX-ACCESS   not-accessible
    STATUS       current
    DESCRIPTION
        "An entry in the zxr10VrrpExtOperTable containing the private
        operational characteristics of a virtual router. On a VRRP
        router, a given virtual router is identified by a combination
        of the IF index and VRID."

     INDEX    { zxr10VrrpOperIfIndex, zxr10VrrpOperVrId }
    ::= { zxr10VrrpExtOperTable 1 }

Zxr10VrrpExtOperEntry ::=
     SEQUENCE {
         zxr10VrrpOperIfIndex
            Integer32,
         zxr10VrrpOperVrId
             VrId,
         zxr10VrrpOperTimerLearnMode
             TruthValue,
         zxr10VrrpOperPreemptMode
             TruthValue,
         zxr10VrrpOperPreemptDelay
             Integer32,
         zxr10VrrpOperPrivateAdvInterval
             Integer32,
         zxr10VrrpOperVersion
             INTEGER,
         zxr10VrrpOperCfgPriority
             Integer32,
         zxr10VrrpOperAcceptMode
             TruthValue,
         zxr10VrrpOperBackupRouteMode
             TruthValue,
         zxr10VrrpOperCheckTtlMode
             TruthValue,
         zxr10VrrpOperOutInterface1
             OCTET STRING,
         zxr10VrrpOperOutInterface2
             OCTET STRING,
         zxr10VrrpOperOutInterface3
             OCTET STRING,
         zxr10VrrpOperReloadDelay
             Integer32,
         zxr10VrrpOperPktSendMode
             INTEGER,
         zxr10VrrpOperStateChangeNum
             Integer32,
         zxr10VrrpOperStateLastChangeTime
             TimeStamp,
         zxr10VrrpOperMasterIpAddrType
             InetAddressType,
         zxr10VrrpOperMasterIpAddr
             InetAddress,
         zxr10VrrpOperMasterRunPriority
             Integer32,
         zxr10VrrpOperMasterAdverInterval
             Integer32,
         zxr10VrrpOperMasterDownInterval
             Integer32,
         zxr10VrrpOperState
             INTEGER,
         zxr10VrrpOperRunPriority
             Integer32,
         zxr10VrrpOperPrimaryVIPType
             InetAddressType,
         zxr10VrrpOperPrimaryVIPAddr
             InetAddress
 }

zxr10VrrpOperIfIndex OBJECT-TYPE
    SYNTAX       Integer32
    MAX-ACCESS   not-accessible
    STATUS       current
    DESCRIPTION
        "This object contains the interface index of VRRP group."
    ::= { zxr10VrrpExtOperEntry 1 }

zxr10VrrpOperVrId OBJECT-TYPE
    SYNTAX       VrId
    MAX-ACCESS   not-accessible
    STATUS       current
    DESCRIPTION
        "This object contains the Virtual Router Identifier (VRID)."
    ::= { zxr10VrrpExtOperEntry 2 }

zxr10VrrpOperTimerLearnMode OBJECT-TYPE
    SYNTAX       TruthValue
    MAX-ACCESS   read-only
    STATUS       current
    DESCRIPTION
        "The current learn mode state of the virtual router. This object has
        two defined values:

        - `true', which indicates that the virtual router is
         set the learn mode.

        - `false', which indicates the virtual router is
         not set the learn mode."
    DEFVAL       { false }
    ::= { zxr10VrrpExtOperEntry 3 }

zxr10VrrpOperPreemptMode OBJECT-TYPE
    SYNTAX       TruthValue
    MAX-ACCESS   read-only
    STATUS       current
    DESCRIPTION
        "The current preempt state of the virtual router. This object has
        two defined values:

        - `true', which indicates that the virtual router is
         set the preempt mode.

        - `false', which indicates the virtual router is
         not set the preempt mode."
    DEFVAL       { true }
    ::= { zxr10VrrpExtOperEntry 4 }

zxr10VrrpOperPreemptDelay OBJECT-TYPE
    SYNTAX       Integer32(0..3600)
    UNITS        "seconds"
    MAX-ACCESS   read-only
    STATUS       current
    DESCRIPTION
        "The current set preempt delay time of the virtual router."
    DEFVAL       { 0 }
    ::= { zxr10VrrpExtOperEntry 5 }

zxr10VrrpOperPrivateAdvInterval OBJECT-TYPE
    SYNTAX       Integer32 (50..40000)
     UNITS        "milliseconds"
    MAX-ACCESS   read-only
    STATUS       current
    DESCRIPTION
        "The time interval, in milliseconds, between sending
        advertisement messages. Only the master router sends
        VRRP advertisements."
    DEFVAL       { 1000 }
    ::= { zxr10VrrpExtOperEntry 6 }

zxr10VrrpOperVersion OBJECT-TYPE
    SYNTAX       INTEGER {
         v2(2),
         v3(3)
     }
    MAX-ACCESS   read-only
    STATUS       current
    DESCRIPTION
        "The version of VRRP protocol."
    ::= { zxr10VrrpExtOperEntry 7 }

zxr10VrrpOperCfgPriority OBJECT-TYPE
    SYNTAX       Integer32(1..254)
    MAX-ACCESS   read-only
    STATUS       current
    DESCRIPTION
        "The actual configured priority which was used for the
        virtual router master election process. Higher values imply
        higher priority."
    DEFVAL       { 100 }
    ::= { zxr10VrrpExtOperEntry 8 }

zxr10VrrpOperAcceptMode OBJECT-TYPE
    SYNTAX       TruthValue
    MAX-ACCESS   read-only
    STATUS       current
    DESCRIPTION
        "Controls whether a virtual router in Master state will accept
        packets addressed to the address owner's IPvX address as its
        own if it is not the IPvX address owner."
    DEFVAL       { true }
    ::= { zxr10VrrpExtOperEntry 9 }

zxr10VrrpOperBackupRouteMode OBJECT-TYPE
    SYNTAX       TruthValue
    MAX-ACCESS   read-only
    STATUS       current
    DESCRIPTION
        "Controls whether a virtual router in Backup state will forward
        packets addressed to virtual mac address."
    ::= { zxr10VrrpExtOperEntry 10 }

zxr10VrrpOperCheckTtlMode OBJECT-TYPE
    SYNTAX       TruthValue
    MAX-ACCESS   read-only
    STATUS       current
    DESCRIPTION
        "Controls whether a virtual router verify that the IPv4 TTL or the
        IPv6 hop limit to 255."
    DEFVAL       { true }
    ::= { zxr10VrrpExtOperEntry 11 }

zxr10VrrpOperOutInterface1 OBJECT-TYPE
    SYNTAX       OCTET STRING
    MAX-ACCESS   read-only
    STATUS       current
    DESCRIPTION
        "The first interface of the virtual router sent the vrrp packets."
    ::= { zxr10VrrpExtOperEntry 12 }

zxr10VrrpOperOutInterface2 OBJECT-TYPE
    SYNTAX       OCTET STRING
    MAX-ACCESS   read-only
    STATUS       current
    DESCRIPTION
        "The second interface of the virtual router sent the vrrp packets."
    ::= { zxr10VrrpExtOperEntry 13 }

zxr10VrrpOperOutInterface3 OBJECT-TYPE
    SYNTAX       OCTET STRING
    MAX-ACCESS   read-only
    STATUS       current
    DESCRIPTION
        "The third interface of the virtual router sent the vrrp packets."
    ::= { zxr10VrrpExtOperEntry 14 }

zxr10VrrpOperReloadDelay OBJECT-TYPE
    SYNTAX       Integer32(0..65535)
    UNITS        "seconds"
    MAX-ACCESS   read-only
    STATUS       current
    DESCRIPTION
        "The time that an instance of the state machine for virtual router
        delays to run when the interface starts up, in seconds."
    DEFVAL       { 0 }
    ::= { zxr10VrrpExtOperEntry 15 }

zxr10VrrpOperPktSendMode OBJECT-TYPE
    SYNTAX       INTEGER {
         all(1),
         rotation(2)
     }
    MAX-ACCESS   read-only
    STATUS       current
    DESCRIPTION
        "The send mode that a virtual router in Master state sends VRRP
        advertisement packets from out-interface.

        - `all', which indicates that the virtual will send advertisement
        packets from all out-interfaces each time.

        - `rotation', which indicates that the virtual will send advertisement
        packets from all out-interfaces in rotation."
    DEFVAL       { all }
    ::= { zxr10VrrpExtOperEntry 16 }

zxr10VrrpOperStateChangeNum OBJECT-TYPE
    SYNTAX       Integer32
    MAX-ACCESS   read-only
    STATUS       current
    DESCRIPTION
        "The numbers of the virtual router changing state."
    ::= { zxr10VrrpExtOperEntry 17 }

zxr10VrrpOperStateLastChangeTime OBJECT-TYPE
    SYNTAX       TimeStamp
    UNITS        "ticks"
    MAX-ACCESS   read-only
    STATUS       current
    DESCRIPTION
        "The time that the state of a virtual router changed last time."
    ::= { zxr10VrrpExtOperEntry 18 }

zxr10VrrpOperMasterIpAddrType OBJECT-TYPE
   SYNTAX       InetAddressType
   MAX-ACCESS   read-only
   STATUS       current
   DESCRIPTION
       "The IP address type of zxr10VrrpOperMasterIpAddr.
       ipv4(1) and ipv6(2) are the only two values supported
       in this MIB module."
   ::= { zxr10VrrpExtOperEntry 19 }

zxr10VrrpOperMasterIpAddr OBJECT-TYPE
    SYNTAX       InetAddress
    MAX-ACCESS   read-only
    STATUS       current
    DESCRIPTION
        "The master router's real (primary) IP address. This is
        the IP address listed as the source in VRRP advertisement
        last received by this virtual router."
    ::= { zxr10VrrpExtOperEntry 20 }

zxr10VrrpOperMasterRunPriority OBJECT-TYPE
    SYNTAX       Integer32
    MAX-ACCESS   read-only
    STATUS       current
    DESCRIPTION
        "The actual running priority of the virtual router in Master state."
    ::= { zxr10VrrpExtOperEntry 21 }

zxr10VrrpOperMasterAdverInterval OBJECT-TYPE
    SYNTAX       Integer32
    UNITS        "milliseconds"
    MAX-ACCESS   read-only
    STATUS       current
    DESCRIPTION
        "The time interval of Master sending advertisements."
    ::= { zxr10VrrpExtOperEntry 22 }

zxr10VrrpOperMasterDownInterval OBJECT-TYPE
    SYNTAX       Integer32
    UNITS        "milliseconds"
    MAX-ACCESS   read-only
    STATUS       current
    DESCRIPTION
        "Time interval for Backup to declare Master down."
    ::= { zxr10VrrpExtOperEntry 23 }

zxr10VrrpOperState OBJECT-TYPE
     SYNTAX       INTEGER {
         initialize(1),
         backup(2),
         master(3)
     }
     MAX-ACCESS   read-only
     STATUS       current

     DESCRIPTION
         "The current state of the virtual router. This object has
         three defined values:

           - `initialize', which indicates that all the
             virtual router is waiting for a startup event.

           - `backup', which indicates the virtual router is
             monitoring the availability of the master router.

           - `master', which indicates that the virtual router
             is forwarding packets for IP addresses that are
             associated with this router."

     ::= { zxr10VrrpExtOperEntry 24 }

zxr10VrrpOperRunPriority OBJECT-TYPE
     SYNTAX       Integer32
     MAX-ACCESS   read-only
     STATUS       current
     DESCRIPTION
         "The actual running priority of the virtual router."
     ::= { zxr10VrrpExtOperEntry 25 }

zxr10VrrpOperPrimaryVIPType OBJECT-TYPE
   SYNTAX       InetAddressType
   MAX-ACCESS   read-only
   STATUS       current
   DESCRIPTION
       "The IP address type of zxr10VrrpOperPrimaryVIPAddr.
       ipv4(1) and ipv6(2) are the only two values supported
       in this MIB module."
   ::= { zxr10VrrpExtOperEntry 26 }

zxr10VrrpOperPrimaryVIPAddr OBJECT-TYPE
    SYNTAX       InetAddress
    MAX-ACCESS   read-only
    STATUS       current
    DESCRIPTION
        "The VRRP primary virtual IP address."
    ::= { zxr10VrrpExtOperEntry 27 }

-- *******************************************************************
--  VRRP VF(Virtual Forwarder) Configuration Table
-- *******************************************************************

zxr10VrrpVFCfgTable OBJECT-TYPE
    SYNTAX       SEQUENCE OF Zxr10VrrpVFCfgEntry
    MAX-ACCESS   not-accessible
    STATUS       current
    DESCRIPTION
        "Operation table for a VRRP virtual forwarder which consists
        of a sequence (i.e., one or more conceptual rows) of
        'zxr10VrrpVFCfgEntry' items."

    ::= { zxr10VrrpVFCfgObjects 1 }

zxr10VrrpVFCfgEntry OBJECT-TYPE
    SYNTAX       Zxr10VrrpVFCfgEntry
    MAX-ACCESS   not-accessible
    STATUS       current
    DESCRIPTION
        "An entry in the zxr10VrrpVFCfgTable containing the private
        informative characteristics of a virtual forwarder. On a VRRP
        router, a given virtual router is identified by a combination
        of the IF name, VRID."

     INDEX    { zxr10VrrpVFCfgIfName, zxr10VrrpVFCfgVrId}
    ::= { zxr10VrrpVFCfgTable 1 }

Zxr10VrrpVFCfgEntry ::=
     SEQUENCE {
         zxr10VrrpVFCfgIfName
             DisplayString,         
         zxr10VrrpVFCfgVrId
             VrId,         
         zxr10VrrpVFCfgOwnerID
             Integer32,
         zxr10VrrpVFCfgFwdWeight
             Integer32,
         zxr10VrrpVFCfgLowWeight
             Integer32,
         zxr10VrrpVFCfgPreemptEnable
             TruthValue,
         zxr10VrrpVFCfgPreemptDelay
             Integer32,
         zxr10VrrpVFCfgRedirectTime
             Integer32,
         zxr10VrrpVFCfgTimeOut
             Integer32,
         zxr10VrrpVFCfgRunMode
             INTEGER,
         zxr10VrrpVFCfgPolicy
             INTEGER,
         zxr10VrrpVFCfgFwdDelay
             Integer32,
         zxr10VrrpVFCfgIfIndex
             Integer32
 }
   
 zxr10VrrpVFCfgIfName OBJECT-TYPE
    SYNTAX       DisplayString(SIZE(1..31))
    MAX-ACCESS   not-accessible
    STATUS       current
    DESCRIPTION
        "This object contains the interface name of VRRP groups."
    ::= { zxr10VrrpVFCfgEntry 1 }

zxr10VrrpVFCfgVrId OBJECT-TYPE
    SYNTAX       VrId
    MAX-ACCESS   not-accessible
    STATUS       current
    DESCRIPTION
        "This object contains the Virtual Router Identifier (VRID)."
    ::= { zxr10VrrpVFCfgEntry 2 }

zxr10VrrpVFCfgOwnerID OBJECT-TYPE
    SYNTAX       Integer32
    MAX-ACCESS   read-only
    STATUS       current
    DESCRIPTION
        "This object contains the Virtual Forwarder Identifier (VFID)."
    ::= { zxr10VrrpVFCfgEntry 3 }

zxr10VrrpVFCfgFwdWeight OBJECT-TYPE
    SYNTAX       Integer32(1..255)
    MAX-ACCESS   read-only
    STATUS       current
    DESCRIPTION
        "The actual configured forward weight which was used for 
         the virtual forwarder election process. 
         Higher values imply higher weight."
    DEFVAL       { 100 }
    ::= { zxr10VrrpVFCfgEntry 4 }

zxr10VrrpVFCfgLowWeight OBJECT-TYPE
    SYNTAX       Integer32(1..254)
    MAX-ACCESS   read-only
    STATUS       current
    DESCRIPTION
        "This object specifies the invalid weight to be used for the
        virtual forwarder becomes unavailable. Higher values imply
        higher invalid weight."
    DEFVAL       { 1 }
    ::= { zxr10VrrpVFCfgEntry 5 }

zxr10VrrpVFCfgPreemptEnable OBJECT-TYPE
    SYNTAX       TruthValue
    MAX-ACCESS   read-only
    STATUS       current
    DESCRIPTION
        "The current preempt state of the virtual forwarder. This object has
        two defined values:

        - 'true', which indicates that the virtual forwarder is
         set the preempt mode.

        - 'false', which indicates the virtual forwarder is
         not set the preempt mode."
    DEFVAL       { true }
    ::= { zxr10VrrpVFCfgEntry 6 }

zxr10VrrpVFCfgPreemptDelay OBJECT-TYPE
    SYNTAX       Integer32(0..3600)
    UNITS        "seconds"
    MAX-ACCESS   read-only
    STATUS       current
    DESCRIPTION
        "The current set preempt delay time of the virtual forwarder."
    DEFVAL       { 0 }
    ::= { zxr10VrrpVFCfgEntry 7 }

zxr10VrrpVFCfgRedirectTime OBJECT-TYPE
    SYNTAX       Integer32(1..3600)
    UNITS        "seconds"
    MAX-ACCESS   read-only
    STATUS       current
    DESCRIPTION
        "The redirect time of virtual forwarder which is in TakeOver state."
    DEFVAL       { 600 }
    ::= { zxr10VrrpVFCfgEntry 8 }

zxr10VrrpVFCfgTimeOut OBJECT-TYPE
    SYNTAX       Integer32(600..64800)
    UNITS        "seconds"
    MAX-ACCESS   read-only
    STATUS       current
    DESCRIPTION
        "The aging time of virtual forwarder which is in TakeOver state."
    DEFVAL       { 14400 }
    ::= { zxr10VrrpVFCfgEntry 9 }

zxr10VrrpVFCfgRunMode OBJECT-TYPE
    SYNTAX       INTEGER {
           standard(1),
           balance(2)
       }
    MAX-ACCESS   read-only
    STATUS       current
    DESCRIPTION
        "The current running mode of the virtual router. This object has
        two defined values:

        - 'standard', which indicates that the virtual router is
         working on the standard mode.

        - 'balance', which indicates the virtual router is
         working on the balance mode."
    DEFVAL       { standard }
    ::= { zxr10VrrpVFCfgEntry 10 }

zxr10VrrpVFCfgPolicy OBJECT-TYPE
    SYNTAX       INTEGER {
           roundRobin(1),
           weighted(2),
           hostDependent(3)           
       }
    MAX-ACCESS   read-only
    STATUS       current
    DESCRIPTION
        "The current balance policy of the virtual router. This object has
        three defined values:

        - 'roundRobin', which indicates that the virtual router is
         set round robin policy.

        - 'weighted', which indicates the virtual router is
         set weighted policy.
        
        - 'hostDependent', which indicates the virtual router is
         set host dependent policy."
    DEFVAL       { roundRobin }
    ::= { zxr10VrrpVFCfgEntry 11 }

zxr10VrrpVFCfgFwdDelay OBJECT-TYPE
    SYNTAX       Integer32(0..1800)
    UNITS        "seconds"
    MAX-ACCESS   read-only
    STATUS       current
    DESCRIPTION
        "The forwarding delay time of virtual forwarder."
    DEFVAL       { 0 }
    ::= { zxr10VrrpVFCfgEntry 12 }
    
zxr10VrrpVFCfgIfIndex OBJECT-TYPE
    SYNTAX       Integer32
    MAX-ACCESS   read-only
    STATUS       current
    DESCRIPTION
        "This object contains the interface index of VRRP groups."
    ::= { zxr10VrrpVFCfgEntry 13 }

-- *******************************************************************
--  VRRP VF(Virtual Forwarder) Operation Table
-- *******************************************************************

zxr10VrrpVFOperTable OBJECT-TYPE
    SYNTAX       SEQUENCE OF Zxr10VrrpVFOperEntry
    MAX-ACCESS   not-accessible
    STATUS       current
    DESCRIPTION
        "Operation table for a VRRP virtual forwarder which consists
        of a sequence (i.e., one or more conceptual rows) of
        'zxr10VrrpVFOperEntry' items."

    ::= { zxr10VrrpVFOperObjects 1 }

zxr10VrrpVFOperEntry OBJECT-TYPE
    SYNTAX       Zxr10VrrpVFOperEntry
    MAX-ACCESS   not-accessible
    STATUS       current
    DESCRIPTION
        "An entry in the zxr10VrrpVFOperTable containing the private
        informative characteristics of a virtual forwarder. On a VRRP
        router, a given virtual forwarder is identified by a combination
        of the IF name, VRID and VFID."

     INDEX    { zxr10VrrpVFOperIfName, zxr10VrrpVFOperVrId, zxr10VrrpVFOperVFID}
    ::= { zxr10VrrpVFOperTable 1 }

Zxr10VrrpVFOperEntry ::=
     SEQUENCE {
         zxr10VrrpVFOperIfName
             DisplayString,          
         zxr10VrrpVFOperVrId
             VrId,
         zxr10VrrpVFOperVFID
             Integer32,
         zxr10VrrpVFOperRunWeight
             Integer32,
         zxr10VrrpVFOperVFState
             INTEGER,
         zxr10VrrpVFOperVFMac
             MacAddress,
         zxr10VrrpVFOperRunPriority
             Integer32,
         zxr10VrrpVFOperIpAddrType
             InetAddressType,
         zxr10VrrpVFOperIpAddr
             InetAddress,
         zxr10VrrpVFOperLocation
             INTEGER,
         zxr10VrrpVFOperVFNum
             Integer32,
         zxr10VrrpVFOperIfIndex
             Integer32
 }

zxr10VrrpVFOperIfName OBJECT-TYPE
    SYNTAX       DisplayString(SIZE(1..31))
    MAX-ACCESS   not-accessible
    STATUS       current
    DESCRIPTION
        "This object contains the interface name of VRRP groups."
    ::= { zxr10VrrpVFOperEntry 1 }
    
zxr10VrrpVFOperVrId OBJECT-TYPE
    SYNTAX       VrId
    MAX-ACCESS   not-accessible
    STATUS       current
    DESCRIPTION
        "This object contains the Virtual Router Identifier (VRID)."
    ::= { zxr10VrrpVFOperEntry 2 }

zxr10VrrpVFOperVFID OBJECT-TYPE
    SYNTAX       Integer32
    MAX-ACCESS   not-accessible
    STATUS       current
    DESCRIPTION
        "This object contains the Virtual Forwarder Identifier (VFID)."
    ::= { zxr10VrrpVFOperEntry 3 }

zxr10VrrpVFOperRunWeight OBJECT-TYPE
    SYNTAX       Integer32(1..255)
    MAX-ACCESS   read-only
    STATUS       current
    DESCRIPTION
        "This object specifies the weight to be used for identifying the
        ability of forwarding for virtual forwarder. Higher values imply
         higher weight."
    ::= { zxr10VrrpVFOperEntry 4 }

zxr10VrrpVFOperVFState OBJECT-TYPE
    SYNTAX INTEGER {
           initialize(1),
           active(2),
           takeover(3),
           listening(4)
       }
    MAX-ACCESS   read-only
    STATUS       current
    DESCRIPTION
        "The current state of the virtual forwarder.  This object
        has four defined values:

        - 'initialize', which indicates that the
           virtual forwarder is waiting for a startup event.

        - 'active', which indicates that the virtual router is
           forwarder owner and is responsible for forwarding flow.

        - 'takeover', which indicates that the virtual forwarder
          is forwarding flow for taking the place of active forwarder. 

        - 'listening', which indicates that the virtual forwarder
          is monitoring the availability of the active forwarder."
    ::= { zxr10VrrpVFOperEntry 5 }

zxr10VrrpVFOperVFMac OBJECT-TYPE
   SYNTAX       MacAddress
   MAX-ACCESS   read-only
   STATUS       current
   DESCRIPTION
       "The virtual MAC address of the virtual forwarder."
   ::= { zxr10VrrpVFOperEntry 6 }

zxr10VrrpVFOperRunPriority OBJECT-TYPE
    SYNTAX       Integer32(1..255)
    MAX-ACCESS   read-only
    STATUS       current
    DESCRIPTION
        "This object specifies the priority to be used for the
         virtual forwarder election process. Higher values imply
         higher priority."
    ::= { zxr10VrrpVFOperEntry 7 }
    
zxr10VrrpVFOperIpAddrType OBJECT-TYPE
   SYNTAX       InetAddressType
   MAX-ACCESS   read-only
   STATUS       current
   DESCRIPTION
       "The IP address type of zxr10VrrpVFOperIpAddr.
       ipv4(1) and ipv6(2) are the only two values supported
       in this MIB module."
   ::= { zxr10VrrpVFOperEntry 8 }
   
zxr10VrrpVFOperIpAddr OBJECT-TYPE
   SYNTAX       InetAddress
   MAX-ACCESS   read-only
   STATUS       current
   DESCRIPTION
       "The virtual forwarder's real IP address of interface."
   ::= { zxr10VrrpVFOperEntry 9 }

zxr10VrrpVFOperLocation OBJECT-TYPE
    SYNTAX INTEGER {
           local(1),
           remote(2),
           none(3)
       }
    MAX-ACCESS   read-only
    STATUS       current
    DESCRIPTION
        "The current location of the virtual forwarder.  This object
        has three defined values:

        - 'local', which indicates that the virtual forwarder is configured locally.

        - 'remote', which indicates that the virtual router is remote.

        - 'none', which indicates that the virtual forwarder is not configured or does not exist."
    ::= { zxr10VrrpVFOperEntry 10 }

zxr10VrrpVFOperVFNum OBJECT-TYPE
    SYNTAX       Integer32
    MAX-ACCESS   read-only
    STATUS       current
    DESCRIPTION
        "This object contains the total number of virtual forwarder in one VRRP group."
    ::= { zxr10VrrpVFOperEntry 11 }
    
zxr10VrrpVFOperIfIndex OBJECT-TYPE
    SYNTAX       Integer32
    MAX-ACCESS   read-only
    STATUS       current
    DESCRIPTION
        "This object contains the interface index of VRRP groups."
    ::= { zxr10VrrpVFOperEntry 12 }

-- *******************************************************************
--  VRRP VF(Virtual Forwarder) Tracking Interface Table
-- *******************************************************************

zxr10VrrpVFTrackIfTable OBJECT-TYPE
     SYNTAX       SEQUENCE OF Zxr10VrrpVFTrackIfEntry
     MAX-ACCESS   not-accessible
     STATUS       current
     DESCRIPTION
         "Tracking interface table for a VRRP virtual forwarder which consists of a
          sequence (i.e., one or more conceptual rows) of
          'zxr10VrrpVFTrackIfEntry' items."
     ::= { zxr10VrrpVFTrackManages 1 }

zxr10VrrpVFTrackIfEntry OBJECT-TYPE
     SYNTAX       Zxr10VrrpVFTrackIfEntry
     MAX-ACCESS   not-accessible
     STATUS       current
     DESCRIPTION
         "An entry in the zxr10VrrpVFTrackIfTable containing the tracking
          characteristics of a VRRP virtual forwarder. On a VRRP router,
          a given virtual router is identified by a combination
          of the IF name and VRID. Rows in the table cannot be modified."
     INDEX  {
                zxr10VrrpVFTrackIfStandByIfName,
                zxr10VrrpVFTrackIfVrid,
                zxr10VrrpVFTrackIfName
            }
     ::= { zxr10VrrpVFTrackIfTable 1 }

Zxr10VrrpVFTrackIfEntry ::=
     SEQUENCE {
         zxr10VrrpVFTrackIfStandByIfName
             DisplayString,
         zxr10VrrpVFTrackIfVrid
             VrId,         
         zxr10VrrpVFTrackIfName
             DisplayString,           
         zxr10VrrpVFTrackIfState
             INTEGER,
         zxr10VrrpVFTrackIfPriReduce
             Integer32,
         zxr10VrrpVFTrackIfPolicy
             INTEGER,
         zxr10VrrpVFTrackIfStandByIfIdx
             Integer32,
         zxr10VrrpVFTrackIfIdx
             Integer32
 }

 zxr10VrrpVFTrackIfStandByIfName OBJECT-TYPE
    SYNTAX       DisplayString(SIZE(1..31))
    MAX-ACCESS   not-accessible
    STATUS       current
    DESCRIPTION
        "The interface name of VRRP groups."
    ::= { zxr10VrrpVFTrackIfEntry 1 }
    
zxr10VrrpVFTrackIfVrid OBJECT-TYPE
     SYNTAX       VrId
     MAX-ACCESS   not-accessible
     STATUS       current
     DESCRIPTION
        "This object contains the Virtual Router Identifier (VRID) of the
        tracked interface."
     ::= { zxr10VrrpVFTrackIfEntry 2 }

zxr10VrrpVFTrackIfName OBJECT-TYPE
    SYNTAX       DisplayString(SIZE(1..31))
    MAX-ACCESS   not-accessible
    STATUS       current
    DESCRIPTION
        "The name of the tracked interface."
    ::= { zxr10VrrpVFTrackIfEntry 3 }    

zxr10VrrpVFTrackIfState OBJECT-TYPE
    SYNTAX          INTEGER
                    {
         up(1),
         down(2)
     }
     MAX-ACCESS   read-only
     STATUS       current

     DESCRIPTION
         "The current state of the tracked interface. This object has
         two defined values:
           - `up', which indicates the protocol status of the tracked interface.
           - `down', which indicates the protocol status of the tracked interface."
      ::= { zxr10VrrpVFTrackIfEntry 4 }
 
zxr10VrrpVFTrackIfPriReduce OBJECT-TYPE
     SYNTAX       Integer32 (1..254)
     MAX-ACCESS   read-only
     STATUS       current
     DESCRIPTION
         "This object specifies the priority to be reduced when 
          the tracked interface is down."
     DEFVAL { 10 }
     ::= { zxr10VrrpVFTrackIfEntry 5 }

zxr10VrrpVFTrackIfPolicy OBJECT-TYPE
    SYNTAX          INTEGER { priorityDecrement(1)}
    MAX-ACCESS      read-only
    STATUS          current
    DESCRIPTION
        "The policy of tracking interface."
    ::= { zxr10VrrpVFTrackIfEntry 6 }
    
zxr10VrrpVFTrackIfStandByIfIdx OBJECT-TYPE
     SYNTAX       Integer32
     MAX-ACCESS   read-only
     STATUS       current
     DESCRIPTION
         "The interface index of VRRP groups."
     ::= { zxr10VrrpVFTrackIfEntry 7 }
     
zxr10VrrpVFTrackIfIdx OBJECT-TYPE
     SYNTAX       Integer32
     MAX-ACCESS   read-only
     STATUS       current
     DESCRIPTION
         "The index of the tracked interface."
     ::= { zxr10VrrpVFTrackIfEntry 8 }  

-- *******************************************************************
--  VRRP VF(Virtual Forwarder) Tracking Detect Table
-- *******************************************************************

zxr10VrrpVFTrackDetectTable OBJECT-TYPE
     SYNTAX       SEQUENCE OF Zxr10VrrpVFTrackDetectEntry
     MAX-ACCESS   not-accessible
     STATUS       current
     DESCRIPTION
         "The table of tracking detect associated with the VRRP virtual forwarder."
     ::= { zxr10VrrpVFTrackManages 2 }

zxr10VrrpVFTrackDetectEntry OBJECT-TYPE
     SYNTAX       Zxr10VrrpVFTrackDetectEntry
     MAX-ACCESS   not-accessible
     STATUS       current
     DESCRIPTION
         "An entry in the table contains a tracking detect that is
         associated with a virtual forwarder. The number of rows for
         a given ifName and VrId will equal the number of tracking detect
         associated by the virtual forwarder.
         Rows in the table cannot be modified."
     INDEX    { zxr10VrrpVFTrackStandByIfName, zxr10VrrpVFTrackVrid, zxr10VrrpVFTrackName }
     ::= { zxr10VrrpVFTrackDetectTable 1 }

Zxr10VrrpVFTrackDetectEntry ::=
     SEQUENCE {
         zxr10VrrpVFTrackStandByIfName
             DisplayString,         
         zxr10VrrpVFTrackVrid
             VrId,
         zxr10VrrpVFTrackName
             DisplayString,
         zxr10VrrpVFTrackType
             INTEGER,
         zxr10VrrpVFDetectType
             DisplayString,
         zxr10VrrpVFPolicyType
             INTEGER,
         zxr10VrrpVFTrackPriReduce
             Integer32,
         zxr10VrrpVFTrackState
             INTEGER,
         zxr10VrrpVFTrackStandByIfIdx
             Integer32
 }

zxr10VrrpVFTrackStandByIfName OBJECT-TYPE
    SYNTAX       DisplayString(SIZE(1..31))
    MAX-ACCESS   not-accessible
    STATUS       current
    DESCRIPTION
        "The interface name of VRRP groups."
    ::= { zxr10VrrpVFTrackDetectEntry 1 }
    
zxr10VrrpVFTrackVrid OBJECT-TYPE
     SYNTAX       VrId
     MAX-ACCESS   not-accessible
     STATUS       current
     DESCRIPTION
         "This object contains the Virtual Router Identifier (VRID) of the
         virtual forwarder tracking detect."
     ::= { zxr10VrrpVFTrackDetectEntry 2 }

zxr10VrrpVFTrackName OBJECT-TYPE
     SYNTAX       DisplayString(SIZE(1..32))
     MAX-ACCESS   not-accessible
     STATUS       current
     DESCRIPTION
         "The name of tracking detect for a virtual forwarder."
     ::= { zxr10VrrpVFTrackDetectEntry 3 }

zxr10VrrpVFTrackType OBJECT-TYPE
     SYNTAX INTEGER {
         object(1),
         group(2)
     }
     MAX-ACCESS   read-only
     STATUS       current
     DESCRIPTION
         "The type of tracking detect for a virtual forwarder."
     ::= { zxr10VrrpVFTrackDetectEntry 4 }
     
zxr10VrrpVFDetectType OBJECT-TYPE
     SYNTAX       DisplayString(SIZE(0..32))
     MAX-ACCESS   read-only
     STATUS       current
     DESCRIPTION
         "The type of tracking detect for a virtual forwarder."
     ::= { zxr10VrrpVFTrackDetectEntry 5 }
     
zxr10VrrpVFPolicyType OBJECT-TYPE
     SYNTAX INTEGER {
         normal(1),
         link(2),
         peer(3)
     }
     MAX-ACCESS   read-only
     STATUS       current
     DESCRIPTION
         "The type of tracking policy for a virtual forwarder."
     ::= { zxr10VrrpVFTrackDetectEntry 6 }
     
zxr10VrrpVFTrackPriReduce OBJECT-TYPE
     SYNTAX       Integer32
     MAX-ACCESS   read-only
     STATUS       current
     DESCRIPTION
         "The assigned reduced priority when tracking detect down for a virtual
         forwarder."
     ::= { zxr10VrrpVFTrackDetectEntry 7 }
 
zxr10VrrpVFTrackState OBJECT-TYPE
    SYNTAX INTEGER {
         up(1),
         localdown(2),
         transdown(3),
         localsd(4),
         transsd(5),
         unknown(6)
     }     
     MAX-ACCESS   read-only
     STATUS       current
     DESCRIPTION
         "The tracking detect state for a virtual forwarder."
     ::= { zxr10VrrpVFTrackDetectEntry 8 }
     
zxr10VrrpVFTrackStandByIfIdx OBJECT-TYPE
     SYNTAX       Integer32
     MAX-ACCESS   read-only
     STATUS       current
     DESCRIPTION
         "The interface index of VRRP groups."
     ::= { zxr10VrrpVFTrackDetectEntry 9 }

END
