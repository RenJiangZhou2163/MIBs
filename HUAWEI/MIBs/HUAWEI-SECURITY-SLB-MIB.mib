--
-- HUAWEI-SECURITY-SLB-MIB.mib
-- MIB generated by MG-SOFT Visual MIB Builder Version 4.0 Build 341
-- Monday, January 13, 2014 at 16:49:11
--

--  HUAWEI-SECURITY-SLB-MIB.mib
-- MIB generated by MG-SOFT Visual MIB Builder Version 4.0 Build 341
-- Friday, January 10, 2014 at 14:17:55
-- 
--  =============================================================================
-- Copyright (C) 2014 by HUAWEI TECHNOLOGIES. All rights reserved.
--    
-- Description: The MIB is designed to get SLB information. 
-- Reference: Huawei Enterprise MIB
-- Version: V1.00
-- History: 
--          Version: V1.00 The initial version created by maoshanshan 90005469. 
-- =============================================================================

	HUAWEI-SECURITY-SLB-MIB DEFINITIONS ::= BEGIN
 
		IMPORTS
			enterprises			
				FROM RFC1155-SMI			
			OBJECT-GROUP, MODULE-COMPLIANCE, NOTIFICATION-GROUP			
				FROM SNMPv2-CONF					
			IpAddress, Gauge32, OBJECT-TYPE, MODULE-IDENTITY, NOTIFICATION-TYPE			
				FROM SNMPv2-SMI;
	
	
		-- 1.3.6.1.4.1.2011.6.122.67
		hwSlb MODULE-IDENTITY 
			LAST-UPDATED "201401071609Z"		-- January 07, 2014 at 16:09 GMT
			ORGANIZATION 
				"Huawei Technologies Co.,Ltd."
			CONTACT-INFO 
				"
				Huawei Industrial Base
                Bantian, Longgang
                Shenzhen 518129
                People's Republic of China
                Website: http://www.huawei.com
                Email: support@huawei.com

				"
			DESCRIPTION 
				"
				V1.00
				The HUAWEI-SECURITY-SLB-MIB contains objects to manage the firewall SLB module.
				"
				--  Revision history
				 REVISION    "201401071609Z"
                                 DESCRIPTION "V1.00, completed the first draft."
			::= { hwSecurity 67 }

		
	
--
-- Node definitions
--
	
--  1.3.6.1.4.1.2011.6.122.67
-- January 07, 2014 at 16:09 GMT
-- 
-- Node definitions
-- 
--  1.3.6.1.4.1.2011.6.122.68
-- January 07, 2013 at 16:09 GMT
-- 
-- Node definitions
-- 
--  January 07, 2013 at 16:09 GMT
-- 
-- Node definitions
-- 
-- 1.3.6.1.4.1.2011
-- 1.3.6.1.4.1.2011
-- 1.3.6.1.4.1.2011
		-- 1.3.6.1.4.1.2011
		huawei OBJECT IDENTIFIER ::= { enterprises 2011 }

		
--    1.3.6.1.4.1.2011.6
-- 1.3.6.1.4.1.2011.6
-- 1.3.6.1.4.1.2011.6
		-- 1.3.6.1.4.1.2011.6
		huaweiUtility OBJECT IDENTIFIER ::= { huawei 6 }

		
--    1.3.6.1.4.1.2011.6.122
-- 1.3.6.1.4.1.2011.6.122
-- 1.3.6.1.4.1.2011.6.122
		-- 1.3.6.1.4.1.2011.6.122
		hwSecurity OBJECT IDENTIFIER ::= { huaweiUtility 122 }

		
--   1.3.6.1.4.1.2011.6.122.68.1
-- 1.3.6.1.4.1.2011.6.122.67.1
		-- 1.3.6.1.4.1.2011.6.122.67.1
		hwSlbNotification OBJECT IDENTIFIER ::= { hwSlb 1 }

		
--   1.3.6.1.4.1.2011.6.122.68.1.1
-- 1.3.6.1.4.1.2011.6.122.67.1.1
		-- 1.3.6.1.4.1.2011.6.122.67.1.1
		hwSlbTrapObjects OBJECT IDENTIFIER ::= { hwSlbNotification 1 }

		
--    ===============================================
-- TrapObject.
-- ===============================================
-- 1.3.6.1.4.1.2011.6.122.45.1.1.1
-- 1.3.6.1.4.1.2011.6.122.68.1.1.1
-- 1.3.6.1.4.1.2011.6.122.67.1.1.1
		-- 1.3.6.1.4.1.2011.6.122.67.1.1.1
		hwSlbGroupIndex OBJECT-TYPE
			SYNTAX Gauge32
			MAX-ACCESS accessible-for-notify
			STATUS current
			DESCRIPTION
				"The Index of the SLB Group"
			::= { hwSlbTrapObjects 1 }

		
--    1.3.6.1.4.1.2011.6.122.45.1.1.1
-- 1.3.6.1.4.1.2011.6.122.45.1.1.2	
-- 1.3.6.1.4.1.2011.6.122.68.1.1.2
-- 1.3.6.1.4.1.2011.6.122.67.1.1.2
		-- 1.3.6.1.4.1.2011.6.122.67.1.1.2
		hwSlbGroupName OBJECT-TYPE
			SYNTAX OCTET STRING
			MAX-ACCESS accessible-for-notify
			STATUS current
			DESCRIPTION
				"The Name of the SLB Group."
			::= { hwSlbTrapObjects 2 }

		
--   1.3.6.1.4.1.2011.6.122.68.1.1.3
-- 1.3.6.1.4.1.2011.6.122.67.1.1.3
		-- 1.3.6.1.4.1.2011.6.122.67.1.1.3
		hwSlbServerIndex OBJECT-TYPE
			SYNTAX Gauge32
			MAX-ACCESS accessible-for-notify
			STATUS current
			DESCRIPTION
				"The Index of the SLB Real Server"
			::= { hwSlbTrapObjects 3 }

		
--   1.3.6.1.4.1.2011.6.122.68.1.1.4
-- 1.3.6.1.4.1.2011.6.122.67.1.1.4
		-- 1.3.6.1.4.1.2011.6.122.67.1.1.4
		hwSlbServerIp OBJECT-TYPE
			SYNTAX IpAddress
			MAX-ACCESS accessible-for-notify
			STATUS current
			DESCRIPTION
				"The IP address of the SLB Real Server"
			::= { hwSlbTrapObjects 4 }

		
--   1.3.6.1.4.1.2011.6.122.68.1.1.5
-- 1.3.6.1.4.1.2011.6.122.67.1.1.5
		-- 1.3.6.1.4.1.2011.6.122.67.1.1.5
		hwSlbOldStatus OBJECT-TYPE
			SYNTAX OCTET STRING
			MAX-ACCESS accessible-for-notify
			STATUS current
			DESCRIPTION
				"The Old Status of the SLB Real Server"
			::= { hwSlbTrapObjects 5 }

		
--  1.3.6.1.4.1.2011.6.122.67.1.1.6
		-- 1.3.6.1.4.1.2011.6.122.67.1.1.6
		hwSlbNewStatus OBJECT-TYPE
			SYNTAX OCTET STRING
			MAX-ACCESS accessible-for-notify
			STATUS current
			DESCRIPTION
				"The New Status of the SLB Real Server"
			::= { hwSlbTrapObjects 6 }

		
--   1.3.6.1.4.1.2011.6.122.68.2
-- 1.3.6.1.4.1.2011.6.122.67.2
		-- 1.3.6.1.4.1.2011.6.122.67.2
		hwSlbTraps OBJECT IDENTIFIER ::= { hwSlb 2 }

		
--    ===============================================
-- definition of traps.      
-- ===============================================                                
-- 1.3.6.1.4.1.2011.6.122.68.2.1
-- 1.3.6.1.4.1.2011.6.122.67.2.1
		-- 1.3.6.1.4.1.2011.6.122.67.2.1
		hwSlbRserverStateUp NOTIFICATION-TYPE
			OBJECTS { hwSlbGroupIndex, hwSlbGroupName, hwSlbServerIndex, hwSlbServerIp, hwSlbOldStatus, 
				hwSlbNewStatus }
			STATUS current
			DESCRIPTION 
				"The SLB Real Server status changes to up"
			::= { hwSlbTraps 1 }

		
--   1.3.6.1.4.1.2011.6.122.68.2.2
-- 1.3.6.1.4.1.2011.6.122.67.2.2
		-- 1.3.6.1.4.1.2011.6.122.67.2.2
		hwSlbRserverStateDown NOTIFICATION-TYPE
			OBJECTS { hwSlbGroupIndex, hwSlbGroupName, hwSlbServerIndex, hwSlbServerIp, hwSlbOldStatus, 
				hwSlbNewStatus }
			STATUS current
			DESCRIPTION 
				"The SLB Real Server status changes to down"
			::= { hwSlbTraps 2 }

		
--   1.3.6.1.4.1.2011.6.122.68.3
-- 1.3.6.1.4.1.2011.6.122.67.3
		-- 1.3.6.1.4.1.2011.6.122.67.3
		hwSlbConformance OBJECT IDENTIFIER ::= { hwSlb 3 }

		
--   1.3.6.1.4.1.2011.6.122.68.3.1
-- 1.3.6.1.4.1.2011.6.122.67.3.1
		-- 1.3.6.1.4.1.2011.6.122.67.3.1
		hwSlbCompliances OBJECT IDENTIFIER ::= { hwSlbConformance 1 }

		
--   1.3.6.1.4.1.2011.6.122.68.3.1.1
-- this module
-- 1.3.6.1.4.1.2011.6.122.67.3.1.1
-- this module
		-- 1.3.6.1.4.1.2011.6.122.67.3.1.1
		hwSlbCompliance MODULE-COMPLIANCE
			STATUS current
			DESCRIPTION 
				"Description."
			MODULE -- this module
				MANDATORY-GROUPS { hwSlbObjectGroup, hwSlbTrapGroup }
			::= { hwSlbCompliances 1 }

		
--   1.3.6.1.4.1.2011.6.122.68.3.2
-- 1.3.6.1.4.1.2011.6.122.67.3.2
		-- 1.3.6.1.4.1.2011.6.122.67.3.2
		hwSlbMibGroups OBJECT IDENTIFIER ::= { hwSlbConformance 2 }

		
--   1.3.6.1.4.1.2011.6.122.68.3.2.1
-- 1.3.6.1.4.1.2011.6.122.67.3.2.1
		-- 1.3.6.1.4.1.2011.6.122.67.3.2.1
		hwSlbObjectGroup OBJECT-GROUP
			OBJECTS { hwSlbGroupIndex, hwSlbGroupName, hwSlbServerIndex, hwSlbServerIp, hwSlbOldStatus, 
				hwSlbNewStatus }
			STATUS current
			DESCRIPTION 
				"Description."
			::= { hwSlbMibGroups 1 }

		
--   1.3.6.1.4.1.2011.6.122.68.3.2.2
-- 1.3.6.1.4.1.2011.6.122.67.3.2.2
		-- 1.3.6.1.4.1.2011.6.122.67.3.2.2
		hwSlbTrapGroup NOTIFICATION-GROUP
			NOTIFICATIONS { hwSlbRserverStateUp, hwSlbRserverStateDown }
			STATUS current
			DESCRIPTION 
				"Description."
			::= { hwSlbMibGroups 2 }

		
	
	END

--
-- HUAWEI-SECURITY-SLB-MIB.mib
--
