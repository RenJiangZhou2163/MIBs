--
-- HUAWEI-SECURITY-PPPOE-MIB.mib
-- MIB generated by MG-SOFT Visual MIB Builder Version 4.0 Build 341
-- Wednesday, Feb 3, 2017 at 16:30:10
--

--   =============================================================================
-- Copyright (C) 2017 by HUAWEI TECHNOLOGIES. All rights reserved.
--    
-- Description:  
-- Reference: Huawei Enterprise MIB
-- Version: V1.00
-- History: 
--          V1.00 The initial version created by Chenchao 00353594. 
-- =============================================================================


	HUAWEI-SECURITY-PPPOE-MIB DEFINITIONS ::= BEGIN
 
		IMPORTS
			enterprises			
				FROM RFC1155-SMI			
			OBJECT-GROUP			
				FROM SNMPv2-CONF			
			IpAddress, Unsigned32, Integer32, OBJECT-TYPE, MODULE-IDENTITY, NOTIFICATION-TYPE			
				FROM SNMPv2-SMI
			MODULE-COMPLIANCE, OBJECT-GROUP, NOTIFICATION-GROUP
                                FROM SNMPv2-CONF  			
			TruthValue, RowStatus, DateAndTime, TimeInterval, TEXTUAL-CONVENTION			
				FROM SNMPv2-TC;
	
	
		hwPPPOEMibObjects MODULE-IDENTITY 
                LAST-UPDATED "201702041120Z"                -- Feb 4, 2017 at 11:20 GMT
			ORGANIZATION 
				"Huawei Technologies Co.,Ltd."
        CONTACT-INFO 
                   "Huawei Industrial Base
                    Bantian, Longgang
                    Shenzhen 518129
                    People's Republic of China
                    Website: http://www.huawei.com
                    Email: support@huawei.com
                   "

            DESCRIPTION 
                "
                V1.00
                The HUAWEI-SECURITY-PPPOE-MIB contains objects to manage the firewall PPPOE module.
                "
                
            REVISION  "201702041120Z"

            DESCRIPTION "The HUAWEI-SECURITY-PPPOE-MIB contains objects to manage the firewall PPPOE module."

			::= { hwSecurity 80 }


--
-- Node definitions
--
                -- 1.3.6.1.4.1.2011
                huawei OBJECT IDENTIFIER ::= { enterprises 2011 }
        
                -- 1.3.6.1.4.1.2011.6
                huaweiUtility OBJECT IDENTIFIER ::= { huawei 6 }
        
                -- 1.3.6.1.4.1.2011.6.122
                hwSecurity OBJECT IDENTIFIER ::= { huaweiUtility 122 }		

-- ===============================================
-- PPPOETrapObject.
-- ===============================================
	            hwPPPOETrapObject OBJECT IDENTIFIER ::= { hwPPPOEMibObjects 1 }
	            hwPPPOEBindInterface OBJECT-TYPE
					SYNTAX OCTET STRING
					MAX-ACCESS accessible-for-notify
					STATUS current
					DESCRIPTION
						"Ethernet interface which bind pppoe-server."
					::= { hwPPPOETrapObject 1 }
                  
-- ===============================================
-- definition of traps.      
-- ===============================================

                hwPPPOETrap OBJECT IDENTIFIER ::= { hwPPPOEMibObjects 2 }
                hwPPPOENotifications OBJECT IDENTIFIER ::= { hwPPPOETrap 1 }
                                                
                hwPPPOEUsersReachMax NOTIFICATION-TYPE
                STATUS     current
                DESCRIPTION
                               "This notification is generated when the number of PPPOE
                                online users reach the spec."
                ::= { hwPPPOENotifications 1 }                
			                                   
			    hwPPPOEUsersBelowThreshold NOTIFICATION-TYPE
                STATUS     current
                DESCRIPTION
                               "This notification is generated when the number of PPPOE
                                online users restores to be lower than 95% of the spec."
                ::= { hwPPPOENotifications 2 }
                
                hwPPPOEUsersReachInterMax NOTIFICATION-TYPE
                OBJECTS {
                           hwPPPOEBindInterface
                        }
                STATUS     current
                DESCRIPTION
                               "This notification is generated when the number of PPPOE
                                online users reach the interface spec."
                ::= { hwPPPOENotifications 3 }
                
                hwPPPOEUsersBelowInterThreshold NOTIFICATION-TYPE
                OBJECTS {
                           hwPPPOEBindInterface
                        }
                STATUS     current
                DESCRIPTION
                               "This notification is generated when the number of PPPOE
                                online users restores to be lower than 95% of the interface spec."
                ::= { hwPPPOENotifications 4 }  
        END

--
-- HUAWEI-SECURITY-PPPOE-MIB
--
