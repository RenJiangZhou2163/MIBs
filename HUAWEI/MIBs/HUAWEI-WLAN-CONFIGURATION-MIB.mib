-- ============================================================================
-- Copyright (C) 2020 by  HUAWEI TECHNOLOGIES. All rights reserved.
-- Description: The mib is used for configuration.
-- Reference: 
-- Version: V3.21
-- ============================================================================
-- Module definition

	HUAWEI-WLAN-CONFIGURATION-MIB DEFINITIONS ::= BEGIN

		IMPORTS
			hwWlan
				FROM HUAWEI-WLAN-MIB
		        hwWlanApName,hwWlanApMac
		                FROM HUAWEI-WLAN-AP-MIB      
		        hwWlanRadioID
		                FROM HUAWEI-WLAN-AP-RADIO-MIB
			OBJECT-GROUP, MODULE-COMPLIANCE, NOTIFICATION-GROUP
				FROM SNMPv2-CONF
			IpAddress, Integer32, Unsigned32, Counter64, TimeTicks, OBJECT-TYPE,
			MODULE-IDENTITY, NOTIFICATION-TYPE
				FROM SNMPv2-SMI
			MacAddress, RowStatus, DateAndTime
				FROM SNMPv2-TC;
		--1.3.6.1.4.1.2011.6.139.11
 		hwWlanConfig MODULE-IDENTITY
                                                         
			LAST-UPDATED "202004271515Z"            -- Apr 27, 2020 at 15:15 GMT
			ORGANIZATION
				"Huawei Technologies Co.,Ltd."
			CONTACT-INFO
			 "Huawei Industrial Base
				   Bantian, Longgang
				   Shenzhen 518129
				   People's Republic of China
				   Website: http://www.huawei.com
				   Email: support@huawei.com
				
				"
				DESCRIPTION
				"V3.21 add node hwSsidTwtSwitch, hwSsidProfile80211rPrivateSwitch."
				REVISION "202004271515Z" -- Apr 17, 2020 at 15:15 GMT				
				DESCRIPTION
				"V3.20 modify description of node hwWlanRadioCalibratePolicy."
				REVISION "202004171613Z" -- Apr 17, 2020 at 16:13 GMT
				DESCRIPTION
				"V3.19 modify hwApSysBCMCSuppressionThreshold."
				REVISION "202004161512Z" -- Apr 16, 2020 at 15:12 GMT
				DESCRIPTION
				"V3.18 modify description of node hw5gRadioProfileSmartAntennaEnable, hw5gRadioAutonavigationBeaconInterval."
				REVISION "202003300945Z" -- Mar 30, 2020 at 09:45 GMT
				DESCRIPTION
				"V3.17 add node hwWlanClusterSynConfigScheduleEnable, hwWlanClusterSynConfigScheduleTime and hwWlanClusterSynConfigScheduleInterval."
				REVISION "202003241421Z" -- Mar 24, 2020 at 14:21 GMT
				DESCRIPTION
				"V3.17 modify node hwSecurityPolicy and hwSecurityWpaEncrypt."
				REVISION "202003241121Z" -- Mar 24, 2020 at 11:21 GMT
				DESCRIPTION
				"V3.16 add node hwWlanGlobalAeroscoutLocalIPv4 and hwWlanGlobalAeroscoutLocalIPv6."
				REVISION "202003231821Z" -- Mar 23, 2020 at 18:21 GMT
				DESCRIPTION
				"V3.15 add node hwSsidBeamformingSwitch."
				REVISION "202003191845Z" -- Mar 19, 2020 at 18:45 GMT
				DESCRIPTION
				"V3.14 modify the range of hwAPPortLinkProfileSpeed."
				REVISION "202003191030Z" -- Mar 19, 2020 at 10:30 GMT
				DESCRIPTION
				"V3.13 modify the description of hwSsidClientEdcaVoiceAIFSN, hwSsidClientEdcaVideoAIFSN, hwSsidClientEdcaBeAIFSN and hwSsidClientEdcaBkAIFSN."
				REVISION "202003101030Z" -- Mar 10, 2020 at 10:30 GMT
				DESCRIPTION
				"V3.12 modify the description of hw5gRadioRtsCtsMode node"
				REVISION "202003071156Z" -- Mar 7, 2020 at 11:56 GMT
				DESCRIPTION
				"V3.11 modify the value range of hwApProfPoeMaxPower node"
				REVISION "202002291733Z" -- Feb 29, 2020 at 17:33 GMT
				DESCRIPTION
				"V3.10 add node hwWlanIDIndexedSpManagementVlan and add node hwWlanAPProvisionManagementVlan"
				REVISION "202002261713Z" -- Feb 26, 2020 at 17:13 GMT
				DESCRIPTION
				"V3.09 modify node hwAPWiredPortProfilePortSTPSwitchs and add node hwRrmCalibrate5gMinTxPwr, hwRrmCalibrate5gMaxTxPwr"
				REVISION "202002122025Z" -- Feb 12, 2020 at 20:25 GMT
                DESCRIPTION
				"V3.08 modify node hwWidsDeviceReportInterval description, the value range changes to 60-3600"
				REVISION "202001161429Z" -- Jan 16, 2020 at 14:29 GMT
				DESCRIPTION
				"V3.07 add node hwAPPortLinkProfileSpeed"
				REVISION "202001111500Z"  --  Jan 11, 2020 at 15:00 GMT
				
				DESCRIPTION
	                        "V3.06 add node hwSysWmiMeshDataInterval"
	                        REVISION "201912211713Z"  --  Dec 21, 2019 at 17:13 GMT
				DESCRIPTION
				"V3.05 modify node hwSecurityWpaPtkUpdateInterval"
				REVISION "201912102156Z"  --  Dec 10, 2019 at 21:56 GMT

                                                                                     DESCRIPTION
				"V3.04 add node hwApSystemProfileNPFastForwardingSwitch"
				REVISION "201911182024Z"  --  Nov 18, 2019 at 20:24 GMT
				
				DESCRIPTION
				"V3.03 modify description of node hwApProfHighTempApEnvironmentThreshold,hwApProfHighTempCpuThreshold,hwApProfHighTempNpThreshold,hwApProfLowTempApEnvironmentThreshold,hwApProfLowTempCpuThreshold,hwApProfLowTempNpThreshold"
				REVISION "201910261100Z"  --  Oct 26, 2019 at 11:00 GMT

				DESCRIPTION
				"V3.01 modify description of node hwWlanPPSKSsid"
				REVISION "201910221500Z"  --  Oct 22, 2019 at 15:00 GMT

				DESCRIPTION
				"V3.01 modify node hwWlanRadioCalibrateReferenceDataAnalysis and add node hwWlanRadioCalibrateEnvironmentDeteriorateValue and hwWlanRadioCalibrateScheduleTimeRange"
				REVISION "201909111013Z"  --  Sep 11, 2019 at 10:13 GMT
				
				DESCRIPTION
				"V3.00 add node hwVapSplitTunnelAcl, hwVapSplitTunnelAclIPv6 "
				REVISION "201909051013Z"  --  Sep 5, 2019 at 10:13 GMT
				
				DESCRIPTION
				"V2.99 add node hwSysWmiTerminalDhcpOptionDataInterval, hwSysWmiTerminalHttpUaDataInterval, hwSysWmiTerminalMdnsDataInterval "
				REVISION "201908222200Z"  --  August 22, 2019 at 22:00 GMT

				DESCRIPTION
				"V2.98 modify description of node hwVapOptinon82InsertRidFormat, hwVapOptinon82RidUserDefined, hwVapOptinon82RidMacFormat and hwVapOptinon82InsertCidFormat"
				REVISION "201908151630Z"  --  August 15, 2019 at 16:30 GMT

				DESCRIPTION
				"V2.97 add node hwVapProfileMdnsSnooping, hwWmiTerminalDhcpOptionDataInterval, hwWmiTerminalHttpUaDataInterval, hwWmiTerminalMdnsDataInterval "
				REVISION "201908151100Z"  --  August 15, 2019 at 11:00 GMT

				DESCRIPTION
				"V2.96 add node hwAPGrpReferenceDataAnalysis, hwAPSpReferenceDataAnalysis, hwFatApReferenceDataAnalysis, hwIDIndexedAPSpReferenceDataAnalysis and hwWlanRadioCalibrateReferenceDataAnalysis
				and modify node hwWmiLogModuleist and "
				REVISION "201908071021Z"  --  August 7, 2019 at 10:21 GMT
				
                DESCRIPTION
				"V2.95 add node hwWlanIotOperateTable, hwWlanIotOperateEntry, hwWlanIotOperateCardId and hwWlanIotOperateType"
				REVISION "201907271428Z"  --  July 27, 2019 at 14:28 GMT						     
				
                DESCRIPTION				
				"V2.94 modify node hwAPWiredPortDot1xClientProfileName."
				REVISION "201907191840Z"  --  July 19, 2019 at 18:40 GMT

 				DESCRIPTION		
				"V2.93 modify node hwWmiLogModuleist."
				REVISION "201907181037Z"  --  July 18, 2019 at 10:37 GMT 		
				
				DESCRIPTION		
				"V2.91 modify node hwLocationSurFilterViaACPort, hwLocationSurFilterDataSourceID, hwApProfStaArpProxyBeforeAssoc and hwFatApStaArpProxyBeforeAssoc."
				REVISION "201906201700Z"  --  June 20, 2019 at 17:00 GMT
				
 				DESCRIPTION		
				"V2.91 add node hwWlanRadioCalibrateSensitivityCustomValue."
				REVISION "201906102002Z"  --  June 10, 2019 at 20:02 GMT
				  
 				DESCRIPTION		
				"V2.90 add pki cert MIB."
				REVISION "201906051120Z"  --  June 05, 2019 at 11:20 GMT
				  
 				DESCRIPTION		
				"V2.89 add the node hwApProfUcSuppressionAutoDetectSwitch."
				REVISION "201905251120Z"  --  May 25, 2019 at 11:20 GMT
				
 				DESCRIPTION		
				"V2.88 add the node hwWmiLogModuleist and hwSysWmiLogMIDList, modified the node hwApProfStaArpProxyBeforeAssoc."
				REVISION "201905131120Z"  --  May 13, 2019 at 11:20 GMT
				
				DESCRIPTION
				"V2.87 modify  hwIDIndexedAPSpAutoChannelSelectSwitch, hwIDIndexedAPSpAutoTxPowerSelectSwitch,  hwAPSpAutoTxPowerSelectSwitch,  hwAPSpAutoChannelSelectSwitch and hwWlanRadioCalibrateSensitivity, modify the description of node hwWidsFloodDetectInterval and hwWidsFloodDetectThreshold. "
				REVISION "201905061556Z"  --  May 06, 2019 at 15:56 GMT
			
				DESCRIPTION
				"V2.86 add the description of node hwWlanClusterRedundancyTrackVRRPType,hwIoTProfileAntennaStatus."
				REVISION "201905061100Z"  -- May 06, 2019 at 11:00 GMT

				DESCRIPTION
				"V2.85 modify the description of node hwAPPortLinkProfileLldpTlvType, hwAPPortLinkProfileCrcAlarmThreshold and hwAPPortLinkProfileCrcAlarmResumeThreshold."
				REVISION "201904301700Z"  -- Apr 30, 2019 at 17:00 GMT
				
				DESCRIPTION
				"V2.84 add the node hwAPGrpAutoBandwidthSelectSwitch."
				REVISION "201904151121Z"  -- Apr 15, 2019 at 11:21 GMT

				DESCRIPTION
				"V2.83 modify the node hwRrmUacClientSnrThreshold ."
				REVISION "201904121121Z"  -- Apr 12, 2019 at 11:21 GMT
				
				DESCRIPTION
				"V2.82 add the node hwWidsContainMinRssi and hwWidsContainMinStaNum ."
				REVISION "201904101321Z"  -- Apr 10, 2019 at 13:21 GMT
				DESCRIPTION
				"V2.81 add the node of hwAPPortLinkProfileLldpLegacyPowerCapability."
				REVISION "201903211100Z"  -- Mar 21, 2019 at 11:00 GMT


				DESCRIPTION
				"V2.80 add the node of hwVapMdnsPolicyLocalACSwitch,
				       modify the node of hwAPTrafficProfileOptimizeBcMcMismatchAct."
				REVISION "201903191450Z"  -- Mar 19, 2019 at 14:50 GMT
				
				DESCRIPTION
				"V2.79 add the node of hwVapAutonavigationRoamOptimizeSwitch, hwSsidVhtTxNssCount, hwSsidVhtRxNssCount, hwSsidVhtTxMcsMap
						hwSsidVhtRxMcsMap, hwSsidHETxNssCount, hwSsidHERxNssCount, hwSsidHETxMcsMap, hwSsidHERxMcsMap"
				REVISION "201903181447Z"  -- Mar 18, 2019 at 14:47 GMT
				
				DESCRIPTION
				"V2.78 add the node of hwApProfStationConnectivityDetectSwitch and hwApProfStationConnectivityDetectStaMacTable"
				REVISION "201903161136Z"  -- Mar 16, 2019 at 11:36 GMT
				                  
				DESCRIPTION
				"V2.77 add the node of hwApProfLogServerPort"
				REVISION "201903071600Z"  -- Mar 07, 2019 at 16:00 GMT 
				
			    DESCRIPTION                  
				"V2.76 add the table of hwApSysBCMCSuppressionTable and hwVAPProfileAntiAttackTable."
				REVISION "201903021800Z"  -- Mar 02, 2019 at 18:00 GMT                     
                  
			    DESCRIPTION
				"V2.75 add the node of AP neighbor relation table."
				REVISION "201903021201Z"  -- Mar 02, 2019 at 12:01 GMT   
				  
			 	DESCRIPTION
				"V2.74 add the node of hwApProfConsoleBLEMode , add node hwWlanGlobalRogueDeviceLogSwitch, add node hwApProfDiskUsageThreshold"
				REVISION "201901231525Z"  -- Jan 23, 2019 at 15:25 GMT 
				
				DESCRIPTION
				"V2.73 add the node of hwLocationCollectLocationDataSwitch,hwLocationCollectLocationDataRSSIThreshold"
				REVISION "201901181107Z"  -- Jan 18, 2019 at 11:07 GMT 

				DESCRIPTION 
		        "V2.72 add the node of hwSecurityWepDot1xMode" 
                REVISION "201901081107Z"  -- Jan 08, 2019 at 11:07 GMT 
		
				DESCRIPTION 
		        "V2.71 modify the node of hwHighwayStationMinSpeed and hwWlanLBRssiThreshold" 
                REVISION "201901031107Z"  -- Jan 03, 2019 at 11:07 GMT 
		
				DESCRIPTION 
		        "V2.70 modify the node of hwApProfManagementVlan,hwApProfEapStartTransform,hwApProfEapResponseMode,
				hwApProfEapResponseTransform,hwApProfDhcpv4Option12,hwAPWiredPortProfilePortMode" 
                REVISION "201812251851Z"  -- Dec 25, 2018 at 18:51 GMT 
				
				DESCRIPTION 
		        "V2.68 modify the node of hwSsidDtimInterval" 
                REVISION "201812242051Z"  -- Dec 24, 2018 at 20:51 GMT 

				DESCRIPTION 
		        "V2.68 add the node of hwAPGrpAPIPVersion,hwUndoWlanProtectIPv6Address" 
                REVISION "201812221456Z"  -- Dec 22, 2018 at 14:56 GMT 
		        
				DESCRIPTION 
                "V2.67 add the node of hwApProfBcSuppresionAutoDetectThreshold,hwApProfMcSuppresionAutoDetectThreshold,hwApProfUcSuppresionAutoDetectThreshold" 
                REVISION "201812191538Z"  -- Dec 17, 2018 at 12:24 GMT 
                
			    DESCRIPTION 
                "V2.66 add the node of hwAPWiredPortProfilePortForwardMode " 
                REVISION "201812171124Z"  -- Dec 17, 2018 at 12:24 GMT 
				
				DESCRIPTION 
                "V2.65 add the node of hwApProfDhcpv4Option12 " 
                REVISION "201812101324Z"  -- Dec 10, 2018 at 13:24 GMT 
				 
                DESCRIPTION 
                "V2.64 add the node of hwSsidInterAcRoamSwitch " 
                REVISION "201812031446Z"  -- Dec 2, 2018 at 14:46 GMT 

				DESCRIPTION
				"V2.63 modify the node of hwSecurityPolicy"
						REVISION "201811301746Z"  -- Nov 30, 2018 at 17:46 GMT
						
				DESCRIPTION
				"V2.62 modify the of table hwSsidProfileTable, add node hwSsidServiceGuarantee"
						REVISION "201811151744Z"  -- Nov 15, 2018 at 17:44 GMT 
						
				DESCRIPTION
				"V2.61 modify the of table hwSysWmiConfigTable, add node hwSysWmiEmdiDataInterval hwSysWmiCpcarDataInterval hwSysWmiNeighborDataInterval"
						REVISION "201811121055Z"  -- Nov 12, 2018 at 10:55 GMT  
				DESCRIPTION
				"V2.60 modify the of node hwWlanPPSKPskUserGroup, hwWlanPPSKPskValue "
						REVISION "201811081428Z"  -- Nov 8, 2018 at 14:28 GMT 
			 	DESCRIPTION				
				"V2.59 modify the of node hwWdsNdTrustPort"
						REVISION "201811021055Z"  -- Nov 2, 2018 at 10:55 GMT  
                                                                              DESCRIPTION				
				"V2.58 modify the of node hwRrmUacClientNumAccessThreshold, hwRrmUacClientNumRoamThreshold"
						REVISION "201810291236Z"  -- Oct 29, 2018 at 12:36 GMT   

				DESCRIPTION				
				"V2.57 modify the of node hwAPGrpHighwayProfileName,hwWmiCpcarDataInterval,hwWmiEmdiDataInterval"
						REVISION "201810272040Z"  -- Oct 27, 2018 at 20:40 GMT   
				DESCRIPTION				
				"V2.56 modify the datatype of node hwWlanLicenseClientLocalLicense,hwWlanLicenseClientLicenseRemain,hwWlanLicenseClientAllocedLicense"
						REVISION "201810252040Z"  -- Oct 25, 2018 at 20:40 GMT   
				DESCRIPTION				
				"V2.55 add node hwAPGrpCardNetProtocolType,hwAPGrpCardNetPort,hwAPGrpCardNetExtPort,hwAPSpIoTNetProtocolType,hwAPSpIoTNetPort,hwAPSpIoTNetExtPort"
						REVISION "201810232140Z"  -- Oct 23, 2018 at 21:40 GMT 
				DESCRIPTION				
				"V2.54 add node hwWmiCpcarDataInterval,hwWmiEmdiDataInterval,hwVapServiceExpAnalysisSwitch,hwVapServiceExpAnalysisSnoopingPort,modify nide hwSsidMaxStaNum"
						REVISION "201810230958Z"  -- Oct 23, 2018 at 09:58 GMT  
				DESCRIPTION				
				"V2.53 modify description of node hwWlanLBDeauthFailTime	hwWlanLBBtmFailTime	hwWlanLBSteerRestrictTime
						hwWlanLBSteerProbeRestrictThreshold	hwWlanLBSteerAuthRestrictThreshold
						hwWlanLBRssiThreshold	hwWlanLBRssiDiffGap"
						REVISION "201810172053Z"  -- Oct 17, 2018 at 20:53 GMT  
				DESCRIPTION				
				"V2.52 add node hwSoftgreUntaggedVlanId, modify description of node hwApSystemWmiProfile, modify max access of node hwApSystemWmiIndex and node hwSysWmiIndex"
						REVISION "201810171409Z"  -- Oct 17, 2018 at 14:09 GMT  
				  DESCRIPTION				
				"V2.51 modify nodes hwAPGrpRadioWorkMode, hwAPSpRadioWorkMode, hwFatApRadioWorkMode, hwIDIndexedAPSpRadioWorkMode, add table hwWlanPPSKTable, hwSecurityPolicy add 3 enum:wpaPpsk(13), wpa2Ppsk(14),wpaWpa2Ppsk(15)"
						REVISION "201810160928Z"  -- Oct 16, 2018 at 09:28 GMT  
				DESCRIPTION				
				"V2.50 add node hwRrmDynamicEdcaThresholdBE"
						REVISION "201810151536Z"  -- Oct 15, 2018 at 15:36 GMT
				DESCRIPTION
				"V2.49 add node hwWlanLBDeauthFailTime	hwWlanLBBtmFailTime	hwWlanLBSteerRestrictTime
						hwWlanLBSteerProbeRestrictThreshold	hwWlanLBSteerAuthRestrictThreshold
						hwWlanLBRssiThreshold	hwWlanLBRssiDiffGap"
						REVISION "201809291153Z"  -- Sep 29, 2018 at 11:53 GMT
				  
				DESCRIPTION				
				"V2.48 add node hwWmiNeighborDataInterval"
						REVISION "201809211718Z"  -- Sep 21, 2018 at 18:17 GMT
				  
				DESCRIPTION
                "V2.47 add globalconfig hwWlanLicenseCentralizedSwitch hwWlanLicenseCentralizedServerIPv4Addr 
					   hwWlanLicenseCentralizedServerIPv6Addr hwWlanLicenseCentralizedClientIPv4Addr hwWlanLicenseCentralizedClientIPv6Addr hwWlanLicenseCentralizedRole 
					   hwWlanLicensePoolUsed hwWlanLicensePoolTotal.
					   add table hwWlanLicenseCentralizedTable.
				            add node hwWlanLicenseClientMac hwWlanLicenseClientIPv4Addr hwWlanLicenseClientIPv6Addr hwWlanLicenseClientRole hwWlanLicenseClientState 
							hwWlanLicenseClientLocalLicense hwWlanLicenseClientLicenseRemain hwWlanLicenseClientAllocedLicense"
                        REVISION "201809181004Z"  -- Sep 18, 2018 at 10:04 GMT  
				DESCRIPTION
                "V2.46 add table hwWmiProfileTable hwApSystemWmiProfileTable hwSysWmiConfigTable.
				            add node hwWmiServerProfileName hwWmiServerIPv4 hwWmiServerPOrt hwWmiReportInterval hwWmiKeepAliveInterval hwWmiRetryConnectionInterval hwWmiRetryConnectionCnt
					   hwWmiMaxPacketSize hwWmiDeviceDataInterval hwWmiSsidDataInterval hwWmiRadioDataInterval hwWmiInterfaceDataInterval hwWmiTerminalDataInterval hwWmiLogDataInterval
					   hwWmiLocationDataInterval hwWmiSecurityDataInterval hwWmiRowStatus hwApSystemWmiIndex hwApSystemWmiProfile hwApSystemWmiRowStatus hwSysWmiIndex hwSysWmiServerIPv4
					   hwSysWmiServerPort hwSysWmiReportInterval hwSysWmiKeepAliveInterval hwSysWmiRetryConnectionInterval hwSysWmiRetryConnectionCnt hwSysWmiMaxPacketSize hwSysWmiDeviceDataInterval
					   hwSysWmiSsidDataInterval hwSysWmiRadioDataInterval hwSysWmiInterfaceDataInterval hwSysWmiTerminalDataInterval hwSysWmiLogDataInterval hwSysWmiLocationDataInterval hwSysWmiSecurityDataInterval
					   hwSysWmiRoamDataInterval hwSysWmiApplicationStatisticsDataInterval."
                       REVISION "201809170952Z"  -- Sep 17, 2018 at 09:52 GMT					   
				DESCRIPTION
				"V2.45, add node  hwAPGrpHighwayProfileName  hwVapHighwayEnable hw2gRadioHighwayBssid hw5gRadioHighwayBssid hwAPSpRadioAntennaGain hwIDIndexedAPSpRadioAntennaGain"
						REVISION "201809070926Z"  -- Sep 05, 2018 at 19:01 GMT  				
                DESCRIPTION
				"V2.44, Modify the range of the node of hwRrmUacReachThresholdHideSsidSwitch "
						REVISION "201809051901Z"  -- Sep 05, 2018 at 19:01 GMT  
                DESCRIPTION
				"V2.43, add node hwVapNaviACID and hwVapNaviACWlanId, Modify the range of the node of hwVapType"
						REVISION "201809041852Z"  -- Sep 04, 2018 at 18:52 GMT 
				DESCRIPTION
				"V2.42, add node hwWlanNaviACManagement and hwHighwayObjects"
						REVISION "201809041452Z"  -- Sep 04, 2018 at 14:52 GMT 
				DESCRIPTION
				"V2.41, Modify the range of the node of hwSsidHideWhileReachMaxSta"
						REVISION "201808281103Z"  -- August 28, 2018 at 11:03 GMT  
				DESCRIPTION
				"V2.40, update hwRrmSmartRoamQuickKickoffSwitch  description"
						REVISION "201808101046Z"  -- August 10, 2018 at 10:46 GMT
			 	DESCRIPTION
				"V2.39,  Change hwApProfBoardcastSuppression default from 1 to 2,  hwVapBackUp add invalid(3) ,hwWlanRadioCalibrateFlexibleRadioProcess ,delete hwWlanBLEAPIKey hwWlanBLESecretKey hwWlanBLEApplicationID hwWlanBLELocationID  hwWlanBLEProtocol hwWlanBLESSLPolicyName, add node hwAPGrpCardConnType "
	  					REVISION "201808091946Z"  -- August 09, 2018 at 19:46 GMT
				DESCRIPTION
				"V2.38,  Modify the range of the node of hwRrmBandSteerClientBandsExpire."
	  					REVISION "201808061946Z"  -- August 06, 2018 at 19:46 GMT
                                                                             DESCRIPTION
                                                                             "V2.37,  change the node hwWidsWhitelistProfileSsid STRING SIZE"
				                REVISION "201807231907Z"  -- July 23, 2018 at 19:07 GMT	
				DESCRIPTION
				"V2.36,  change the node hwApProfTemporaryManagement description"
				                REVISION "201807171939Z"  -- July 17, 2018 at 19:39 GMT	
				DESCRIPTION
				"V2.35,  add node hw5gRadioDot11axGuardIntervalMode and hw2gRadioDot11axGuardIntervalMode"
				                REVISION "201807101036Z"  -- July 10, 2018 at 10:36 GMT				  
			    DESCRIPTION
				"V2.34,  add node hwFatApRadioServiceIdxEntry and hwWlanMeshProfileSwitchProbeInterval to hwWlanMeshProfileEntry."
				                REVISION "201806211510Z"  -- June 21, 2018 at 15:10 GMT
			    DESCRIPTION
				"V2.32,  Modify the hwAPSpLocation ,hwApProfSpectrumServerPort,hwWlanIDIndexedAPSpLocation ."
				                REVISION "201805181530Z"  -- May 18, 2018 at 15:30 GMT
			    DESCRIPTION
				"V2.32,  Modify the hwHotspot2ProfileEntry."
				                REVISION "201805112030Z"  -- May 11, 2018 at 20:30 GMT
			    DESCRIPTION
				"V2.31,  add node HwHotspot2ProfileEntry and hwLocationSurFilterReportFrequency to hwHotspot2ProfileEntry."
				                REVISION "201805102030Z"  -- May 10, 2018 at 20:30 GMT
			    DESCRIPTION
				"V2.30, modify node hwRrmBandSteerDenyThreshold,hwRrmBandSteerLbClientThreshold,hwRrmSmartRoamSwitch.
				Add node hwRrmLbDeauthFailTime,hwRrmLbBtmFailTime,hwRrmLbSteerRestrictTime,hwRrmLbSteerProbeRestrictThreshold,
				hwRrmLbSteerAuthRestrictThreshold,hwRrmSmartRoamAdvancedScan,hwRrmSmartRoamQuickKickoffBackOffTime."
				                REVISION "201805101430Z"  -- May 10, 2018 at 14:30 GMT        
			    DESCRIPTION
				"V2.29, modify node hwVapType and add node hwVapRadiusTemplate,hwVapBackUpState,hwVapBackUpMode,hwVapRadiusState."
				                REVISION "201804242111Z"  -- May 10, 2018 at 14:11 GMT	
			    DESCRIPTION
				"V2.28, modify node hw2gRadioProfileUtmostPowerSwitch and hw5gRadioProfileUtmostPowerSwitch."
				                REVISION "201804242111Z"  -- Apr 24, 2018 at 21:11 GMT	
				DESCRIPTION
				"V2.27, add node hwAPTrafficProfileRateLimitClientDynamic and hwAPTrafficProfileRateLimitClientDynamicThr."
				                REVISION "201804172111Z"  -- Apr 17, 2018 at 21:11 GMT	
				DESCRIPTION
				"V2.26, add node hwApProfLldpReportEnable."
				                REVISION "201803051705Z"  -- Mar 05, 2018 at 17:05 GMT	
				DESCRIPTION
				"V2.25, add node hwWlanIDIndexedAPSpDomainName and hwAPGrpDomainName"
				                REVISION "201802081458Z"
			    DESCRIPTION
				"V2.24, add node hwAPWiredPortProfilePortSec,hwAPWiredPortProfilePortSecMACMaxNum,hwAPWiredPortProfilePortSecStickyMac and hwAPWiredPortProfilePortSecProtectAction"
				                REVISION "201802011458Z"
			    DESCRIPTION
				"V2.23, modify node hwAPGroupCardWiredPortProfile and hwAPSpIoTWiredPortProfile"
								REVISION "201712271823Z"
				DESCRIPTION
				"V2.22, modify node hw2gRadioGuardIntervalMode,hw2gRadioProfileSmartAntennaLowPerThreshold,hw2gRadioProfileSmartAntThruputTrainThreshold,
				hw2gRadioProfileSmartAntennaHighPerThreshold,hw2gRadioProfileSmartAntennaTrainingInterval,
				hw5gRadioGuardIntervalMode,hw5gRadioProfileSmartAntennaLowPerThreshold,hw5gRadioProfileSmartAntThruputTrainThreshold,
				hw5gRadioProfileSmartAntennaHighPerThreshold,hw5gRadioProfileSmartAntennaTrainingInterval."
								REVISION "201712262050Z"		-- Dec 26, 2017 at 20:50 GMT 
			 	DESCRIPTION
				"V2.21, modify node description of hwAPGrpRadioSecondChannel,hwAPSpRadioSecondChannel,
				hwFatApRadioSecondChannel,hwIDIndexedAPSpRadioSecondChannel."
								REVISION "201712220950Z"		-- Dec 22, 2017 at 09:50 GMT 
				DESCRIPTION
				"V2.20, modify node name of hwRrmMultimediaOptimizedEdca."
								REVISION "201712200950Z"		-- Dec 20, 2017 at 09:50 GMT  
				DESCRIPTION
				"V2.19, modify node value of hwUCCProfLyncVoice8021pValue, hwUCCProfLyncVoiceDscpValue,  hwUCCProfLyncVideo8021pValue, hwUCCProfLyncVideoDscpValue,
                                                                             hwUCCProfLyncShare8021pValue, hwUCCProfLyncShareDscpValue, hwUCCProfLyncFileTransfer8021pValue and hwUCCProfLyncFileTransferDscpValue"
								REVISION "201712191150Z"		-- Dec 19, 2017 at 11:50 GMT
                                                                             DESCRIPTION
				"V2.18, add node hwWlanGlobalBleSourceIPAddress, hwWlanGlobalBleSourceIPv6Address,hwWlanBLESourceIPAddress and hwWlanBLESourceIPv6Address"
								REVISION "201712181100Z"		-- Dec 18, 2017 at 11:00 GMT

				DESCRIPTION
				"V2.17, modify node hw2gRadioProfileCCAThreshold and hw5gRadioProfileCCAThreshold"
								REVISION "201712131540Z"		-- Dec 13, 2017 at 15:40 GMT
				DESCRIPTION
				"V2.15, add table hwWlanStaWhitelistProfileOuiTable.
						Add node hwWlanGlobalSpectrumAnalysisSourceIPAddress and hwWlanGlobalSpectrumAnalysisSourceIPv6Address 
						Modify node hwSfnRoamCheckRssiAccumulateThreshold and hwSfnRoamCheckGapRssiThreshold
				        Modify node hw2gRadioBeaconInterval,hw5gRadioBeaconInterval,hwRrmDynamicEdcaSwitch
				        Modify node hw2gRadioProfileSmartAntennaEnable and hw5gRadioProfileSmartAntennaEnable"
								REVISION "201712091442Z"		-- Dec 9, 2017 at 14:42 GMT				  
				DESCRIPTION
				"V2.15, add table hwWlanStaWhitelistProfileOuiTable.
				        Modify node hwAPTrafficProfilePriorityMapUpTrustModeNotTunnel to hwAPTrafficProfilePriorityMapUpPayloadTrustMode
				        Modify node value of hw2gRadioProfileSmartAntennaEnable and hw5gRadioProfileSmartAntennaEnable"
								REVISION "201711251140Z"		-- Nov 25, 2017 at 11:40 GMT
				DESCRIPTION
				"V2.14, add node hwAirScanInterval"
								REVISION "201711201540Z"		-- Nov 20, 2017 at 15:40 GMT
				DESCRIPTION
				"V2.13, add node hwAPGrpVapServiceVlan,hwAPGrpVapVlanPool,hwAPSpVapServiceVlan,hwAPSpVapVlanPool,hwIDIndexedAPSpVapServiceVlan and hwIDIndexedAPSpVapVlanPool"
								REVISION "201711152030Z"		-- Nov 15, 2017 at 20:30 GMT						  
				DESCRIPTION
				"V2.12, modify node hw2gRadioBeaconInterval,hwRrmUacClientSnrThreshold,hwIDIndexedAPSpRadioEirp,hw2gRadioRtsCtsThreshold,hw5gRadioRtsCtsMode"
								REVISION "201711061500Z"		-- Nov 6, 2017 at 15:00 GMT				  
				DESCRIPTION
				"V2.11, Add node hwRrmMultimediaOptimizedEdca"
								REVISION "201710311100Z"		-- Oct 31, 2017 at 11:00 GMT
				DESCRIPTION
			    "V2.10, Add node hwWlanStaDelayOffLineSwitch ,  hwWlanStaDelayOffLineAgingTime, hwWlanStaDelayOffLineNewStaOnlineSwitch and hwWlanStaDelayOffLineMaxNum"
								REVISION "201710190930Z"		-- Oct 19, 2017 at 09:30 GMT
                                                                                    DESCRIPTION
			    "V2.09, modify hwVapStaNetworkReachableDetectSwitch to hwVapStaNetworkDetectSwitch"
								REVISION "201710171717Z"		-- Oct 17, 2017 at 17:17 GMT
                                                                                    DESCRIPTION
			    "V2.08, Add node hwAPGrpSfnRoamCtsSwitch,hwAPGrpSfnRoamBeaconSwitch,hwAPGrpSfnRoamCtsDelay,hwAPSpSfnRoamCtsSwitch,hwAPSpSfnRoamBeaconSwitch,hwAPSpSfnRoamCtsDelay,hwApProfChannelLoadMode,
			    hwApProfCardConnectType,hwAPWiredPortProfileTrafficOptimizeTcpAdjustMss,hwAPPortLinkProfileLldpdot3TlvType,hwAPPortLinkProfileLldpdot3PowerFormat,hwAPPortLinkProfileLldpLegacyTlvType,
			    hw2gRadioProfileCCAThreshold,hw2gRadioProfileSmartAntennaLowPerThreshold,hw2gRadioProfileSmartAntennaHighPerThreshold,hw2gRadioProfileSmartAntennaTrainingInterval,hw2gRadioProfileSmartAntennaTrainingMPDUNum,
			    hw2gRadioProfileSmartAntThruputTrainThreshold,hw5gRadioProfileCCAThreshold,hw5gRadioProfileSmartAntennaLowPerThreshold,hw5gRadioProfileSmartAntennaHighPerThreshold,hw5gRadioProfileSmartAntennaTrainingInterval,
			    hw5gRadioProfileSmartAntennaTrainingMPDUNum,hw5gRadioProfileSmartAntThruputTrainThreshold,hwSfnRoamCheckHighThreshold,hwSfnRoamCheckLowThreshold,hwSfnRoamCheckRssiAccumulateThreshold,hwSfnRoamCheckStaHoldingTimes,
			    hwSfnRoamCheckGapRssiThreshold,hwSfnRoamCheckBetterSnrTimes,hwSfnRoamCheckInterval,hwSfnRoamReportInterval,hwRrmMultimediaOptimizedThresholdVoice,hwRrmMultimediaOptimizedThresholdVideo,
			    hwRrmSmartRoamQuickKickoffSwitch,hwRrmSmartRoamQuickKickoffCheckType,hwRrmLoadBalanceGapStaNumThreshold,hwAirScanEnhancement,hwVapStaNetworkReachableDetectSwitch,hwSsidAdvertiseApNameSwitch,hwLocationPrivateMUVersion,
			    hwFatApChannelLoadMode,hwWlanLBGapStaNumThreshold,hwIDIndexedAPSpSfnRoamCtsSwitch,hwIDIndexedAPSpSfnRoamBeaconSwitch,hwIDIndexedAPSpSfnRoamCtsDelay,hwAPGroupCardWiredPortProfile,hwAPSpIoTWiredPortProfile"
								REVISION "201710102000Z"		-- Nov 10, 2017 at 20:00 GMT
                                                                                    
                                                                                    DESCRIPTION
			    "V2.07, Add node hwVapSfnRoamSwitch and hwAPTrafficProfileSvpVoice and hwAPTrafficProfilePriorityMapUpTrustModeNotTunnel"
								REVISION "201709131519Z"		-- Sep 13, 2017 at 15:19 GMT
                                                                                   DESCRIPTION
			    "V2.06, Add node hwSsidMuMIMOOptimizeSwitch"
								REVISION "201709111122Z"		-- Sep 11, 2017 at 11:22 GMT
				                                                   DESCRIPTION
			    "V2.05, Add node hwSsidSingleTxchainSwitch and hwApProfTemporaryManagementPsk"
								REVISION "201709081625Z"		-- Sep 8, 2017 at 16:25 GMT
				                                                   DESCRIPTION
			    "V2.04, Modify description of node hwWlanRadioCalibrateAutoStartTime and hwWlanRadioCalibratePolicy"
								REVISION "201709052225Z"		-- Sep 5, 2017 at 22:25 GMT
                                                                      DESCRIPTION
			 	"V2.03, Modify description of node hwWlanRadioCalibrateAutoStartTime and hwWlanRadioCalibratePolicy"
								REVISION "201709011710Z"		-- Sep 1, 2017 at 17:10 GMT
																	  DESCRIPTION
			 	"V2.02, Modify node hwAPGrpWPProfile"
								REVISION "201708291710Z"		-- Aug 29, 2017 at 17:10 GMT
																	  DESCRIPTION
			 	"V2.01, Modify node hwApProfProtectLinkSwitchMode, hwApProfProtectLinkSwitchGapThreshold"
								REVISION "201708202130Z"		-- Aug 20, 2017 at 21:30 GMT
																	  DESCRIPTION
			 	"V2.00, Add node hwAPWiredPortProfileMLDSnooping"
                                REVISION "201708172130Z"		-- Aug 17, 2017 at 21:30 GMT
                                                                      DESCRIPTION
			 	"V1.99, Add node hwApProfProtectLinkSwitchMode, hwApProfProtectLinkSwitchEchoProbeTime, hwApProfProtectLinkSwitchStartThreshold, hwApProfProtectLinkSwitchGapThreshold"
                                REVISION "201708011907Z"		-- Aug 01, 2017 at 19:07 GMT

                                                                      DESCRIPTION
			 	"V1.98, Add node hwRrmLoadBalanceRssiThreshold				"
                                REVISION "201708011540Z"		-- Aug 01, 2017 at 15:40 GMT

	 			DESCRIPTION
			 	"V1.97, Add node hwAPSpAutoChannelSelectSwitch, hwAPSpAutoTxPowerSelectSwitch
				"
                                REVISION "201707272004Z"		-- Jul 27, 2017 at 20:04 GMT
				DESCRIPTION
				"V1.96, Modify the default value of hwIDIndexedAPSpRadioEirp\hwRrmUacClientSnrThreshold
				"
                                REVISION "201706241640Z"		-- Jun 24, 2017 at 16:40 GMT

				DESCRIPTION
				"V1.95, Delete node hwApProfFlowControlSwitch.
				"
                                REVISION "201706221100Z"		-- Jane 22, 2017 at 11:00 GMT
				DESCRIPTION
				"V1.94, Modify the default value of hwRrmErrRateThreshold node.
				"
                                REVISION "201706141030Z"		-- Jane 14, 2017 at 10:30 GMT
			        DESCRIPTION
				"V1.93, Add node hwApProfFlowControlSwitch.
				"
                                REVISION "201706131730Z"		-- Jane 13, 2017 at 17:30 GMT
			        DESCRIPTION
				"V1.92, Add hwAPGrpSiteCode and hwWlanIndexedAPSpLocation.
				"
                                REVISION "201706131330Z"		-- Jane 13, 2017 at 13:30 GMT	

			        DESCRIPTION
				"V1.91, Add error rate check interval and traffic threshold nodes.
				"
                                REVISION "201706130830Z"		-- Jane 13, 2017 at 08:30 GMT	
				DESCRIPTION
				"V1.90, Add smart-roam quick-kickoff-snr nodes.
				"
                                REVISION "201706092010Z"		-- Jane 09, 2017 at 20:10 GMT	
                                                                                     DESCRIPTION
				"V1.89, Modify node description of hwSsidText
				"
                                REVISION "201706051058Z"		-- Jane 05, 2017 at 10:58 GMT	
                                                                                     DESCRIPTION
				"V1.88, Modify node description of hwAPWiredPortProfileLearnIpv6Address
				"
                                REVISION "201706021530Z"		-- Jane 02, 2017 at 15:30 GMT		  
                                                                                     DESCRIPTION
				"V1.87, Modify node description of hwHotspot2CarryP2PCrossConnectInfo
				"
                                REVISION "201705241500Z"		-- May 24, 2017 at 15:00 GMT

                                                                                     DESCRIPTION
				"V1.86, Modify node description of hwHotspot2CarryP2PCrossConnectInfo
				"
                                REVISION "201705171530Z"		-- May 17, 2017 at 15:30 GMT
				DESCRIPTION
				"V1.85, Modify node default value description of hwApSystemProfileTable
				"
                                REVISION "201705112000Z"		-- May 11, 2017 at 20:00 GMT			        
				DESCRIPTION
				"V1.84, Modify node default value description of hwRrmErrRateThreshold.
				"
                                REVISION "201705111505Z"		-- May 11, 2017 at 15:05 GMT
				DESCRIPTION
				"V1.83, Modify node description of hwHotspot2CarryP2PCrossConnectInfo.
				"
                                REVISION "201705101930Z"		-- May 10, 2017 at 19:30 GMT
				DESCRIPTION
				"V1.82, Add node of DFS smart selection switch and recover delay time.
				"
                                REVISION "201704291430Z"		-- April 29, 2017 at 14:30 GMT
				DESCRIPTION
				"V1.81, Add node of BLE, calibrate, paibo and load balance.
				"
                                REVISION "201703271430Z"		-- March 27, 2017 at 14:30 GMT
                                DESCRIPTION
				"V1.80, Modify node description of hwVapTunnelForwardProtocol.
				"
                                REVISION "201703271000Z"		-- March 27, 2017 at 10:00 GMT
				DESCRIPTION
				"V1.79, Add node of hwSsidQbssLoadSwitch.
				"
                                REVISION "201703091030Z"		-- March 09, 2017 at 10:30 GMT
				DESCRIPTION
				"V1.78, Add node of hwApProfCapwapDtlsDataSwitch.
				"
                                REVISION "201702061708Z"		-- Feb 06, 2017 at 17:08 GMT
				DESCRIPTION
				"V1.77, Add nodes of hwAPPortLinkProfileEEESwitch and Broadcast suppression.
				"
                                REVISION "201701051528Z"  		-- Jan 5, at 15:28 GMT
				DESCRIPTION
				"V1.76, Modify nodes sizes of hwFatApRadioMeshProfile and hwFatApLocationProfile.
				"
                                REVISION "201612211727Z"  		-- DEC 21, 2016 at 17:27 GMT
				DESCRIPTION
				"V1.75, Add nodes of hwVapDefenceProfile, hwVapTimeRange and hwVapPermitVlanList.
				"
                                REVISION "201612201058Z"  		-- DEC 20, 2016 at 10:58 GMT
				  
				DESCRIPTION
				"V1.74, Add nodes of AP configuration.
				"
                                REVISION "201612171058Z"  		-- DEC 17, 2016 at 10:58 GMT
				DESCRIPTION
				"V1.73, Add nodes of hwRrmSmartRoamQuickKickoffSnrThr and hwRrmSmartRoamQuickKickoffRateThr.
				"
                                REVISION "201612140920Z"  		-- DEC 14, 2016 at 09:20 GMT
				
				DESCRIPTION
				"V1.72, Add nodes of hwAPGrpCardNetTCPPort and hwAPSpIoTNetTCPPort.
				"
                                REVISION "201611260920Z"  		-- NOV 26, 2016 at 09:20 GMT
				
				DESCRIPTION
				"V1.71, Add nodes of hw2gRadioProfileAutoOffTimeRange and hw5gRadioProfileAutoOffTimeRange.
				"
                                REVISION "201611171050Z"  		-- NOV 17, 2016 at 10:50 GMT
				DESCRIPTION
				"V1.70, Add nodes of hwWlanMeshProfileBeacon2gRate, hwWlanMeshProfileBeacon5gRate, hwWdsProfileBeacon2gRate and hwWdsProfileBeacon5gRate.
				"
                                				REVISION "201611141050Z"  		-- NOV 14, 2016 at 10:50 GMT
				DESCRIPTION
				"V1.69, Modify the OID of node hwWlanBLEBroadcastingMajorDecimal, hwWlanBLEBroadcastingMinorHex, 
							hwWlanBLEBroadcastingMinorDecimal.
						Modify the size list of node hwWlanBLEBroadcastingMajorDecimal and hwWlanBLEBroadcastingMinorDecimal.
				"
                                				REVISION "201611031106Z"  		-- NOV 03, 2016 at 11:06 GMT
				DESCRIPTION
				"V1.68, Add nodes of hwWlanBLEBroadcastingUUIDHex, hwWlanBLEBroadcastingMajorHex, hwWlanBLEBroadcastingMajorDecimal, hwWlanBLEBroadcastingMinorHex, 
							hwWlanBLEBroadcastingMinorDecimal, hwApProfUsbSwitch.
				"
                                				REVISION "201610141444Z"  		-- Oct 14, 2016 at 14:44 GMT
			 	DESCRIPTION
				"V1.67, Modify the size list of node hwApProfPoePowerReserved, hwApProfPoePowerThreshold.
				"
                                				REVISION "201609181539Z"  		-- Sep 18, 2016 at 15:39 GMT
					DESCRIPTION
				"V1.66, Modify the node hwSsidLegacyStaSwitch.
				"
                                				REVISION "201609181013Z"  		-- Sep 18, 2016 at 10:13 GMT
				  
			        DESCRIPTION
				"V1.65, Modify the description of node hw5gRadioChannelSwitchAnnouncementSwitch, hw5gRadioVhtNssMapMaxMcs.
                                 hwIDIndexedAPSpRadioChannel,hwAPGrpRadioChannel,hwAPSpRadioChannel.
				"
                                				REVISION "201609140913Z"  		-- Sep 14, 2016 at 09:13 GMT				
			        DESCRIPTION
				"V1.64, Modify the indexes of node hwAPWiredPortProfileTrafficRemarkEntry.
					Add node of hwApProfLedOffTimeRange.
					Modify the value list of hwAPWiredPortProfileTrafficRemarkIPType and hwAPWiredPortProfileTrafficFilterType
				"
                                				REVISION "201609061146Z"  		-- Sep 6, 2016 at 11:46 GMT
				DESCRIPTION
				"V1.63, Add nodes of hwWlanMobilityServerIPv4, hwWlanMobilityServerIPv6, hwWlanMobilityServerState, hwWlanMobilityServerSwitch,
				        Add Table of hwWlanMobilityMemberIPv4Table, hwWlanMobilityMemberIPv6Table, hwWlanMobilityClientIPv4Table, hwWlanMobilityClientIPv6Table
				"
                                REVISION "201609012041Z"  -- Sep 1, 2016 at 20:41 GMT
                                
			 	DESCRIPTION
					"V1.62, Add Table of hwAPTrafficProfileRemarkTable."
                                REVISION "201608261020Z"  -- Aug 26, 2016 at 10:20 GMT
				
			 	DESCRIPTION
				"V1.61, Add node of hwWlanWideBandEnable."
                                                                REVISION "201608221020Z"
			 	DESCRIPTION
				"V1.60, Add notes,hwApProfPrimaryLinkIPv4, hwApProfPrimaryLinkIPv6, hwApProfBackupLinkIPv4,hwApProfBackupLinkIPv6."
                                                                REVISION "201608181514Z"			 	DESCRIPTION
				"V1.60, Add notes,hwApProfPrimaryLinkIPv4, hwApProfPrimaryLinkIPv6, hwApProfBackupLinkIPv4,hwApProfBackupLinkIPv6."
                                                                REVISION "201608181514Z"		-- Auguest 18, 2016 at 15:14 GMT				  
			 	DESCRIPTION
				"V1.59, Add node of hwWlanGlobalLocationSourceIPAddress and  hwWlanGlobalLocationSourceIPv6Address."
                                                                REVISION "201608170919Z"		-- Aug 17, 2016 at 09:19 GMT           
	                                                                              DESCRIPTION
				"V1.58, Add node of hwWlanReportStaAssocInfo ."
                                                                REVISION "201608161630Z"		-- Aug 16, 2016 at 16:30 GMT
				DESCRIPTION
				"V1.57, Add nodes hwAPSpLongitude, hwAPSpLatitude, hwWlanIDIndexedAPSpLongitude and hwWlanIDIndexedAPSpLatitude."
                                                                REVISION "201608121620Z"		-- Aug 12, 2016 at 16:20 GMT
                                                                                        DESCRIPTION
				"V1.56, Add nodes of of hwAirScanSwitch."
                                                                REVISION "201608091112Z"		-- Aug 9, 2016 at 11:12 GMT
                                                                                      DESCRIPTION
				"V1.55, Change the oid of hwWlanClusterConfig."
                                                                REVISION "201608011100Z"		-- Aug 1, 2016 at 11:00 GMT
                                                                                      DESCRIPTION
				"V1.54, Add nodes of hwWlanClusterConfig."
                                                                REVISION "201607250920Z"		-- July 25, 2016 at 09:20 GMT
			 	DESCRIPTION
				"V1.53, Add notes, hwApProfIGMPSnoopingGroupTable, hwAPWiredPortProfileTrafficRemarkTable."
                                                                REVISION "201607211448Z"		-- July 21, 2016 at 14:48 GMT
			 	DESCRIPTION
				"V1.52, Add notes, hwSsidProfile80211rEnable, hwSsidProfile80211rMode and hwSsidProfile80211rReassociateTimeout."
                                                                REVISION "201607121550Z"		-- July 12, 2016 at 15:50 GMT				
				DESCRIPTION
				"V1.51, Add notes, hwAPTrafficProfileMcToUcDynamicAdatptive, hwAPTrafficProfileIGMPSnoopingMaxBandwidth and hwAPTrafficProfileIGMPSnoopingMaxUser."
                                                                REVISION "201606301550Z"		-- June 30, 2016 at 15:50 GMT				  
			 	DESCRIPTION
				"V1.50, Add notes, hwVapAntiAttackARPFloodSwitch, hwVapAntiAttackARPFloodStaRateThreshold, hwVapAntiAttackARPFloodBlacklistSwitch and so on."
                                                                REVISION "201606212010Z"		-- June 21, 2016 at 20:10 GMT
			 	DESCRIPTION
				"V1.48, Add notes, hwWlanApPwdPolicyConfig and hwWlanIDIndexedAPSpBleProfile."
                                                                REVISION "201606021139Z"		-- June 2, 2016 at 11:39 GMT			 	
			 	DESCRIPTION
				"V1.47, Add notes, hwWidsStaWhitelistProfile."
                                                                REVISION "201606021000Z"		-- June 1, 2016 at 15:00 GMT
			 	DESCRIPTION
				"V1.46, Add notes, hwSsidMuMIMOSwitch and hwWdsMuMIMOSwitch."
                                                                REVISION "201606011500Z"		-- June 1, 2016 at 15:00 GMT
			 	DESCRIPTION
				"V1.45, Add notes, hwVapLearnIpv6AddressStrict and hwAPTrafficProfileOptimizeBcMcMismatchAct, and modify the range of hwSsidMaxStaNum."
                                                                REVISION "201606011400Z"		-- June 1, 2016 at 14:00 GMT
			 	DESCRIPTION
				"V1.44, Add notes for hwIDIndexedAPSpecificRadioIdTable."
                                                                REVISION "201605241711Z"		-- May 24, 2016 at 17:11 GMT
				DESCRIPTION
				"V1.43, Add notes, hwWlanAPProvisionAPMode, hwWlanAPProvisionCommitAPId and hwWlanAPProvisionCommitAll."
                                                                REVISION "201605231613Z"		-- May 23, 2016 at 16:13 GMT
				DESCRIPTION
				"V1.42, Add notes, hwWlanMeshProfileClientModeSwitch."
                                                                REVISION "201605181600Z"		-- May 18, 2016 at 16:00 GMT
				  
				DESCRIPTION
				"V1.41, Modify the range of hwAPGrpCardNetUDPPort, hwAPSpIoTNetUDPPort, hwIoTProfileManagementServerPort, hwIoTSerialStopbits and hwIoTProfileShareKey."
                                                                REVISION "201605131607Z"		-- May 13, 2016 at 16:07 GMT

				DESCRIPTION
				"V1.40, Add notes, hwWlanStaWhitelistStaMacDescription, hwWlanStaBlacklistStaMacDescription." 
                                                                REVISION "201605061138Z"		-- May 6, 2016 at 11:38 GMT
							  
				DESCRIPTION
				"V1.39, Add notes, hwAPWiredPortProfileIGMPSnooping." 
                                                                REVISION "201604151738Z"		-- April 15, 2016 at 17:38 GMT

				DESCRIPTION												
				"The MIB module defines the configuration of AP." 
                                                                REVISION "201603291531Z"		-- March 29, 2016 at 15:31 GMT 
				DESCRIPTION 
				"V1.38, Add notes, hwAPGrpBleProfile, hwAPSpBleProfile."
                                                                
                                                                REVISION "201603251531Z"		-- March 25, 2016 at 15:31 GMT 
				DESCRIPTION 
				"V1.36, Modify the range of hwAPTrafficProfileOptimizeSuppressionBc, hwAPTrafficProfileOptimizeSuppressionUc, hwAPTrafficProfileOptimizeSuppressionMc and hwCellularNetworkProfilePlmnIDList."

                                                                REVISION "201603221531Z"		-- March 22, 2016 at 15:31 GMT 
				DESCRIPTION 
				"V1.36, Modify the range of hwAPTrafficProfileOptimizeSuppressionBc, hwAPTrafficProfileOptimizeSuppressionUc, hwAPTrafficProfileOptimizeSuppressionMc and hwCellularNetworkProfilePlmnIDList."

                                                                REVISION "201603211546Z"		-- March 21, 2016 at 15:46 GMT 
				DESCRIPTION 
				"V1.35, Add nodes for hwVapAntiAttackBroadcastFloodSwitch, hwVapAntiAttackBroadcastFloodStaRateThreshold and hwVapAntiAttackBroadcastFloodBlacklistSwitch."
				
                                                                REVISION "201603152015Z"		-- March 15, 2016 at 20:15 GMT 
				DESCRIPTION 
				"V1.34, Modify the description of hwApProfMeshRole."

			REVISION "201603101136Z"		-- March 10, 2016 at 11:36 GMT 
				DESCRIPTION 
				"V1.33, Modify the range of mib nodes."

                                                    REVISION "201602271436Z"		-- Feb 27, 2016 at 14:36 GMT 
				DESCRIPTION 
				"V1.32, Modify the description of hwAPGrpRadioFrequency and hwAPSpRadioFrequency." 
			REVISION "201602051436Z"		-- Feb 5, 2016 at 14:36 GMT 
				DESCRIPTION 
				"V1.31, Add nodes for hwBleProfileTable, hwAPGroupCardTable, hwAPSpecificCardTable, hwIoTSerialProfileTable, hwIoTProfileTable and hwIoTProfileManagementServerTable ." 
			REVISION "201601121347Z"		-- JAN 12, 2016 at 13:47 GMT 
				DESCRIPTION 
				"V1.30, Add nodes for hwWlanIDIndexedAPSpecificTable, hwIDIndexedAPSpecificWiredPortTable, hwIDIndexedAPSpecificRadioIdTable and hwIDIndexedAPSpecificVapTable ." 
			REVISION "201512231525Z"		-- DEC 23, 2015 at 15:25 GMT 
				DESCRIPTION 
				"V1.29, Add nodes for hwAPWiredPortProfileTable and hwAPPortLinkProfileTable." 
            REVISION "201512172024Z"		-- DEC 17, 2015 at 20:24 GMT 
				DESCRIPTION 
				"V1.28, Modify nodes for hwAPWiredPortProfilePortMode , hwAPGrpWPInterfaceNum, hwAPSpWPInterfaceNum, hwWlanApDataCollectionInterval." 				
            REVISION "201511211025Z"		-- NOV 21, 2015 at 10:25 GMT 
				DESCRIPTION 
				"V1.27, Add nodes for hwApSystemProfileTable and hwAPPortLinkProfileTable." 
            REVISION "201510292030Z"		-- Oct 29, 2015 at 20:30 GMT 
				DESCRIPTION 
				"V1.26, Modify the range of mib nodes."
			REVISION "201510101030Z"		-- Oct 10, 2015 at 10:30 GMT 
				DESCRIPTION 
				"V1.25, Modify the range of mib nodes."
			REVISION "201509251030Z"		-- Sept 25, 2015 at 10:30 GMT 
				DESCRIPTION 
				"V1.24, Modify the range of hwSsidClientEdcaVoiceTXOPLimit."
			REVISION "201509151030Z"		-- Sept 15, 2015 at 10:30 GMT 
				DESCRIPTION 
				"V1.23, Add invalid parameter in the hwAPSpecificRadioTable."
			REVISION "201508261530Z"		-- August 26, 2015 at 15:30 GMT
    			DESCRIPTION 
				"V1.22, Modify the nodes of HUAWEI-WLAN-CONFIGURATION-MIB file." 
			REVISION "201508051530Z"		-- August 5, 2015 at 15:30 GMT
    			DESCRIPTION 
				"V1.21, Modify the nodes of HUAWEI-WLAN-CONFIGURATION-MIB file." 
			REVISION "201508050950Z"		-- August 5, 2015 at 9:50 GMT
    			DESCRIPTION 
				"V1.20, Modify the nodes of HUAWEI-WLAN-CONFIGURATION-MIB file." 
			REVISION "201507230950Z"		-- July 23, 2015 at 9:50 GMT
    			DESCRIPTION 
				"V1.19, Modify the range of hwSecurityWapiAcPrvKeyFileName." 
                                                       REVISION "201507221048Z"		-- July 22, 2015 at 10:48 GMT
			DESCRIPTION
				"V1.18, Add nodes for hwVapOptinon82RidUserDefined, hwVapOptinon82RidMacFormat,hwVapOptinon82InsertCidFormat , hwVapOptinon82CidUserDefined, 
							hwVapOptinon82CidMacFormat, hwSsidBeacon2gRate, hwSsidBeacon5gRate, hwSsidDenyBroadcastProbe, hwSsidProbeResponseRetry, 
							hwSsidUapsd, hwSsidActiveDullClient, hwWlanMeshProfilePriorityMapTrustMode, hwWlanMeshProfilePriorityDscpMap80211e, 
							hwWdsProfilePriorityMapTrustMode, hwWdsProfilePriorityDscpMap80211e"
			REVISION "201507101400Z"		-- July 10, 2015 at 14:00 GMT
			DESCRIPTION
				"V1.17, Add nodes for hw2gRadioProfileRadioType,hw5gRadioProfileRadioType,hwWlanCountryCodeTable"
    			REVISION "201506231400Z"		-- June 23, 2015 at 14:00 GMT
			DESCRIPTION
				"V1.16, Add nodes for hwWlanMeshProfileTable,hwApSystemProfileTable,hwAPTrafficProfileTable,hwSoftgreProfileTable."
			REVISION "201506211040Z"		-- June 21, 2015 at 10:40 GMT
			DESCRIPTION
				"V1.15, Add nodes for report sta info."
			REVISION "201506160910Z"		-- June 16, 2015 at 9:10 GMT
			DESCRIPTION
				"V1.14, Add nodes for eirp."			
			REVISION "201506021110Z"		-- June 2, 2015 at 11:10 GMT
			DESCRIPTION
				"V1.13, Add nodes for antenna output mode."
			REVISION "201505131430Z"		-- May 13, 2015 at 14:30 GMT
			DESCRIPTION
				"V1.12, Modify the range of hwAPTrafficProfileFilterACLID."
			REVISION "201505121430Z"                               -- May 12, 2015 at 14:30 GMT 
			DESCRIPTION 
				"V1.11, Add the description of mib nodes." 
			REVISION "201505111430Z"		-- May 11, 2015 at 14:30 GMT
			DESCRIPTION
				"V1.10, Change value of hwLocationPrivateMuEnable."   
			REVISION "201505041430Z"		-- May 4, 2015 at 14:30 GMT
			DESCRIPTION
				"V1.09, Add nodes for hwWlanMeshProfileTable."   
			REVISION "201504271550Z"		-- April 27, 2015 at 15:50 GMT
			DESCRIPTION
				"V1.08, Add nodes for utmost power switch."   
			REVISION "201504231150Z"		-- April 23, 2015 at 11:50 GMT
			DESCRIPTION
				"V1.07, Add some nodes."   
			REVISION "201504200930Z"		-- April 20, 2015 at 9:30 GMT
			DESCRIPTION
				"V1.06, Modify the range of some nodes."
			REVISION "201504131015Z"		-- April 13, 2015 at 10:15 GMT
			DESCRIPTION
				"V1.05, Modify the sequence of some table's index and the range of some nodes."
			REVISION "201504101455Z"		-- April 10, 2015 at 14:55 GMT
			DESCRIPTION
				"V1.04, 1.Modify the range of hwWidsConfidentOuiWhitelistOui, hwAPGrpWidsProfile, hwAPGrpLocationProfile, hwAPGrpSpectrumProfile, 
											hwAPSp2gRadioProfile, hwAPSpDomainProfile, hwAPSp5gRadioProfile, hwAPSpWidsProfile,
											hwAPSpLocationProfile, hwAPSpSpectrumProfile, hwWidsContainProfile, hwWidsSpoofProfile, hwWidsConfidentProfile.
						2.Add hwWlanLoadBalanceStaticGroupTable.
						3.Delete the node hwRrmLoadBalanceGrpName and add node hwRrmSmartRoamType."
			REVISION "201503301835Z"		-- March 30, 2015 at 18:35 GMT
			DESCRIPTION
				"V1.02, Modify the name of the node of hwAPProvision."
		    REVISION "201503090935Z"		-- March 9, 2015 at 09:35 GMT
			DESCRIPTION
				"V1.01, Modify the range of hwApProfHighTempThreshold and hwAPWiredPortProfilePortEthTrunkID."
	                REVISION "201502021055Z"		-- February 2, 2015 at 10:55 GMT
			DESCRIPTION
				"V1.00, Inital version."
			::= { hwWlan 11 }

--
--Node definitions
--

		--1.3.6.1.4.1.2011.6.139.11.1
		hwWlanConfigObjects OBJECT IDENTIFIER ::= { hwWlanConfig 1 }

		--1.3.6.1.4.1.2011.6.139.11.1.1
		hwWlanGlobalConfig OBJECT IDENTIFIER ::= { hwWlanConfigObjects 1 }

		 --1.3.6.1.4.1.2011.6.139.11.1.1.1
		hwWlanGlobalApUsername OBJECT-TYPE
			SYNTAX OCTET STRING (SIZE (4..31))
			MAX-ACCESS read-write
			STATUS current
			DESCRIPTION 
				"This object indicates user names for Telnet-based login to APs."
			::= { hwWlanGlobalConfig 1 }

		 --1.3.6.1.4.1.2011.6.139.11.1.1.2
		hwWlanGlobalApPassword OBJECT-TYPE
			SYNTAX OCTET STRING (SIZE (8..32))
			MAX-ACCESS read-write
			STATUS current
			DESCRIPTION 
				"This object indicates passwords for Telnet-based login to APs."
			::= { hwWlanGlobalConfig 2 }

		 --1.3.6.1.4.1.2011.6.139.11.1.1.3
		hwWlanUsernamePasswordApMac OBJECT-TYPE
			SYNTAX MacAddress
			MAX-ACCESS read-write
			STATUS current
			DESCRIPTION 
				"This object indicates query and setting of MAC addresses of clients logging in to APs."
			::= { hwWlanGlobalConfig 3 }

		 --1.3.6.1.4.1.2011.6.139.11.1.1.4
		hwWlanGlobalApLldpSwitch OBJECT-TYPE
			SYNTAX INTEGER
				{
				disable(1) ,
				enable(2)
				}
			MAX-ACCESS read-write
			STATUS current
			DESCRIPTION 
				"This object indicates the status of the global LLDP function. The default value is 2."
			::= { hwWlanGlobalConfig 4 }

		 --1.3.6.1.4.1.2011.6.139.11.1.1.5
		hwWlanGlobalIpv6Enable OBJECT-TYPE
			SYNTAX INTEGER
				{
				disable(1),
				enable(2)
				}
			MAX-ACCESS read-write
			STATUS current
			DESCRIPTION 
				"This object indicates the status of the global IPv6 function. The default value is 1."
			::= { hwWlanGlobalConfig 5 }

		 --1.3.6.1.4.1.2011.6.139.11.1.1.6
		hwWlanStationIpv6Enable OBJECT-TYPE
			SYNTAX INTEGER
				{
				disable(1) ,
				enable(2)
				}
			MAX-ACCESS read-write
			STATUS current
			DESCRIPTION
				"This object indicates the status of the IPv6 function of users. The default value is 1 . 1: disable 2: enable."
			::= { hwWlanGlobalConfig 6 }

		 --1.3.6.1.4.1.2011.6.139.11.1.1.7
		hwWlanApDataCollectionInterval OBJECT-TYPE
			SYNTAX Integer32 (5..60 | 255)
			MAX-ACCESS read-write
			STATUS current
			DESCRIPTION 
				"This object indicates the period of caching AP performance. The default value is 15. It is expressed in minutes."
			::= { hwWlanGlobalConfig 7 }

		 --1.3.6.1.4.1.2011.6.139.11.1.1.8
		hwTestRtCollectOnoff OBJECT-TYPE
			SYNTAX Integer32
			MAX-ACCESS read-write
			STATUS current
			DESCRIPTION 
				"This object indicates the status of the real-time collection switch."
			::= { hwWlanGlobalConfig 8 }

		 --1.3.6.1.4.1.2011.6.139.11.1.1.9
		hwTestApNormalCollectCycle OBJECT-TYPE
			SYNTAX Integer32
			MAX-ACCESS read-write
			STATUS current
			DESCRIPTION 
				"This object indicates the regular period of an AC collecting AP performance data."
			::= { hwWlanGlobalConfig 9 }

		 --1.3.6.1.4.1.2011.6.139.11.1.1.10
		hwTestApRtCollectCycle OBJECT-TYPE
			SYNTAX Integer32
			MAX-ACCESS read-write
			STATUS current
			DESCRIPTION 
				"This object indicates the real-time period of an AC collecting AP performance data."
			::= { hwWlanGlobalConfig 10 }

		 --1.3.6.1.4.1.2011.6.139.11.1.1.11
		hwWlanConfigCommitAll OBJECT-TYPE
			SYNTAX Integer32
			MAX-ACCESS read-write
			STATUS current
			DESCRIPTION 
				"Description."
			::= { hwWlanGlobalConfig 11 }

		--1.3.6.1.4.1.2011.6.139.11.1.1.12
		hwWlanProtect OBJECT IDENTIFIER ::= { hwWlanGlobalConfig 12 }

		 --1.3.6.1.4.1.2011.6.139.11.1.1.12.1
		hwWlanProtectIpAddress OBJECT-TYPE
			SYNTAX IpAddress
			MAX-ACCESS read-write
			STATUS current
			DESCRIPTION 
				"This object indicates the IP address of the standby AC."
			::= { hwWlanProtect 1 }

		 --1.3.6.1.4.1.2011.6.139.11.1.1.12.2
		hwWlanProtectIPv6Address OBJECT-TYPE
			SYNTAX OCTET STRING
			MAX-ACCESS read-write
			STATUS current
			DESCRIPTION 
				"This object indicates setting of the IPv6 address of the standby AC."
			::= { hwWlanProtect 2 }

		 --1.3.6.1.4.1.2011.6.139.11.1.1.12.3
		hwWlanProtectPriority OBJECT-TYPE
			SYNTAX Unsigned32 (0..7)
			MAX-ACCESS read-write
			STATUS current
			DESCRIPTION 
				"This object indicates the AC priority that determines whether the AC can be selected as the active AC. The default value is 0."
			::= { hwWlanProtect 3 }

		 --1.3.6.1.4.1.2011.6.139.11.1.1.12.4
		hwWlanProtectSwitch OBJECT-TYPE
			SYNTAX INTEGER
				{
				enable(1) ,
				disable(2)
				}
			MAX-ACCESS read-write
			STATUS current
			DESCRIPTION 
				"This object indicates the status of the hot backup function. The default value is 2."
			::= { hwWlanProtect 4 }

		 --1.3.6.1.4.1.2011.6.139.11.1.1.12.5
		hwWlanProtectRestoreSwitch OBJECT-TYPE
			SYNTAX INTEGER
				{
				enable(1) ,
				disable(2)
				}
			MAX-ACCESS read-write
			STATUS current
			DESCRIPTION 
				"This object indicates the status of the switchback function. The default value is 1."
			::= { hwWlanProtect 5 }

		 --1.3.6.1.4.1.2011.6.139.11.1.1.12.6
		hwUndoWlanProtectIpAddress OBJECT-TYPE
			SYNTAX Integer32
			MAX-ACCESS read-write
			STATUS current
			DESCRIPTION 
				"This object indicates whether to restore the default setting of the IP address of the standby AC."
			::= { hwWlanProtect 6 }

		 --1.3.6.1.4.1.2011.6.139.11.1.1.12.7
		hwUndoWlanProtectPriority OBJECT-TYPE
			SYNTAX Integer32
			MAX-ACCESS read-write
			STATUS current
			DESCRIPTION 
				"This object indicates whether to restore the default setting of the priority of the standby AC."
			::= { hwWlanProtect 7 }
		
		-- 1.3.6.1.4.1.2011.6.139.11.1.1.12.8
		hwUndoWlanProtectIPv6Address OBJECT-TYPE
			SYNTAX Integer32
			MAX-ACCESS read-write
			STATUS current
			DESCRIPTION
				"This object indicates whether to restore the default setting of the IPv6 address of the standby AC."
			::= { hwWlanProtect 8 }
		

		-- 1.3.6.1.4.1.2011.6.139.11.1.1.13
		hwWlanBackupHsbConfig OBJECT IDENTIFIER ::= { hwWlanGlobalConfig 13 }

		 --1.3.6.1.4.1.2011.6.139.11.1.1.13.1
		hwWlanCfgHsbServiceType OBJECT-TYPE
			SYNTAX INTEGER
				{
				disable(1),
				hsbGroup(2),
				hsbService(3)
				}
			MAX-ACCESS read-write
			STATUS current
			DESCRIPTION 
				"This object indicates the HSB type. The default value is 1."
			::= { hwWlanBackupHsbConfig 1 }

		 --1.3.6.1.4.1.2011.6.139.11.1.1.13.2
		hwWlanCfgHsbGroupId OBJECT-TYPE
			SYNTAX Unsigned32
			MAX-ACCESS read-write
			STATUS current
			DESCRIPTION 
				"This object indicates the HSB group ID. If the HSB type is set to Disable, the ID is 0xFFFFFFFF."
			::= { hwWlanBackupHsbConfig 2 }

		 --1.3.6.1.4.1.2011.6.139.11.1.1.13.3
		hwWlanCfgHsbTunnelId OBJECT-TYPE
			SYNTAX Unsigned32
			MAX-ACCESS read-write
			STATUS current
			DESCRIPTION 
				"This object indicates the ID of the HSB channel. If the HSB type is set to Disable, the ID is 0xFFFFFFFF."
			::= { hwWlanBackupHsbConfig 3 }

		--1.3.6.1.4.1.2011.6.139.11.1.1.14
		hwWlanCommitTable OBJECT-TYPE
			SYNTAX SEQUENCE OF HwWlanCommitEntry 
			MAX-ACCESS not-accessible
			STATUS current
			DESCRIPTION 
				"Description."
			::= { hwWlanGlobalConfig 14 }

		--1.3.6.1.4.1.2011.6.139.11.1.1.14.1
		hwWlanCommitEntry OBJECT-TYPE
			SYNTAX HwWlanCommitEntry 
			MAX-ACCESS not-accessible
			STATUS current
			DESCRIPTION 
				"Description."
			INDEX { hwWlanCommitApMac }
			::= { hwWlanCommitTable 1 }


		HwWlanCommitEntry ::=
			SEQUENCE {				
				hwWlanCommitApMac
					MacAddress,
				hwWlanConfigCommit
					Integer32 
			 }

		 --1.3.6.1.4.1.2011.6.139.11.1.1.14.1.1
		hwWlanCommitApMac OBJECT-TYPE
			SYNTAX MacAddress
			MAX-ACCESS not-accessible
			STATUS current
			DESCRIPTION 
				"Description."
			::= { hwWlanCommitEntry 1 }

		 --1.3.6.1.4.1.2011.6.139.11.1.1.14.1.2
		hwWlanConfigCommit OBJECT-TYPE
			SYNTAX Integer32
			MAX-ACCESS read-write
			STATUS current
			DESCRIPTION 
				"Description."
			::= { hwWlanCommitEntry 2 }

		
		-- 1.3.6.1.4.1.2011.6.139.11.1.1.15
		hwWlanReportStaInfo OBJECT-TYPE
			SYNTAX INTEGER
				{
				disable(1),
				enable(2)
				}
			MAX-ACCESS read-write
			STATUS current
			DESCRIPTION
				"This object indicates the switch of recording user information in the log. 1:disable 2:enable."
			::= { hwWlanGlobalConfig 15 }

		-- 1.3.6.1.4.1.2011.6.139.11.1.1.16
		hwWlanBLELowPowerWarningThreshold OBJECT-TYPE
			SYNTAX Integer32
			MAX-ACCESS read-write
			STATUS current
			DESCRIPTION
				"Description."
			::= { hwWlanGlobalConfig 16 }

		-- 1.3.6.1.4.1.2011.6.139.11.1.1.17
		hwWlanBLEMonitorListTable OBJECT-TYPE
			SYNTAX SEQUENCE OF HwWlanBLEMonitorListEntry
			MAX-ACCESS not-accessible
			STATUS current
			DESCRIPTION
				"Description."
			::= { hwWlanGlobalConfig 17 }
			
		-- 1.3.6.1.4.1.2011.6.139.11.1.1.17.1
		hwWlanBLEMonitorListEntry OBJECT-TYPE
			SYNTAX HwWlanBLEMonitorListEntry
			MAX-ACCESS not-accessible
			STATUS current
			DESCRIPTION
				"Description."
			INDEX { hwWlanBLEMonitoringListMac }
			::= { hwWlanBLEMonitorListTable 1 }
			
		HwWlanBLEMonitorListEntry ::=
			SEQUENCE { 
				hwWlanBLEMonitoringListMac
					MacAddress,
				hwWlanBLEMonitoringListRowStatue
					RowStatus
			 }

		-- 1.3.6.1.4.1.2011.6.139.11.1.1.17.1.1
		hwWlanBLEMonitoringListMac OBJECT-TYPE
			SYNTAX MacAddress
			MAX-ACCESS not-accessible
			STATUS current
			DESCRIPTION
				"Description."
			::= { hwWlanBLEMonitorListEntry 1 }
			
		-- 1.3.6.1.4.1.2011.6.139.11.1.1.17.1.2
		hwWlanBLEMonitoringListRowStatue OBJECT-TYPE
			SYNTAX RowStatus
			MAX-ACCESS read-write
			STATUS current
			DESCRIPTION
				"Description."
			::= { hwWlanBLEMonitorListEntry 2 }
		-- 1.3.6.1.4.1.2011.6.139.11.1.1.18
		hwWlanApPwdPolicyConfig OBJECT IDENTIFIER ::= { hwWlanGlobalConfig 18 }
		
--  1.3.6.1.4.1.2011.6.139.11.1.1.18.1
		-- 1.3.6.1.4.1.2011.6.139.11.1.1.18.1
		hwApPwdPolicyEnable OBJECT-TYPE
			SYNTAX INTEGER
				{
				disable(1),
				enable(2)
				}
			MAX-ACCESS read-write
			STATUS current
			DESCRIPTION
				"Ap password policy,the default is disable"
			::= { hwWlanApPwdPolicyConfig 1 }
		
--  1.3.6.1.4.1.2011.6.139.11.1.1.18.2
		-- 1.3.6.1.4.1.2011.6.139.11.1.1.18.2
		hwApPwdPolicyExpire OBJECT-TYPE
			SYNTAX Unsigned32 (0..999)
			MAX-ACCESS read-write
			STATUS current
			DESCRIPTION
				"Set the days of password expire,the default is 90"
			::= { hwWlanApPwdPolicyConfig 2 }
		
--  1.3.6.1.4.1.2011.6.139.11.1.1.18.3
		-- 1.3.6.1.4.1.2011.6.139.11.1.1.18.3
		hwApPwdPolicyHistoryRecordNum OBJECT-TYPE
			SYNTAX Unsigned32 (0..12)
			MAX-ACCESS read-write
			STATUS current
			DESCRIPTION
				"The number of password history record,the default is 5"
			::= { hwWlanApPwdPolicyConfig 3 }
		
--  1.3.6.1.4.1.2011.6.139.11.1.1.18.4
		-- 1.3.6.1.4.1.2011.6.139.11.1.1.18.4
		hwApPwdPolicyAlertBefore OBJECT-TYPE
			SYNTAX Unsigned32 (0..999)
			MAX-ACCESS read-write
			STATUS current
			DESCRIPTION
				"The days of password before-expire,the default is 30"
			::= { hwWlanApPwdPolicyConfig 4 }
		
--  1.3.6.1.4.1.2011.6.139.11.1.1.18.5
		-- 1.3.6.1.4.1.2011.6.139.11.1.1.18.5
		hwApPwdPolicyAlertOriginal OBJECT-TYPE
			SYNTAX INTEGER
				{
				disable(1),
				enable(2)
				}
			MAX-ACCESS read-write
			STATUS current
			DESCRIPTION
				"Set password original-alert,the default is enable"
			::= { hwWlanApPwdPolicyConfig 5 }
		
--  1.3.6.1.4.1.2011.6.139.11.1.1.18.6
		-- 1.3.6.1.4.1.2011.6.139.11.1.1.18.6
		hwApPwdSetTime OBJECT-TYPE
			SYNTAX OCTET STRING (SIZE (0..32))
			MAX-ACCESS read-only
			STATUS current
			DESCRIPTION
				"Get the password set time"
			::= { hwWlanApPwdPolicyConfig 6 }
		
--  1.3.6.1.4.1.2011.6.139.11.1.1.18.7
		-- 1.3.6.1.4.1.2011.6.139.11.1.1.18.7
		hwApPwdIsExpired OBJECT-TYPE
			SYNTAX INTEGER
				{
				notexpired(1),
				expired(2)
				}
			MAX-ACCESS read-only
			STATUS current
			DESCRIPTION
				"Query password is expired or not"
			::= { hwWlanApPwdPolicyConfig 7 }
		
--  1.3.6.1.4.1.2011.6.139.11.1.1.18.8
		-- 1.3.6.1.4.1.2011.6.139.11.1.1.18.8
		hwApPwdIsOrginal OBJECT-TYPE
			SYNTAX INTEGER
				{
				notoriginal(1),
				original(2)
				}
			MAX-ACCESS read-only
			STATUS current
			DESCRIPTION
				"Query password is original or not"
			::= { hwWlanApPwdPolicyConfig 8 }

                                           -- 1.3.6.1.4.1.2011.6.139.11.1.1.19
		hwWlanReportStaAssocInfo OBJECT-TYPE
			SYNTAX INTEGER
				{
				disable(1),
				enable(2)
				}
			MAX-ACCESS read-write
			STATUS current
			DESCRIPTION
				"This object indicates the switch of recording user online and offline information in the log. 1:disable 2:enable."
			::= { hwWlanGlobalConfig 19 }	
		-- 1.3.6.1.4.1.2011.6.139.11.1.1.20
		hwWlanGlobalLocationSourceIPAddress OBJECT-TYPE
			SYNTAX IpAddress
			MAX-ACCESS read-write
			STATUS current
			DESCRIPTION
				"This object indicates the global source IPv4 address for reporting location data in AeroScout or Ekahau location mode. You choose an IPv4 or IPv6 address."
			::= { hwWlanGlobalConfig 20 }
		-- 1.3.6.1.4.1.2011.6.139.11.1.1.21
		hwWlanGlobalLocationSourceIPv6Address OBJECT-TYPE
			SYNTAX OCTET STRING
			MAX-ACCESS read-write
			STATUS current
			DESCRIPTION
				"This object indicates the global source IPv6 address for reporting location data in AeroScout or Ekahau location mode. You choose an IPv4 or IPv6 address."
			::= { hwWlanGlobalConfig 21 }
		
		-- 1.3.6.1.4.1.2011.6.139.11.1.1.22
		hwWlanBLEEquipReportInterval OBJECT-TYPE
			SYNTAX Unsigned32 (1..60)
			MAX-ACCESS read-write
			STATUS current
			DESCRIPTION
				"Description."
			DEFVAL { 10 }
			::= { hwWlanGlobalConfig 22 }

		-- 1.3.6.1.4.1.2011.6.139.11.1.1.23
		hwWlanStaDelayOffline OBJECT IDENTIFIER ::= { hwWlanGlobalConfig 23 }
		
		-- 1.3.6.1.4.1.2011.6.139.11.1.1.23.1
		hwWlanStaDelayOffLineSwitch  OBJECT-TYPE
			SYNTAX INTEGER
				{
				disable(1),
				enable(2)
				}
			MAX-ACCESS read-write
			STATUS current
			DESCRIPTION
				"This object indicates the switch of station delay offline. 1:disable 2:enable."
			::= { hwWlanStaDelayOffline 1 }
		
		-- 1.3.6.1.4.1.2011.6.139.11.1.1.23.2
		hwWlanStaDelayOffLineAgingTime OBJECT-TYPE
			SYNTAX Integer32 (1..86400)
			MAX-ACCESS read-write
			STATUS current
			DESCRIPTION
				"This object indicates the station delay offline aging time. range(1..86400)"
			DEFVAL { 180 }
			::= { hwWlanStaDelayOffline 2 }
		
		-- 1.3.6.1.4.1.2011.6.139.11.1.1.23.3
		hwWlanStaDelayOffLineNewStaOnlineSwitch OBJECT-TYPE
			SYNTAX INTEGER
				{
				disable(1),
				enable(2)
				}
			MAX-ACCESS read-write
			STATUS current
			DESCRIPTION
				"This object indicates the switch of station delay offline new station online. 1:disable 2:enable."
			::= { hwWlanStaDelayOffline 3 }
		
		-- 1.3.6.1.4.1.2011.6.139.11.1.1.23.4
		hwWlanStaDelayOffLineMaxNum  OBJECT-TYPE
			SYNTAX Integer32 (1..1024000)
			MAX-ACCESS read-write
			STATUS current
			DESCRIPTION
				"This object indicates the max number of station delay offline. range (1..max)"
			::= { hwWlanStaDelayOffline 4 }
			
		-- 1.3.6.1.4.1.2011.6.139.11.1.1.24
		hwWlanGlobalSpectrumAnalysisSourceIPAddress OBJECT-TYPE
			SYNTAX IpAddress
			MAX-ACCESS read-write
			STATUS current
			DESCRIPTION
				"This object indicates the spectrum-analysis source IPv4 address for reporting spectrum-analysis data in spectrum-analysis server. You choose an IPv4 or IPv6 address."
			::= { hwWlanGlobalConfig 24 }
		-- 1.3.6.1.4.1.2011.6.139.11.1.1.25
		hwWlanGlobalSpectrumAnalysisSourceIPv6Address OBJECT-TYPE
			SYNTAX OCTET STRING
			MAX-ACCESS read-write
			STATUS current
			DESCRIPTION
				"This object indicates the spectrum-analysis source IPv6 address for reporting spectrum-analysis data in spectrum-analysis server. You choose an IPv4 or IPv6 address."
			::= { hwWlanGlobalConfig 25 }	

                                  	-- 1.3.6.1.4.1.2011.6.139.11.1.1.26
		hwWlanGlobalBleSourceIPAddress OBJECT-TYPE
			SYNTAX IpAddress
			MAX-ACCESS read-write
			STATUS current
			DESCRIPTION
				"This object indicates the global source IPv4 address for reporting ble location data. You choose an IPv4 address."
			::= { hwWlanGlobalConfig 26 }
			
		-- 1.3.6.1.4.1.2011.6.139.11.1.1.27
		hwWlanGlobalBleSourceIPv6Address OBJECT-TYPE
			SYNTAX OCTET STRING
			MAX-ACCESS read-write
			STATUS current
			DESCRIPTION
				"This object indicates the global source IPv6 address for reporting ble location data. You choose an IPv6 address."
			::= { hwWlanGlobalConfig 27 }	
			
		-- 1.3.6.1.4.1.2011.6.139.11.1.1.28
		hwWlanManualContainListTable OBJECT-TYPE
			SYNTAX SEQUENCE OF HwWlanManualContainListEntry
			MAX-ACCESS not-accessible
			STATUS current
			DESCRIPTION
				"Description."
			::= { hwWlanGlobalConfig 28 }
		-- 1.3.6.1.4.1.2011.6.139.11.1.1.28.1
		hwWlanManualContainListEntry OBJECT-TYPE
			SYNTAX HwWlanManualContainListEntry
			MAX-ACCESS not-accessible
			STATUS current
			DESCRIPTION
				"Description."
			INDEX { hwWlanManualContainListMac }
			::= { hwWlanManualContainListTable 1 }
		HwWlanManualContainListEntry ::=
			SEQUENCE { 
				hwWlanManualContainListMac
					MacAddress,
				hwWlanManualContainListRowStatus
					RowStatus
			 }
		-- 1.3.6.1.4.1.2011.6.139.11.1.1.28.1.1
		hwWlanManualContainListMac OBJECT-TYPE
			SYNTAX MacAddress
			MAX-ACCESS not-accessible
			STATUS current
			DESCRIPTION
				"Description."
			::= { hwWlanManualContainListEntry 1 }
		-- 1.3.6.1.4.1.2011.6.139.11.1.1.28.1.2
		hwWlanManualContainListRowStatus OBJECT-TYPE
			SYNTAX RowStatus
			MAX-ACCESS read-write
			STATUS current
			DESCRIPTION
				"Description."
			::= { hwWlanManualContainListEntry 2 }
		
		-- 1.3.6.1.4.1.2011.6.139.11.1.1.29
		hwWlanLicenseCentralizedManagement OBJECT IDENTIFIER ::= { hwWlanGlobalConfig 29 }
		
		-- 1.3.6.1.4.1.2011.6.139.11.1.1.29.1
		hwWlanLicenseCentralizedGlobal OBJECT IDENTIFIER ::= { hwWlanLicenseCentralizedManagement 1 }
		
		-- 1.3.6.1.4.1.2011.6.139.11.1.1.29.1.1
		hwWlanLicenseCentralizedSwitch OBJECT-TYPE
			SYNTAX INTEGER
				{
				disable(1),
				enable(2)
				}
			MAX-ACCESS read-write
			STATUS current
			DESCRIPTION
				"This object indicates the swtich of license centralized. The default value is 1."
			::= { hwWlanLicenseCentralizedGlobal 1 }
		
		-- 1.3.6.1.4.1.2011.6.139.11.1.1.29.1.2
		hwWlanLicenseCentralizedServerIPv4Addr OBJECT-TYPE
			SYNTAX IpAddress
			MAX-ACCESS read-write
			STATUS current
			DESCRIPTION
				"This object indicates the  ipv4 address of license centralized server."
			::= { hwWlanLicenseCentralizedGlobal 2 }
		
		-- 1.3.6.1.4.1.2011.6.139.11.1.1.29.1.3
		hwWlanLicenseCentralizedServerIPv6Addr OBJECT-TYPE
			SYNTAX OCTET STRING
			MAX-ACCESS read-write
			STATUS current
			DESCRIPTION
				"This object indicates the  ipv6 address of license centralized server."
			::= { hwWlanLicenseCentralizedGlobal 3 }
		
		-- 1.3.6.1.4.1.2011.6.139.11.1.1.29.1.4
		hwWlanLicenseCentralizedClientIPv4Addr OBJECT-TYPE
			SYNTAX IpAddress
			MAX-ACCESS read-write
			STATUS current
			DESCRIPTION
				"This object indicates the  ipv4 address of license centralized client."
			::= { hwWlanLicenseCentralizedGlobal 4 }
		
		-- 1.3.6.1.4.1.2011.6.139.11.1.1.29.1.5
		hwWlanLicenseCentralizedClientIPv6Addr OBJECT-TYPE
			SYNTAX OCTET STRING
			MAX-ACCESS read-write
			STATUS current
			DESCRIPTION
				"This object indicates the  ipv6 address of license centralized client."
			::= { hwWlanLicenseCentralizedGlobal 5 }
		
		-- 1.3.6.1.4.1.2011.6.139.11.1.1.29.1.6
		hwWlanLicenseCentralizedRole OBJECT-TYPE
			SYNTAX INTEGER
				{
				server(1),
				client(2)
				}
			MAX-ACCESS read-only
			STATUS current
			DESCRIPTION
				"This object indicates the current role of license centralized device."
			::= { hwWlanLicenseCentralizedGlobal 6 }
		
		-- 1.3.6.1.4.1.2011.6.139.11.1.1.29.1.7
		hwWlanLicensePoolUsed OBJECT-TYPE
			SYNTAX Integer32
			MAX-ACCESS read-only
			STATUS current
			DESCRIPTION
				"This object indicates the  used of license in license pool."
			::= { hwWlanLicenseCentralizedGlobal 7 }
		
		-- 1.3.6.1.4.1.2011.6.139.11.1.1.29.1.8
		hwWlanLicensePoolTotal OBJECT-TYPE
			SYNTAX Integer32
			MAX-ACCESS read-only
			STATUS current
			DESCRIPTION
				"This object indicates the total number of license pool."
			::= { hwWlanLicenseCentralizedGlobal 8 }
			
		--1.3.6.1.4.1.2011.6.139.11.1.1.30
		hwWlanGlobalRogueDeviceLogSwitch OBJECT-TYPE
			SYNTAX INTEGER
				{
				disable(1),
				enable(2)
				}
			MAX-ACCESS read-write
			STATUS current
			DESCRIPTION
				"This object indicates the status of rogue device log switch. The default value is 1. 1: disable 2: enable."
			::= { hwWlanGlobalConfig 30 }
		
		-- 1.3.6.1.4.1.2011.6.139.11.1.1.31
		hwWlanNeighborRelation OBJECT IDENTIFIER ::= { hwWlanGlobalConfig 31 }
		
		-- 1.3.6.1.4.1.2011.6.139.11.1.1.31.1
		hwWlanNeighborRelationTable OBJECT-TYPE
			SYNTAX SEQUENCE OF HwWlanNeighborRelationEntry
			MAX-ACCESS not-accessible
			STATUS current
			DESCRIPTION
				"Description."
			::= { hwWlanNeighborRelation 1 }
		
		-- 1.3.6.1.4.1.2011.6.139.11.1.1.31.1.1
		hwWlanNeighborRelationEntry OBJECT-TYPE
			SYNTAX HwWlanNeighborRelationEntry
			MAX-ACCESS not-accessible
			STATUS current
			DESCRIPTION
				"Description."
			INDEX { hwWlanNeighborRelationApName, hwWlanNeighborRelationNeighborApName }
			::= { hwWlanNeighborRelationTable 1 }
		
		HwWlanNeighborRelationEntry ::=
			SEQUENCE { 
				hwWlanNeighborRelationApName
					OCTET STRING,
				hwWlanNeighborRelationNeighborApName
					OCTET STRING,
				hwWlanNeighborRelationNeighborRowStatus
					RowStatus
			 }

		-- 1.3.6.1.4.1.2011.6.139.11.1.1.31.1.1.1
		hwWlanNeighborRelationApName OBJECT-TYPE
			SYNTAX OCTET STRING (SIZE (1..63))
			MAX-ACCESS not-accessible
			STATUS current
			DESCRIPTION
				"Description."
			::= { hwWlanNeighborRelationEntry 1 }
		
		-- 1.3.6.1.4.1.2011.6.139.11.1.1.31.1.1.2
		hwWlanNeighborRelationNeighborApName OBJECT-TYPE
			SYNTAX OCTET STRING (SIZE (1..63))
			MAX-ACCESS not-accessible
			STATUS current
			DESCRIPTION
				"Description."
			::= { hwWlanNeighborRelationEntry 2 }
		-- 1.3.6.1.4.1.2011.6.139.11.1.1.31.1.1.3
		hwWlanNeighborRelationNeighborRowStatus OBJECT-TYPE
			SYNTAX RowStatus
			MAX-ACCESS read-write
			STATUS current
			DESCRIPTION
				"This object indicates the row status of this table."
			::= { hwWlanNeighborRelationEntry 3 }
		 
		-- 1.3.6.1.4.1.2011.6.139.11.1.1.32
		hwWlanIotOperateTable OBJECT-TYPE
			SYNTAX SEQUENCE OF HwWlanIotOperateEntry
			MAX-ACCESS not-accessible
			STATUS current
			DESCRIPTION
				"Description."
			::= { hwWlanGlobalConfig 32 }
		
		-- 1.3.6.1.4.1.2011.6.139.11.1.1.32.1
		hwWlanIotOperateEntry OBJECT-TYPE
			SYNTAX HwWlanIotOperateEntry
			MAX-ACCESS not-accessible
			STATUS current
			DESCRIPTION
				"Description."
			INDEX { hwWlanIotOperateCardId, hwWlanIDIndexedAPSpApId }
			::= { hwWlanIotOperateTable 1 }
		
		HwWlanIotOperateEntry ::=
			SEQUENCE { 

				hwWlanIotOperateCardId
					Unsigned32,
				hwWlanIotOperateType
					INTEGER
			 }

		
		-- 1.3.6.1.4.1.2011.6.139.11.1.1.32.1.1
		hwWlanIotOperateCardId OBJECT-TYPE
			SYNTAX Unsigned32
			MAX-ACCESS not-accessible
			STATUS current
			DESCRIPTION
				"This object indicates the AP card ID."
			::= { hwWlanIotOperateEntry 1 }
		
		-- 1.3.6.1.4.1.2011.6.139.11.1.1.32.1.2
		hwWlanIotOperateType OBJECT-TYPE
			SYNTAX INTEGER
				{
				reboot(1),
				resetfactoryconfiguration(2),
				switchfirmware(3),
				resetnetworkconfiguration(4)
				}
			MAX-ACCESS read-write
			STATUS current
			DESCRIPTION
				"This object indicates the operation type to the IOT card of the AP."
			::= { hwWlanIotOperateEntry 2 }

		--1.3.6.1.4.1.2011.6.139.11.1.1.33
		hwWlanGlobalAntiInterferenceSwitch OBJECT-TYPE
			SYNTAX INTEGER
				{
				disable(1),
				enable(2)
				}
			MAX-ACCESS read-write
			STATUS current
			DESCRIPTION
				"This object indicates the status of anti-interference switch. The default value is 2. 1: disable 2: enable."
			::= { hwWlanGlobalConfig 33 }

		--1.3.6.1.4.1.2011.6.139.11.1.1.34
		hwWlanGlobalAntiInterferencePerPacketTpcSwitch OBJECT-TYPE
			SYNTAX INTEGER
				{
				disable(1),
				enable(2)
				}
			MAX-ACCESS read-write
			STATUS current
			DESCRIPTION
				"This object indicates the status of anti-interference per-packet-TPC switch. The default value is 2. 1: disable 2: enable."
			::= { hwWlanGlobalConfig 34 }
		-- 1.3.6.1.4.1.2011.6.139.11.1.1.35
		hwWlanGlobalAeroscoutLocalIPv4 OBJECT-TYPE
			SYNTAX IpAddress
			MAX-ACCESS read-write
			STATUS current
			DESCRIPTION
				"This object indicates the aeroscout local IPv4 address for receiving message from aeroscout server."
			::= { hwWlanGlobalConfig 35 }
		-- 1.3.6.1.4.1.2011.6.139.11.1.1.36
		hwWlanGlobalAeroscoutLocalIPv6 OBJECT-TYPE
			SYNTAX OCTET STRING
			MAX-ACCESS read-write
			STATUS current
			DESCRIPTION
				"This object indicates the aeroscout local IPv6 address for receiving message from aeroscout server."
			::= { hwWlanGlobalConfig 36 }
			
		-- 1.3.6.1.4.1.2011.6.139.11.1.2
		hwApAuthObjects OBJECT IDENTIFIER ::= { hwWlanConfigObjects 2 }

		 --1.3.6.1.4.1.2011.6.139.11.1.2.1
		hwWlanApAuthMode OBJECT-TYPE
			SYNTAX INTEGER
				{
				macAuth(1) ,
				snAuth(2) ,
				noAuth(3)
				}
			MAX-ACCESS read-write
			STATUS current
			DESCRIPTION 
				"This object indicates the AP authentication mode. The default value is 1."
			::= { hwApAuthObjects 1 }

		--1.3.6.1.4.1.2011.6.139.11.1.2.2
		hwWlanApMacWhitelistTable OBJECT-TYPE
			SYNTAX SEQUENCE OF HwWlanApMacWhitelistEntry 
			MAX-ACCESS not-accessible
			STATUS current
			DESCRIPTION 
				"This table is used to add and delete AP MAC addresses in the white lists."
			::= { hwApAuthObjects 2 }

		--1.3.6.1.4.1.2011.6.139.11.1.2.2.1
		hwWlanApMacWhitelistEntry OBJECT-TYPE
			SYNTAX HwWlanApMacWhitelistEntry 
			MAX-ACCESS not-accessible
			STATUS current
			DESCRIPTION 
				"The index of this table is hwWlanApMacWhitelistMacAddr."
			INDEX { hwWlanApMacWhitelistMacAddr }
			::= { hwWlanApMacWhitelistTable 1 }


		HwWlanApMacWhitelistEntry ::=
			SEQUENCE {				
				hwWlanApMacWhitelistMacAddr
					MacAddress,
				hwWlanApMacWhitelistRowStatus
					RowStatus 
			 }

		 --1.3.6.1.4.1.2011.6.139.11.1.2.2.1.1
		hwWlanApMacWhitelistMacAddr OBJECT-TYPE
			SYNTAX MacAddress
			MAX-ACCESS not-accessible
			STATUS current
			DESCRIPTION 
				"This object indicates the MAC address of an AP."
			::= { hwWlanApMacWhitelistEntry 1 }

		 --1.3.6.1.4.1.2011.6.139.11.1.2.2.1.2
		hwWlanApMacWhitelistRowStatus OBJECT-TYPE
			SYNTAX RowStatus
			MAX-ACCESS read-create
			STATUS current
			DESCRIPTION 
				"This object indicates the row status of this table."
			::= { hwWlanApMacWhitelistEntry 2 }

		--1.3.6.1.4.1.2011.6.139.11.1.2.3
		hwWlanApSnWhitelistTable OBJECT-TYPE
			SYNTAX SEQUENCE OF HwWlanApSnWhitelistEntry 
			MAX-ACCESS not-accessible
			STATUS current
			DESCRIPTION 
				"This table is used to add and delete AP sequence numbers in the white lists of AP sequence numbers."
			::= { hwApAuthObjects 3 }

		--1.3.6.1.4.1.2011.6.139.11.1.2.3.1
		hwWlanApSnWhitelistEntry OBJECT-TYPE
			SYNTAX HwWlanApSnWhitelistEntry 
			MAX-ACCESS not-accessible
			STATUS current
			DESCRIPTION 
				"The index of this table is hwWlanApSnWhitelistSn."
			INDEX { hwWlanApSnWhitelistSn }
			::= { hwWlanApSnWhitelistTable 1 }


		HwWlanApSnWhitelistEntry ::=
			SEQUENCE {				
				hwWlanApSnWhitelistSn
					OCTET STRING,
				hwWlanApSnWhitelistRowStatus
					RowStatus 
			 }

		 --1.3.6.1.4.1.2011.6.139.11.1.2.3.1.1
		hwWlanApSnWhitelistSn OBJECT-TYPE
			SYNTAX OCTET STRING
			MAX-ACCESS not-accessible
			STATUS current
			DESCRIPTION 
				"Description."
			::= { hwWlanApSnWhitelistEntry 1 }

		 --1.3.6.1.4.1.2011.6.139.11.1.2.3.1.2
		hwWlanApSnWhitelistRowStatus OBJECT-TYPE
			SYNTAX RowStatus
			MAX-ACCESS read-create
			STATUS current
			DESCRIPTION 
				"Indicate the row status of this table."
			::= { hwWlanApSnWhitelistEntry 2 }

		--1.3.6.1.4.1.2011.6.139.11.1.2.4
		hwWlanApMacBlacklistTable OBJECT-TYPE
			SYNTAX SEQUENCE OF HwWlanApMacBlacklistEntry 
			MAX-ACCESS not-accessible
			STATUS current
			DESCRIPTION 
				"This table describes the AP MAC blacklist.This table is used to add an AP's MAC address to the blacklist or delete an AP's MAC address from the blacklist."
			::= { hwApAuthObjects 4 }

		--1.3.6.1.4.1.2011.6.139.11.1.2.4.1
		hwWlanApMacBlacklistEntry OBJECT-TYPE
			SYNTAX HwWlanApMacBlacklistEntry 
			MAX-ACCESS not-accessible
			STATUS current
			DESCRIPTION 
				"The index of this table is hwWlanApMacBlacklistMacAddr."
			INDEX { hwWlanApMacBlacklistMacAddr }
			::= { hwWlanApMacBlacklistTable 1 }


		HwWlanApMacBlacklistEntry ::=
			SEQUENCE {				
				hwWlanApMacBlacklistMacAddr
					MacAddress,
				hwWlanApMacBlacklistRowStatus
					RowStatus 
			 }

		 --1.3.6.1.4.1.2011.6.139.11.1.2.4.1.1
		hwWlanApMacBlacklistMacAddr OBJECT-TYPE
			SYNTAX MacAddress
			MAX-ACCESS not-accessible
			STATUS current
			DESCRIPTION 
				"This object indicates the MAC address of an AP."
			::= { hwWlanApMacBlacklistEntry 1 }

		 --1.3.6.1.4.1.2011.6.139.11.1.2.4.1.2
		hwWlanApMacBlacklistRowStatus OBJECT-TYPE
			SYNTAX RowStatus
			MAX-ACCESS read-create
			STATUS current
			DESCRIPTION 
				"This object indicates the row status of this table."
			::= { hwWlanApMacBlacklistEntry 2 }

		--1.3.6.1.4.1.2011.6.139.11.1.3
		hwAPGroupTable OBJECT-TYPE
			SYNTAX SEQUENCE OF HwAPGroupEntry 
			MAX-ACCESS not-accessible
			STATUS current
			DESCRIPTION 
				"This table is used to create or delete AP groups and bind or unbind the AP system profile, 2G radio profile, and domain profile."
			::= { hwWlanConfigObjects 3 }

		--1.3.6.1.4.1.2011.6.139.11.1.3.1
		hwAPGroupEntry OBJECT-TYPE
			SYNTAX HwAPGroupEntry 
			MAX-ACCESS not-accessible
			STATUS current
			DESCRIPTION 
				"The index of this table is hwAPGroupName."
			INDEX { hwAPGroupName }
			::= { hwAPGroupTable 1 }


		HwAPGroupEntry ::=
			SEQUENCE { 
				hwAPGroupName
					OCTET STRING,
				hwAPGrpAPSystemProfile
					OCTET STRING,
				hwAPGrpDomainProfile
					OCTET STRING,
				hwAPGrpRowStatus
					RowStatus,
				hwAPGrpWidsProfile
					OCTET STRING,
				hwAPGrpBleProfile
					OCTET STRING,
				hwAPGrpUUIDString
					OCTET STRING,
				hwAPGrpUUIDHex
					OCTET STRING,
				hwAPGrpSiteCode
					OCTET STRING,
				hwAPGrpDomainName
					OCTET STRING,
				hwAPGrpLocation
					OCTET STRING,
				hwAPGrpApNum
					Unsigned32,
				hwAPGrpHighwayProfileName
					OCTET STRING,
				hwAPGrpAPIPVersion
					INTEGER
			 }

		 --1.3.6.1.4.1.2011.6.139.11.1.3.1.1
		hwAPGroupName OBJECT-TYPE
			SYNTAX OCTET STRING (SIZE (1..35))
			MAX-ACCESS not-accessible
			STATUS current
			DESCRIPTION 
				"This object indicates the AP group name. It is the index of the table."
			::= { hwAPGroupEntry 1 }

		 --1.3.6.1.4.1.2011.6.139.11.1.3.1.2
		hwAPGrpAPSystemProfile OBJECT-TYPE
			SYNTAX OCTET STRING (SIZE (1..35))
			MAX-ACCESS read-write
			STATUS current
			DESCRIPTION 
				"This object indicates the system profile to which AP groups are bound. The default value is default."
			::= { hwAPGroupEntry 2 }

		
		-- 1.3.6.1.4.1.2011.6.139.11.1.3.1.4
		hwAPGrpDomainProfile OBJECT-TYPE
			SYNTAX OCTET STRING (SIZE (1..35))
			MAX-ACCESS read-write
			STATUS current
			DESCRIPTION 
				"This object indicates the domain profile to which AP groups are bound. The default value is default."
			::= { hwAPGroupEntry 4 }

		
		-- 1.3.6.1.4.1.2011.6.139.11.1.3.1.5
		hwAPGrpRowStatus OBJECT-TYPE
			SYNTAX RowStatus
			MAX-ACCESS read-write
			STATUS current
			DESCRIPTION 
				"This object indicates the row status of this table. ROWSTATUS_CREATEANDFLOW and ROWSTATUS_DESTROY are commonly used ?	ROWSTATUS_UNDEFINED: undefined  ROWSTATUS_ACTIVE: active ROWSTATUS_NOTINSERVICE: notInService ?	ROWSTATUS_NOTREADY: notReady ?	ROWSTATUS_CREATEANDFLOW: createAndGo ? ROWSTATUS_CREATEANDWAIT: createAndWait ?	ROWSTATUS_DESTROY: destroy"
			::= { hwAPGroupEntry 5 }

		
		-- 1.3.6.1.4.1.2011.6.139.11.1.3.1.6
		hwAPGrpWidsProfile OBJECT-TYPE
			SYNTAX OCTET STRING (SIZE (0..35))
			MAX-ACCESS read-write
			STATUS current
			DESCRIPTION
				"This object indicates the bound WIDS profile."
			::= { hwAPGroupEntry 6 }

		
                -- 1.3.6.1.4.1.2011.6.139.11.1.3.1.7
		hwAPGrpBleProfile OBJECT-TYPE
			SYNTAX OCTET STRING (SIZE (0..35))
			MAX-ACCESS read-write
			STATUS current
			DESCRIPTION
				"This object indicates the bound BLE profile."
			::= { hwAPGroupEntry 7 }
			
		-- 1.3.6.1.4.1.2011.6.139.11.1.3.1.8
		hwAPGrpUUIDString OBJECT-TYPE
			SYNTAX OCTET STRING (SIZE (0..16))
			MAX-ACCESS read-write
			STATUS current
			DESCRIPTION
				"This object indicates the UUID String value of Group."
			::= { hwAPGroupEntry 8 }
		
		-- 1.3.6.1.4.1.2011.6.139.11.1.3.1.9
		hwAPGrpUUIDHex OBJECT-TYPE
			SYNTAX OCTET STRING (SIZE (0..32))
			MAX-ACCESS read-write
			STATUS current
			DESCRIPTION
				"This object indicates the UUID Hex value of Group."
			::= { hwAPGroupEntry 9 }
		
		-- 1.3.6.1.4.1.2011.6.139.11.1.3.1.10
		hwAPGrpSiteCode OBJECT-TYPE
			SYNTAX OCTET STRING (SIZE (0..14))
			MAX-ACCESS read-write
			STATUS current
			DESCRIPTION
				"This object indicates the site code of Group."
			::= { hwAPGroupEntry 10 }

		
		-- 1.3.6.1.4.1.2011.6.139.11.1.3.1.11
		hwAPGrpDomainName OBJECT-TYPE
			SYNTAX OCTET STRING (SIZE (0..255))
			MAX-ACCESS read-write
			STATUS current
			DESCRIPTION
				"This object indicates the domain name of Group."
			::= { hwAPGroupEntry 11 }
		-- 1.3.6.1.4.1.2011.6.139.11.1.3.1.12			
		hwAPGrpLocation OBJECT-TYPE
			SYNTAX OCTET STRING (SIZE (0..63))
			MAX-ACCESS read-write
			STATUS current
			DESCRIPTION
				"This object indicates the ap location of Group."
			::= { hwAPGroupEntry 12 }
		-- 1.3.6.1.4.1.2011.6.139.11.1.3.1.13	

		hwAPGrpApNum OBJECT-TYPE
			SYNTAX Unsigned32
			MAX-ACCESS read-only
			STATUS current
			DESCRIPTION
				"This object indicates the ap numbers of Group."
			::= { hwAPGroupEntry 13 }			
		-- 1.3.6.1.4.1.2011.6.139.11.1.3.1.14
		hwAPGrpHighwayProfileName OBJECT-TYPE
			SYNTAX OCTET STRING (SIZE (0..35))
			MAX-ACCESS read-write
			STATUS current
			DESCRIPTION
				"This object indicates the UUID String value of Group."
			::= { hwAPGroupEntry 14 }
		
		-- 1.3.6.1.4.1.2011.6.139.11.1.3.1.15
		hwAPGrpAPIPVersion OBJECT-TYPE
			SYNTAX INTEGER
				{
				all(1),
				ipv4(2),
				ipv6(3)
				}
			MAX-ACCESS read-write
			STATUS current
			DESCRIPTION
				"This object indicates the IP Version of AP."
			DEFVAL { all }
			::= { hwAPGroupEntry 15 }
		

		-- 1.3.6.1.4.1.2011.6.139.11.1.4
		hwAPGroupWiredPortTable OBJECT-TYPE
			SYNTAX SEQUENCE OF HwAPGroupWiredPortEntry 
			MAX-ACCESS not-accessible
			STATUS current
			DESCRIPTION 
				"This table is the AP wired port profile table.This table is used to bind a wired port profile to an AP group or unbind a wired port profile from an AP group."
			::= { hwWlanConfigObjects 4 }

		--1.3.6.1.4.1.2011.6.139.11.1.4.1
		hwAPGroupWiredPortEntry OBJECT-TYPE
			SYNTAX HwAPGroupWiredPortEntry 
			MAX-ACCESS not-accessible
			STATUS current
			DESCRIPTION 
				"Indexes of this table are hwAPGroupName, hwAPGrpWPInterfaceType, and hwAPGrpWPInterfaceNum."
			INDEX { hwAPGroupName, hwAPGrpWPInterfaceType, hwAPGrpWPInterfaceNum }
			::= { hwAPGroupWiredPortTable 1 }


		HwAPGroupWiredPortEntry ::=
			SEQUENCE {				
				hwAPGrpWPInterfaceType
					INTEGER,
				hwAPGrpWPInterfaceNum
					Unsigned32,
				hwAPGrpWPProfile
					OCTET STRING,
				hwAPGrpWPRowStatus
					RowStatus 
			 }

		 --1.3.6.1.4.1.2011.6.139.11.1.4.1.1
		hwAPGrpWPInterfaceType OBJECT-TYPE
			SYNTAX INTEGER
				{
				fe(1) ,
				ge(2) ,
				trunk(3),
				multige(4),
				xge(5)				
				}
			MAX-ACCESS not-accessible
			STATUS current
			DESCRIPTION 
				"This object indicates the interface type. It is the index of the table."
			::= { hwAPGroupWiredPortEntry 1 }

		 --1.3.6.1.4.1.2011.6.139.11.1.4.1.2
		hwAPGrpWPInterfaceNum OBJECT-TYPE
			SYNTAX Unsigned32 (0..27)
			MAX-ACCESS not-accessible
			STATUS current
			DESCRIPTION 
				"This object indicates the interface index."
			::= { hwAPGroupWiredPortEntry 2 }

		 --1.3.6.1.4.1.2011.6.139.11.1.4.1.3
		hwAPGrpWPProfile OBJECT-TYPE
			SYNTAX OCTET STRING (SIZE (1..35))
			MAX-ACCESS read-write
			STATUS current
			DESCRIPTION 
				"This object indicates the bound wired port profile."
			::= { hwAPGroupWiredPortEntry 3 }

		 --1.3.6.1.4.1.2011.6.139.11.1.4.1.4
		hwAPGrpWPRowStatus OBJECT-TYPE
			SYNTAX RowStatus
			MAX-ACCESS read-write
			STATUS current
			DESCRIPTION 
				"This object indicates the row status of this table. ROWSTATUS_CREATEAN."
			::= { hwAPGroupWiredPortEntry 4 }

		--1.3.6.1.4.1.2011.6.139.11.1.5
		hwAPGroupRadioTable OBJECT-TYPE
			SYNTAX SEQUENCE OF HwAPGroupRadioEntry 
			MAX-ACCESS not-accessible
			STATUS current
			DESCRIPTION 
				"This table is used to bind a 5G radio profile, Mesh profile, WDS profile, WIDS profile, location profile, or spectrum profile to an AP group or unbind a 5G radio profile, Mesh profile, WDS profile, WIDS profile, location profile, or spectrum profile from an AP group.."
			::= { hwWlanConfigObjects 5 }

		--1.3.6.1.4.1.2011.6.139.11.1.5.1
		hwAPGroupRadioEntry OBJECT-TYPE
			SYNTAX HwAPGroupRadioEntry 
			MAX-ACCESS not-accessible
			STATUS current
			DESCRIPTION 
				"Indexes of this table are hwAPGroupName and hwAPGrpRadioId."
			INDEX { hwAPGrpRadioId, hwAPGroupName }
			::= { hwAPGroupRadioTable 1 }


		HwAPGroupRadioEntry ::=
			SEQUENCE {				
				hwAPGrpRadioId
					Unsigned32,
				hwAPGrpRadio5gProfile
					OCTET STRING,
				hwAPGrpMeshProfile
					OCTET STRING,
				hwAPGrpWdsProfile
					OCTET STRING,
				hwAPGrpLocationProfile
					OCTET STRING, 
				hwAPGrpRadioRowStatus
					RowStatus,
				hwAPGrpRadio2gProfile
					OCTET STRING,
				hwAPGrpMeshWhitelistProfile
					OCTET STRING,
				hwAPGrpWdsWhitelistProfile
					OCTET STRING,
				hwAPGrpRadioSwitch
					INTEGER,
				hwAPGrpRadioChannel
					Unsigned32,
				hwAPGrpRadioBandwidth
					INTEGER,
				hwAPGrpRadioEirp
					Unsigned32,
				hwAPGrpRadioAntennaGain
					Integer32,
				hwAPGrpRadioCoverageDistance
					Unsigned32,
				hwAPGrpRadioWorkMode
					INTEGER,
				hwAPGrpRadioFrequency
					INTEGER,
				hwAPGrpSpectrumAnalysisSwitch
					INTEGER,
				hwAPGrpWidsDeviceDetectSwitch
					INTEGER,
				hwAPGrpWidsAttackDetectEnBmp
					Unsigned32,
				hwAPGrpWidsRogueContainSwitch
					INTEGER,
				hwAPGrpRadioSecondChannel
					Unsigned32,
				hwAPGrpAutoChannelSelectSwitch
					INTEGER,
				hwAPGrpAutoTxPowerSelectSwitch
					INTEGER,
				hwAPGrpSfnRoamCtsSwitch
					INTEGER,
				hwAPGrpSfnRoamBeaconSwitch
					INTEGER,
				hwAPGrpSfnRoamCtsDelay
					Integer32,
		       	hwAPGroupRadioCalibrateFlexibleRadio   
					INTEGER,
				hwAPGrpAutoBandwidthSelectSwitch
					INTEGER,
				hwAPGrpReferenceDataAnalysis
					INTEGER
			 }

		 --1.3.6.1.4.1.2011.6.139.11.1.5.1.1
		hwAPGrpRadioId OBJECT-TYPE
			SYNTAX Unsigned32 (0..2)
			MAX-ACCESS not-accessible
			STATUS current
			DESCRIPTION 
				"This object indicates the radio ID. It is the index of the table."
			::= { hwAPGroupRadioEntry 1 }

		 --1.3.6.1.4.1.2011.6.139.11.1.5.1.2
		hwAPGrpRadio5gProfile OBJECT-TYPE
			SYNTAX OCTET STRING (SIZE (1..35))
			MAX-ACCESS read-write
			STATUS current
			DESCRIPTION 
				"This object indicates the bound 5G radio profile."
			::= { hwAPGroupRadioEntry 2 }

		 --1.3.6.1.4.1.2011.6.139.11.1.5.1.3
		hwAPGrpMeshProfile OBJECT-TYPE
			SYNTAX OCTET STRING (SIZE (0..35))
			MAX-ACCESS read-write
			STATUS current
			DESCRIPTION 
				"This object indicates the bound Mesh profile."
			::= { hwAPGroupRadioEntry 3 }

		 --1.3.6.1.4.1.2011.6.139.11.1.5.1.4
		hwAPGrpWdsProfile OBJECT-TYPE
			SYNTAX OCTET STRING (SIZE (0..35))
			MAX-ACCESS read-write
			STATUS current
			DESCRIPTION 
				"This object indicates the bound WDS profile."
			::= { hwAPGroupRadioEntry 4 }

		--1.3.6.1.4.1.2011.6.139.11.1.5.1.6
		hwAPGrpLocationProfile OBJECT-TYPE
			SYNTAX OCTET STRING (SIZE (0..35))
			MAX-ACCESS read-write
			STATUS current
			DESCRIPTION 
				"This object indicates the bound location profile."
			::= { hwAPGroupRadioEntry 6 } 
		
		-- 1.3.6.1.4.1.2011.6.139.11.1.5.1.8
		hwAPGrpRadioRowStatus OBJECT-TYPE
			SYNTAX RowStatus
			MAX-ACCESS read-write
			STATUS current
			DESCRIPTION 
				"This object indicates the row status of this table. ROWSTATUS_CREATEANDFLOW and ROWSTATUS_DESTROY are commonly used ? ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ? ROWSTATUS_DESTROY: destroy."
			::= { hwAPGroupRadioEntry 8 }


		-- 1.3.6.1.4.1.2011.6.139.11.1.5.1.9
		hwAPGrpRadio2gProfile OBJECT-TYPE
			SYNTAX OCTET STRING (SIZE (1..35))
			MAX-ACCESS read-write
			STATUS current
			DESCRIPTION
				"This object indicates the 2G radio profile to which AP groups are bound. The default value is default."
			::= { hwAPGroupRadioEntry 9 }


		-- 1.3.6.1.4.1.2011.6.139.11.1.5.1.10
		hwAPGrpMeshWhitelistProfile OBJECT-TYPE
			SYNTAX OCTET STRING (SIZE (0..35))
			MAX-ACCESS read-write
			STATUS current
			DESCRIPTION
				"This object indicates the bound whitelist profile."
			::= { hwAPGroupRadioEntry 10 }

		
		-- 1.3.6.1.4.1.2011.6.139.11.1.5.1.11
		hwAPGrpWdsWhitelistProfile OBJECT-TYPE
			SYNTAX OCTET STRING (SIZE (0..35))
			MAX-ACCESS read-write
			STATUS current
			DESCRIPTION
				"This object indicates the bound whitelist profile."
			::= { hwAPGroupRadioEntry 11 }

		
		-- 1.3.6.1.4.1.2011.6.139.11.1.5.1.12
		hwAPGrpRadioSwitch OBJECT-TYPE
			SYNTAX INTEGER
				{
				disable(1),
				enable(2)
				}
			MAX-ACCESS read-write
			STATUS current
			DESCRIPTION
				"This object indicates the name of a 2G radio profile. It is the index of the table."
			::= { hwAPGroupRadioEntry 12 }

		
		-- 1.3.6.1.4.1.2011.6.139.11.1.5.1.13
		hwAPGrpRadioChannel OBJECT-TYPE
			SYNTAX Unsigned32
			MAX-ACCESS read-write
			STATUS current
			DESCRIPTION
				"This object indicates a radio-frequency channel. For 2.4G, the value ranges from 1 to 13. For 5G, the value ranges from 36 to 196 (with a separation interval of 4)."
			::= { hwAPGroupRadioEntry 13 }

		
		-- 1.3.6.1.4.1.2011.6.139.11.1.5.1.14
		hwAPGrpRadioBandwidth OBJECT-TYPE
			SYNTAX INTEGER
				{
				ht20(1),
				ht40Plus(2),
				ht40Minus(3),
				ht80(4),
				ht160(5),
				invalid(255) 
				}
			MAX-ACCESS read-write
			STATUS current
			DESCRIPTION
				"This object indicate a bandwidth. The default value is 1."
			::= { hwAPGroupRadioEntry 14 }


		-- 1.3.6.1.4.1.2011.6.139.11.1.5.1.15
		hwAPGrpRadioEirp OBJECT-TYPE
			SYNTAX Unsigned32 (1..127)
			MAX-ACCESS read-write
			STATUS current
			DESCRIPTION
				"This object indicates a power value. The default value is 127. The configuration is saved but the actual power is determined by the maximum power supported by the AP."
			::= { hwAPGroupRadioEntry 15 }


		-- 1.3.6.1.4.1.2011.6.139.11.1.5.1.16
		hwAPGrpRadioAntennaGain OBJECT-TYPE
			SYNTAX Integer32 (-10..30 | 255)
			MAX-ACCESS read-write
			STATUS current
			DESCRIPTION
				"This object indicates antenna gains. The default value 0xFF indicates that the default gain of an AP is used. It is expressed in dB. Default gains vary with different types of APs."
			::= { hwAPGroupRadioEntry 16 }


		-- 1.3.6.1.4.1.2011.6.139.11.1.5.1.17
		hwAPGrpRadioCoverageDistance OBJECT-TYPE
			SYNTAX Unsigned32 (1..400)
			MAX-ACCESS read-write
			STATUS current
			DESCRIPTION
				"This object indicates a radio coverage distance. The default value is 3. The unit is 0.1 km."
			::= { hwAPGroupRadioEntry 17 }


		-- 1.3.6.1.4.1.2011.6.139.11.1.5.1.18
		hwAPGrpRadioWorkMode OBJECT-TYPE
			SYNTAX INTEGER
				{
				normal(1),
				monitor(2),
				dualband(3),
				proxyScan(4)
				}
			MAX-ACCESS read-write
			STATUS current
			DESCRIPTION
				"This object indicates the radio working mode. The default value is 1."
			::= { hwAPGroupRadioEntry 18 }


		-- 1.3.6.1.4.1.2011.6.139.11.1.5.1.19
		hwAPGrpRadioFrequency OBJECT-TYPE
			SYNTAX INTEGER
				{
				frequency2G(1),
				frequency5G(2)
				}
			MAX-ACCESS read-write
			STATUS current
			DESCRIPTION
				"This object indicates the setting of the frequency band for radio 0. The default value is 1. 1: frequency2G, 2: frequency5G."
			::= { hwAPGroupRadioEntry 19 }

		

		-- 1.3.6.1.4.1.2011.6.139.11.1.5.1.20
		hwAPGrpSpectrumAnalysisSwitch OBJECT-TYPE
			SYNTAX INTEGER
				{
				disable(1),
				enable(2)
				}
			MAX-ACCESS read-write
			STATUS current
			DESCRIPTION
				"This object indicates the status of the spectrum analysis function. The default value is 1."
			::= { hwAPGroupRadioEntry 20 }

		

		-- 1.3.6.1.4.1.2011.6.139.11.1.5.1.21
		hwAPGrpWidsDeviceDetectSwitch OBJECT-TYPE
			SYNTAX INTEGER
				{
				disable(1),
				enable(2)
				}
			MAX-ACCESS read-write
			STATUS current
			DESCRIPTION
				"This object indicates the status of the device detection function. The default value is 1."
			::= { hwAPGroupRadioEntry 21 }

		

		-- 1.3.6.1.4.1.2011.6.139.11.1.5.1.22
		hwAPGrpWidsAttackDetectEnBmp OBJECT-TYPE
			SYNTAX Unsigned32
			MAX-ACCESS read-write
			STATUS current
			DESCRIPTION
				"This object indicates the bit map of the brute force attack switch. bit0:weak-iv, bit1:spoof, bit2:flood, bit3:wpa-psk, bit4:wpa2-psk, bit5:wapi-psk, bit6:wep-psk."
			::= { hwAPGroupRadioEntry 22 }

		

		-- 1.3.6.1.4.1.2011.6.139.11.1.5.1.23
		hwAPGrpWidsRogueContainSwitch OBJECT-TYPE
			SYNTAX INTEGER
				{
				disable(1),
				enable(2)
				}
			MAX-ACCESS read-write
			STATUS current
			DESCRIPTION
				"This object indicates the status of the device detection function. The default value is 1."
			::= { hwAPGroupRadioEntry 23 }

		-- 1.3.6.1.4.1.2011.6.139.11.1.5.1.24
		hwAPGrpRadioSecondChannel OBJECT-TYPE
			SYNTAX Unsigned32
			MAX-ACCESS read-write
			STATUS current
			DESCRIPTION
				"This object indicates a radio-frequency channel. The value ranges from 42,58,106,122,138,155."
			::= { hwAPGroupRadioEntry 24 }
			
		-- 1.3.6.1.4.1.2011.6.139.11.1.5.1.25
		hwAPGrpAutoChannelSelectSwitch OBJECT-TYPE
			SYNTAX INTEGER
				{
				disable(1),
				enable(2)
				}
			MAX-ACCESS read-write
			STATUS current
			DESCRIPTION
				"This object indicates the status of the automatic channel selection function. The default value is 2."
			DEFVAL { enable }
			::= { hwAPGroupRadioEntry 25 }
		
		-- 1.3.6.1.4.1.2011.6.139.11.1.5.1.26
		hwAPGrpAutoTxPowerSelectSwitch OBJECT-TYPE
			SYNTAX INTEGER
				{
				disable(1),
				enable(2)
				}
			MAX-ACCESS read-write
			STATUS current
			DESCRIPTION
				"This object indicates the status of the automatic power selection function. The default value is 2."
			DEFVAL { enable }
			::= { hwAPGroupRadioEntry 26 }

		
		-- 1.3.6.1.4.1.2011.6.139.11.1.5.1.27
		hwAPGrpSfnRoamCtsSwitch OBJECT-TYPE
			SYNTAX INTEGER
				{
				disable(1),
				enable(2)
				}
			MAX-ACCESS read-write
			STATUS current
			DESCRIPTION
				"Description."
			DEFVAL { enable }
			::= { hwAPGroupRadioEntry 27 }

		
		-- 1.3.6.1.4.1.2011.6.139.11.1.5.1.28
		hwAPGrpSfnRoamBeaconSwitch OBJECT-TYPE
			SYNTAX INTEGER
				{
				disable(1),
				enable(2)
				}
			MAX-ACCESS read-write
			STATUS current
			DESCRIPTION
				"Description."
			DEFVAL { enable }
			::= { hwAPGroupRadioEntry 28 }

		
		-- 1.3.6.1.4.1.2011.6.139.11.1.5.1.29
		hwAPGrpSfnRoamCtsDelay OBJECT-TYPE
			SYNTAX Integer32 (0..255)
			MAX-ACCESS read-write
			STATUS current
			DESCRIPTION
				"Description."
			DEFVAL { 0 }
			::= { hwAPGroupRadioEntry 29 }
		-- 1.3.6.1.4.1.2011.6.139.11.1.5.1.30
		hwAPGroupRadioCalibrateFlexibleRadio OBJECT-TYPE
			SYNTAX INTEGER
				{
				disable(1),
				enable(2)
				}
			MAX-ACCESS read-write
			STATUS current
			DESCRIPTION
				"Description."
			DEFVAL { enable }
			::= { hwAPGroupRadioEntry 30 }
		
		-- 1.3.6.1.4.1.2011.6.139.11.1.5.1.31
		hwAPGrpAutoBandwidthSelectSwitch OBJECT-TYPE
			SYNTAX INTEGER
				{
				disable(1),
				enable(2)
				}
			MAX-ACCESS read-write
			STATUS current
			DESCRIPTION
				"This object indicates the status of the automatic bandwidth selection function. The default value is 1."
			DEFVAL { disable }
			::= { hwAPGroupRadioEntry 31 }

		-- 1.3.6.1.4.1.2011.6.139.11.1.5.1.32
		hwAPGrpReferenceDataAnalysis OBJECT-TYPE
			SYNTAX INTEGER
				{
				disable(1),
				enable(2)
				}
			MAX-ACCESS read-write
			STATUS current
			DESCRIPTION
				"This object indicates the status of the referencing data-analysis  function. The default value is 2."
			DEFVAL { enable }
			::= { hwAPGroupRadioEntry 32 }				
	
--  1.3.6.1.4.1.2011.6.139.11.1.6
		-- 1.3.6.1.4.1.2011.6.139.11.1.6
		hwAPGroupVapTable OBJECT-TYPE
			SYNTAX SEQUENCE OF HwAPGroupVapEntry 
			MAX-ACCESS not-accessible
			STATUS current
			DESCRIPTION 
				"This table is used to create VAPs in an AP group."
			::= { hwWlanConfigObjects 6 }

		--1.3.6.1.4.1.2011.6.139.11.1.6.1
		hwAPGroupVapEntry OBJECT-TYPE
			SYNTAX HwAPGroupVapEntry 
			MAX-ACCESS not-accessible
			STATUS current
			DESCRIPTION 
				"Indexes of this table are hwAPGroupName, hwAPGrpRadioId, and hwAPGrpWlanId."
			INDEX { hwAPGroupName, hwAPGrpRadioId, hwAPGrpWlanId }
			::= { hwAPGroupVapTable 1 }


		HwAPGroupVapEntry ::=
			SEQUENCE {				
				hwAPGrpWlanId
					Unsigned32,
				hwAPGrpVapProfile
					OCTET STRING,
				hwAPGrpVapRowStatus
					RowStatus,
				hwAPGrpVapServiceVlan
					Unsigned32,
				hwAPGrpVapVlanPool
					OCTET STRING	
			 }

		 --1.3.6.1.4.1.2011.6.139.11.1.6.1.1
		hwAPGrpWlanId OBJECT-TYPE
			SYNTAX Unsigned32 (1..16)
			MAX-ACCESS not-accessible
			STATUS current
			DESCRIPTION 
				"This object indicates the WLAN ID. It is the index of the table."
			::= { hwAPGroupVapEntry 1 }

		 --1.3.6.1.4.1.2011.6.139.11.1.6.1.2
		hwAPGrpVapProfile OBJECT-TYPE
			SYNTAX OCTET STRING (SIZE (1..35))
			MAX-ACCESS read-write
			STATUS current
			DESCRIPTION 
				"This object indicates the bound VAP profile."
			::= { hwAPGroupVapEntry 2 }

		 --1.3.6.1.4.1.2011.6.139.11.1.6.1.3
		hwAPGrpVapRowStatus OBJECT-TYPE
			SYNTAX RowStatus
			MAX-ACCESS read-write
			STATUS current
			DESCRIPTION 
				"This object indicates the row status of this table. ROWSTATUS_CREATEANDFLOW and ROWSTATUS_DESTROY are commonly used."
			::= { hwAPGroupVapEntry 3 }

		--1.3.6.1.4.1.2011.6.139.11.1.6.1.4
		hwAPGrpVapServiceVlan OBJECT-TYPE
			SYNTAX Unsigned32 (0..4094)
			MAX-ACCESS read-write
			STATUS current
			DESCRIPTION
				"This object indicates the service VLAN for the VAP. The invalid value is 0."
			::= { hwAPGroupVapEntry 4 }
		

		--1.3.6.1.4.1.2011.6.139.11.1.6.1.5
		hwAPGrpVapVlanPool OBJECT-TYPE
			SYNTAX OCTET STRING (SIZE (0..31))
			MAX-ACCESS read-write
			STATUS current
			DESCRIPTION
				"This object indicates the VLAN pool to which the VAP is bound."
			::= { hwAPGroupVapEntry 5 }

		--1.3.6.1.4.1.2011.6.139.11.1.7
		hwAPSpecificTable OBJECT-TYPE
			SYNTAX SEQUENCE OF HwAPSpecificEntry 
			MAX-ACCESS not-accessible
			STATUS current
			DESCRIPTION 
				"This table is used to create or delete an AP specific profile and bind an AP system profile, 2G radio profile, or domain profile to it or unbind an AP system profile, 2G radio profile, or domain profile from it."
			::= { hwWlanConfigObjects 7 }

		--1.3.6.1.4.1.2011.6.139.11.1.7.1
		hwAPSpecificEntry OBJECT-TYPE
			SYNTAX HwAPSpecificEntry 
			MAX-ACCESS not-accessible
			STATUS current
			DESCRIPTION 
				"The index of this table is hwAPSpApMac."
			INDEX { hwAPSpApMac }
			::= { hwAPSpecificTable 1 }


		HwAPSpecificEntry ::=
			SEQUENCE { 
				hwAPSpAPSystemProfile
					OCTET STRING,
				hwAPSpDomainProfile
					OCTET STRING,
				hwAPSpRowStatus
					RowStatus,
				hwAPSpApMac
					MacAddress,
				hwAPSpApId
					Unsigned32,
				hwAPSpApTypeInfo
					OCTET STRING,
				hwAPSpWidsProfile
					OCTET STRING,
				hwAPSpBleProfile
					OCTET STRING,
				hwAPSpLongitude
					OCTET STRING,
				hwAPSpLatitude
					OCTET STRING,
				hwAPSpApAddressMode
					INTEGER,
				hwAPSpApIPv4Address
					IpAddress,
				hwAPSpApIPv4Mask
					IpAddress,
				hwAPSpApIPv4Gateway
					IpAddress,
				hwAPSpApIPv6Address
					OCTET STRING,
				hwAPSpApIPv6PrefixLen
					Integer32,
				hwAPSpApIPv6Gateway
					OCTET STRING,
				hwAPSpIPv4ACList
					OCTET STRING,
				hwAPSpIPv6ACList
					OCTET STRING,
				hwAPSpGroupName
					OCTET STRING,
				hwAPSpApName
					OCTET STRING,
			 	hwAPSpBranchGroupName
					OCTET STRING,
				hwAPSpLocation
					OCTET STRING,
				hwAPSpSiteCode
					OCTET STRING,
				hwAPSpDomainName
					OCTET STRING,				
			 	hwAPSpApZoneName
					OCTET STRING
			 }

		-- 1.3.6.1.4.1.2011.6.139.11.1.7.1.2
		hwAPSpAPSystemProfile OBJECT-TYPE
			SYNTAX OCTET STRING (SIZE (0..35))
			MAX-ACCESS read-write
			STATUS current
			DESCRIPTION 
				"This object indicates the system profile bound to the AP specific profile."
			::= { hwAPSpecificEntry 2 }


		-- 1.3.6.1.4.1.2011.6.139.11.1.7.1.4
		hwAPSpDomainProfile OBJECT-TYPE
			SYNTAX OCTET STRING (SIZE (0..35))
			MAX-ACCESS read-write
			STATUS current
			DESCRIPTION 
				"This object indicates the domain profile bound to the AP specific profile."
			::= { hwAPSpecificEntry 4 }


		-- 1.3.6.1.4.1.2011.6.139.11.1.7.1.5
		hwAPSpRowStatus OBJECT-TYPE
			SYNTAX RowStatus
			MAX-ACCESS read-write
			STATUS current
			DESCRIPTION 
				"This object indicates the row status of this table. ROWSTATUS_CREATEANDFLOW and ROWSTATUS_DESTROY are commonly used?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwAPSpecificEntry 5 }


		-- 1.3.6.1.4.1.2011.6.139.11.1.7.1.6
		hwAPSpApMac OBJECT-TYPE
			SYNTAX MacAddress
			MAX-ACCESS not-accessible
			STATUS current
			DESCRIPTION
				"This object indicates the MAC address of an AP."
			::= { hwAPSpecificEntry 6 }


		-- 1.3.6.1.4.1.2011.6.139.11.1.7.1.7
		hwAPSpApId OBJECT-TYPE
			SYNTAX Unsigned32
			MAX-ACCESS read-write
			STATUS current
			DESCRIPTION
				"This object indicates the AP ID."
			::= { hwAPSpecificEntry 7 }


		-- 1.3.6.1.4.1.2011.6.139.11.1.7.1.8
		hwAPSpApTypeInfo OBJECT-TYPE
			SYNTAX OCTET STRING (SIZE (0..35))
			MAX-ACCESS read-write
			STATUS current
			DESCRIPTION
				"This object indicates the domain profile bound to the AP specific profile."
			::= { hwAPSpecificEntry 8 }


		-- 1.3.6.1.4.1.2011.6.139.11.1.7.1.9
		hwAPSpWidsProfile OBJECT-TYPE
			SYNTAX OCTET STRING (SIZE (0..35))
			MAX-ACCESS read-write
			STATUS current
			DESCRIPTION
				"This object indicates the bound WIDS profile."
			::= { hwAPSpecificEntry 9 }

		
		-- 1.3.6.1.4.1.2011.6.139.11.1.7.1.10
		hwAPSpBleProfile OBJECT-TYPE
			SYNTAX OCTET STRING (SIZE (0..35))
			MAX-ACCESS read-write
			STATUS current
			DESCRIPTION
				"This object indicates the bound BLE profile."
			::= { hwAPSpecificEntry 10 }
			
		-- 1.3.6.1.4.1.2011.6.139.11.1.7.1.11
		hwAPSpLongitude OBJECT-TYPE
			SYNTAX OCTET STRING (SIZE (0..15))
			MAX-ACCESS read-write
			STATUS current
			DESCRIPTION
				"This object indicates the longitude."
			::= { hwAPSpecificEntry 11 }
			
		-- 1.3.6.1.4.1.2011.6.139.11.1.7.1.12
		hwAPSpLatitude OBJECT-TYPE
			SYNTAX OCTET STRING (SIZE (0..14))
			MAX-ACCESS read-write
			STATUS current
			DESCRIPTION
				"This object indicates the latitude."
			::= { hwAPSpecificEntry 12 }
		
		-- 1.3.6.1.4.1.2011.6.139.11.1.7.1.13
		hwAPSpApAddressMode OBJECT-TYPE
			SYNTAX INTEGER
				{
				invalid(-1),
				static(1),
				dhcp(2),
				slaac(3)
				}
			MAX-ACCESS read-write
			STATUS current
			DESCRIPTION
				"This object indicates the IP address allocation mode."
			::= { hwAPSpecificEntry 13 }
		
		-- 1.3.6.1.4.1.2011.6.139.11.1.7.1.14
		hwAPSpApIPv4Address OBJECT-TYPE
			SYNTAX IpAddress
			MAX-ACCESS read-write
			STATUS current
			DESCRIPTION
				"This object indicates the AP's IPv4 address.
 	hwAPSpApIPv4Address takes effect if hwAPSpApAddressMode is set to static."
			::= { hwAPSpecificEntry 14 }
		
		-- 1.3.6.1.4.1.2011.6.139.11.1.7.1.15
		hwAPSpApIPv4Mask OBJECT-TYPE
			SYNTAX IpAddress
			MAX-ACCESS read-write
			STATUS current
			DESCRIPTION
				"This object indicates the AP's IPv4 mask.
 	hwAPSpApIPv4Mask takes effect if hwAPSpApAddressMode is set to static."
			::= { hwAPSpecificEntry 15 }
		
		-- 1.3.6.1.4.1.2011.6.139.11.1.7.1.16
		hwAPSpApIPv4Gateway OBJECT-TYPE
			SYNTAX IpAddress
			MAX-ACCESS read-write
			STATUS current
			DESCRIPTION
				"This object indicates the AP's IPv4 gateway.
 	hwAPSpApIPv4Gateway takes effect if hwAPSpApAddressMode is set to static."
			::= { hwAPSpecificEntry 16 }
		
		-- 1.3.6.1.4.1.2011.6.139.11.1.7.1.17
		hwAPSpApIPv6Address OBJECT-TYPE
			SYNTAX OCTET STRING (SIZE (0..46))
			MAX-ACCESS read-write
			STATUS current
			DESCRIPTION
				"This object indicates the AP's IPv6 address.
 	hwAPSpApIPv6Address takes effect if hwAPSpApAddressMode is set to static."
			::= { hwAPSpecificEntry 17 }
		
		-- 1.3.6.1.4.1.2011.6.139.11.1.7.1.18
		hwAPSpApIPv6PrefixLen OBJECT-TYPE
			SYNTAX Integer32 (0..128)
			MAX-ACCESS read-write
			STATUS current
			DESCRIPTION
				"This object indicates the length of the IPv6 address prefix."
			::= { hwAPSpecificEntry 18 }
		
		-- 1.3.6.1.4.1.2011.6.139.11.1.7.1.19
		hwAPSpApIPv6Gateway OBJECT-TYPE
			SYNTAX OCTET STRING (SIZE (0..46))
			MAX-ACCESS read-write
			STATUS current
			DESCRIPTION
				"This object indicates the AP's IPv6 gateway.
 	hwAPSpApIPv6Gateway takes effect if hwAPSpApAddressMode is set to static."
			::= { hwAPSpecificEntry 19 }
		
		-- 1.3.6.1.4.1.2011.6.139.11.1.7.1.20
		hwAPSpIPv4ACList OBJECT-TYPE
			SYNTAX OCTET STRING
			MAX-ACCESS read-write
			STATUS current
			DESCRIPTION
				"This object indicates the AC IPv4 address list.
 	NOTE AC lists are separated by question marks (?).A maximum of four AC lists can be configured."
			::= { hwAPSpecificEntry 20 }
		
		-- 1.3.6.1.4.1.2011.6.139.11.1.7.1.21
		hwAPSpIPv6ACList OBJECT-TYPE
			SYNTAX OCTET STRING
			MAX-ACCESS read-write
			STATUS current
			DESCRIPTION
				"This object indicates the AC IPv6 address list.
 	NOTE AC lists are separated by question marks (?).A maximum of four AC lists can be configured."
			::= { hwAPSpecificEntry 21 }
		
		-- 1.3.6.1.4.1.2011.6.139.11.1.7.1.22
		hwAPSpGroupName OBJECT-TYPE
			SYNTAX OCTET STRING (SIZE (0..35))
			MAX-ACCESS read-write
			STATUS current
			DESCRIPTION
				"Description."
			::= { hwAPSpecificEntry 22 }
		
		-- 1.3.6.1.4.1.2011.6.139.11.1.7.1.23
		hwAPSpApName OBJECT-TYPE
			SYNTAX OCTET STRING (SIZE (0..31))
			MAX-ACCESS read-write
			STATUS current
			DESCRIPTION
				"Description."
			::= { hwAPSpecificEntry 23 }
		-- 1.3.6.1.4.1.2011.6.139.11.1.7.1.24
		hwAPSpBranchGroupName OBJECT-TYPE
			SYNTAX OCTET STRING (SIZE (0..35))
			MAX-ACCESS read-write
			STATUS current
			DESCRIPTION
				"This object indicates the AP branch group name."
			::= { hwAPSpecificEntry 24 }
		-- 1.3.6.1.4.1.2011.6.139.11.1.7.1.25
		hwAPSpLocation OBJECT-TYPE
			SYNTAX OCTET STRING (SIZE (0..63))
			MAX-ACCESS read-write
			STATUS current
			DESCRIPTION
				"This object indicates the ap location."
			::= { hwAPSpecificEntry 25 }
		-- 1.3.6.1.4.1.2011.6.139.11.1.7.1.26
		hwAPSpSiteCode OBJECT-TYPE
			SYNTAX OCTET STRING (SIZE (0..14))
			MAX-ACCESS read-write
			STATUS current
			DESCRIPTION
				"This object indicates the site code."
			::= { hwAPSpecificEntry 26 }			
		-- 1.3.6.1.4.1.2011.6.139.11.1.7.1.27
		hwAPSpDomainName OBJECT-TYPE
			SYNTAX OCTET STRING (SIZE (0..255))
			MAX-ACCESS read-write
			STATUS current
			DESCRIPTION
				"This object indicates the domain name."
			::= { hwAPSpecificEntry 27 }			
		
		-- 1.3.6.1.4.1.2011.6.139.11.1.7.1.28
		hwAPSpApZoneName OBJECT-TYPE
			SYNTAX OCTET STRING (SIZE (0..35))
			MAX-ACCESS read-write
			STATUS current
			DESCRIPTION
				"This object indicates the AP zone name."
			::= { hwAPSpecificEntry 28 }		
--   1.3.6.1.4.1.2011.6.139.11.1.8
-- 1.3.6.1.4.1.2011.6.139.11.1.8
		-- 1.3.6.1.4.1.2011.6.139.11.1.8
		hwAPSpecificWiredPortTable OBJECT-TYPE
			SYNTAX SEQUENCE OF HwAPSpecificWiredPortEntry 
			MAX-ACCESS not-accessible
			STATUS current
			DESCRIPTION 
				"This table is used to bind an AP wired port profile to an AP specific profile or unbind an AP wired port profile from an AP specific profile.."
			::= { hwWlanConfigObjects 8 }

		--1.3.6.1.4.1.2011.6.139.11.1.8.1
		hwAPSpecificWiredPortEntry OBJECT-TYPE
			SYNTAX HwAPSpecificWiredPortEntry 
			MAX-ACCESS not-accessible
			STATUS current
			DESCRIPTION 
				"Indexes of this table are  hwAPSpWPInterfaceType, hwAPSpWPInterfaceNum and hwAPSpApMac."
			INDEX { hwAPSpWPInterfaceType, hwAPSpWPInterfaceNum, hwAPSpApMac }
			::= { hwAPSpecificWiredPortTable 1 }


		HwAPSpecificWiredPortEntry ::=
			SEQUENCE {				
				hwAPSpWPInterfaceType
					INTEGER,
				hwAPSpWPInterfaceNum
					Unsigned32,
				hwAPSpWPProfile
					OCTET STRING,
				hwAPSpWPRowStatus
					RowStatus,
				hwAPSpWPApId
					Unsigned32
			 }

		 --1.3.6.1.4.1.2011.6.139.11.1.8.1.1
		hwAPSpWPInterfaceType OBJECT-TYPE
			SYNTAX INTEGER
				{
				fe(1),
				ge(2),
				trunk(3),
				multige(4),
				xge(5)
				}
			MAX-ACCESS not-accessible
			STATUS current
			DESCRIPTION 
				"This object indicates the interface type."
			::= { hwAPSpecificWiredPortEntry 1 }

		 --1.3.6.1.4.1.2011.6.139.11.1.8.1.2
		hwAPSpWPInterfaceNum OBJECT-TYPE
			SYNTAX Unsigned32 (0..27)
			MAX-ACCESS not-accessible
			STATUS current
			DESCRIPTION 
				"This object indicates the interface index."
			::= { hwAPSpecificWiredPortEntry 2 }

		 --1.3.6.1.4.1.2011.6.139.11.1.8.1.3
		hwAPSpWPProfile OBJECT-TYPE
			SYNTAX OCTET STRING (SIZE (0..35))
			MAX-ACCESS read-write
			STATUS current
			DESCRIPTION 
				"This object indicates the bound wired port profile."
			::= { hwAPSpecificWiredPortEntry 3 }

		 --1.3.6.1.4.1.2011.6.139.11.1.8.1.4
		hwAPSpWPRowStatus OBJECT-TYPE
			SYNTAX RowStatus
			MAX-ACCESS read-write
			STATUS current
			DESCRIPTION 
				"This object indicates the row status of this table. ROWSTATUS_CREATEANDFLOW and ROWSTATUS_DESTROY are commonly used?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwAPSpecificWiredPortEntry 4 }

		-- 1.3.6.1.4.1.2011.6.139.11.1.8.1.5
		hwAPSpWPApId OBJECT-TYPE
			SYNTAX Unsigned32
			MAX-ACCESS read-only
			STATUS current
			DESCRIPTION
				"This object indicates the AP ID."
			::= { hwAPSpecificWiredPortEntry 5 }

		
		--1.3.6.1.4.1.2011.6.139.11.1.9
		hwAPSpecificRadioTable OBJECT-TYPE
			SYNTAX SEQUENCE OF HwAPSpecificRadioEntry 
			MAX-ACCESS not-accessible
			STATUS current
			DESCRIPTION 
				"This table records the information about profiles bound based on radio in an AP specific profile, including 5G radio profile, Mesh profile, WDS profile, WIDS profile, location profile, and spectrum profile."
			::= { hwWlanConfigObjects 9 }

		--1.3.6.1.4.1.2011.6.139.11.1.9.1
		hwAPSpecificRadioEntry OBJECT-TYPE
			SYNTAX HwAPSpecificRadioEntry 
			MAX-ACCESS not-accessible
			STATUS current
			DESCRIPTION 
				"Indexes of this table are hwAPSpecificName and hwAPSpRadio."
			INDEX { hwAPSpRadio,hwAPSpApMac }
			::= { hwAPSpecificRadioTable 1 }


		HwAPSpecificRadioEntry ::=
			SEQUENCE {				
				hwAPSpRadio
					Unsigned32,
				hwAPSp5gRadioProfile
					OCTET STRING,
				hwAPSpMeshProfile
					OCTET STRING,
				hwAPSpWdsProfile
					OCTET STRING,
				hwAPSpLocationProfile
					OCTET STRING,
				hwAPSpRadioRowStatus
					RowStatus,
				hwAPSpRadio2gProfile
					OCTET STRING,
				hwAPSpMeshWhitelistProfile
					OCTET STRING,
				hwAPSpWdsWhitelistProfile
					OCTET STRING,
				hwAPSpRadioSwitch
					INTEGER,
				hwAPSpRadioChannel
					Unsigned32,
				hwAPSpRadioBandwidth
					INTEGER,
				hwAPSpRadioEirp
					Unsigned32,
				hwAPSpRadioAntennaGain
					Integer32,
				hwAPSpRadioCoverageDistance
					Unsigned32,
				hwAPSpRadioWorkMode
					INTEGER,
				hwAPSpRadioFrequency
					INTEGER,
				hwAPSpSpectrumAnalysisSwitch
					INTEGER,
				hwAPSpWidsDeviceDetectSwitch
					INTEGER,
				hwAPSpWidsAttackDetectEnBmp
					Unsigned32,
				hwAPSpWidsRogueContainSwitch
					INTEGER,
				hwAPSpRadioApId
					Unsigned32,
				hwAPSpRadioSecondChannel
					Unsigned32,
				hwAPSpAutoChannelSelectSwitch
					INTEGER,
				hwAPSpAutoTxPowerSelectSwitch
					INTEGER,
				hwAPSpSfnRoamCtsSwitch
					INTEGER,
				hwAPSpSfnRoamBeaconSwitch
					INTEGER,
				hwAPSpSfnRoamCtsDelay
					Integer32, 
			    hwAPSpRadioCalibrateFlexibleRadio  
					INTEGER,
				hwAPSpAutoBandwidthSelectSwitch
					INTEGER,
				hwAPSpReferenceDataAnalysis
					INTEGER
			 }

		 --1.3.6.1.4.1.2011.6.139.11.1.9.1.1
		hwAPSpRadio OBJECT-TYPE
			SYNTAX Unsigned32 (0..2)
			MAX-ACCESS not-accessible
			STATUS current
			DESCRIPTION 
				"This object indicates the radio ID. It is the index of the table."
			::= { hwAPSpecificRadioEntry 1 }

		 --1.3.6.1.4.1.2011.6.139.11.1.9.1.2
		hwAPSp5gRadioProfile OBJECT-TYPE
			SYNTAX OCTET STRING (SIZE (0..35))
			MAX-ACCESS read-write
			STATUS current
			DESCRIPTION 
				"This object indicates the bound 5G radio profile."
			::= { hwAPSpecificRadioEntry 2 }

		 --1.3.6.1.4.1.2011.6.139.11.1.9.1.3
		hwAPSpMeshProfile OBJECT-TYPE
			SYNTAX OCTET STRING (SIZE (0..35))
			MAX-ACCESS read-write
			STATUS current
			DESCRIPTION 
				"This object indicates the bound Mesh profile."
			::= { hwAPSpecificRadioEntry 3 }

		 --1.3.6.1.4.1.2011.6.139.11.1.9.1.4
		hwAPSpWdsProfile OBJECT-TYPE
			SYNTAX OCTET STRING (SIZE (0..35))
			MAX-ACCESS read-write
			STATUS current
			DESCRIPTION 
				"This object indicates the bound WDS profile."
			::= { hwAPSpecificRadioEntry 4 }

	
	 --1.3.6.1.4.1.2011.6.139.11.1.9.1.6
		hwAPSpLocationProfile OBJECT-TYPE
			SYNTAX OCTET STRING (SIZE (0..35))
			MAX-ACCESS read-write
			STATUS current
			DESCRIPTION 
				"This object indicates the bound location profile."
			::= { hwAPSpecificRadioEntry 6 }
			

		-- 1.3.6.1.4.1.2011.6.139.11.1.9.1.8
		hwAPSpRadioRowStatus OBJECT-TYPE
			SYNTAX RowStatus
			MAX-ACCESS read-write
			STATUS current
			DESCRIPTION 
				"This object indicates the row status of this table. ROWSTATUS_CREATEANDFLOW and ROWSTATUS_DESTROY are commonly used."
			::= { hwAPSpecificRadioEntry 8 }


		-- 1.3.6.1.4.1.2011.6.139.11.1.9.1.9
		hwAPSpRadio2gProfile OBJECT-TYPE
			SYNTAX OCTET STRING (SIZE (0..35))
			MAX-ACCESS read-write
			STATUS current
			DESCRIPTION
				"This object indicates the system profile to which AP groups are bound. The default value is default."
			::= { hwAPSpecificRadioEntry 9 }


		-- 1.3.6.1.4.1.2011.6.139.11.1.9.1.10
		hwAPSpMeshWhitelistProfile OBJECT-TYPE
			SYNTAX OCTET STRING (SIZE (0..35))
			MAX-ACCESS read-write
			STATUS current
			DESCRIPTION
				"This object indicates the bound whitelist profile."
			::= { hwAPSpecificRadioEntry 10 }


		-- 1.3.6.1.4.1.2011.6.139.11.1.9.1.11
		hwAPSpWdsWhitelistProfile OBJECT-TYPE
			SYNTAX OCTET STRING (SIZE (0..35))
			MAX-ACCESS read-write
			STATUS current
			DESCRIPTION
				"This object indicates the bound whitelist profile."
			::= { hwAPSpecificRadioEntry 11 }


		-- 1.3.6.1.4.1.2011.6.139.11.1.9.1.12
		hwAPSpRadioSwitch OBJECT-TYPE
			SYNTAX INTEGER
				{
				disable(1),
				invalid(255)
				}
			MAX-ACCESS read-write
			STATUS current
			DESCRIPTION
				"This object indicates the name of a 2G radio profile. It is the index of the table."
			::= { hwAPSpecificRadioEntry 12 }


		-- 1.3.6.1.4.1.2011.6.139.11.1.9.1.13
		hwAPSpRadioChannel OBJECT-TYPE
			SYNTAX Unsigned32
			MAX-ACCESS read-write
			STATUS current
			DESCRIPTION
				"This object indicates a radio-frequency channel. For 2.4G, the value ranges from 1 to 13. For 5G, the value ranges from 36 to 196 (with a separation interval of 4)."
			::= { hwAPSpecificRadioEntry 13 }


		-- 1.3.6.1.4.1.2011.6.139.11.1.9.1.14
		hwAPSpRadioBandwidth OBJECT-TYPE
			SYNTAX INTEGER
				{
				ht20(1),
				ht40Plus(2),
				ht40Minus(3),
				ht80(4),
				ht160(5),
				invalid(255)
				}
			MAX-ACCESS read-write
			STATUS current
			DESCRIPTION
				"This object indicate a bandwidth. The default value is 1."
			::= { hwAPSpecificRadioEntry 14 }


		-- 1.3.6.1.4.1.2011.6.139.11.1.9.1.15
		hwAPSpRadioEirp OBJECT-TYPE
			SYNTAX Unsigned32 (1..127 | 255)
			MAX-ACCESS read-write
			STATUS current
			DESCRIPTION
				"This object indicates a power value. The default value is 127. The configuration is saved but the actual power is determined by the maximum power supported by the AP."
			::= { hwAPSpecificRadioEntry 15 }


		-- 1.3.6.1.4.1.2011.6.139.11.1.9.1.16
		hwAPSpRadioAntennaGain OBJECT-TYPE
			SYNTAX Integer32 (-10..30 | 255)
			MAX-ACCESS read-write
			STATUS current
			DESCRIPTION
				"This object indicates antenna gains. The default value 0xFF indicates that the default gain of an AP is used. It is expressed in dB. Default gains vary with different types of APs."
			::= { hwAPSpecificRadioEntry 16 }


		-- 1.3.6.1.4.1.2011.6.139.11.1.9.1.17
		hwAPSpRadioCoverageDistance OBJECT-TYPE
			SYNTAX Unsigned32 (1..400 | 65535)
			MAX-ACCESS read-write
			STATUS current
			DESCRIPTION
				"This object indicates a radio coverage distance. The default value is 3. The unit is 0.1 km."
			::= { hwAPSpecificRadioEntry 17 }


		-- 1.3.6.1.4.1.2011.6.139.11.1.9.1.18
		hwAPSpRadioWorkMode OBJECT-TYPE
			SYNTAX INTEGER
				{
				normal(1),
				monitor(2),
				dualband(3),
				proxyScan(4),
				invalid(255)
				}
			MAX-ACCESS read-write
			STATUS current
			DESCRIPTION
				"This object indicates the radio working mode. The default value is 1."
			::= { hwAPSpecificRadioEntry 18 }


		-- 1.3.6.1.4.1.2011.6.139.11.1.9.1.19
		hwAPSpRadioFrequency OBJECT-TYPE
			SYNTAX INTEGER
				{
				frequency2G(1),
				frequency5G(2),
				invalid(255)
				}
			MAX-ACCESS read-write
			STATUS current
			DESCRIPTION
				"This object indicates the setting of the frequency band for radio 0. The default value is invalid. 1: frequency2G, 2: frequency5G."
			::= { hwAPSpecificRadioEntry 19 }

		

		-- 1.3.6.1.4.1.2011.6.139.11.1.9.1.20
		hwAPSpSpectrumAnalysisSwitch OBJECT-TYPE
			SYNTAX INTEGER
				{
				enable(2),
				invalid(255)
				}
			MAX-ACCESS read-write
			STATUS current
			DESCRIPTION
				"This object indicates the status of the spectrum analysis function. The default value is 1."
			::= { hwAPSpecificRadioEntry 20 }

		

		-- 1.3.6.1.4.1.2011.6.139.11.1.9.1.21
		hwAPSpWidsDeviceDetectSwitch OBJECT-TYPE
			SYNTAX INTEGER
				{
				enable(2),
				invalid(255)
				}
			MAX-ACCESS read-write
			STATUS current
			DESCRIPTION
				"This object indicates the status of the device detection function. The default value is 1."
			::= { hwAPSpecificRadioEntry 21 }

		

		-- 1.3.6.1.4.1.2011.6.139.11.1.9.1.22
		hwAPSpWidsAttackDetectEnBmp OBJECT-TYPE
			SYNTAX Unsigned32
			MAX-ACCESS read-write
			STATUS current
			DESCRIPTION
				"This object indicates the bit map of the brute force attack switch. bit0:weak-iv, bit1:spoof, bit2:flood, bit3:wpa-psk, bit4:wpa2-psk, bit5:wapi-psk, bit6:wep-psk."
			::= { hwAPSpecificRadioEntry 22 }

		
		-- 1.3.6.1.4.1.2011.6.139.11.1.9.1.23
		hwAPSpWidsRogueContainSwitch OBJECT-TYPE
			SYNTAX INTEGER
				{
				enable(2),
				invalid(255)
				}
			MAX-ACCESS read-write
			STATUS current
			DESCRIPTION
				"This object indicates the status of the device detection function. The default value is 1."
			::= { hwAPSpecificRadioEntry 23 }


		-- 1.3.6.1.4.1.2011.6.139.11.1.9.1.24
		hwAPSpRadioApId OBJECT-TYPE
			SYNTAX Unsigned32
			MAX-ACCESS read-only
			STATUS current
			DESCRIPTION
				"This object indicates the AP ID."
			::= { hwAPSpecificRadioEntry 24 }

		-- 1.3.6.1.4.1.2011.6.139.11.1.9.1.25
		hwAPSpRadioSecondChannel OBJECT-TYPE
			SYNTAX Unsigned32
			MAX-ACCESS read-write
			STATUS current
			DESCRIPTION
				"This object indicates a radio-frequency channel. The value ranges from 42,58,106,122,138,155."
			::= { hwAPSpecificRadioEntry 25 }
			
		-- 1.3.6.1.4.1.2011.6.139.11.1.9.1.26
		hwAPSpAutoChannelSelectSwitch OBJECT-TYPE
			SYNTAX INTEGER
				{
				disable(1),
				enable(2),
				invalid(255)
				}
			MAX-ACCESS read-write
			STATUS current
			DESCRIPTION
				"This object indicates the status of the automatic channel selection function. The default value is 255."
			::= { hwAPSpecificRadioEntry 26 }
		
		-- 1.3.6.1.4.1.2011.6.139.11.1.9.1.27
		hwAPSpAutoTxPowerSelectSwitch OBJECT-TYPE
			SYNTAX INTEGER
				{
				disable(1),
 				enable(2),
				invalid(255)
				}
			MAX-ACCESS read-write
			STATUS current
			DESCRIPTION
				"This object indicates the status of the automatic power selection function. The default value is 255."
			::= { hwAPSpecificRadioEntry 27 }
		
		-- 1.3.6.1.4.1.2011.6.139.11.1.9.1.28
		hwAPSpSfnRoamCtsSwitch OBJECT-TYPE
			SYNTAX INTEGER
				{
				disable(1),
				invalid(255)
				}
			MAX-ACCESS read-write
			STATUS current
			DESCRIPTION
				"This object indicates the status of Cts Switch. The default value is 255."
			::= { hwAPSpecificRadioEntry 28 }

		
		-- 1.3.6.1.4.1.2011.6.139.11.1.9.1.29
		hwAPSpSfnRoamBeaconSwitch OBJECT-TYPE
			SYNTAX INTEGER
				{
				disable(1),
				invalid(255)
				}
			MAX-ACCESS read-write
			STATUS current
			DESCRIPTION
				"This object indicates the status of Beacon Switch. The default value is 255."
			::= { hwAPSpecificRadioEntry 29 }

		
		-- 1.3.6.1.4.1.2011.6.139.11.1.9.1.30
		hwAPSpSfnRoamCtsDelay OBJECT-TYPE
			SYNTAX Integer32 (0..255)
			MAX-ACCESS read-write
			STATUS current
			DESCRIPTION
				"This object indicates Cts Delay time. The default value is 0."
			DEFVAL { 0 }
			::= { hwAPSpecificRadioEntry 30 }

		
		-- 1.3.6.1.4.1.2011.6.139.11.1.9.1.31
		hwAPSpRadioCalibrateFlexibleRadio OBJECT-TYPE
			SYNTAX INTEGER
				{
				disable(1),
				invalid(255)
				}
			MAX-ACCESS read-write
			STATUS current
			DESCRIPTION
				"This object indicates the status of Beacon Switch. The default value is 255."
			::= { hwAPSpecificRadioEntry 31 }
		                                
		-- 1.3.6.1.4.1.2011.6.139.11.1.9.1.32
		hwAPSpAutoBandwidthSelectSwitch OBJECT-TYPE
			SYNTAX INTEGER
				{
				disable(1),
				enable(2),
				invalid(255)
				}
			MAX-ACCESS read-write
			STATUS current
			DESCRIPTION
				"This object indicates the status of the automatic bandwidth selection function. The default value is 255."
			DEFVAL { invalid }
			::= { hwAPSpecificRadioEntry 32 }     
			
		-- 1.3.6.1.4.1.2011.6.139.11.1.9.1.33
		hwAPSpReferenceDataAnalysis OBJECT-TYPE
			SYNTAX INTEGER
				{
				disable(1),
				enable(2),
				invalid(255)
				}
			MAX-ACCESS read-write
			STATUS current
			DESCRIPTION
				"This object indicates the status of the referencing data-analysis  function. The default value is 255."
			DEFVAL { invalid }
			::= { hwAPSpecificRadioEntry 33 } 
			
--  1.3.6.1.4.1.2011.6.139.11.1.10
		-- 1.3.6.1.4.1.2011.6.139.11.1.10
		hwAPSpecificVapTable OBJECT-TYPE
			SYNTAX SEQUENCE OF HwAPSpecificVapEntry 
			MAX-ACCESS not-accessible
			STATUS current
			DESCRIPTION 
				"This table is used to create VAPs in an AP specific profile."
			::= { hwWlanConfigObjects 10 }

		--1.3.6.1.4.1.2011.6.139.11.1.10.1
		hwAPSpecificVapEntry OBJECT-TYPE
			SYNTAX HwAPSpecificVapEntry 
			MAX-ACCESS not-accessible
			STATUS current
			DESCRIPTION 
				"Indexes of this table are hwAPSpWlan, hwAPSpRadio, and hwAPSpApMac."
			INDEX { hwAPSpWlan, hwAPSpRadio, hwAPSpApMac}
			::= { hwAPSpecificVapTable 1 }


		HwAPSpecificVapEntry ::=
			SEQUENCE {				
				hwAPSpWlan
					Unsigned32,
				hwAPSpVapProfile
					OCTET STRING,
				hwAPSpVapRowStatus
					RowStatus,
				hwAPSpVapApId
					Unsigned32,
				hwAPSpVapServiceVlan
					Unsigned32,
				hwAPSpVapVlanPool
					OCTET STRING
			 }

		 --1.3.6.1.4.1.2011.6.139.11.1.10.1.1
		hwAPSpWlan OBJECT-TYPE
			SYNTAX Unsigned32 (1..16)
			MAX-ACCESS not-accessible
			STATUS current
			DESCRIPTION 
				"This object indicates the WLAN ID. It is the index of the table."
			::= { hwAPSpecificVapEntry 1 }

		 --1.3.6.1.4.1.2011.6.139.11.1.10.1.2
		hwAPSpVapProfile OBJECT-TYPE
			SYNTAX OCTET STRING (SIZE (1..35))
			MAX-ACCESS read-write
			STATUS current
			DESCRIPTION 
				"This object indicates the bound VAP profile."
			::= { hwAPSpecificVapEntry 2 }

		 --1.3.6.1.4.1.2011.6.139.11.1.10.1.3
		hwAPSpVapRowStatus OBJECT-TYPE
			SYNTAX RowStatus
			MAX-ACCESS read-write
			STATUS current
			DESCRIPTION 
				"This object indicates the row status of this table. createAndGo(4) and destroy(6) are commonly used."
			::= { hwAPSpecificVapEntry 3 }

		-- 1.3.6.1.4.1.2011.6.139.11.1.10.1.4
		hwAPSpVapApId OBJECT-TYPE
			SYNTAX Unsigned32
			MAX-ACCESS read-only
			STATUS current
			DESCRIPTION
				"This object indicates the AP ID."
			::= { hwAPSpecificVapEntry 4 }

		--1.3.6.1.4.1.2011.6.139.11.1.10.1.5
		hwAPSpVapServiceVlan OBJECT-TYPE
			SYNTAX Unsigned32 (0..4094)
			MAX-ACCESS read-write
			STATUS current
			DESCRIPTION
				"This object indicates the service VLAN for the VAP. The invalid value is 0."
			::= { hwAPSpecificVapEntry 5 }		

		--1.3.6.1.4.1.2011.6.139.11.1.10.1.6
		hwAPSpVapVlanPool OBJECT-TYPE
			SYNTAX OCTET STRING (SIZE (0..31))
			MAX-ACCESS read-write
			STATUS current
			DESCRIPTION
				"This object indicates the VLAN pool to which the VAP is bound."
			::= { hwAPSpecificVapEntry 6 }	

		--1.3.6.1.4.1.2011.6.139.11.1.11
		hwRegulatoryDomainProfileTable OBJECT-TYPE
			SYNTAX SEQUENCE OF HwRegulatoryDomainProfileEntry 
			MAX-ACCESS not-accessible
			STATUS current
			DESCRIPTION 
				"This table is used to configure country codes, calibration channels, and calibration channel bandwidths."
			::= { hwWlanConfigObjects 11 }

		--1.3.6.1.4.1.2011.6.139.11.1.11.1
		hwRegulatoryDomainProfileEntry OBJECT-TYPE
			SYNTAX HwRegulatoryDomainProfileEntry 
			MAX-ACCESS not-accessible
			STATUS current
			DESCRIPTION 
				"The index of this table is hwRegulatoryDomainProfileName."
			INDEX { hwRegulatoryDomainProfileName }
			::= { hwRegulatoryDomainProfileTable 1 }


		HwRegulatoryDomainProfileEntry ::=
			SEQUENCE {				
				hwRegulatoryDomainProfileName
					OCTET STRING,
				hwCountryCode
					OCTET STRING,
				hwDcaChannel5GBandwidth
					INTEGER,
				hwDcaChannel5GChannelSet
					OCTET STRING,
				hwDcaChannel2GChannelSet
					OCTET STRING,
				hwRegulatoryDomainProfilRowStatus
					RowStatus,
			                   hwWlanWideBandEnable
					INTEGER,
			                   hwApProfChannelLoadMode
					INTEGER			
			 }

		 --1.3.6.1.4.1.2011.6.139.11.1.11.1.1
		hwRegulatoryDomainProfileName OBJECT-TYPE
			SYNTAX OCTET STRING (SIZE (1..35))
			MAX-ACCESS not-accessible
			STATUS current
			DESCRIPTION 
				"This object indicates the name of a regulatory domain profile. It is the index of the table."
			::= { hwRegulatoryDomainProfileEntry 1 }

		 --1.3.6.1.4.1.2011.6.139.11.1.11.1.2
		hwCountryCode OBJECT-TYPE
			SYNTAX OCTET STRING (SIZE (2..8))
			MAX-ACCESS read-write
			STATUS current
			DESCRIPTION 
				"This object indicates the country code. Its value range is subject to the country code table. The default value is CN."
			::= { hwRegulatoryDomainProfileEntry 2 }

		 --1.3.6.1.4.1.2011.6.139.11.1.11.1.3
		hwDcaChannel5GBandwidth OBJECT-TYPE
			SYNTAX INTEGER
				{
				bw20Mhz(1),
				bw40Mhz(2),
				bw80Mhz(3)
				}
			MAX-ACCESS read-write
			STATUS current
			DESCRIPTION 
				"This object indicates the calibration bandwidth on the 5 GHz frequency band. The default value is 1 ?	1: bw20 MHz ?	2: bw40 MHz ?	3: bw80 MHz."
			::= { hwRegulatoryDomainProfileEntry 3 }

		 --1.3.6.1.4.1.2011.6.139.11.1.11.1.4
		hwDcaChannel5GChannelSet OBJECT-TYPE
			SYNTAX OCTET STRING (SIZE (1..256))
			MAX-ACCESS read-write
			STATUS current
			DESCRIPTION 
				"This object indicates the calibration channel set on the 5 GHz frequency band."
			::= { hwRegulatoryDomainProfileEntry 4 }

		 --1.3.6.1.4.1.2011.6.139.11.1.11.1.5
		hwDcaChannel2GChannelSet OBJECT-TYPE
			SYNTAX OCTET STRING (SIZE (1..256))
			MAX-ACCESS read-write
			STATUS current
			DESCRIPTION 
				"This object indicates the calibration channel set on the 2 GHz frequency band."
			::= { hwRegulatoryDomainProfileEntry 5 }

		 --1.3.6.1.4.1.2011.6.139.11.1.11.1.6
		hwRegulatoryDomainProfilRowStatus OBJECT-TYPE
			SYNTAX RowStatus
			MAX-ACCESS read-write
			STATUS current
			DESCRIPTION 
				"This object indicates the row status of this table. ROWSTATUS_CREATEANDFLOW and ROWSTATUS_DESTROY are commonly used ?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwRegulatoryDomainProfileEntry 6 }
			
		--1.3.6.1.4.1.2011.6.139.11.1.11.1.7
		hwWlanWideBandEnable OBJECT-TYPE
			SYNTAX INTEGER
				{
				disable(1),
				enable(2)
				}
			MAX-ACCESS read-write
			STATUS current
			DESCRIPTION
				"This object indicates wide band status. The default value is disable."
			::= { hwRegulatoryDomainProfileEntry 7 }	
			
		--1.3.6.1.4.1.2011.6.139.11.1.11.1.8
		hwApProfChannelLoadMode OBJECT-TYPE
			SYNTAX INTEGER
				{
				indoor(1),
				outdoor(2)
				}
			MAX-ACCESS read-write
			STATUS current
			DESCRIPTION
				"This object indicates channel lode mode. The default value is outdoor."
			::= { hwRegulatoryDomainProfileEntry 8 }	
			
		--1.3.6.1.4.1.2011.6.139.11.1.12
		hwApSystemProfileTable OBJECT-TYPE
			SYNTAX SEQUENCE OF HwApSystemProfileEntry 
			MAX-ACCESS not-accessible
			STATUS current
			DESCRIPTION 
				"This table is used to create or delete an AP system profile and configure AP attributes."
			::= { hwWlanConfigObjects 12 }

		--1.3.6.1.4.1.2011.6.139.11.1.12.1
		hwApSystemProfileEntry OBJECT-TYPE
			SYNTAX HwApSystemProfileEntry 
			MAX-ACCESS not-accessible
			STATUS current
			DESCRIPTION 
				"The index of this table is hwApSystemProfName."
			INDEX { hwApSystemProfName }
			::= { hwApSystemProfileTable 1 }


		HwApSystemProfileEntry ::=
			SEQUENCE {				
				hwApSystemProfName
					OCTET STRING,
				hwApProfStatInterval
					Unsigned32,
				hwApProfSampleTime
					Unsigned32,
				hwApProfLedSwitch
					INTEGER,
				hwApProfMaxStaNum
					Unsigned32,
				hwApProfMtu
					Unsigned32,
				hwApProfMeshRole
					INTEGER,
				hwApProfTemporaryManagement
					INTEGER,
				hwApProfManagementVlan
					Unsigned32,
				hwApProfHighTempThreshold
					Unsigned32,
				hwApProfLowTempThreshold
					Integer32,
				hwApProfOpHRxPowerThreshold
					Unsigned32,
				hwApProfOpLRxPowerThreshold
					Unsigned32,
				hwApProfOpHTempThreshold
					Unsigned32,
				hwApProfOpLTempThreshold
					Integer32,
				hwApProfMemoryUsageThreshold
					Unsigned32,
				hwApProfCpuUsageThreshold
					Unsigned32,
				hwApProfTelnetSwitch
					INTEGER,
				hwApProfSTelnetSwitch
					INTEGER,
				hwApProfConsoleSwitch
					INTEGER,
				hwApProfLogRecordLevel
					INTEGER,
				hwApProfLogServerIp
					IpAddress,
				hwApProfLogServerIpv6
					OCTET STRING,
				hwApProfAlarmRestrictionSwitch
					INTEGER,
				hwApProfAlarmRestrictionPeriod
					Unsigned32,
				hwApProfKeepServiceSwitch
					INTEGER,
				hwApProfProtectPriority
					Unsigned32,
				hwApProfProtectACIp
					IpAddress,
				hwApProfProtectACIpv6
					OCTET STRING,
				hwApProfEapStartMode
					INTEGER,
				hwApProfEapStartTransform
					INTEGER,
				hwApProfEapStartUnicastMac
					MacAddress,
				hwApProfEapResponseMode
					INTEGER,
				hwApProfEapResponseTransform
					INTEGER,
				hwApProfEapResponseUnicastMac
					MacAddress,
				hwApProfLldpRestartDelay
					Unsigned32,
				hwApProfLldpAdminStatus
					INTEGER,
				hwApProfLldpRetransDelay
					Unsigned32,
				hwApProfLldpRetransHoldMultiplier
					Unsigned32,
				hwApProfLldpInterval
					Unsigned32,
				hwApProfLldpReportInterval
					Unsigned32,
				hwApProfStaAccessMode
					INTEGER,
				hwApProfStaAccessModeProfile
					OCTET STRING,
				hwApProfRowStatus
					RowStatus,
				hwApProfSFTPSwitch
				    INTEGER,
				hwApProfDynamicBlackListAgingTime
					Unsigned32,
				hwApProfAntennaOutputMode
				        INTEGER,
				hwApProfMppActiveReselectionSwitch
					INTEGER,
				hwApProfSpectrumServerIPAddress
					IpAddress,
				hwApProfSpectrumServerIPv6Address
					OCTET STRING,
				hwApProfSpectrumServerPort
					Unsigned32,
				hwApProfSpectrumViaACSwitch
					INTEGER,
				hwApProfSpectrumViaACPort
					Unsigned32,
				hwApProfSpectrumNonWifiDeviceAgingTime
					Unsigned32,
				hwApProfPoeMaxPower
					Unsigned32,
				hwApProfPoePowerReserved
					Unsigned32,
				hwApProfPoePowerThreshold
					Unsigned32,
				hwApProfPoeAfInrushSwitch
					INTEGER,
				hwApProfPoeHighInrushSwitch
					INTEGER,
				hwApProfPrimaryLinkIPv4
					IpAddress,
				hwApProfPrimaryLinkIPv6
					OCTET STRING,
				hwApProfBackupLinkIPv4
					IpAddress,
				hwApProfBackupLinkIPv6
					OCTET STRING,
				hwApProfLedOffTimeRange
					OCTET STRING,
				hwApProfUsbSwitch
					INTEGER,
			 	hwApProfBroadcastSuppressionArpEnable
					INTEGER,
			 	hwApProfBroadcastSuppressionArpThreshold
					Unsigned32,
				hwApProfBroadcastSuppressionIgmpEnable
					INTEGER,
			 	hwApProfBroadcastSuppressionIgmpThreshold
					Unsigned32,
				hwApProfBroadcastSuppressionNdEnable
					INTEGER,
			 	hwApProfBroadcastSuppressionNdThreshold
					Unsigned32,
				hwApProfBroadcastSuppressionOtherEnable
					INTEGER,
			 	hwApProfBroadcastSuppressionOtherThreshold
					Unsigned32,
				hwApProfBroadcastSuppressionAllEnable
					INTEGER,    
			                   hwApProfCapwapDtlsDataSwitch
					INTEGER,
   			                   hwApProfTemporaryManagementPsk
					OCTET STRING,
				hwApProfProtectLinkSwitchMode
				                   INTEGER,  	
				hwApProfProtectLinkSwitchEchoProbeTime
				                   Unsigned32,
				hwApProfProtectLinkSwitchStartThreshold
					Unsigned32,
				hwApProfProtectLinkSwitchGapThreshold
				        Unsigned32,
				hwApProfCardConnectType
					INTEGER,
				hwApProfLldpReportEnable
					INTEGER,			
				hwApProfDhcpv4Option12
					INTEGER,  
				hwApProfBcSuppresionAutoDetectThreshold
				    Unsigned32,
				hwApProfMcSuppresionAutoDetectThreshold
				    Unsigned32,
				hwApProfUcSuppresionAutoDetectThreshold
				    Unsigned32,
				hwApProfConsoleBLEMode
					INTEGER, 				
				hwApProfDiskUsageThreshold
					Unsigned32,
				hwApProfLogServerPort
					Unsigned32,
				hwApProfStationConnectivityDetectSwitch
				    INTEGER,					
				hwApProfStaArpNDProxyBeforeAssoc
					INTEGER,
				hwApProfUcSuppressionAutoDetectSwitch
					INTEGER,
				hwApProfPkiCertFileType
					INTEGER,
				hwApProfPkiCertFileName
					OCTET STRING,
				hwApProfPkiCertFilePassword
					OCTET STRING,
				hwApProfHighTempApEnvironmentThreshold
					Unsigned32,
				hwApProfHighTempCpuThreshold
					Unsigned32,
				hwApProfHighTempNpThreshold
					Unsigned32,
				hwApProfLowTempApEnvironmentThreshold
					Integer32,
				hwApProfLowTempCpuThreshold
					Integer32,
				hwApProfLowTempNpThreshold
					Integer32,
				hwApSystemProfileNPFastForwardingSwitch
					INTEGER,
				hwApSystemProfileNPCapwapReassemblySwitch
					INTEGER
			 }

		 --1.3.6.1.4.1.2011.6.139.11.1.12.1.1
		hwApSystemProfName OBJECT-TYPE
			SYNTAX OCTET STRING (SIZE (1..35))
			MAX-ACCESS not-accessible
			STATUS current
			DESCRIPTION 
				"This object indicates the name of an AP system profile. It is the index of the table."
			::= { hwApSystemProfileEntry 1 }


		-- 1.3.6.1.4.1.2011.6.139.11.1.12.1.3
		hwApProfStatInterval OBJECT-TYPE
			SYNTAX Unsigned32 (60..900)
			MAX-ACCESS read-write
			STATUS current
			DESCRIPTION 
				"Description."
			::= { hwApSystemProfileEntry 3 }

		 --1.3.6.1.4.1.2011.6.139.11.1.12.1.4
		hwApProfSampleTime OBJECT-TYPE
			SYNTAX Unsigned32 (2..300)
			MAX-ACCESS read-write
			STATUS current
			DESCRIPTION 
				"This object indicates the sampling interval for the AC to collecting AP performance data. The default value is 30. It is expressed in seconds."
			::= { hwApSystemProfileEntry 4 }

		 --1.3.6.1.4.1.2011.6.139.11.1.12.1.5
		hwApProfLedSwitch OBJECT-TYPE
			SYNTAX INTEGER
				{
				off(1),
				on(2)
				}
			MAX-ACCESS read-write
			STATUS current
			DESCRIPTION 
				"This object indicates whether to enable the AP's LED indicator. The default value is 2."
			::= { hwApSystemProfileEntry 5 }

		 --1.3.6.1.4.1.2011.6.139.11.1.12.1.6
		hwApProfMaxStaNum OBJECT-TYPE
			SYNTAX Unsigned32 (1..256)
			MAX-ACCESS read-write
			STATUS current
			DESCRIPTION 
				"This object indicates the maximum number of access users on an AP. The default value is 128."
			::= { hwApSystemProfileEntry 6 }

		 --1.3.6.1.4.1.2011.6.139.11.1.12.1.7
		hwApProfMtu OBJECT-TYPE
			SYNTAX Unsigned32 (128..1700)
			MAX-ACCESS read-write
			STATUS current
			DESCRIPTION 
				"This object indicates the MTU of an AP interface. The default value is 1500."
			::= { hwApSystemProfileEntry 7 }

		 --1.3.6.1.4.1.2011.6.139.11.1.12.1.8
		hwApProfMeshRole OBJECT-TYPE
			SYNTAX INTEGER
				{
				mp(1),
				mpp(2)
				}
			MAX-ACCESS read-write
			STATUS current
			DESCRIPTION 
				"This object indicates a Mesh role. The default value is 1."
			::= { hwApSystemProfileEntry 8 }

		 --1.3.6.1.4.1.2011.6.139.11.1.12.1.9
		hwApProfTemporaryManagement OBJECT-TYPE
			SYNTAX INTEGER
				{
				disable(1),
				enable(2)
				}
			MAX-ACCESS read-write
			STATUS current
			DESCRIPTION 
				"This object indicates the status of the AP-based offline VAP switch. The default value is 2."
			::= { hwApSystemProfileEntry 9 }

		 --1.3.6.1.4.1.2011.6.139.11.1.12.1.10
		hwApProfManagementVlan OBJECT-TYPE
			SYNTAX Unsigned32 (1..4094|4294967295)
			MAX-ACCESS read-write
			STATUS current
			DESCRIPTION 
				"This object indicates the management VLAN for APs. The default value is 0xFFFFFFFF."
			::= { hwApSystemProfileEntry 10 }

		 --1.3.6.1.4.1.2011.6.139.11.1.12.1.11
		hwApProfHighTempThreshold OBJECT-TYPE
			SYNTAX Unsigned32 (20..110|4294967295)
			MAX-ACCESS read-write
			STATUS current
			DESCRIPTION 
				"This object indicates the high temperature alarm threshold on an AP. The default value 0xFFFFFFFF indicates the system threshold of the AP NOTE System thresholds vary with different AP types. For details, see AP device information."
			::= { hwApSystemProfileEntry 11 }

		 --1.3.6.1.4.1.2011.6.139.11.1.12.1.12
		hwApProfLowTempThreshold OBJECT-TYPE
			SYNTAX Integer32 (-70..10|65535)
			MAX-ACCESS read-write
			STATUS current
			DESCRIPTION 
				"This object indicates the low temperature alarm threshold on an AP. The default value 0xFFFF indicates the system threshold of the AP."
			::= { hwApSystemProfileEntry 12 }

		 --1.3.6.1.4.1.2011.6.139.11.1.12.1.13
		hwApProfOpHRxPowerThreshold OBJECT-TYPE
			SYNTAX Unsigned32 (1000..65535)
			MAX-ACCESS read-write
			STATUS current
			DESCRIPTION 
				"This object indicates the high power threshold of an optical module. The default value is 1000."
			::= { hwApSystemProfileEntry 13 }

		 --1.3.6.1.4.1.2011.6.139.11.1.12.1.14
		hwApProfOpLRxPowerThreshold OBJECT-TYPE
			SYNTAX Unsigned32 (1..250)
			MAX-ACCESS read-write
			STATUS current
			DESCRIPTION 
				"This object indicates the low power threshold of an optical module. The default value is 50."
			::= { hwApSystemProfileEntry 14 }

		 --1.3.6.1.4.1.2011.6.139.11.1.12.1.15
		hwApProfOpHTempThreshold OBJECT-TYPE
			SYNTAX Unsigned32 (70..125)
			MAX-ACCESS read-write
			STATUS current
			DESCRIPTION 
				"This object indicates the high temperature threshold of an optical module. The default value is 70."
			::= { hwApSystemProfileEntry 15 }

		 --1.3.6.1.4.1.2011.6.139.11.1.12.1.16
		hwApProfOpLTempThreshold OBJECT-TYPE
			SYNTAX Integer32 (-40..-5)
			MAX-ACCESS read-write
			STATUS current
			DESCRIPTION 
				"This object indicates the low temperature threshold of an optical module. The default value is -5."
			::= { hwApSystemProfileEntry 16 }

		 --1.3.6.1.4.1.2011.6.139.11.1.12.1.17
		hwApProfMemoryUsageThreshold OBJECT-TYPE
			SYNTAX Unsigned32 (30..100)
			MAX-ACCESS read-write
			STATUS current
			DESCRIPTION 
				"This object indicates the memory usage alarm threshold of an AP. The default value is 80. It is expressed in percentage."
			::= { hwApSystemProfileEntry 17 }

		 --1.3.6.1.4.1.2011.6.139.11.1.12.1.18
		hwApProfCpuUsageThreshold OBJECT-TYPE
			SYNTAX Unsigned32 (50..100)
			MAX-ACCESS read-write
			STATUS current
			DESCRIPTION 
				"This object indicates the CPU usage alarm threshold of an AP. The default value is 90. It is expressed in percentage."
			::= { hwApSystemProfileEntry 18 }

		 --1.3.6.1.4.1.2011.6.139.11.1.12.1.19
		hwApProfTelnetSwitch OBJECT-TYPE
			SYNTAX INTEGER
				{
				disable(1),
				enable(2)
				}
			MAX-ACCESS read-write
			STATUS current
			DESCRIPTION 
				"This object indicates whether to enable Telnet. The default value is 1."
			::= { hwApSystemProfileEntry 19 }

		 --1.3.6.1.4.1.2011.6.139.11.1.12.1.20
		hwApProfSTelnetSwitch OBJECT-TYPE
			SYNTAX INTEGER
				{
				disable(1),
				enable(2)
				}
			MAX-ACCESS read-write
			STATUS current
			DESCRIPTION 
				"This object indicates whether to enable SSH. The default value is 2."
			::= { hwApSystemProfileEntry 20 }

		 --1.3.6.1.4.1.2011.6.139.11.1.12.1.21
		hwApProfConsoleSwitch OBJECT-TYPE
			SYNTAX INTEGER
				{
				disable(1),
				enable(2)
				}
			MAX-ACCESS read-write
			STATUS current
			DESCRIPTION 
				"This object indicates whether to enable the console. The default value is 2."
			::= { hwApSystemProfileEntry 21 }

		 --1.3.6.1.4.1.2011.6.139.11.1.12.1.22
		hwApProfLogRecordLevel OBJECT-TYPE
			SYNTAX INTEGER
				{
				emergency(1),
				alert(2),
				critical(3),
				error(4),
				warning(5),
				notice(6),
				info(7),
				debug(8)
				}
			MAX-ACCESS read-write
			STATUS current
			DESCRIPTION 
				"This object indicates the log backup level. The default value is 7."
			::= { hwApSystemProfileEntry 22 }

		 --1.3.6.1.4.1.2011.6.139.11.1.12.1.23
		hwApProfLogServerIp OBJECT-TYPE
			SYNTAX IpAddress
			MAX-ACCESS read-write
			STATUS current
			DESCRIPTION 
				"This object indicates the IP address of the log server."
			::= { hwApSystemProfileEntry 23 }

		 --1.3.6.1.4.1.2011.6.139.11.1.12.1.24
		hwApProfLogServerIpv6 OBJECT-TYPE
			SYNTAX OCTET STRING
			MAX-ACCESS read-write
			STATUS current
			DESCRIPTION 
				"This object indicates the IPv6 address of the log server."
			::= { hwApSystemProfileEntry 24 }

		 --1.3.6.1.4.1.2011.6.139.11.1.12.1.25
		hwApProfAlarmRestrictionSwitch OBJECT-TYPE
			SYNTAX INTEGER
				{
				disable(1),
				enable(2)
				}
			MAX-ACCESS read-write
			STATUS current
			DESCRIPTION 
				"This object indicates the status of the alarm suppression switch. The default value is 2."
			::= { hwApSystemProfileEntry 25 }

		 --1.3.6.1.4.1.2011.6.139.11.1.12.1.26
		hwApProfAlarmRestrictionPeriod OBJECT-TYPE
			SYNTAX Unsigned32 (10..300)
			MAX-ACCESS read-write
			STATUS current
			DESCRIPTION 
				"This object indicates the alarm suppression period. The default value is 60 seconds."
			::= { hwApSystemProfileEntry 26 }

		 --1.3.6.1.4.1.2011.6.139.11.1.12.1.27
		hwApProfKeepServiceSwitch OBJECT-TYPE
			SYNTAX INTEGER
				{
				enable(1),
				disable(2),
				allowaccess(3),
				allowAccessAlsoNoauth(4)
				}
			MAX-ACCESS read-write
			STATUS current
			DESCRIPTION 
				"This object indicates whether to enable the offline service retaining function. The default value is 2."
			::= { hwApSystemProfileEntry 27 }

		 --1.3.6.1.4.1.2011.6.139.11.1.12.1.28
		hwApProfProtectPriority OBJECT-TYPE
			SYNTAX Unsigned32 (0..7|4294967295)
			MAX-ACCESS read-write
			STATUS current
			DESCRIPTION 
				"This object indicates the AC priority. A smaller value indicates a higher priority. The default value 0xFFFFFFFF indicates that no priority is configured."
			::= { hwApSystemProfileEntry 28 }

		 --1.3.6.1.4.1.2011.6.139.11.1.12.1.29
		hwApProfProtectACIp OBJECT-TYPE
			SYNTAX IpAddress
			MAX-ACCESS read-write
			STATUS current
			DESCRIPTION 
				"This object indicates the IP address of the standby AC."
			::= { hwApSystemProfileEntry 29 }

		 --1.3.6.1.4.1.2011.6.139.11.1.12.1.30
		hwApProfProtectACIpv6 OBJECT-TYPE
			SYNTAX OCTET STRING
			MAX-ACCESS read-write
			STATUS current
			DESCRIPTION 
				"This object indicates the IPv6 address of the standby AC."
			::= { hwApSystemProfileEntry 30 }

		 --1.3.6.1.4.1.2011.6.139.11.1.12.1.31
		hwApProfEapStartMode OBJECT-TYPE
			SYNTAX INTEGER
				{
				broadcast(1),
				multicast(2),
				unicast(3)
				}
			MAX-ACCESS read-write
			STATUS current
			DESCRIPTION 
				"This object indicates the EAP Start packet conversion mode. The default value is 2."
			::= { hwApSystemProfileEntry 31 }

		 --1.3.6.1.4.1.2011.6.139.11.1.12.1.32
		hwApProfEapStartTransform OBJECT-TYPE
			SYNTAX INTEGER
				{
				equalBssid(1) ,
				always(2)
				}
			MAX-ACCESS read-write
			STATUS current
			DESCRIPTION 
				"This object indicates the EAP Start packet conversion mode. The default value is 1."
			::= { hwApSystemProfileEntry 32 }

		 --1.3.6.1.4.1.2011.6.139.11.1.12.1.33
		hwApProfEapStartUnicastMac OBJECT-TYPE
			SYNTAX MacAddress
			MAX-ACCESS read-write
			STATUS current
			DESCRIPTION 
				"This object indicates that EAP Start packets are converted to those with specific MAC addresses."
			::= { hwApSystemProfileEntry 33 }

		 --1.3.6.1.4.1.2011.6.139.11.1.12.1.34
		hwApProfEapResponseMode OBJECT-TYPE
			SYNTAX INTEGER
				{
				broadcast(1),
				multicast(2) ,
				specific(3),
				learnling(4)
				
				}
			MAX-ACCESS read-write
			STATUS current
			DESCRIPTION 
				"This object indicates the EAP Response packet conversion mode. The default value is 4."
			::= { hwApSystemProfileEntry 34 }

		 --1.3.6.1.4.1.2011.6.139.11.1.12.1.35
		hwApProfEapResponseTransform OBJECT-TYPE
			SYNTAX INTEGER
				{
				equalBssid(1) ,
				always(2)
				}
			MAX-ACCESS read-write
			STATUS current
			DESCRIPTION 
				"This object indicates the EAP Response packet conversion mode. The default value is 1."
			::= { hwApSystemProfileEntry 35 }

		 --1.3.6.1.4.1.2011.6.139.11.1.12.1.36
		hwApProfEapResponseUnicastMac OBJECT-TYPE
			SYNTAX MacAddress
			MAX-ACCESS read-write
			STATUS current
			DESCRIPTION 
				"This object indicates that EAP Response packets are converted to those with specific MAC addresses."
			::= { hwApSystemProfileEntry 36 }

		 --1.3.6.1.4.1.2011.6.139.11.1.12.1.37
		hwApProfLldpRestartDelay OBJECT-TYPE
			SYNTAX Unsigned32 (1..10)
			MAX-ACCESS read-write
			STATUS current
			DESCRIPTION 
				"This object indicates the delay for re-enabling LLDP. The default value is 2. It is expressed in seconds."
			::= { hwApSystemProfileEntry 37 }

		 --1.3.6.1.4.1.2011.6.139.11.1.12.1.38
		hwApProfLldpAdminStatus OBJECT-TYPE
			SYNTAX INTEGER
				{
				txrx(1),
				rx(2),
				tx(3)
				}
			MAX-ACCESS read-write
			STATUS current
			DESCRIPTION 
				"This object indicates the operation mode of LLDP. The default value is 1."
			::= { hwApSystemProfileEntry 38 }

		 --1.3.6.1.4.1.2011.6.139.11.1.12.1.39
		hwApProfLldpRetransDelay OBJECT-TYPE
			SYNTAX Unsigned32 (1..8192)
			MAX-ACCESS read-write
			STATUS current
			DESCRIPTION 
				"This object indicates the message retransmitting delay. The default value is 2. It is expressed in seconds."
			::= { hwApSystemProfileEntry 39 }

		 --1.3.6.1.4.1.2011.6.139.11.1.12.1.40
		hwApProfLldpRetransHoldMultiplier OBJECT-TYPE
			SYNTAX Unsigned32 (2..10)
			MAX-ACCESS read-write
			STATUS current
			DESCRIPTION 
				"This object indicates the hold time multiplier of device information on neighbors (cardinal number is the interval time). The default value is 4."
			::= { hwApSystemProfileEntry 40 }

		 --1.3.6.1.4.1.2011.6.139.11.1.12.1.41
		hwApProfLldpInterval OBJECT-TYPE
			SYNTAX Unsigned32 (5..32768)
			MAX-ACCESS read-write
			STATUS current
			DESCRIPTION 
				"This object indicates the interval at which LLDP packets are sent. The default value is 30 seconds."
			::= { hwApSystemProfileEntry 41 }

		 --1.3.6.1.4.1.2011.6.139.11.1.12.1.42
		hwApProfLldpReportInterval OBJECT-TYPE
			SYNTAX Unsigned32 (5..3600)
			MAX-ACCESS read-write
			STATUS current
			DESCRIPTION 
				"This object indicates the interval at which LLDP packets are reported. The default value is 30 seconds."
			::= { hwApSystemProfileEntry 42 }

		 --1.3.6.1.4.1.2011.6.139.11.1.12.1.43
		hwApProfStaAccessMode OBJECT-TYPE
			SYNTAX INTEGER
				{
				unknown(-1) ,
				disable(1) ,
				blacklist(2) ,
				whitelist(3)
				}
			MAX-ACCESS read-write
			STATUS current
			DESCRIPTION 
				"This object indicates the access mode. The default value is 1."
			::= { hwApSystemProfileEntry 43 }

		 --1.3.6.1.4.1.2011.6.139.11.1.12.1.44
		hwApProfStaAccessModeProfile OBJECT-TYPE
			SYNTAX OCTET STRING (SIZE (0..35))
			MAX-ACCESS read-write
			STATUS current
			DESCRIPTION 
				"This object indicates blacklist and whitelist profiles."
			::= { hwApSystemProfileEntry 44 }

		 --1.3.6.1.4.1.2011.6.139.11.1.12.1.45
		hwApProfRowStatus OBJECT-TYPE
			SYNTAX RowStatus
			MAX-ACCESS read-write
			STATUS current
			DESCRIPTION 
				"This object indicates the row status of this table. ROWSTATUS_CREATEANDFLOW and ROWSTATUS_DESTROY are commonly used ?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwApSystemProfileEntry 45 }
			
		--1.3.6.1.4.1.2011.6.139.11.1.12.1.46
		hwApProfSFTPSwitch OBJECT-TYPE
			SYNTAX INTEGER
				{
				disable(1),
				enable(2)
				}
			MAX-ACCESS read-write
			STATUS current
			DESCRIPTION 
				"This object indicates whether to enable the SFTP. The default value is 2."
			::= { hwApSystemProfileEntry 46 }
			
		--1.3.6.1.4.1.2011.6.139.11.1.12.1.47
		hwApProfDynamicBlackListAgingTime OBJECT-TYPE
            SYNTAX Unsigned32 (180..3600)
			MAX-ACCESS read-write
			STATUS current
			DESCRIPTION 
				"This object indicates the aging time of the dynamic blacklist entries. The default value is 300."
			::= { hwApSystemProfileEntry 47 }

                --1.3.6.1.4.1.2011.6.139.11.1.12.1.48
		hwApProfAntennaOutputMode OBJECT-TYPE
			SYNTAX INTEGER
				{
				combine(1),
				split(2)
				}
			MAX-ACCESS read-write
			STATUS current
			DESCRIPTION 
				"Description."
			::= { hwApSystemProfileEntry 48 }
			
		-- 1.3.6.1.4.1.2011.6.139.11.1.12.1.49
		hwApProfMppActiveReselectionSwitch OBJECT-TYPE
			SYNTAX INTEGER
				{
				disable(1),
				enable(2)
				}
			MAX-ACCESS read-write
			STATUS current
			DESCRIPTION
				"This object indicates of mpp active reselection."
			::= { hwApSystemProfileEntry 49 }

		

		-- 1.3.6.1.4.1.2011.6.139.11.1.12.1.50
		hwApProfSpectrumServerIPAddress OBJECT-TYPE
			SYNTAX IpAddress
			MAX-ACCESS read-write
			STATUS current
			DESCRIPTION
				"This object indicates the IPv6 address of the spectrum analysis server. You choose an IPv4 or IPv6 address. By default, the IPv4 address 255.255.255.255 is used."
			::= { hwApSystemProfileEntry 50 }

		

		-- 1.3.6.1.4.1.2011.6.139.11.1.12.1.51
		hwApProfSpectrumServerIPv6Address OBJECT-TYPE
			SYNTAX OCTET STRING
			MAX-ACCESS read-write
			STATUS current
			DESCRIPTION
				"This object indicates the IPv6 address of the spectrum analysis server. You choose an IPv4 or IPv6 address. By default, it is not configured."
			::= { hwApSystemProfileEntry 51 }

		

		-- 1.3.6.1.4.1.2011.6.139.11.1.12.1.52
		hwApProfSpectrumServerPort OBJECT-TYPE
			SYNTAX Unsigned32 (0 | 1..65535)
			MAX-ACCESS read-write
			STATUS current
			DESCRIPTION
				"This object indicates the port of the spectrum analysis server. The default value is 0."
			::= { hwApSystemProfileEntry 52 }

		

		-- 1.3.6.1.4.1.2011.6.139.11.1.12.1.53
		hwApProfSpectrumViaACSwitch OBJECT-TYPE
			SYNTAX INTEGER
				{
				disable(1),
				enable(2)
				}
			MAX-ACCESS read-write
			STATUS current
			DESCRIPTION
				"This object indicates the status of the spectrum analysis function. The default value is 1."
			::= { hwApSystemProfileEntry 53 }

		

		-- 1.3.6.1.4.1.2011.6.139.11.1.12.1.54
		hwApProfSpectrumViaACPort OBJECT-TYPE
			SYNTAX Unsigned32 (0 | 5000..65535)
			MAX-ACCESS read-write
			STATUS current
			DESCRIPTION
				"This object indicates the port number used by the AP to report spectrum analysis data to the AC. The default value is 0."
			::= { hwApSystemProfileEntry 54 }

		

		-- 1.3.6.1.4.1.2011.6.139.11.1.12.1.55
		hwApProfSpectrumNonWifiDeviceAgingTime OBJECT-TYPE
			SYNTAX Unsigned32 (1..30)
			MAX-ACCESS read-write
			STATUS current
			DESCRIPTION
				"This object indicates the aging time of non-WLAN devices on the AC. The default value is 3 minutes."
			::= { hwApSystemProfileEntry 55 }

		
		-- 1.3.6.1.4.1.2011.6.139.11.1.12.1.56
		hwApProfPoeMaxPower OBJECT-TYPE
			SYNTAX Unsigned32 (15400..750000)
			MAX-ACCESS read-write
			STATUS current
			DESCRIPTION
				"This object indicates the maximum output power of the AP.The default value is 750000."
			::= { hwApSystemProfileEntry 56 }

		
		-- 1.3.6.1.4.1.2011.6.139.11.1.12.1.57
		hwApProfPoePowerReserved OBJECT-TYPE
			SYNTAX Unsigned32 (0..100 | 255)
			MAX-ACCESS read-write
			STATUS current
			DESCRIPTION
				"This object indicates the percentage of reserved PoE power to the available PoE power.The default value is 255."
			::= { hwApSystemProfileEntry 57 }

		
		-- 1.3.6.1.4.1.2011.6.139.11.1.12.1.58
		hwApProfPoePowerThreshold OBJECT-TYPE
			SYNTAX Unsigned32 (0..100 | 255)
			MAX-ACCESS read-write
			STATUS current
			DESCRIPTION
				"This object indicates the alarm threshold of PoE power consumption percentage.The default value is 255."
			::= { hwApSystemProfileEntry 58 }

		
		-- 1.3.6.1.4.1.2011.6.139.11.1.12.1.59
		hwApProfPoeAfInrushSwitch OBJECT-TYPE
			SYNTAX INTEGER
				{
				disable(1),
				enable(2)
				}
			MAX-ACCESS read-write
			STATUS current
			DESCRIPTION
				"This object indicates whether to enable the IEEE 802.3at-compliant device to provide power in accordance with IEEE 802.3af.The default value is 1."
			::= { hwApSystemProfileEntry 59 }

		
		-- 1.3.6.1.4.1.2011.6.139.11.1.12.1.60
		hwApProfPoeHighInrushSwitch OBJECT-TYPE
			SYNTAX INTEGER
				{
				disable(1),
				enable(2)
				}
			MAX-ACCESS read-write
			STATUS current
			DESCRIPTION
				"This object indicates whether to enable the device to allow high inrush current during power-on.The default value is 1."
			::= { hwApSystemProfileEntry 60 }
		 --1.3.6.1.4.1.2011.6.139.11.1.12.1.61
		hwApProfPrimaryLinkIPv4 OBJECT-TYPE
			SYNTAX IpAddress
			MAX-ACCESS read-write
			STATUS current
			DESCRIPTION
				"This object indicates the IP address of the primary AC."
			::= { hwApSystemProfileEntry 61 }

		 --1.3.6.1.4.1.2011.6.139.11.1.12.1.62
		hwApProfPrimaryLinkIPv6 OBJECT-TYPE
			SYNTAX OCTET STRING
			MAX-ACCESS read-write
			STATUS current
			DESCRIPTION
				"This object indicates the IPv6 address of the primary AC."
			::= { hwApSystemProfileEntry 62 }
		
		 --1.3.6.1.4.1.2011.6.139.11.1.12.1.63
		hwApProfBackupLinkIPv4 OBJECT-TYPE
			SYNTAX IpAddress
			MAX-ACCESS read-write
			STATUS current
			DESCRIPTION
				"This object indicates the IP address of the backup AC."
			::= { hwApSystemProfileEntry 63 }

		 --1.3.6.1.4.1.2011.6.139.11.1.12.1.64
		hwApProfBackupLinkIPv6 OBJECT-TYPE
			SYNTAX OCTET STRING
			MAX-ACCESS read-write
			STATUS current
			DESCRIPTION
				"This object indicates the IPv6 address of the backup AC."
			::= { hwApSystemProfileEntry 64 }
			
		 --1.3.6.1.4.1.2011.6.139.11.1.12.1.65
		hwApProfLedOffTimeRange OBJECT-TYPE
			SYNTAX OCTET STRING (SIZE (0..32))
			MAX-ACCESS read-write
			STATUS current
			DESCRIPTION
				"This object indicates whether to make a configured Led off time range effective."
			::= { hwApSystemProfileEntry 65 }
			
		-- 1.3.6.1.4.1.2011.6.139.11.1.12.1.66
		hwApProfUsbSwitch OBJECT-TYPE
			SYNTAX INTEGER
				{
				disable(1),
				enable(2)
				}
			MAX-ACCESS read-write
			STATUS current
			DESCRIPTION
				"This object indicates whether to enable the USB. The default value is 1."
			::= { hwApSystemProfileEntry 66 }
		 
		 --1.3.6.1.4.1.2011.6.139.11.1.12.1.67
		hwApProfBroadcastSuppressionArpEnable OBJECT-TYPE
			SYNTAX INTEGER
				{
				disable(1),
				enable(2)
				}
			MAX-ACCESS read-write
			STATUS current
			DESCRIPTION
				"This object indicates whether to enable the arp broadcast suppression.The default value is 2."
			::= { hwApSystemProfileEntry 67 }
		
		-- 1.3.6.1.4.1.2011.6.139.11.1.12.1.68
		hwApProfBroadcastSuppressionArpThreshold OBJECT-TYPE
			SYNTAX Unsigned32 (64..1024)
			MAX-ACCESS read-write
			STATUS current
			DESCRIPTION
				"This object indicates the threshold of arp broadcast suppression. The default value is 256."
			::= { hwApSystemProfileEntry 68 }
			
		hwApProfBroadcastSuppressionIgmpEnable OBJECT-TYPE
			SYNTAX INTEGER
				{
				disable(1),
				enable(2)
				}
			MAX-ACCESS read-write
			STATUS current
			DESCRIPTION
				"This object indicates whether to enable the igmp broadcast suppression.The default value is 2."
			::= { hwApSystemProfileEntry 69 }
		
		-- 1.3.6.1.4.1.2011.6.139.11.1.12.1.70
		hwApProfBroadcastSuppressionIgmpThreshold OBJECT-TYPE
			SYNTAX Unsigned32 (64..1024)
			MAX-ACCESS read-write
			STATUS current
			DESCRIPTION
				"This object indicates the threshold of igmp broadcast suppression. The default value is 256."
			::= { hwApSystemProfileEntry 70 }
			
		hwApProfBroadcastSuppressionNdEnable OBJECT-TYPE
			SYNTAX INTEGER
				{
				disable(1),
				enable(2)
				}
			MAX-ACCESS read-write
			STATUS current
			DESCRIPTION
				"This object indicates whether to enable the nd broadcast suppression.The default value is 2."
			::= { hwApSystemProfileEntry 71 }
		
		-- 1.3.6.1.4.1.2011.6.139.11.1.12.1.72
		hwApProfBroadcastSuppressionNdThreshold OBJECT-TYPE
			SYNTAX Unsigned32 (64..1024)
			MAX-ACCESS read-write
			STATUS current
			DESCRIPTION
				"This object indicates the threshold of nd broadcast suppression. The default value is 256."
			::= { hwApSystemProfileEntry 72 }
			
		hwApProfBroadcastSuppressionOtherEnable OBJECT-TYPE
			SYNTAX INTEGER
				{
				disable(1),
				enable(2)
				}
			MAX-ACCESS read-write
			STATUS current
			DESCRIPTION
				"This object indicates whether to enable the other broadcast suppression.The default value is 2."
			::= { hwApSystemProfileEntry 73 }
		
		-- 1.3.6.1.4.1.2011.6.139.11.1.12.1.74
		hwApProfBroadcastSuppressionOtherThreshold OBJECT-TYPE
			SYNTAX Unsigned32 (64..1024)
			MAX-ACCESS read-write
			STATUS current
			DESCRIPTION
				"This object indicates the threshold of other broadcast suppression. The default value is 256."
			::= { hwApSystemProfileEntry 74 }
			
		hwApProfBroadcastSuppressionAllEnable OBJECT-TYPE
			SYNTAX INTEGER
				{
				disable(1),
				enable(2)
				}
			MAX-ACCESS read-write
			STATUS current
			DESCRIPTION
				"This object indicates whether to enable all the broadcast suppression.The default value is 2."
			::= { hwApSystemProfileEntry 75 }
        
        -- 1.3.6.1.4.1.2011.6.139.11.1.12.1.76
		hwApProfCapwapDtlsDataSwitch OBJECT-TYPE
			SYNTAX INTEGER
				{
				disable(1),
				enable(2),
				notconfig(3)				
				}
			MAX-ACCESS read-write
			STATUS current
			DESCRIPTION
				"This object indicates the status of the DTLS function of data-link. The default value is 3."
			::= { hwApSystemProfileEntry 76 }

                -- 1.3.6.1.4.1.2011.6.139.11.1.12.1.77
		hwApProfTemporaryManagementPsk OBJECT-TYPE
                        SYNTAX OCTET STRING (SIZE (6|8..108))
			MAX-ACCESS read-write
			STATUS current
			DESCRIPTION
				"This object indicates the psk of the AP-based offline VAP."
			::= { hwApSystemProfileEntry 77 }

                                     -- 1.3.6.1.4.1.2011.6.139.11.1.12.1.78
		hwApProfProtectLinkSwitchMode OBJECT-TYPE
			SYNTAX INTEGER
				{
				priority(1),
				networkstabilization(2)				
				}
			MAX-ACCESS read-write
			STATUS current
			DESCRIPTION
				"This object indicates the mode of the ac protect link-switch. The default value is 1."
			::= { hwApSystemProfileEntry 78 } 

		-- 1.3.6.1.4.1.2011.6.139.11.1.12.1.79
		hwApProfProtectLinkSwitchEchoProbeTime OBJECT-TYPE
			SYNTAX Unsigned32 (6..100)
			MAX-ACCESS read-write
			STATUS current
			DESCRIPTION
				"This object indicates the time of echo probe. The default value is 20."
			::= { hwApSystemProfileEntry 79 }
 
		-- 1.3.6.1.4.1.2011.6.139.11.1.12.1.80
		hwApProfProtectLinkSwitchStartThreshold OBJECT-TYPE
			SYNTAX Unsigned32 (5..60)
			MAX-ACCESS read-write
			STATUS current
			DESCRIPTION
				"This object indicates the start threshold of packet-loss rate. The default value is 20."
			::= { hwApSystemProfileEntry 80 }
 
		-- 1.3.6.1.4.1.2011.6.139.11.1.12.1.81
		hwApProfProtectLinkSwitchGapThreshold OBJECT-TYPE
			SYNTAX Unsigned32 (5..60)
			MAX-ACCESS read-write
			STATUS current
			DESCRIPTION
				"This object indicates the gap threshold of packet-loss rate. The default value is 15."
			::= { hwApSystemProfileEntry 81 }
			
		-- 1.3.6.1.4.1.2011.6.139.11.1.12.1.82
		hwApProfCardConnectType OBJECT-TYPE
			SYNTAX INTEGER
				{
				serial(1),
				ethernet(2)
				}
			MAX-ACCESS read-write
			STATUS current
			DESCRIPTION
				"Description."
			::= { hwApSystemProfileEntry 82 }
			
		-- 1.3.6.1.4.1.2011.6.139.11.1.12.1.83
		hwApProfLldpReportEnable OBJECT-TYPE
			SYNTAX INTEGER
				{
				disable(1),
				enable(2)
				}
			MAX-ACCESS read-write
			STATUS current
			DESCRIPTION
				"This object indicates whether to enable the lldp report .The default value is 1."
			::= { hwApSystemProfileEntry 83 }

		-- 1.3.6.1.4.1.2011.6.139.11.1.12.1.84
		hwApProfDhcpv4Option12 OBJECT-TYPE
			SYNTAX INTEGER
				{
				apTypeApMac(1),
				apName(2),
				disable(3)
				}
			MAX-ACCESS read-write
			STATUS current
			DESCRIPTION
				"This object indicates the type of dhcpve option12 .The default value is 1."
			::= { hwApSystemProfileEntry 84 }
			
			-- 1.3.6.1.4.1.2011.6.139.11.1.12.1.85
		hwApProfBcSuppresionAutoDetectThreshold OBJECT-TYPE
			SYNTAX Unsigned32 (64..1024)
			MAX-ACCESS read-write
			STATUS current
			DESCRIPTION
				"This object indicates the value of broadcast value .The default value is 256."
			::= { hwApSystemProfileEntry 85 }
			  
		-- 1.3.6.1.4.1.2011.6.139.11.1.12.1.86
		hwApProfMcSuppresionAutoDetectThreshold OBJECT-TYPE
			SYNTAX Unsigned32 (64..1024)
			MAX-ACCESS read-write
			STATUS current
			DESCRIPTION
				"This object indicates the value of multicast value .The default value is 256."
			::= { hwApSystemProfileEntry 86 } 
			
		-- 1.3.6.1.4.1.2011.6.139.11.1.12.1.87
		hwApProfUcSuppresionAutoDetectThreshold OBJECT-TYPE
			SYNTAX Unsigned32 (64..1024)
			MAX-ACCESS read-write
			STATUS current
			DESCRIPTION
				"This object indicates the value of unicast value .The default value is 256."
			::= { hwApSystemProfileEntry 87 }   
 		
		-- 1.3.6.1.4.1.2011.6.139.11.1.12.1.88
		hwApProfConsoleBLEMode OBJECT-TYPE
			SYNTAX INTEGER
				{
				disable(1),
				dynamic(2),
				persistent(3)
				}
			MAX-ACCESS read-write
			STATUS current
			DESCRIPTION
				"This object indicates the type of ble console .The default value is 2."
			::= { hwApSystemProfileEntry 88 }
		-- 1.3.6.1.4.1.2011.6.139.11.1.12.1.89
		hwApProfDiskUsageThreshold OBJECT-TYPE
			SYNTAX Unsigned32 (6..100)
			MAX-ACCESS read-write
			STATUS current
			DESCRIPTION
				"This object indicates the AP disk usage rate alarm threshold. The default value is 95."
			::= { hwApSystemProfileEntry 89 }		
		
		-- 1.3.6.1.4.1.2011.6.139.11.1.12.1.90
		hwApProfLogServerPort OBJECT-TYPE
			SYNTAX Unsigned32 (0..65535)
			MAX-ACCESS read-write
			STATUS current
			DESCRIPTION
				"This object indicates syslog server port. The default value is 514."
			::= { hwApSystemProfileEntry 90 }
		
		-- 1.3.6.1.4.1.2011.6.139.11.1.12.1.91
		hwApProfStationConnectivityDetectSwitch OBJECT-TYPE
			SYNTAX INTEGER
				{
				disable(1),
				enable(2)
				}
			MAX-ACCESS read-write
			STATUS current
			DESCRIPTION
				"This object indicates whether to disable the Station Connectivity Detect. The default value is enable."
			::= { hwApSystemProfileEntry 91 }

		-- 1.3.6.1.4.1.2011.6.139.11.1.12.1.92
		hwApProfStaArpNDProxyBeforeAssoc OBJECT-TYPE
			SYNTAX INTEGER
				{
				no(1),
				yes(2)
				}
			MAX-ACCESS read-write
			STATUS current
			DESCRIPTION
				"This object indicates the mode of the station arp-nd-proxy before association .The default value is 1."
			::= { hwApSystemProfileEntry 92 }
		
		-- 1.3.6.1.4.1.2011.6.139.11.1.12.1.93
		hwApProfUcSuppressionAutoDetectSwitch OBJECT-TYPE
			SYNTAX INTEGER
				{
				disable(1),
				enable(2)
				}
			MAX-ACCESS read-write
			STATUS current
			DESCRIPTION
				"This object indicates the switch of the unicast-suppression auto detect .The default value is 2."
			::= { hwApSystemProfileEntry 93 }
		
		-- 1.3.6.1.4.1.2011.6.139.11.1.12.1.94
		hwApProfPkiCertFileType OBJECT-TYPE
			SYNTAX INTEGER
				{
				pem(1),
				pkcs12(2),
				invalid(255)
				}
			MAX-ACCESS read-write
			STATUS current
			DESCRIPTION
				"This object indicates the AP PKI certificate file type."
			::= { hwApSystemProfileEntry 94 }
		
		-- 1.3.6.1.4.1.2011.6.139.11.1.12.1.95
		hwApProfPkiCertFileName OBJECT-TYPE
			SYNTAX OCTET STRING (SIZE (0..63))
			MAX-ACCESS read-write
			STATUS current
			DESCRIPTION
				"This object indicates the AP PKI certificate filename."
			::= { hwApSystemProfileEntry 95 }	
	
		-- 1.3.6.1.4.1.2011.6.139.11.1.12.1.96
		hwApProfPkiCertFilePassword OBJECT-TYPE
			SYNTAX OCTET STRING (SIZE (6..68))
			MAX-ACCESS read-write
			STATUS current
			DESCRIPTION
				"This object indicates the AP PKI certificate file password."
			::= { hwApSystemProfileEntry 96 }	
			
		-- 1.3.6.1.4.1.2011.6.139.11.1.12.1.97
		hwApProfHighTempApEnvironmentThreshold OBJECT-TYPE
			SYNTAX Unsigned32 (4294967295 | 20..110)
			MAX-ACCESS read-write
			STATUS current
			DESCRIPTION
				"Description."
			::= { hwApSystemProfileEntry 97 }
		
		-- 1.3.6.1.4.1.2011.6.139.11.1.12.1.98
		hwApProfHighTempCpuThreshold OBJECT-TYPE
			SYNTAX Unsigned32 (4294967295 | 20..110)
			MAX-ACCESS read-write
			STATUS current
			DESCRIPTION
				"Description."
			::= { hwApSystemProfileEntry 98 }
		
		-- 1.3.6.1.4.1.2011.6.139.11.1.12.1.99
		hwApProfHighTempNpThreshold OBJECT-TYPE
			SYNTAX Unsigned32 (4294967295 | 20..110)
			MAX-ACCESS read-write
			STATUS current
			DESCRIPTION
				"Description."
			::= { hwApSystemProfileEntry 99 }
		
		-- 1.3.6.1.4.1.2011.6.139.11.1.12.1.100
		hwApProfLowTempApEnvironmentThreshold OBJECT-TYPE
			SYNTAX Integer32 (-70..10 | 65535)
			MAX-ACCESS read-write
			STATUS current
			DESCRIPTION
				"Description."
			::= { hwApSystemProfileEntry 100 }
		
		-- 1.3.6.1.4.1.2011.6.139.11.1.12.1.101
		hwApProfLowTempCpuThreshold OBJECT-TYPE
			SYNTAX Integer32 (-70..10 | 65535)
			MAX-ACCESS read-write
			STATUS current
			DESCRIPTION
				"Description."
			::= { hwApSystemProfileEntry 101 }
		
		-- 1.3.6.1.4.1.2011.6.139.11.1.12.1.102
		hwApProfLowTempNpThreshold OBJECT-TYPE
			SYNTAX Integer32 (-70..10)
			MAX-ACCESS read-write
			STATUS current
			DESCRIPTION
				"Description."
			::= { hwApSystemProfileEntry 102 }

		
		-- 1.3.6.1.4.1.2011.6.139.11.1.12.1.103
		hwApSystemProfileNPFastForwardingSwitch OBJECT-TYPE
			SYNTAX INTEGER
				{
				enable(1),
				disable(2)
				}
			MAX-ACCESS read-write
			STATUS current
			DESCRIPTION
				"This object indicates whether to enable the NP fast forwarding function. The default value is 1. "
			::= { hwApSystemProfileEntry 103 }

		-- 1.3.6.1.4.1.2011.6.139.11.1.12.1.104
		hwApSystemProfileNPCapwapReassemblySwitch OBJECT-TYPE
			SYNTAX INTEGER
				{
				enable(1),
				disable(2)
				}
			MAX-ACCESS read-write
			STATUS current
			DESCRIPTION
				"This object indicates whether to enable the NP capwap reassembly function. The default value is 1. "
			::= { hwApSystemProfileEntry 104 }
		
		-- 1.3.6.1.4.1.2011.6.139.11.1.13
		hwAPWiredPortProfileTable OBJECT-TYPE
			SYNTAX SEQUENCE OF HwAPWiredPortProfileEntry 
			MAX-ACCESS not-accessible
			STATUS current
			DESCRIPTION 
				"This table is used to create or delete an AP wired port link profile and modify or query attributes."
			::= { hwWlanConfigObjects 13 }

		--1.3.6.1.4.1.2011.6.139.11.1.13.1
		hwAPWiredPortProfileEntry OBJECT-TYPE
			SYNTAX HwAPWiredPortProfileEntry 
			MAX-ACCESS not-accessible
			STATUS current
			DESCRIPTION 
				"The index of this table is hwAPWiredPortProfileName."
			INDEX { hwAPWiredPortProfileName }
			::= { hwAPWiredPortProfileTable 1 }


		HwAPWiredPortProfileEntry ::=
			SEQUENCE {				
				hwAPWiredPortProfileName
					OCTET STRING,
				hwAPWiredPortPortLinkProfileName
					OCTET STRING,
				hwAPWiredPortProfilePortDesc
					OCTET STRING,
				hwAPWiredPortProfilePortEthTrunkID
					Unsigned32,
				hwAPWiredPortProfilePortSTPSwitch
					INTEGER,
				hwAPWiredPortProfilePortMode
					INTEGER,
				hwAPWiredPortProfilePortVlanPvid
					Unsigned32,
				hwAPWiredPortProfilePortVlanTagged
					OCTET STRING,
				hwAPWiredPortProfilePortVlanUntagged
					OCTET STRING,
				hwAPWiredPortProfileUserIsolate
					INTEGER,
				hwAPWiredPortProfileDhcpTrust
					INTEGER,
				hwAPWiredPortProfileNdTrust
					INTEGER,
				hwAPWiredPortProfileRowStatus
					RowStatus,
				hwAPWiredPortProfileLearnAddress
					INTEGER,
				hwAPWiredPortProfileIpBindCheck
					INTEGER,
				hwAPWiredPortProfileArpBindCheck
					INTEGER,
				hwAPWiredPortProfileSTPAutoShutdown
					INTEGER,
				hwAPWiredPortProfileSTPAutoShutdownRecoveryTime
					Unsigned32,
				hwAPWiredPortProfileTrafficOptimizeSuppressionBc
					Unsigned32,
				hwAPWiredPortProfileTrafficOptimizeSuppressionUc
					Unsigned32,
				hwAPWiredPortProfileTrafficOptimizeSuppressionMc
					Unsigned32,
				hwAPWiredPortProfileIGMPSnooping
					INTEGER,
				hwAPWiredPortProfileLearnIpv6Address
					INTEGER,
				hwAPWiredPortProfileMLDSnooping
					INTEGER,	
				hwAPWiredPortProfileTrafficOptimizeTcpAdjustMss
					Unsigned32,
				hwAPWiredPortProfilePortSec
					INTEGER,
				hwAPWiredPortProfilePortSecMACMaxNum
					Integer32,
				hwAPWiredPortProfilePortSecStickyMac
					INTEGER,
				hwAPWiredPortProfilePortSecProtectAction
					INTEGER,
				hwAPWiredPortProfilePortForwardMode
					INTEGER,
				hwAPWiredPortDot1xClientProfileName
					OCTET STRING
			 }

		 --1.3.6.1.4.1.2011.6.139.11.1.13.1.1
		hwAPWiredPortProfileName OBJECT-TYPE
			SYNTAX OCTET STRING (SIZE (1..35))
			MAX-ACCESS not-accessible
			STATUS current
			DESCRIPTION 
				"This object indicates the name of an AP wired port link profile."
			::= { hwAPWiredPortProfileEntry 1 }

		 --1.3.6.1.4.1.2011.6.139.11.1.13.1.2
		hwAPWiredPortPortLinkProfileName OBJECT-TYPE
			SYNTAX OCTET STRING (SIZE (1..35))
			MAX-ACCESS read-write
			STATUS current
			DESCRIPTION 
				"This object indicates the bound AP wired port link profile."
			::= { hwAPWiredPortProfileEntry 2 }

		 --1.3.6.1.4.1.2011.6.139.11.1.13.1.3
		hwAPWiredPortProfilePortDesc OBJECT-TYPE
			SYNTAX OCTET STRING (SIZE (0..242))
			MAX-ACCESS read-write
			STATUS current
			DESCRIPTION 
				"This object indicates the description of an interface."
			::= { hwAPWiredPortProfileEntry 3 }

		 --1.3.6.1.4.1.2011.6.139.11.1.13.1.4
		hwAPWiredPortProfilePortEthTrunkID OBJECT-TYPE
			SYNTAX Unsigned32 (0 | 255)
			MAX-ACCESS read-write
			STATUS current
			DESCRIPTION 
				"This object indicates the ID of a Trunk. 0 is valid and 0xFFFFFFFF is invalid. The default value is 0xFFFFFFFF."
			::= { hwAPWiredPortProfileEntry 4 }

		 --1.3.6.1.4.1.2011.6.139.11.1.13.1.5
		hwAPWiredPortProfilePortSTPSwitch OBJECT-TYPE
			SYNTAX INTEGER
				{
				disable(1),
				enable(2),
                auto(3)
				}
			MAX-ACCESS read-write
			STATUS current
			DESCRIPTION 
				"This object indicates whether to enable STP on wired ports. The default value is 3."
			::= { hwAPWiredPortProfileEntry 5 }

		 --1.3.6.1.4.1.2011.6.139.11.1.13.1.6
		hwAPWiredPortProfilePortMode OBJECT-TYPE
			SYNTAX INTEGER
				{
				root(1),
				endpoint(2),
				middle(3),
				null(256)
				}
			MAX-ACCESS read-write
			STATUS current
			DESCRIPTION 
				"This object indicates the mode of the wired port. the default value is 256."
			::= { hwAPWiredPortProfileEntry 6 }

		 --1.3.6.1.4.1.2011.6.139.11.1.13.1.7
		hwAPWiredPortProfilePortVlanPvid OBJECT-TYPE
			SYNTAX Unsigned32 (0..4094)
			MAX-ACCESS read-write
			STATUS current
			DESCRIPTION 
				"This object indicates the PVID of a port. The default value is 1."
			::= { hwAPWiredPortProfileEntry 7 }

		 --1.3.6.1.4.1.2011.6.139.11.1.13.1.8
		hwAPWiredPortProfilePortVlanTagged OBJECT-TYPE
			SYNTAX OCTET STRING (SIZE (0..1024))
			MAX-ACCESS read-write
			STATUS current
			DESCRIPTION 
				"This object indicates whether to tag ports with VLAN IDs. The default value is 0."
			::= { hwAPWiredPortProfileEntry 8 }

		 --1.3.6.1.4.1.2011.6.139.11.1.13.1.9
		hwAPWiredPortProfilePortVlanUntagged OBJECT-TYPE
			SYNTAX OCTET STRING (SIZE (0..1024))
			MAX-ACCESS read-write
			STATUS current
			DESCRIPTION 
				"This object indicates whether to untag VLAN IDS from ports. The default value is 1."
			::= { hwAPWiredPortProfileEntry 9 }

		 --1.3.6.1.4.1.2011.6.139.11.1.13.1.10
		hwAPWiredPortProfileUserIsolate OBJECT-TYPE
			SYNTAX INTEGER
				{
				disable(1) ,
				l3Isolate(2),
				l2Isolate(3)
				}
			MAX-ACCESS read-write
			STATUS current
			DESCRIPTION 
				"This object indicates the status of the user isolation function. The default value is 1."
			::= { hwAPWiredPortProfileEntry 10 }

		 --1.3.6.1.4.1.2011.6.139.11.1.13.1.11
		hwAPWiredPortProfileDhcpTrust OBJECT-TYPE
			SYNTAX INTEGER
				{
				disable(1) ,
				enable(2)
				}
			MAX-ACCESS read-write
			STATUS current
			DESCRIPTION 
				"This object indicates whether a port is configured as a DHCP trusted port. The default value is 1."
			::= { hwAPWiredPortProfileEntry 11 }

		 --1.3.6.1.4.1.2011.6.139.11.1.13.1.12
		hwAPWiredPortProfileNdTrust OBJECT-TYPE
			SYNTAX INTEGER
				{
				disable(1) ,
				enable(2)
				}
			MAX-ACCESS read-write
			STATUS current
			DESCRIPTION 
				"This object indicates whether a port is configured as a ND trusted port. The default value is 1."
			::= { hwAPWiredPortProfileEntry 12 }

		 --1.3.6.1.4.1.2011.6.139.11.1.13.1.13
		hwAPWiredPortProfileRowStatus OBJECT-TYPE
			SYNTAX RowStatus
			MAX-ACCESS read-create
			STATUS current
			DESCRIPTION 
				"This object indicates the row status of this table. ROWSTATUS_CREATEANDFLOW and ROWSTATUS_DESTROY are commonly used."
			::= { hwAPWiredPortProfileEntry 13 }

		-- 1.3.6.1.4.1.2011.6.139.11.1.13.1.14
		hwAPWiredPortProfileLearnAddress OBJECT-TYPE
			SYNTAX INTEGER
				{
				disable(1),
				enable(2)
				}
			MAX-ACCESS read-write
			STATUS current
			DESCRIPTION
				"This object indicates whether to enable ipv4 address learning.The default value is 1."
			::= { hwAPWiredPortProfileEntry 14 }

		-- 1.3.6.1.4.1.2011.6.139.11.1.13.1.15
		hwAPWiredPortProfileIpBindCheck OBJECT-TYPE
			SYNTAX INTEGER
				{
				disable(1),
				enable(2)
				}
			MAX-ACCESS read-write
			STATUS current
			DESCRIPTION
				"This object indicates whether to enable IP packet checking against the binding table.The default value is 1."
			::= { hwAPWiredPortProfileEntry 15 }

		-- 1.3.6.1.4.1.2011.6.139.11.1.13.1.16
		hwAPWiredPortProfileArpBindCheck OBJECT-TYPE
			SYNTAX INTEGER
				{
				disable(1),
				enable(2)
				}
			MAX-ACCESS read-write
			STATUS current
			DESCRIPTION
				"This object indicates whether to enable ARP packet checking against the binding table.The default value is 1."
			::= { hwAPWiredPortProfileEntry 16 }

		-- 1.3.6.1.4.1.2011.6.139.11.1.13.1.17
		hwAPWiredPortProfileSTPAutoShutdown  OBJECT-TYPE
			SYNTAX INTEGER
				{
				disable(1),
				enable(2)
				}
			MAX-ACCESS read-write
			STATUS current
			DESCRIPTION
				"This object indicates whether to enable STP-triggered port shutdown.The default value is 1."
			::= { hwAPWiredPortProfileEntry 17 }

		-- 1.3.6.1.4.1.2011.6.139.11.1.13.1.18
		hwAPWiredPortProfileSTPAutoShutdownRecoveryTime OBJECT-TYPE
			SYNTAX Unsigned32 (600..3600)
			MAX-ACCESS read-write
			STATUS current
			DESCRIPTION
				"This object indicates the automatic port recovery time after an STP-triggered shutdown.The default value is 600."
			::= { hwAPWiredPortProfileEntry 18 }

		-- 1.3.6.1.4.1.2011.6.139.11.1.13.1.19
		hwAPWiredPortProfileTrafficOptimizeSuppressionBc OBJECT-TYPE
			SYNTAX Unsigned32 (0..14881000)
			MAX-ACCESS read-write
			STATUS current
			DESCRIPTION
				"This object indicates the rate limit for broadcast storm suppression.The default value is 0xFFFFFFFF."
			::= { hwAPWiredPortProfileEntry 19 }

		-- 1.3.6.1.4.1.2011.6.139.11.1.13.1.20
		hwAPWiredPortProfileTrafficOptimizeSuppressionUc OBJECT-TYPE
			SYNTAX Unsigned32 (0..14881000)
			MAX-ACCESS read-write
			STATUS current
			DESCRIPTION
				"This object indicates the rate limit for unknown unicast storm suppression.The default value is 0xFFFFFFFF."
			::= { hwAPWiredPortProfileEntry 20 }

		-- 1.3.6.1.4.1.2011.6.139.11.1.13.1.21
		hwAPWiredPortProfileTrafficOptimizeSuppressionMc OBJECT-TYPE
			SYNTAX Unsigned32 (0..14881000)
			MAX-ACCESS read-write
			STATUS current
			DESCRIPTION
				"This object indicates the rate limit for multicast storm suppression.The default value is 0xFFFFFFFF."
			::= { hwAPWiredPortProfileEntry 21 }
			
		-- 1.3.6.1.4.1.2011.6.139.11.1.13.1.22
		hwAPWiredPortProfileIGMPSnooping OBJECT-TYPE
			SYNTAX INTEGER
				{
				disable(1),
				enable(2)
				}
			MAX-ACCESS read-write
			STATUS current
			DESCRIPTION
				"This object indicates whether to enable IGMP-snooping.The default value is 1."
			::= { hwAPWiredPortProfileEntry 22 }
			
		-- 1.3.6.1.4.1.2011.6.139.11.1.13.1.23
		hwAPWiredPortProfileLearnIpv6Address OBJECT-TYPE
			SYNTAX INTEGER
				{
				disable(1),
				enable(2)
				}
			MAX-ACCESS read-write
			STATUS current
			DESCRIPTION
				"This object indicates whether to enable ipv6 address learning.The default value is 1."
			::= { hwAPWiredPortProfileEntry 23 }
     
 		-- 1.3.6.1.4.1.2011.6.139.11.1.13.1.24
		hwAPWiredPortProfileMLDSnooping OBJECT-TYPE
			SYNTAX INTEGER
				{
				disable(1),
				enable(2)
				}
			MAX-ACCESS read-write
			STATUS current
			DESCRIPTION
				"This object indicates whether to enable MLD-snooping.The default value is 1."
			::= { hwAPWiredPortProfileEntry 24 }    
		
				
		-- 1.3.6.1.4.1.2011.6.139.11.1.13.1.25
		hwAPWiredPortProfileTrafficOptimizeTcpAdjustMss OBJECT-TYPE
			SYNTAX Unsigned32 (4294967295 | 128..2048)
			MAX-ACCESS read-write
			STATUS current
			DESCRIPTION
				"Description."
			::= { hwAPWiredPortProfileEntry 25 }

		
		-- 1.3.6.1.4.1.2011.6.139.11.1.13.1.26
		hwAPWiredPortProfilePortSec OBJECT-TYPE
			SYNTAX INTEGER
				{
				disable(1),
				enable(2)
				}
			MAX-ACCESS read-write
			STATUS current
			DESCRIPTION
				"This object indicates the status of the port security function. The default value is 1."
			::= { hwAPWiredPortProfileEntry 26 }

		
		-- 1.3.6.1.4.1.2011.6.139.11.1.13.1.27
		hwAPWiredPortProfilePortSecMACMaxNum OBJECT-TYPE
			SYNTAX Integer32 (1..64)
			MAX-ACCESS read-write
			STATUS current
			DESCRIPTION
				"This object indicates the max number of the port security mac. The default value is 1."
			::= { hwAPWiredPortProfileEntry 27 }

		
		-- 1.3.6.1.4.1.2011.6.139.11.1.13.1.28
		hwAPWiredPortProfilePortSecStickyMac OBJECT-TYPE
			SYNTAX INTEGER
				{
				disable(1),
				enable(2)
				}
			MAX-ACCESS read-write
			STATUS current
			DESCRIPTION
				"This object indicates the status of the port security sticky mac function. The default value is 1."
			::= { hwAPWiredPortProfileEntry 28 }

		
		-- 1.3.6.1.4.1.2011.6.139.11.1.13.1.29
		hwAPWiredPortProfilePortSecProtectAction OBJECT-TYPE
			SYNTAX INTEGER
				{
				restrict(1),
				protect(2)
				}
			MAX-ACCESS read-write
			STATUS current
			DESCRIPTION
				"This object indicates the protect action of the port security function. The default value is 1."
			::= { hwAPWiredPortProfileEntry 29 }
		-- 1.3.6.1.4.1.2011.6.139.11.1.13.1.30
		hwAPWiredPortProfilePortForwardMode OBJECT-TYPE
			SYNTAX INTEGER
				{
				directForward(1),
				tunnel(2)
				}
			MAX-ACCESS read-write
			STATUS current
			DESCRIPTION
				"This object indicates whether to config port forward mode.The default value is direct forward."
			::= { hwAPWiredPortProfileEntry 30 }		

		--1.3.6.1.4.1.2011.6.139.11.1.13.1.31
		hwAPWiredPortDot1xClientProfileName OBJECT-TYPE
			SYNTAX OCTET STRING (SIZE (0..31))
			MAX-ACCESS read-write
			STATUS current
			DESCRIPTION
				"This object indicates the bound dot1x client profile."
			::= { hwAPWiredPortProfileEntry 31 }
		


		--1.3.6.1.4.1.2011.6.139.11.1.14
		hwAPWiredPortProfileTrafficFilterTable OBJECT-TYPE
			SYNTAX SEQUENCE OF HwAPWiredPortProfileTrafficFilterEntry 
			MAX-ACCESS not-accessible
			STATUS current
			DESCRIPTION 
				"This table is used to configure ACL-based packet filtering in an AP wired port profile."
			::= { hwWlanConfigObjects 14 }

		--1.3.6.1.4.1.2011.6.139.11.1.14.1
		hwAPWiredPortProfileTrafficFilterEntry OBJECT-TYPE
			SYNTAX HwAPWiredPortProfileTrafficFilterEntry 
			MAX-ACCESS not-accessible
			STATUS current
			DESCRIPTION 
				"Indexes of this table are hwAPWiredPortProfileName."
			INDEX { hwAPWiredPortProfileName, hwAPWiredPortProfileTrafficFilterType,hwAPWiredPortProfileTrafficFilterDirection }
			::= { hwAPWiredPortProfileTrafficFilterTable 1 }


		HwAPWiredPortProfileTrafficFilterEntry ::=
			SEQUENCE {				
				hwAPWiredPortProfileTrafficFilterDirection
					INTEGER,
				hwAPWiredPortProfileTrafficFilterType
					INTEGER,
				hwAPWiredPortProfileTrafficFilterAclID
					Integer32,
				hwAPWiredPortProfileTrafficFilterRowStatus
				        RowStatus
			 }

		 --1.3.6.1.4.1.2011.6.139.11.1.14.1.1
		hwAPWiredPortProfileTrafficFilterDirection OBJECT-TYPE
			SYNTAX INTEGER
				{
				inbound(1),
				outbound(2)
				}
			MAX-ACCESS not-accessible
			STATUS current
			DESCRIPTION 
				"This object indicates the direction of the ACL-based packet filtering."
			::= { hwAPWiredPortProfileTrafficFilterEntry 1 }

		 --1.3.6.1.4.1.2011.6.139.11.1.14.1.2
		hwAPWiredPortProfileTrafficFilterType OBJECT-TYPE
			SYNTAX INTEGER
				{
				ipv4(1),
				ipv6(2),
				l2(3)
				}
			MAX-ACCESS not-accessible
			STATUS current
			DESCRIPTION 
				"This object indicates the type of the ACL-based packet filtering."
			::= { hwAPWiredPortProfileTrafficFilterEntry 2 }

		 --1.3.6.1.4.1.2011.6.139.11.1.14.1.3
		hwAPWiredPortProfileTrafficFilterAclID OBJECT-TYPE
			SYNTAX Integer32 (3000..3031|4000..4031)
			MAX-ACCESS read-write
			STATUS current
			DESCRIPTION 
				"This object indicates ACL rules for packet filtering."
			::= { hwAPWiredPortProfileTrafficFilterEntry 3 }
                
                 --1.3.6.1.4.1.2011.6.139.11.1.14.1.4
		hwAPWiredPortProfileTrafficFilterRowStatus OBJECT-TYPE
			SYNTAX RowStatus
			MAX-ACCESS read-create
			STATUS current
			DESCRIPTION 
				"This object indicates packet filtering rules configured on the wired interface."
			::= { hwAPWiredPortProfileTrafficFilterEntry 4 }
			
		--1.3.6.1.4.1.2011.6.139.11.1.15
		hwAPPortLinkProfileTable OBJECT-TYPE
			SYNTAX SEQUENCE OF HwAPPortLinkProfileEntry 
			MAX-ACCESS not-accessible
			STATUS current
			DESCRIPTION 
				"This table is used to create or delete an AP wired port link profile and configure parameters."
			::= { hwWlanConfigObjects 15 }

		--1.3.6.1.4.1.2011.6.139.11.1.15.1
		hwAPPortLinkProfileEntry OBJECT-TYPE
			SYNTAX HwAPPortLinkProfileEntry 
			MAX-ACCESS not-accessible
			STATUS current
			DESCRIPTION 
				"The index of this table is hwAPPortLinkProfileName."
			INDEX { hwAPPortLinkProfileName }
			::= { hwAPPortLinkProfileTable 1 }


		HwAPPortLinkProfileEntry ::=
			SEQUENCE {				
				hwAPPortLinkProfileName
					OCTET STRING,
				hwAPPortLinkProfileLldpEnable
					INTEGER,
				hwAPPortLinkProfileLldpTlvType
					Unsigned32,
				hwAPPortLinkProfileCrcAlarmEnable
					INTEGER,
				hwAPPortLinkProfileCrcAlarmThreshold
					Unsigned32,
				hwAPPortLinkProfileCrcAlarmResumeThreshold
					Unsigned32,
				hwAPPortLinkProfileRowStatus
					RowStatus,
				hwAPPortLinkProfilePoeSwitch
					INTEGER,
				hwAPPortLinkProfilePoePriority
					INTEGER,
				hwAPPortLinkProfilePoeForcePowerSwitch
					INTEGER,
				hwAPPortLinkProfilePoeLegacySwitch
					INTEGER,
				hwAPPortLinkProfilePoeOffTimeRange
					OCTET STRING,
				hwAPPortLinkProfileAdminStatus
					INTEGER,
				hwAPPortLinkProfileLldpdot3TlvType
					Unsigned32,
				hwAPPortLinkProfileLldpdot3PowerFormat
					INTEGER,
				hwAPPortLinkProfileLldpLegacyTlvType
					Unsigned32,
				hwAPPortLinkProfileLldpLegacyPowerCapability
					INTEGER,
				hwAPPortLinkProfileSpeed
					Unsigned32
			 }

		 --1.3.6.1.4.1.2011.6.139.11.1.15.1.1
		hwAPPortLinkProfileName OBJECT-TYPE
			SYNTAX OCTET STRING (SIZE (1..35))
			MAX-ACCESS not-accessible
			STATUS current
			DESCRIPTION 
				"This object indicates the name of an AP wired port link profile."
			::= { hwAPPortLinkProfileEntry 1 }

		 --1.3.6.1.4.1.2011.6.139.11.1.15.1.2
		hwAPPortLinkProfileLldpEnable OBJECT-TYPE
			SYNTAX INTEGER
				{
				disable(1),
				enable(2)
				}
			MAX-ACCESS read-write
			STATUS current
			DESCRIPTION 
				"This object indicates the status of the LLDP function. The default value is 2."
			::= { hwAPPortLinkProfileEntry 2 }

		 --1.3.6.1.4.1.2011.6.139.11.1.15.1.3
		hwAPPortLinkProfileLldpTlvType OBJECT-TYPE
			SYNTAX Unsigned32(0..31)
			MAX-ACCESS read-write
			STATUS current
			DESCRIPTION 
				"This object indicates the types of TLVs that can be advertised from an AP's wired port. The default value is all(31) ?	0: invalid ?	bit0: management-address ?	bit1: port-description ?	bit2: system-capability  ?	bit3: system-description ?	bit4: system-name."
			::= { hwAPPortLinkProfileEntry 3 }

		 --1.3.6.1.4.1.2011.6.139.11.1.15.1.4
		hwAPPortLinkProfileCrcAlarmEnable OBJECT-TYPE
			SYNTAX INTEGER
				{
				disable(1),
				enable(2)
				}
			MAX-ACCESS read-write
			STATUS current
			DESCRIPTION 
				"This object indicates the status of the CRC error alarm function. The default value is 1."
			::= { hwAPPortLinkProfileEntry 4 }

		 --1.3.6.1.4.1.2011.6.139.11.1.15.1.5
		hwAPPortLinkProfileCrcAlarmThreshold OBJECT-TYPE
			SYNTAX Unsigned32 (1..100)
			MAX-ACCESS read-write
			STATUS current
			DESCRIPTION 
				"This object indicates a CRC error alarm threshold. The default value is 50. The unit is 1/10000."
			::= { hwAPPortLinkProfileEntry 5 }

		 --1.3.6.1.4.1.2011.6.139.11.1.15.1.6
		hwAPPortLinkProfileCrcAlarmResumeThreshold OBJECT-TYPE
			SYNTAX Unsigned32 (1..100)
			MAX-ACCESS read-write
			STATUS current
			DESCRIPTION 
				"This object indicates a CRC error alarm clearing threshold. The default value is 20. The unit is 1/10000."
			::= { hwAPPortLinkProfileEntry 6 }

		 --1.3.6.1.4.1.2011.6.139.11.1.15.1.7
		hwAPPortLinkProfileRowStatus OBJECT-TYPE
			SYNTAX RowStatus
			MAX-ACCESS read-create
			STATUS current
			DESCRIPTION 
				"This object indicates the row status of this table. ROWSTATUS_CREATEANDFLOW and ROWSTATUS_DESTROY are commonly used ?	ROWSTATUS_UNDEFINED: undefined ?	ROWSTATUS_ACTIVE: active ?	ROWSTATUS_NOTINSERVICE:notInService ?	ROWSTATUS_NOTREADY: notReady ?	ROWSTATUS_CREATEANDFLOW: createAndGo ?	ROWSTATUS_CREATEANDWAIT: createAndWait ?	ROWSTATUS_DESTROY: destroy."
			::= { hwAPPortLinkProfileEntry 7 }


 		 -- 1.3.6.1.4.1.2011.6.139.11.1.15.1.8
		hwAPPortLinkProfilePoeSwitch OBJECT-TYPE
			SYNTAX INTEGER
				{
				disable(1),
				enable(2)
				}
			MAX-ACCESS read-write
			STATUS current
			DESCRIPTION
				"This object indicates whether to enable the PoE function on the interface.The default value is 2."
			::= { hwAPPortLinkProfileEntry 8 }

		
		 -- 1.3.6.1.4.1.2011.6.139.11.1.15.1.9
		hwAPPortLinkProfilePoePriority OBJECT-TYPE
			SYNTAX INTEGER
				{
				critical(1),
				high(2),
				low(3)     
				}
			MAX-ACCESS read-write
			STATUS current
			DESCRIPTION
				"This object indicates the power priority of PoE interfaces.The default value is 3."
			::= { hwAPPortLinkProfileEntry 9 }

		
		 -- 1.3.6.1.4.1.2011.6.139.11.1.15.1.10
		hwAPPortLinkProfilePoeForcePowerSwitch OBJECT-TYPE
			SYNTAX INTEGER
				{
				disable(1),
				enable(2)
				}
			MAX-ACCESS read-write
			STATUS current
			DESCRIPTION
				"This object indicates whether to enable forcible PoE power supply on an interface.The default value is 1."
			::= { hwAPPortLinkProfileEntry 10 }

		
		 -- 1.3.6.1.4.1.2011.6.139.11.1.15.1.11
		hwAPPortLinkProfilePoeLegacySwitch OBJECT-TYPE
			SYNTAX INTEGER
				{
				disable(1),
				enable(2)
				}
			MAX-ACCESS read-write
			STATUS current
			DESCRIPTION
				"This object indicates whether to enable the PSE to check compatibility of the connected PDs.The default value is 1."
			::= { hwAPPortLinkProfileEntry 11 }

		
		 -- 1.3.6.1.4.1.2011.6.139.11.1.15.1.12
		hwAPPortLinkProfilePoeOffTimeRange OBJECT-TYPE
			SYNTAX OCTET STRING (SIZE (0..32))
			MAX-ACCESS read-write
			STATUS current
			DESCRIPTION
				"This object indicates whether to make a configured PoE power-off time range effective on interfaces."
			::= { hwAPPortLinkProfileEntry 12 }

			
		-- 1.3.6.1.4.1.2011.6.139.11.1.15.1.13
		hwAPPortLinkProfileAdminStatus OBJECT-TYPE
			SYNTAX INTEGER
				{
				down(1),
				up(2)
				}
			MAX-ACCESS read-write
			STATUS current
			DESCRIPTION
				"This object indicates whether to enable port shutdown.The default value is 2."
			::= { hwAPPortLinkProfileEntry 13 }
		
		-- 1.3.6.1.4.1.2011.6.139.11.1.15.1.14
		hwAPPortLinkProfileLldpdot3TlvType OBJECT-TYPE
			SYNTAX Unsigned32 (0..31)
			MAX-ACCESS read-write
			STATUS current
			DESCRIPTION
				"Description."
			DEFVAL { 1 }
			::= { hwAPPortLinkProfileEntry 14 }
		
		-- 1.3.6.1.4.1.2011.6.139.11.1.15.1.15
		hwAPPortLinkProfileLldpdot3PowerFormat OBJECT-TYPE
			SYNTAX INTEGER
				{
				default(1),
				ab(2),
				at(3),
				bt(4)
				}
			MAX-ACCESS read-write
			STATUS current
			DESCRIPTION
				"Description."
			DEFVAL { default }
			::= { hwAPPortLinkProfileEntry 15 }
		
		-- 1.3.6.1.4.1.2011.6.139.11.1.15.1.16
		hwAPPortLinkProfileLldpLegacyTlvType OBJECT-TYPE
			SYNTAX Unsigned32 (0..31)
			MAX-ACCESS read-write
			STATUS current
			DESCRIPTION
				"Description."
			DEFVAL { 1 }
			::= { hwAPPortLinkProfileEntry 16 }
		-- 1.3.6.1.4.1.2011.6.139.11.1.15.1.17
		hwAPPortLinkProfileLldpLegacyPowerCapability OBJECT-TYPE
			SYNTAX INTEGER
				{
				enable(1),
				disable(2)
				}
			MAX-ACCESS read-write
			STATUS current
			DESCRIPTION
				"This object indicates whether to enable the Power Capability.The default value is 1."
			::= { hwAPPortLinkProfileEntry 17 }
		
		-- 1.3.6.1.4.1.2011.6.139.11.1.15.1.18
		hwAPPortLinkProfileSpeed OBJECT-TYPE
			SYNTAX Unsigned32 (100 | 1000 | 2500 | 5000 | 65535)
			MAX-ACCESS read-write
			STATUS current
			DESCRIPTION
				"Configure the speed of AP interface."
			::= { hwAPPortLinkProfileEntry 18 }
			
		-- 1.3.6.1.4.1.2011.6.139.11.1.16
		hw2gRadioProfileTable OBJECT-TYPE
			SYNTAX SEQUENCE OF Hw2gRadioProfileEntry 
			MAX-ACCESS not-accessible
			STATUS current
			DESCRIPTION 
				"This table is used to configure 2.4 GHz radio parameters, including physical radio parameters such as channel, power, antenna gain, and working mode, and bind air scan and RRM profiles."
			::= { hwWlanConfigObjects 16 }

		--1.3.6.1.4.1.2011.6.139.11.1.16.1
		hw2gRadioProfileEntry OBJECT-TYPE
			SYNTAX Hw2gRadioProfileEntry 
			MAX-ACCESS not-accessible
			STATUS current
			DESCRIPTION 
				"The index of this table is hw2gRadioProfileName."
			INDEX { hw2gRadioProfileName }
			::= { hw2gRadioProfileTable 1 }


		Hw2gRadioProfileEntry ::=
			SEQUENCE {				
				hw2gRadioProfileName
					OCTET STRING,
				hw2gRadioBeaconInterval
					Unsigned32,
				hw2gRadioGuardIntervalMode
					INTEGER,
				hw2gRadioShortPreamble
					INTEGER,
				hw2gRadioFragmentationThreshold
					Integer32,
				hw2gRadioHtAmpduSwitch
					INTEGER,
				hw2gRadioHtAmpduMaxLengthExponent
					Integer32,
				hw2gRadioDot11bgBasicRate
					Unsigned32,
				hw2gRadioDot11bgSupportRate
					Unsigned32,
				hw2gRadioMulticastRate
					Unsigned32,
				hw2gRadioWmmMandatorySwitch
					INTEGER,
				hw2gRadioApEDCAVoiceECWmax
					Unsigned32,
				hw2gRadioApEDCAVoiceECWmin
					Unsigned32,
				hw2gRadioApEDCAVoiceAIFSN
					Unsigned32,
				hw2gRadioApEDCAVoiceTXOPLimit
					Unsigned32,
				hw2gRadioApEDCAVoiceAckPolicy
					INTEGER,
				hw2gRadioApEDCAVideoECWmax
					Unsigned32,
				hw2gRadioApEDCAVideoECWmin
					Unsigned32,
				hw2gRadioApEDCAVideoAIFSN
					Unsigned32,
				hw2gRadioApEDCAVideoTXOPLimit
					Unsigned32,
				hw2gRadioApEDCAVideoAckPolicy
					INTEGER,
				hw2gRadioApEDCABEECWmax
					Unsigned32,
				hw2gRadioApEDCABEECWmin
					Unsigned32,
				hw2gRadioApEDCABEAIFSN
					Unsigned32,
				hw2gRadioApEDCABETXOPLimit
					Unsigned32,
				hw2gRadioApEDCABEAckPolicy
					INTEGER,
				hw2gRadioApEDCABKECWmax
					Unsigned32,
				hw2gRadioApEDCABKECWmin
					Unsigned32,
				hw2gRadioApEDCABKAIFSN
					Unsigned32,
				hw2gRadioApEDCABKTXOPLimit
					Unsigned32,
				hw2gRadioApEDCABKAckPolicy
					INTEGER,
				hw2gRadioWmmSwitch
					INTEGER,
				hw2gRadioRtsCtsThreshold
					Unsigned32,
				hw2gRadioRtsCtsMode
					INTEGER,
				hw2gRadioPowerAutoAdjustSwitch
					INTEGER,
				hw2gRadioBeamformingSwitch
					INTEGER,
				hw2gRadioWifiLight
					INTEGER,
				hw2gRadioChannelSwitchAnnouncementSwitch
					INTEGER,
				hw2gRadioChannelSwitchMode
					INTEGER,
				hw2gRadioAutoOffServiceSwitch
					INTEGER,
				hw2gRadioAutoOffServiceStartTime
					OCTET STRING,
				hw2gRadioAutoOffServiceEndTime
					OCTET STRING,
				hw2gRadioInterferenceDetectSwitch
					INTEGER,
				hw2gRadioInterferenceIntraFrequencyThreshold
					Unsigned32,
				hw2gRadioInterferenceAdjacentFrequencyThreshold
					Unsigned32,
				hw2gRadioInterferenceStationThreshold
					Unsigned32,
				hw2gRadioRrmProfile
					OCTET STRING,
				hw2gRadioAirScanProfile
					OCTET STRING,
				hw2gRadioProfileRowStatus
					RowStatus,
				hw2gRadioProfileUtmostPowerSwitch
					INTEGER,
				hw2gRadioProfileRadioType
					INTEGER,
				hw2gRadioProfileSmartAntennaEnable
					INTEGER,
				hw2gRadioProfileTxChainNum
					Unsigned32,
				hw2gRadioProfileRxChainNum
					Unsigned32,
				hw2gRadioProfileAutoOffTimeRange
					OCTET STRING,
				hw2gRadioAgileAntennaPolarSwitch
					INTEGER,
				hw2gRadioProfileCCAThreshold
					Integer32,
				hw2gRadioProfileSmartAntennaLowPerThreshold
					Unsigned32,
				hw2gRadioProfileSmartAntennaHighPerThreshold
					Unsigned32,
				hw2gRadioProfileSmartAntennaTrainingInterval
					Unsigned32,
				hw2gRadioProfileSmartAntennaTrainingMPDUNum
					Unsigned32,
				hw2gRadioProfileSmartAntThruputTrainThreshold
					Unsigned32,
			        hw2gRadioDot11axGuardIntervalMode
					INTEGER,		
				hw2gRadioHighwayBssid
					MacAddress,
				hw2gRadioAutonavigationBeaconInterval
					Unsigned32,
				hwRadio2GProfileAmsduSwitch
					INTEGER,
				hw2gRadioVipUserBandwidthReservationRatio
					Unsigned32,
				hw2GRadioRu26ToleranceSwitch
				    INTEGER
			 }

		 --1.3.6.1.4.1.2011.6.139.11.1.16.1.1
		hw2gRadioProfileName OBJECT-TYPE
			SYNTAX OCTET STRING (SIZE (1..35))
			MAX-ACCESS not-accessible
			STATUS current
			DESCRIPTION 
				"This object indicates the name of a 2G radio profile. It is the index of the table."
			::= { hw2gRadioProfileEntry 1 }

		
		-- 1.3.6.1.4.1.2011.6.139.11.1.16.1.6
		hw2gRadioBeaconInterval OBJECT-TYPE
			SYNTAX Unsigned32 (60..1000)
			MAX-ACCESS read-write
			STATUS current
			DESCRIPTION
				"This object indicates a Beacon interval. The default value is 100. It is expressed in ms."
			::= { hw2gRadioProfileEntry 6 }

		
		-- 1.3.6.1.4.1.2011.6.139.11.1.16.1.10
		hw2gRadioGuardIntervalMode OBJECT-TYPE
			SYNTAX INTEGER
				{
				short(1),
				normal(2)
				}
			MAX-ACCESS read-write
			STATUS current
			DESCRIPTION 
				"This object indicates the GI mode. The default value is 1."
			::= { hw2gRadioProfileEntry 10 }

		 --1.3.6.1.4.1.2011.6.139.11.1.16.1.11
		hw2gRadioShortPreamble OBJECT-TYPE
			SYNTAX INTEGER
				{
				disable(1),
				enable(2)
				}
			MAX-ACCESS read-write
			STATUS current
			DESCRIPTION 
				"This object indicates the preamble mode. The default value is 2."
			::= { hw2gRadioProfileEntry 11 }

		 --1.3.6.1.4.1.2011.6.139.11.1.16.1.12
		hw2gRadioFragmentationThreshold OBJECT-TYPE
			SYNTAX Integer32 (256..2346)
			MAX-ACCESS read-write
			STATUS current
			DESCRIPTION 
				"This object indicates the packet fragmentation threshold. The default value is 2346. It is expressed in bytes."
			::= { hw2gRadioProfileEntry 12 }

		 --1.3.6.1.4.1.2011.6.139.11.1.16.1.13
		hw2gRadioHtAmpduSwitch OBJECT-TYPE
			SYNTAX INTEGER
				{
				disable(1) ,
				enable(2)
				}
			MAX-ACCESS read-write
			STATUS current
			DESCRIPTION 
				"This object indicates the status of the aggregation function. The default value is 2."
			::= { hw2gRadioProfileEntry 13 }

		 --1.3.6.1.4.1.2011.6.139.11.1.16.1.14
		hw2gRadioHtAmpduMaxLengthExponent OBJECT-TYPE
			SYNTAX Integer32 (0..3)
			MAX-ACCESS read-write
			STATUS current
			DESCRIPTION 
				"This object indicates the maximum length of frames converged by an MPDU. The default value is 3 ?	0: 8191 bytes ?	1: 16383 bytes ?	2: 32767 bytes ?	3: 65535 bytes."
			::= { hw2gRadioProfileEntry 14 }

		 --1.3.6.1.4.1.2011.6.139.11.1.16.1.15
		hw2gRadioDot11bgBasicRate OBJECT-TYPE
			SYNTAX Unsigned32 (1..4095)
			MAX-ACCESS read-write
			STATUS current
			DESCRIPTION 
				"This object indicates the basic rate set of the 802.11bg protocol. The default value is 3 ?	bit0: 1 Mbit/s ?	bit1: 2 Mbit/s ?	bit2: 5.5 Mbit/s ?	bit3: 6 Mbit/s ?	bit4: 9 Mbit/s ?	bit5: 11 Mbit/s ?	bit6: 12 Mbit/s ?	bit7: 18 Mbit/s ?	bit8: 24 Mbit/s ?	bit9: 36 Mbit/s ?	bit10: 48 Mbit/s ?	bit11: 54 Mbit/s."
			::= { hw2gRadioProfileEntry 15 }

		 --1.3.6.1.4.1.2011.6.139.11.1.16.1.16
		hw2gRadioDot11bgSupportRate OBJECT-TYPE
			SYNTAX Unsigned32 (1..4095)
			MAX-ACCESS read-write
			STATUS current
			DESCRIPTION 
				"This object indicates the supported rate set of the 802.11bg protocol. The default value is 0xFFF ?	bit0: 1 Mbit/s?	bit1: 2 Mbit/s?	bit2: 5.5 Mbit/s?	bit3: 6 Mbit/s?	bit4: 9 Mbit/s?	bit5: 11 Mbit/s?	bit6: 12 Mbit/s ?	bit7: 18 Mbit/s?	bit8: 24 Mbit/s?	bit9: 36 Mbit/s?	bit10: 48 Mbit/s?	bit11: 54 Mbit/s."
			::= { hw2gRadioProfileEntry 16 }

		 --1.3.6.1.4.1.2011.6.139.11.1.16.1.17
		hw2gRadioMulticastRate OBJECT-TYPE
			SYNTAX Unsigned32
			MAX-ACCESS read-write
			STATUS current
			DESCRIPTION 
				"This object indicates the multicast rate. The default value is 0x2F ?	bit0: 1 Mbit/s ?	bit1: 2 Mbit/s ?	bit2: 5.5 Mbit/s ?	bit3: 6 Mbit/s ?	bit4: 9 Mbit/s ?	bit5: 11 Mbit/s ?	bit6: 12 Mbit/s ?	bit7: 18 Mbit/s ?	bit8: 24 Mbit/s ?	bit9: 36 Mbit/s ?	bit10: 48 Mbit/s ?	bit11: 54 Mbit/s."
			::= { hw2gRadioProfileEntry 17 }

		 --1.3.6.1.4.1.2011.6.139.11.1.16.1.18
		hw2gRadioWmmMandatorySwitch OBJECT-TYPE
			SYNTAX INTEGER
				{
				disable(1) ,
				enable(2)
				}
			MAX-ACCESS read-write
			STATUS current
			DESCRIPTION 
				"This object indicates the status of the mandatory WMM matching function. The default value is 1."
			::= { hw2gRadioProfileEntry 18 }

		 --1.3.6.1.4.1.2011.6.139.11.1.16.1.19
		hw2gRadioApEDCAVoiceECWmax OBJECT-TYPE
			SYNTAX Unsigned32 (0..15)
			MAX-ACCESS read-write
			STATUS current
			DESCRIPTION 
				"This object indicates the EDCA parameter ECWmax, namely, exponent form of Cwmax, for voice services on APs. ECWmin and ECWmax determine the average backoff time (ECWmax > ECWmin). The default value is 3."
			::= { hw2gRadioProfileEntry 19 }

		 --1.3.6.1.4.1.2011.6.139.11.1.16.1.20
		hw2gRadioApEDCAVoiceECWmin OBJECT-TYPE
			SYNTAX Unsigned32 (0..15)
			MAX-ACCESS read-write
			STATUS current
			DESCRIPTION 
				"This object indicates the EDCA parameter ECWmin, namely, exponent form of Cwmin, for voice services on APs. ECWmin and ECWmax determine the average backoff time (ECWmax > ECWmin). The default value is 2."
			::= { hw2gRadioProfileEntry 20 }

		 --1.3.6.1.4.1.2011.6.139.11.1.16.1.21
		hw2gRadioApEDCAVoiceAIFSN OBJECT-TYPE
			SYNTAX Unsigned32 (1..15)
			MAX-ACCESS read-write
			STATUS current
			DESCRIPTION 
				"This object indicates the EDCA parameter AIFSN, namely, arbitration interframe spacing number, for voice services on APs. The default value is 1."
			::= { hw2gRadioProfileEntry 21 }

		 --1.3.6.1.4.1.2011.6.139.11.1.16.1.22
		hw2gRadioApEDCAVoiceTXOPLimit OBJECT-TYPE
			SYNTAX Unsigned32 (0..255)
			MAX-ACCESS read-write
			STATUS current
			DESCRIPTION 
				"This object indicates the EDCA parameter TXOPLimit, namely, transmission opportunity limit, for voice services on APs. The default value is 47. The unit is 32 us."
			::= { hw2gRadioProfileEntry 22 }

		 --1.3.6.1.4.1.2011.6.139.11.1.16.1.23
		hw2gRadioApEDCAVoiceAckPolicy OBJECT-TYPE
			SYNTAX INTEGER
				{
				normal(1),
				noAck(2)
				}
			MAX-ACCESS read-write
			STATUS current
			DESCRIPTION 
				"This object indicates the EDCA parameter AckPolicy for voice services on APs. The default value is 1."
			::= { hw2gRadioProfileEntry 23 }

		 --1.3.6.1.4.1.2011.6.139.11.1.16.1.24
		hw2gRadioApEDCAVideoECWmax OBJECT-TYPE
			SYNTAX Unsigned32 (0..15)
			MAX-ACCESS read-write
			STATUS current
			DESCRIPTION 
				"This object indicates the EDCA parameter ECWmax, namely, exponent form of Cwmax, for video services on APs. ECWmin and ECWmax determine the average backoff time (ECWmax > ECWmin). The default value is 4."
			::= { hw2gRadioProfileEntry 24 }

		 --1.3.6.1.4.1.2011.6.139.11.1.16.1.25
		hw2gRadioApEDCAVideoECWmin OBJECT-TYPE
			SYNTAX Unsigned32 (0..15)
			MAX-ACCESS read-write
			STATUS current
			DESCRIPTION 
				"This object indicates the EDCA parameter ECWmin, namely, exponent form of Cwmin, for video services on APs. ECWmin and ECWmax determine the average backoff time (ECWmax > ECWmin). The default value is 3."
			::= { hw2gRadioProfileEntry 25 }

		 --1.3.6.1.4.1.2011.6.139.11.1.16.1.26
		hw2gRadioApEDCAVideoAIFSN OBJECT-TYPE
			SYNTAX Unsigned32 (1..15)
			MAX-ACCESS read-write
			STATUS current
			DESCRIPTION 
				"This object indicates the EDCA parameter AIFSN, namely, arbitration interframe spacing number, for video services on APs. The default value is 1."
			::= { hw2gRadioProfileEntry 26 }

		 --1.3.6.1.4.1.2011.6.139.11.1.16.1.27
		hw2gRadioApEDCAVideoTXOPLimit OBJECT-TYPE
			SYNTAX Unsigned32 (0..255)
			MAX-ACCESS read-write
			STATUS current
			DESCRIPTION 
				"This object indicates the EDCA parameter TXOPLimit, namely, transmission opportunity limit, for video services on APs. The default value is 94. The unit is 32 us."
			::= { hw2gRadioProfileEntry 27 }

		 --1.3.6.1.4.1.2011.6.139.11.1.16.1.28
		hw2gRadioApEDCAVideoAckPolicy OBJECT-TYPE
			SYNTAX INTEGER
				{
				normal(1),
				noAck(2)
				}
			MAX-ACCESS read-write
			STATUS current
			DESCRIPTION 
				"This object indicates the EDCA parameter AckPolicy for video services on APs. The default value is 1."
			::= { hw2gRadioProfileEntry 28 }

		 --1.3.6.1.4.1.2011.6.139.11.1.16.1.29
		hw2gRadioApEDCABEECWmax OBJECT-TYPE
			SYNTAX Unsigned32 (0..15)
			MAX-ACCESS read-write
			STATUS current
			DESCRIPTION 
				"This object indicates the EDCA parameter ECWmax, namely, exponent form of Cwmax, for BE services on APs. ECWmin and ECWmax determine the average backoff time (ECWmax > ECWmin). The default value is 6."
			::= { hw2gRadioProfileEntry 29 }

		 --1.3.6.1.4.1.2011.6.139.11.1.16.1.30
		hw2gRadioApEDCABEECWmin OBJECT-TYPE
			SYNTAX Unsigned32 (0..15)
			MAX-ACCESS read-write
			STATUS current
			DESCRIPTION 
				"This object indicates the EDCA parameter ECWmin, namely, exponent form of Cwmin, for BE services on APs. ECWmin and ECWmax determine the average backoff time (ECWmax > ECWmin). The default value is 4."
			::= { hw2gRadioProfileEntry 30 }

		 --1.3.6.1.4.1.2011.6.139.11.1.16.1.31
		hw2gRadioApEDCABEAIFSN OBJECT-TYPE
			SYNTAX Unsigned32 (1..15)
			MAX-ACCESS read-write
			STATUS current
			DESCRIPTION 
				"This object indicates the EDCA parameter AIFSN, namely, arbitration interframe spacing number, for BE services on APs. The default value is 3."
			::= { hw2gRadioProfileEntry 31 }

		 --1.3.6.1.4.1.2011.6.139.11.1.16.1.32
		hw2gRadioApEDCABETXOPLimit OBJECT-TYPE
			SYNTAX Unsigned32 (0..255)
			MAX-ACCESS read-write
			STATUS current
			DESCRIPTION 
				"This object indicates the EDCA parameter TXOPLimit for BE services on APs. It indicates the transmission opportunity limit. The default value is 0. The unit is 32 us."
			::= { hw2gRadioProfileEntry 32 }

		 --1.3.6.1.4.1.2011.6.139.11.1.16.1.33
		hw2gRadioApEDCABEAckPolicy OBJECT-TYPE
			SYNTAX INTEGER
				{
				normal(1),
				noAck(2)
				}
			MAX-ACCESS read-write
			STATUS current
			DESCRIPTION 
				"This object indicates the EDCA parameter AckPolicy for BE services on APs. The default value is 1."
			::= { hw2gRadioProfileEntry 33 }

		 --1.3.6.1.4.1.2011.6.139.11.1.16.1.34
		hw2gRadioApEDCABKECWmax OBJECT-TYPE
			SYNTAX Unsigned32 (0..15)
			MAX-ACCESS read-write
			STATUS current
			DESCRIPTION 
				"This object indicates the EDCA parameter ECWmax, namely, exponent form of Cwmax, for BK services on APs. ECWmin and ECWmax determine the average backoff time (ECWmax > ECWmin). The default value is 10."
			::= { hw2gRadioProfileEntry 34 }

		 --1.3.6.1.4.1.2011.6.139.11.1.16.1.35
		hw2gRadioApEDCABKECWmin OBJECT-TYPE
			SYNTAX Unsigned32 (0..15)
			MAX-ACCESS read-write
			STATUS current
			DESCRIPTION 
				"This object indicates the EDCA parameter ECWmin, namely, exponent form of Cwmin, for BK services on APs. ECWmin and ECWmax determine the average backoff time (ECWmax > ECWmin). The default value is 4."
			::= { hw2gRadioProfileEntry 35 }

		 --1.3.6.1.4.1.2011.6.139.11.1.16.1.36
		hw2gRadioApEDCABKAIFSN OBJECT-TYPE
			SYNTAX Unsigned32 (1..15)
			MAX-ACCESS read-write
			STATUS current
			DESCRIPTION 
				"This object indicates the EDCA parameter AIFSN, namely, arbitration interframe spacing number, for BK services on APs. The default value is 7."
			::= { hw2gRadioProfileEntry 36 }

		 --1.3.6.1.4.1.2011.6.139.11.1.16.1.37
		hw2gRadioApEDCABKTXOPLimit OBJECT-TYPE
			SYNTAX Unsigned32 (0..255)
			MAX-ACCESS read-write
			STATUS current
			DESCRIPTION 
				"This object indicates the EDCA parameter TXOPLimit, namely, transmission opportunity limit, for BK services on APs. The default value is 0. The unit is 32 us."
			::= { hw2gRadioProfileEntry 37 }

		 --1.3.6.1.4.1.2011.6.139.11.1.16.1.38
		hw2gRadioApEDCABKAckPolicy OBJECT-TYPE
			SYNTAX INTEGER
				{
				normal(1),
				noAck(2)
				}
			MAX-ACCESS read-write
			STATUS current
			DESCRIPTION 
				"This object indicates the EDCA parameter AckPolicy for BK services on APs. The default value is 1."
			::= { hw2gRadioProfileEntry 38 }

		 --1.3.6.1.4.1.2011.6.139.11.1.16.1.39
		hw2gRadioWmmSwitch OBJECT-TYPE
			SYNTAX INTEGER
				{
				disable(1) ,
				enable(2)
				}
			MAX-ACCESS read-write
			STATUS current
			DESCRIPTION 
				"This object indicates the status of the WMM function. The default value is 2."
			::= { hw2gRadioProfileEntry 39 }

		 --1.3.6.1.4.1.2011.6.139.11.1.16.1.40
		hw2gRadioRtsCtsThreshold OBJECT-TYPE
			SYNTAX Unsigned32 (64..2347)
			MAX-ACCESS read-write
			STATUS current
			DESCRIPTION
				"This object indicates the request To Send/Clear To Send (RTS/CTS) threshold. If the length of a frame to be sent by the MAC Layer exceeds this threshold, an RTS frame needs to be sent before this frame. The default value is 1400(from V2R8C10; The default value is 2347 before V2R8C10.). It is expressed in bytes."
			::= { hw2gRadioProfileEntry 40 }

		 --1.3.6.1.4.1.2011.6.139.11.1.16.1.41
		hw2gRadioRtsCtsMode OBJECT-TYPE
			SYNTAX INTEGER
				{
				disable(1) ,
				ctsToSelf(2)  ,
				rtsCts(3)
				}
			MAX-ACCESS read-write
			STATUS current
			DESCRIPTION
				"This object indicates the RTS-CTS mode set for the specified radio profile. The default value is 3(from V2R8C10; The default value is 2 before V2R8C10.)."
			::= { hw2gRadioProfileEntry 41 }

		 --1.3.6.1.4.1.2011.6.139.11.1.16.1.42
		hw2gRadioPowerAutoAdjustSwitch OBJECT-TYPE
			SYNTAX INTEGER
				{
				disable(1) ,
				enable(2)
				}
			MAX-ACCESS read-write
			STATUS current
			DESCRIPTION 
				"This object indicates the status of the user-by-user power control function. The default value is 1."
			::= { hw2gRadioProfileEntry 42 }

		 --1.3.6.1.4.1.2011.6.139.11.1.16.1.43
		hw2gRadioBeamformingSwitch OBJECT-TYPE
			SYNTAX INTEGER
				{
				disable(1) ,
				enable(2)
				}
			MAX-ACCESS read-write
			STATUS current
			DESCRIPTION 
				"This object indicates the status of the beamforming function. The default value is 1."
			::= { hw2gRadioProfileEntry 43 }

		 --1.3.6.1.4.1.2011.6.139.11.1.16.1.44
		hw2gRadioWifiLight OBJECT-TYPE
			SYNTAX INTEGER
				{
				signalStrength(1) ,
				traffic(2)
				}
			MAX-ACCESS read-write
			STATUS current
			DESCRIPTION 
				"This object indicates information reflected by the blinking frequency of the Wireless LED on an AP."
			::= { hw2gRadioProfileEntry 44 }

		 --1.3.6.1.4.1.2011.6.139.11.1.16.1.45
		hw2gRadioChannelSwitchAnnouncementSwitch OBJECT-TYPE
			SYNTAX INTEGER
				{
				disable(1) ,
				enable(2)
				}
			MAX-ACCESS read-write
			STATUS current
			DESCRIPTION 
				"This object indicates the status of the channel switchover announcement function. The default value is 1."
			::= { hw2gRadioProfileEntry 45 }

		 --1.3.6.1.4.1.2011.6.139.11.1.16.1.46
		hw2gRadioChannelSwitchMode OBJECT-TYPE
			SYNTAX INTEGER
				{
				continueTransmitting(1) ,
				stopTransmitting(2)
				}
			MAX-ACCESS read-write
			STATUS current
			DESCRIPTION 
				"This object indicates the channel switch announcement mode. The default value is 1."
			::= { hw2gRadioProfileEntry 46 }

		 --1.3.6.1.4.1.2011.6.139.11.1.16.1.47
		hw2gRadioAutoOffServiceSwitch OBJECT-TYPE
			SYNTAX INTEGER
				{
				disable(1) ,
				enable(2)
				}
			MAX-ACCESS read-write
			STATUS current
			DESCRIPTION 
				"This object indicates the status of the scheduled radio disabling function. The default value is 1."
			::= { hw2gRadioProfileEntry 47 }

		 --1.3.6.1.4.1.2011.6.139.11.1.16.1.48
		hw2gRadioAutoOffServiceStartTime OBJECT-TYPE
			SYNTAX OCTET STRING (SIZE (1..11))
			MAX-ACCESS read-write
			STATUS current
			DESCRIPTION 
				"This object indicates the start time for disabling the radio. The value is in the format of hh:mm:ss NOTE ?	hh specifies the hour. The value is an integer that ranges from 0 to 23.?	mm specifies the minute. The value is an integer that ranges from 0 to 59.?	ss specifies the second. The value is an integer that ranges from 0 to 59."
			::= { hw2gRadioProfileEntry 48 }

		 --1.3.6.1.4.1.2011.6.139.11.1.16.1.49
		hw2gRadioAutoOffServiceEndTime OBJECT-TYPE
			SYNTAX OCTET STRING (SIZE (1..11))
			MAX-ACCESS read-write
			STATUS current
			DESCRIPTION 
				"This object indicates the end time for disabling of the radio. The value is in the format of hh:mm:ss NOTE ?	hh specifies the hour. The value is an integer that ranges from 0 to 23.?	mm specifies the minute. The value is an integer that ranges from 0 to 59.?	ss specifies the second. The value is an integer that ranges from 0 to 59."
			::= { hw2gRadioProfileEntry 49 }

		 --1.3.6.1.4.1.2011.6.139.11.1.16.1.50
		hw2gRadioInterferenceDetectSwitch OBJECT-TYPE
			SYNTAX INTEGER
				{
				disable(1) ,
				enable(2)
				}
			MAX-ACCESS read-write
			STATUS current
			DESCRIPTION 
				"This object indicates the status of the user-by-user power control function. The default value is 1."
			::= { hw2gRadioProfileEntry 50 }

		 --1.3.6.1.4.1.2011.6.139.11.1.16.1.51
		hw2gRadioInterferenceIntraFrequencyThreshold OBJECT-TYPE
			SYNTAX Unsigned32 (1..100)
			MAX-ACCESS read-write
			STATUS current
			DESCRIPTION 
				"This object indicates the alarm threshold for co-channel interference, namely, the percentage of the co-channel interference power against the maximum power. The default value is 50."
			::= { hw2gRadioProfileEntry 51 }

		 --1.3.6.1.4.1.2011.6.139.11.1.16.1.52
		hw2gRadioInterferenceAdjacentFrequencyThreshold OBJECT-TYPE
			SYNTAX Unsigned32 (1..100)
			MAX-ACCESS read-write
			STATUS current
			DESCRIPTION 
				"This object indicates the alarm threshold for adjacent-channel interference, namely, the percentage of the adjacent-channel interference power against the maximum power. The default value is 50."
			::= { hw2gRadioProfileEntry 52 }

		 --1.3.6.1.4.1.2011.6.139.11.1.16.1.53
		hw2gRadioInterferenceStationThreshold OBJECT-TYPE
			SYNTAX Unsigned32 (1..256)
			MAX-ACCESS read-write
			STATUS current
			DESCRIPTION 
				"This object indicates the alarm threshold for station interference. When the number of the STAs detected exceeds the specified alarm threshold, the AP reports alarms to the AC.The default value is 32."
			::= { hw2gRadioProfileEntry 53 }

		 --1.3.6.1.4.1.2011.6.139.11.1.16.1.54
		hw2gRadioRrmProfile OBJECT-TYPE
			SYNTAX OCTET STRING (SIZE (1..35))
			MAX-ACCESS read-write
			STATUS current
			DESCRIPTION 
				"This object indicates the bound RRM profile."
			::= { hw2gRadioProfileEntry 54 }

		 --1.3.6.1.4.1.2011.6.139.11.1.16.1.55
		hw2gRadioAirScanProfile OBJECT-TYPE
			SYNTAX OCTET STRING (SIZE (1..35))
			MAX-ACCESS read-write
			STATUS current
			DESCRIPTION 
				"This object indicates the bound air scan profile."
			::= { hw2gRadioProfileEntry 55 }

		 --1.3.6.1.4.1.2011.6.139.11.1.16.1.56
		hw2gRadioProfileRowStatus OBJECT-TYPE
			SYNTAX RowStatus
			MAX-ACCESS read-write
			STATUS current
			DESCRIPTION 
				"This object indicates the row status of this table. ROWSTATUS_CREATEANDFLOW and ROWSTATUS_DESTROY are commonly used ?	ROWSTATUS_UNDEFINED: undefined?	ROWSTATUS_ACTIVE: active?	ROWSTATUS_NOTINSERVICE: notInService?	ROWSTATUS_NOTREADY: notReady?	ROWSTATUS_CREATEANDFLOW: createAndGo?	ROWSTATUS_CREATEANDWAIT: createAndWait?	ROWSTATUS_DESTROY: destroy."
			::= { hw2gRadioProfileEntry 56 }

		-- 1.3.6.1.4.1.2011.6.139.11.1.16.1.57
		hw2gRadioProfileUtmostPowerSwitch OBJECT-TYPE
			SYNTAX INTEGER
				{
				disable(1),
				auto(2),
				enable(3)
				}
			MAX-ACCESS read-write
			STATUS current
			DESCRIPTION
				"This object indicates the switch for the function of sending packets at maximum power, the default value is 2(auto)."
			::= { hw2gRadioProfileEntry 57 }

		-- 1.3.6.1.4.1.2011.6.139.11.1.16.1.59
		hw2gRadioProfileRadioType OBJECT-TYPE
			SYNTAX INTEGER
				{
				dot11b(1),
				dot11g(5),
				dot11n(9),
				dot11ax(17)
				}
			MAX-ACCESS read-write
			STATUS current
			DESCRIPTION
				"This object indicates the type of radio. The default value is 17. "
			::= { hw2gRadioProfileEntry 59 }

		-- 1.3.6.1.4.1.2011.6.139.11.1.16.1.60
		hw2gRadioProfileSmartAntennaEnable OBJECT-TYPE
			SYNTAX INTEGER
				{
				default(1),
				enable(2),
				disable(3)
				}
			MAX-ACCESS read-write
			STATUS current
			DESCRIPTION
				"This object indicates the status of the smart antenna switch. The default value is 1."
			DEFVAL { default }
			::= { hw2gRadioProfileEntry 60 }

		-- 1.3.6.1.4.1.2011.6.139.11.1.16.1.61
		hw2gRadioProfileTxChainNum OBJECT-TYPE
			SYNTAX Unsigned32 (1..4)
			MAX-ACCESS read-write
			STATUS current
			DESCRIPTION
				"This object indicates the number of the TX chain. The default value is 4."
			DEFVAL { 4 }
			::= { hw2gRadioProfileEntry 61 }
		
		-- 1.3.6.1.4.1.2011.6.139.11.1.16.1.62
		hw2gRadioProfileRxChainNum OBJECT-TYPE
			SYNTAX Unsigned32 (1..4)
			MAX-ACCESS read-write
			STATUS current
			DESCRIPTION
				"This object indicates the number of the RX chain. The default value is 4."
			DEFVAL { 4 }
			::= { hw2gRadioProfileEntry 62 }
	        
	        --1.3.6.1.4.1.2011.6.139.11.1.16.1.63
		hw2gRadioProfileAutoOffTimeRange OBJECT-TYPE
			SYNTAX OCTET STRING (SIZE (0..32))
			MAX-ACCESS read-write
			STATUS current
			DESCRIPTION
				"This object indicates the time range for disabling the radio."
			::= { hw2gRadioProfileEntry 63 }

		-- 1.3.6.1.4.1.2011.6.139.11.1.16.1.64
		hw2gRadioAgileAntennaPolarSwitch OBJECT-TYPE
			SYNTAX INTEGER
				{
				disable(1),
				enable(2)
				}
			MAX-ACCESS read-write
			STATUS current
			DESCRIPTION
				"This object indicates the status of the agile antenna polarization. The default value is 1."
			::= { hw2gRadioProfileEntry 64 }

		
		-- 1.3.6.1.4.1.2011.6.139.11.1.16.1.65
		hw2gRadioProfileCCAThreshold OBJECT-TYPE
			SYNTAX Integer32 (-85..-40 | 0)
			MAX-ACCESS read-write
			STATUS current
			DESCRIPTION
				"This object indicates the value of the CCA threshold. The default value is 0."
			::= { hw2gRadioProfileEntry 65 }

		-- 1.3.6.1.4.1.2011.6.139.11.1.16.1.66
		hw2gRadioProfileSmartAntennaLowPerThreshold OBJECT-TYPE
			SYNTAX Unsigned32 (10|20|30)
			MAX-ACCESS read-write
			STATUS current
			DESCRIPTION
				"This object indicates the value of the smart antenna low per threshold. The default value is 20."
			DEFVAL { 20 }				
			::= { hw2gRadioProfileEntry 66 }

		-- 1.3.6.1.4.1.2011.6.139.11.1.16.1.67
		hw2gRadioProfileSmartAntennaHighPerThreshold OBJECT-TYPE
			SYNTAX Unsigned32 (50|60|70|80|90)
			MAX-ACCESS read-write
			STATUS current
			DESCRIPTION
				"This object indicates the value of the smart antenna high per threshold. The default value is 80."
			DEFVAL { 80 }				
			::= { hw2gRadioProfileEntry 67 }

		-- 1.3.6.1.4.1.2011.6.139.11.1.16.1.68
		hw2gRadioProfileSmartAntennaTrainingInterval OBJECT-TYPE
			SYNTAX Unsigned32 (10..600 | 0)
			MAX-ACCESS read-write
			STATUS current
			DESCRIPTION
				"This object indicates the value of the smart antenna training interval. The default value is 0."
			DEFVAL { 0 }				
			::= { hw2gRadioProfileEntry 68 }

		-- 1.3.6.1.4.1.2011.6.139.11.1.16.1.69
		hw2gRadioProfileSmartAntennaTrainingMPDUNum OBJECT-TYPE
			SYNTAX Unsigned32 (10..1000)
			MAX-ACCESS read-write
			STATUS current
			DESCRIPTION
				"This object indicates the value of the smart antenna training MPDU number. The default value is 640."
			DEFVAL { 640 }				
			::= { hw2gRadioProfileEntry 69 }

		-- 1.3.6.1.4.1.2011.6.139.11.1.16.1.70
		hw2gRadioProfileSmartAntThruputTrainThreshold OBJECT-TYPE
			SYNTAX Unsigned32 (10|20|30|40|50)
			MAX-ACCESS read-write
			STATUS current
			DESCRIPTION
				"This object indicates the value of the smart antenna throughput trigger training threshold. The default value is 10."
			DEFVAL { 10 }				
			::= { hw2gRadioProfileEntry 70 }			
		
		-- 1.3.6.1.4.1.2011.6.139.11.1.16.1.71
		hw2gRadioDot11axGuardIntervalMode OBJECT-TYPE
			SYNTAX INTEGER
				{
				gi0dot8(1),
				gi1dot6(2),
				gi3dot2(3)
				}
			MAX-ACCESS read-write
			STATUS current
			DESCRIPTION
				"This object indicates the dot11ax GI mode. The default value is 1."
			::= { hw2gRadioProfileEntry 71 }
		-- 1.3.6.1.4.1.2011.6.139.11.1.16.1.72
		hw2gRadioHighwayBssid OBJECT-TYPE
			SYNTAX MacAddress
			MAX-ACCESS read-write
			STATUS current
			DESCRIPTION
				"This object indicates the highway bssid."
			::= { hw2gRadioProfileEntry 72 }  
		
		-- 1.3.6.1.4.1.2011.6.139.11.1.16.1.73
		hw2gRadioAutonavigationBeaconInterval OBJECT-TYPE
			SYNTAX Unsigned32 (60..100)
			MAX-ACCESS read-write
			STATUS current
			DESCRIPTION
				"This object indicates a autonavigation beacon interval. The default value is 60. It is expressed in ms."
			::= { hw2gRadioProfileEntry 73 }
		
		-- 1.3.6.1.4.1.2011.6.139.11.1.16.1.74
		hwRadio2GProfileAmsduSwitch OBJECT-TYPE
			SYNTAX INTEGER
				{
				disable(1),
				enable(2)
				}
			MAX-ACCESS read-write
			STATUS current
			DESCRIPTION
				"This object indicates the status of a-msdu switch. The default value is 1."
			::= { hw2gRadioProfileEntry 74 }  	
		
		-- 1.3.6.1.4.1.2011.6.139.11.1.16.1.75
		hw2gRadioVipUserBandwidthReservationRatio OBJECT-TYPE
			SYNTAX Unsigned32 (0..100)
			MAX-ACCESS read-write
			STATUS current
			DESCRIPTION
				"This object indicates the proportion of reserved bandwidth for VIP users. The default value is 20."
			::= { hw2gRadioProfileEntry 75 }  	

		-- 1.3.6.1.4.1.2011.6.139.11.1.16.1.76
		hw2GRadioRu26ToleranceSwitch OBJECT-TYPE
			SYNTAX INTEGER
				{
				disable(1),
				enable(2)
				}
			MAX-ACCESS read-write
			STATUS current
			DESCRIPTION
				"This object indicates the status of ru26-tolerance switch. The default value is 2."
			::= { hw2gRadioProfileEntry 76 }

		-- 1.3.6.1.4.1.2011.6.139.11.1.17
		hw5gRadioProfileTable OBJECT-TYPE
			SYNTAX SEQUENCE OF Hw5gRadioProfileEntry 
			MAX-ACCESS not-accessible
			STATUS current
			DESCRIPTION 
				"This table is used to configure 5 GHz radio parameters, including physical radio parameters such as channel, power, antenna gain, and working mode, and bind air scan profiles and RRM profiles."
			::= { hwWlanConfigObjects 17 }

		--1.3.6.1.4.1.2011.6.139.11.1.17.1
		hw5gRadioProfileEntry OBJECT-TYPE
			SYNTAX Hw5gRadioProfileEntry 
			MAX-ACCESS not-accessible
			STATUS current
			DESCRIPTION 
				"The index of this table is hw5gRadioProfileName."
			INDEX { hw5gRadioProfileName }
			::= { hw5gRadioProfileTable 1 }


		Hw5gRadioProfileEntry ::=
			SEQUENCE {				
				hw5gRadioProfileName
					OCTET STRING,
				hw5gRadioBeaconInterval
					Unsigned32,
				hw5gRadioGuardIntervalMode
					INTEGER,
				hw5gRadioShortPreamble
					INTEGER,
				hw5gRadioFragmentationThreshold
					Unsigned32,
				hw5gRadioHtAmpduSwitch
					INTEGER,
				hw5gRadioHtAmpduMaxLengthExponent
					Unsigned32,
				hw5gRadioVhtAmpduMaxLengthExponent
					Integer32,
				hw5gRadioVhtAmsduSwitch
					INTEGER,
				hw5gRadioVhtAmsduMaxFrameNum
					Unsigned32,
				hw5gRadioDot11aBasicRate
					Unsigned32,
				hw5gRadioDot11aSupportRate
					Unsigned32,
				hw5gRadioMulticastRate
					Unsigned32,
				hw5gRadioVhtNssMapMaxMcs
					OCTET STRING,
				hw5gRadioWmmMandatorySwitch
					INTEGER,
				hw5gRadioApEDCAVoiceECWmax
					Unsigned32,
				hw5gRadioApEDCAVoiceECWmin
					Unsigned32,
				hw5gRadioApEDCAVoiceAIFSN
					Unsigned32,
				hw5gRadioApEDCAVoiceTXOPLimit
					Unsigned32,
				hw5gRadioApEDCAVoiceAckPolicy
					INTEGER,
				hw5gRadioApEDCAVideoECWmax
					Unsigned32,
				hw5gRadioApEDCAVideoECWmin
					Unsigned32,
				hw5gRadioApEDCAVideoAIFSN
					Unsigned32,
				hw5gRadioApEDCAVideoTXOPLimit
					Unsigned32,
				hw5gRadioApEDCAVideoAckPolicy
					INTEGER,
				hw5gRadioApEDCABEECWmax
					Unsigned32,
				hw5gRadioApEDCABEECWmin
					Unsigned32,
				hw5gRadioApEDCABEAIFSN
					Unsigned32,
				hw5gRadioApEDCABETXOPLimit
					Unsigned32,
				hw5gRadioApEDCABEAckPolicy
					INTEGER,
				hw5gRadioApEDCABKECWmax
					Unsigned32,
				hw5gRadioApEDCABKECWmin
					Unsigned32,
				hw5gRadioApEDCABKAIFSN
					Unsigned32,
				hw5gRadioApEDCABKTXOPLimit
					Unsigned32,
				hw5gRadioApEDCABKAckPolicy
					INTEGER,
				hw5gRadioWmmSwitch
					INTEGER,
				hw5gRadioRtsCtsThreshold
					Unsigned32,
				hw5gRadioRtsCtsMode
					INTEGER,
				hw5gRadioPowerAutoAdjustSwitch
					INTEGER,
				hw5gRadioBeamformingSwitch
					INTEGER,
				hw5gRadioWifiLight
					INTEGER,
				hw5gRadioChannelSwitchAnnouncementSwitch
					INTEGER,
				hw5gRadioChannelSwitchMode
					INTEGER,
				hw5gRadioAutoOffServiceSwitch
					INTEGER,
				hw5gRadioAutoOffServiceStartTime
					OCTET STRING,
				hw5gRadioAutoOffServiceEndTime
					OCTET STRING,
				hw5gRadioInterferenceDetectSwitch
					INTEGER,
				hw5gRadioInterferenceIntraFrequencyThreshold
					Unsigned32,
				hw5gRadioInterferenceAdjacentFrequencyThreshold
					Unsigned32,
				hw5gRadioInterferenceStationThreshold
					Unsigned32,
				hw5gRadioRrmProfile
					OCTET STRING,
				hw5gRadioAirScanProfile
					OCTET STRING,
				hw5gRadioProfileRowStatus
					RowStatus,
				hw5gRadioProfileUtmostPowerSwitch
					INTEGER,
				hw5gRadioProfileRadioType
					INTEGER,
				hw5gRadioProfileSmartAntennaEnable
					INTEGER,
				hw5gRadioProfileMuMIMOEnable
					INTEGER,
				hw5gRadioProfileTxChainNum
					Unsigned32,
				hw5gRadioProfileRxChainNum
					Unsigned32,
				hw5gRadioProfileAutoOffTimeRange
					OCTET STRING,
				hw5gRadioAgileAntennaPolarSwitch
					INTEGER,
				hw5gRadioProfileCCAThreshold
					Integer32,
				hw5gRadioProfileSmartAntennaLowPerThreshold
					Unsigned32,
				hw5gRadioProfileSmartAntennaHighPerThreshold
					Unsigned32,
				hw5gRadioProfileSmartAntennaTrainingInterval
					Unsigned32,
				hw5gRadioProfileSmartAntennaTrainingMPDUNum
					Unsigned32,
				hw5gRadioProfileSmartAntThruputTrainThreshold
					Unsigned32,
				hw5gRadioDot11axGuardIntervalMode
					INTEGER,
				hw5gRadioHighwayBssid
					MacAddress,
				hw5gRadioAutonavigationBeaconInterval
				    Unsigned32,
				hw5gRadioVipUserBandwidthReservationRatio
				    Unsigned32,
				hw5GRadioRu26ToleranceSwitch
				    INTEGER					
			 }

		 --1.3.6.1.4.1.2011.6.139.11.1.17.1.1
		hw5gRadioProfileName OBJECT-TYPE
			SYNTAX OCTET STRING (SIZE (1..35))
			MAX-ACCESS not-accessible
			STATUS current
			DESCRIPTION 
				"This object indicates the name of a 5G radio profile. It is the index of the table."
			::= { hw5gRadioProfileEntry 1 }

		
		-- 1.3.6.1.4.1.2011.6.139.11.1.17.1.6
		hw5gRadioBeaconInterval OBJECT-TYPE
			SYNTAX Unsigned32 (60..1000)
			MAX-ACCESS read-write
			STATUS current
			DESCRIPTION
				"This object indicates a Beacon interval. The default value is 100. It is expressed in ms."
			::= { hw5gRadioProfileEntry 6 }

		
		-- 1.3.6.1.4.1.2011.6.139.11.1.17.1.10
		hw5gRadioGuardIntervalMode OBJECT-TYPE
			SYNTAX INTEGER
				{
				short(1),
				normal(2)
				}
			MAX-ACCESS read-write
			STATUS current
			DESCRIPTION 
				"This object indicates the GI mode. The default value is 1."
			::= { hw5gRadioProfileEntry 10 }

		 --1.3.6.1.4.1.2011.6.139.11.1.17.1.11
		hw5gRadioShortPreamble OBJECT-TYPE
			SYNTAX INTEGER
				{
				disable(1),
				enable(2)
				}
			MAX-ACCESS read-write
			STATUS current
			DESCRIPTION 
				"This object indicates whether the short preamble is enabled. The default value is 2."
			::= { hw5gRadioProfileEntry 11 }

		 --1.3.6.1.4.1.2011.6.139.11.1.17.1.12
		hw5gRadioFragmentationThreshold OBJECT-TYPE
			SYNTAX Unsigned32 (256..2346)
			MAX-ACCESS read-write
			STATUS current
			DESCRIPTION 
				"This object indicates the packet fragmentation threshold. The default value is 2346. It is expressed in bytes."
			::= { hw5gRadioProfileEntry 12 }

		 --1.3.6.1.4.1.2011.6.139.11.1.17.1.13
		hw5gRadioHtAmpduSwitch OBJECT-TYPE
			SYNTAX INTEGER
				{
				disable(1) ,
				enable(2)
				}
			MAX-ACCESS read-write
			STATUS current
			DESCRIPTION 
				"This object indicates the status of the aggregation function. The default value is 2."
			::= { hw5gRadioProfileEntry 13 }

		 --1.3.6.1.4.1.2011.6.139.11.1.17.1.14
		hw5gRadioHtAmpduMaxLengthExponent OBJECT-TYPE
			SYNTAX Unsigned32 (0..3)
			MAX-ACCESS read-write
			STATUS current
			DESCRIPTION 
				"This object indicates the maximum length of frames converged by an MPDU. The default value is 3 ?	0: 8191 bytes?	1: 16383 bytes?	2: 32767 bytes ?	3: 65535 bytes."
			::= { hw5gRadioProfileEntry 14 }

		 --1.3.6.1.4.1.2011.6.139.11.1.17.1.15
		hw5gRadioVhtAmpduMaxLengthExponent OBJECT-TYPE
			SYNTAX Integer32 (0..7)
			MAX-ACCESS read-write
			STATUS current
			DESCRIPTION 
				"This object indicates the maximum length of frames converged by an MPDU. The default value is 7 ?	0: 8191 bytes?	1: 16383 bytes?	2: 32767 bytes?	3: 65535 bytes?	4: 131071 bytes?	5: 262143 bytes?	6: 524287 bytes?	7: 1048575 bytes."
			::= { hw5gRadioProfileEntry 15 }

		 --1.3.6.1.4.1.2011.6.139.11.1.17.1.16
		hw5gRadioVhtAmsduSwitch OBJECT-TYPE
			SYNTAX INTEGER
				{
				disable(1),
				enable(2)
				}
			MAX-ACCESS read-write
			STATUS current
			DESCRIPTION 
				"This object indicates the status of the A-MSDU aggregation function. The default value is 1."
			::= { hw5gRadioProfileEntry 16 }

		 --1.3.6.1.4.1.2011.6.139.11.1.17.1.17
		hw5gRadioVhtAmsduMaxFrameNum OBJECT-TYPE
			SYNTAX Unsigned32 (2..15)
			MAX-ACCESS read-write
			STATUS current
			DESCRIPTION 
				"This object indicates the maximum number of sub-frames that can be aggregated into an A-MSDU. The default value is 2."
			::= { hw5gRadioProfileEntry 17 }

		 --1.3.6.1.4.1.2011.6.139.11.1.17.1.18
		hw5gRadioDot11aBasicRate OBJECT-TYPE
			SYNTAX Unsigned32 (1..4095)
			MAX-ACCESS read-write
			STATUS current
			DESCRIPTION 
				"This object indicates the basic rate set of the 802.11bg protocol. The default value is 0x148 (6 Mbit/s/12 Mbit/s/24 Mbit/s) ?	bit0: 1 Mbit/s?	bit1: 2 Mbit/s?	bit2: 5.5 Mbit/s?	bit3: 6 Mbit/s?	bit4: 9 Mbit/s?	bit5: 11 Mbit/s?	bit6: 12 Mbit/s?	bit7: 18 Mbit/s?	bit8: 24 Mbit/s?	bit9: 36 Mbit/s?	bit10: 48 Mbit/s?	bit11: 54 Mbit/s."
			::= { hw5gRadioProfileEntry 18 }

		 --1.3.6.1.4.1.2011.6.139.11.1.17.1.19
		hw5gRadioDot11aSupportRate OBJECT-TYPE
			SYNTAX Unsigned32 (1..4095)
			MAX-ACCESS read-write
			STATUS current
			DESCRIPTION 
				"This object indicates the supported rate set of the 802.11bg protocol. The default value is 0xFD8 (6 Mbit/s/9 Mbit/s/12 Mbit/s/18 Mbit/s/24 Mbit/s/36 Mbit/s/48 Mbit/s/54 Mbit/s).?	bit0: 1 Mbit/s?	bit1: 2 Mbit/s?	bit2: 5.5 Mbit/s?	bit3: 6 Mbit/s?	bit4: 9 Mbit/s?	bit5: 11 Mbit/s?	bit6: 12 Mbit/s?	bit7: 18 Mbit/s?	bit8: 24 Mbit/s?	bit9: 36 Mbit/s?	bit10: 48 Mbit/s?	bit11: 54 Mbit/s."
			::= { hw5gRadioProfileEntry 19 }

		 --1.3.6.1.4.1.2011.6.139.11.1.17.1.20
		hw5gRadioMulticastRate OBJECT-TYPE
			SYNTAX Unsigned32
			MAX-ACCESS read-write
			STATUS current
			DESCRIPTION 
				"This object indicates the multicast rate. The default value is 0x8(6M).?	bit0: 1 Mbit/s?	bit1: 2 Mbit/s?	bit2: 5.5 Mbit/s?	bit3: 6 Mbit/s?	bit4: 9 Mbit/s?	bit5: 11 Mbit/s?	bit6: 12 Mbit/s?	bit7: 18 Mbit/s?	bit8: 24 Mbit/s?	bit9: 36 Mbit/s?	bit10: 48 Mbit/s?	bit11: 54 Mbit/s."
			::= { hw5gRadioProfileEntry 20 }

		 --1.3.6.1.4.1.2011.6.139.11.1.17.1.21
		hw5gRadioVhtNssMapMaxMcs OBJECT-TYPE
			SYNTAX OCTET STRING (SIZE (0..255))
			MAX-ACCESS read-write
			STATUS current
			DESCRIPTION 
				"This object indicates the maximum MCS value for 802.11ac radios. The number of spatial flows is 8 and the maximum MCS value is 7-9. The format is x?x?x?x?x?x?x?x. The default value is 9?9?9?9?9?9?9?9."
			::= { hw5gRadioProfileEntry 21 }

		 --1.3.6.1.4.1.2011.6.139.11.1.17.1.22
		hw5gRadioWmmMandatorySwitch OBJECT-TYPE
			SYNTAX INTEGER
				{
				disable(1) ,
				enable(2)
				}
			MAX-ACCESS read-write
			STATUS current
			DESCRIPTION 
				"This object indicates the status of the mandatory WMM matching function. The default value is 1."
			::= { hw5gRadioProfileEntry 22 }

		 --1.3.6.1.4.1.2011.6.139.11.1.17.1.23
		hw5gRadioApEDCAVoiceECWmax OBJECT-TYPE
			SYNTAX Unsigned32 (0..15)
			MAX-ACCESS read-write
			STATUS current
			DESCRIPTION 
				"This object indicates the EDCA parameter ECWmax, namely, exponent form of Cwmax, for voice services on APs. ECWmin and ECWmax determine the average backoff time (ECWmax > ECWmin). The default value is 3."
			::= { hw5gRadioProfileEntry 23 }

		 --1.3.6.1.4.1.2011.6.139.11.1.17.1.24
		hw5gRadioApEDCAVoiceECWmin OBJECT-TYPE
			SYNTAX Unsigned32 (0..15)
			MAX-ACCESS read-write
			STATUS current
			DESCRIPTION 
				"This object indicates the EDCA parameter ECWmin, namely, exponent form of Cwmin, for voice services on APs. ECWmin and ECWmax determine the average backoff time (ECWmax > ECWmin). The default value is 2."
			::= { hw5gRadioProfileEntry 24 }

		 --1.3.6.1.4.1.2011.6.139.11.1.17.1.25
		hw5gRadioApEDCAVoiceAIFSN OBJECT-TYPE
			SYNTAX Unsigned32 (1..15)
			MAX-ACCESS read-write
			STATUS current
			DESCRIPTION 
				"This object indicates the EDCA parameter AIFSN, namely, arbitration interframe spacing number, for voice services on APs. The default value is 1."
			::= { hw5gRadioProfileEntry 25 }

		 --1.3.6.1.4.1.2011.6.139.11.1.17.1.26
		hw5gRadioApEDCAVoiceTXOPLimit OBJECT-TYPE
			SYNTAX Unsigned32 (0..255)
			MAX-ACCESS read-write
			STATUS current
			DESCRIPTION 
				"This object indicates the EDCA parameter TXOPLimit, namely, transmission opportunity limit, for voice services on APs. The default value is 47. The unit is 32 us."
			::= { hw5gRadioProfileEntry 26 }

		 --1.3.6.1.4.1.2011.6.139.11.1.17.1.27
		hw5gRadioApEDCAVoiceAckPolicy OBJECT-TYPE
			SYNTAX INTEGER
				{
				normal(1),
				noAck(2)
				}
			MAX-ACCESS read-write
			STATUS current
			DESCRIPTION 
				"This object indicates the EDCA parameter AckPolicy for voice services on APs. The default value is 1."
			::= { hw5gRadioProfileEntry 27 }

		 --1.3.6.1.4.1.2011.6.139.11.1.17.1.28
		hw5gRadioApEDCAVideoECWmax OBJECT-TYPE
			SYNTAX Unsigned32 (0..15)
			MAX-ACCESS read-write
			STATUS current
			DESCRIPTION 
				"This object indicates the EDCA parameter ECWmax, namely, exponent form of Cwmax, for video services on APs. ECWmin and ECWmax determine the average backoff time (ECWmax > ECWmin). The default value is 4."
			::= { hw5gRadioProfileEntry 28 }

		 --1.3.6.1.4.1.2011.6.139.11.1.17.1.29
		hw5gRadioApEDCAVideoECWmin OBJECT-TYPE
			SYNTAX Unsigned32 (0..15)
			MAX-ACCESS read-write
			STATUS current
			DESCRIPTION 
				"This object indicates the EDCA parameter ECWmin, namely, exponent form of Cwmin, for video services on APs. ECWmin and ECWmax determine the average backoff time (ECWmax > ECWmin). The default value is 3."
			::= { hw5gRadioProfileEntry 29 }

		 --1.3.6.1.4.1.2011.6.139.11.1.17.1.30
		hw5gRadioApEDCAVideoAIFSN OBJECT-TYPE
			SYNTAX Unsigned32 (1..15)
			MAX-ACCESS read-write
			STATUS current
			DESCRIPTION 
				"This object indicates the EDCA parameter AIFSN, namely, arbitration interframe spacing number, for video services on APs. The default value is 1."
			::= { hw5gRadioProfileEntry 30 }

		 --1.3.6.1.4.1.2011.6.139.11.1.17.1.31
		hw5gRadioApEDCAVideoTXOPLimit OBJECT-TYPE
			SYNTAX Unsigned32 (0..255)
			MAX-ACCESS read-write
			STATUS current
			DESCRIPTION 
				"This object indicates the EDCA parameter TXOPLimit, namely, transmission opportunity limit, for video services on APs. The default value is 94. The unit is 32 us."
			::= { hw5gRadioProfileEntry 31 }

		 --1.3.6.1.4.1.2011.6.139.11.1.17.1.32
		hw5gRadioApEDCAVideoAckPolicy OBJECT-TYPE
			SYNTAX INTEGER
				{
				normal(1),
				noAck(2)
				}
			MAX-ACCESS read-write
			STATUS current
			DESCRIPTION 
				"This object indicates the EDCA parameter AckPolicy for video services on APs. The default value is 1."
			::= { hw5gRadioProfileEntry 32 }

		 --1.3.6.1.4.1.2011.6.139.11.1.17.1.33
		hw5gRadioApEDCABEECWmax OBJECT-TYPE
			SYNTAX Unsigned32 (0..15)
			MAX-ACCESS read-write
			STATUS current
			DESCRIPTION 
				"This object indicates the EDCA parameter ECWmax, namely, exponent form of Cwmax, for BE services on APs. ECWmin and ECWmax determine the average backoff time (ECWmax > ECWmin). The default value is 6."
			::= { hw5gRadioProfileEntry 33 }

		 --1.3.6.1.4.1.2011.6.139.11.1.17.1.34
		hw5gRadioApEDCABEECWmin OBJECT-TYPE
			SYNTAX Unsigned32 (0..15)
			MAX-ACCESS read-write
			STATUS current
			DESCRIPTION 
				"This object indicates the EDCA parameter ECWmin, namely, exponent form of Cwmin, for BE services on APs. ECWmin and ECWmax determine the average backoff time (ECWmax > ECWmin). The default value is 4."
			::= { hw5gRadioProfileEntry 34 }

		 --1.3.6.1.4.1.2011.6.139.11.1.17.1.35
		hw5gRadioApEDCABEAIFSN OBJECT-TYPE
			SYNTAX Unsigned32 (1..15)
			MAX-ACCESS read-write
			STATUS current
			DESCRIPTION 
				"This object indicates the EDCA parameter AIFSN, namely, arbitration interframe spacing number, for BE services on APs. The default value is 3."
			::= { hw5gRadioProfileEntry 35 }

		 --1.3.6.1.4.1.2011.6.139.11.1.17.1.36
		hw5gRadioApEDCABETXOPLimit OBJECT-TYPE
			SYNTAX Unsigned32 (0..255)
			MAX-ACCESS read-write
			STATUS current
			DESCRIPTION 
				"This object indicates the EDCA parameter TXOPLimit, namely, transmission opportunity limit, for BE services on APs. The default value is 0. The unit is 32 us."
			::= { hw5gRadioProfileEntry 36 }

		 --1.3.6.1.4.1.2011.6.139.11.1.17.1.37
		hw5gRadioApEDCABEAckPolicy OBJECT-TYPE
			SYNTAX INTEGER
				{
				normal(1),
				noAck(2)
				}
			MAX-ACCESS read-write
			STATUS current
			DESCRIPTION 
				"This object indicates the EDCA parameter AckPolicy for BE services on APs. The default value is 1."
			::= { hw5gRadioProfileEntry 37 }

		 --1.3.6.1.4.1.2011.6.139.11.1.17.1.38
		hw5gRadioApEDCABKECWmax OBJECT-TYPE
			SYNTAX Unsigned32 (0..15)
			MAX-ACCESS read-write
			STATUS current
			DESCRIPTION 
				"This object indicates the EDCA parameter ECWmax, namely, exponent form of Cwmax, for BK services on APs. ECWmin and ECWmax determine the average backoff time (ECWmax > ECWmin). The default value is 10."
			::= { hw5gRadioProfileEntry 38 }

		 --1.3.6.1.4.1.2011.6.139.11.1.17.1.39
		hw5gRadioApEDCABKECWmin OBJECT-TYPE
			SYNTAX Unsigned32 (0..15)
			MAX-ACCESS read-write
			STATUS current
			DESCRIPTION 
				"This object indicates the EDCA parameter ECWmin, namely, exponent form of Cwmin, for BK services on APs. ECWmin and ECWmax determine the average backoff time (ECWmax > ECWmin). The default value is 4."
			::= { hw5gRadioProfileEntry 39 }

		 --1.3.6.1.4.1.2011.6.139.11.1.17.1.40
		hw5gRadioApEDCABKAIFSN OBJECT-TYPE
			SYNTAX Unsigned32 (1..15)
			MAX-ACCESS read-write
			STATUS current
			DESCRIPTION 
				"This object indicates the EDCA parameter AIFSN, namely, arbitration interframe spacing number, for BK services on APs. The default value is 7.."
			::= { hw5gRadioProfileEntry 40 }

		 --1.3.6.1.4.1.2011.6.139.11.1.17.1.41
		hw5gRadioApEDCABKTXOPLimit OBJECT-TYPE
			SYNTAX Unsigned32 (0..255)
			MAX-ACCESS read-write
			STATUS current
			DESCRIPTION 
				"This object indicates the EDCA parameter TXOPLimit, namely, transmission opportunity limit, for BK services on APs. The default value is 0. The unit is 32 us."
			::= { hw5gRadioProfileEntry 41 }

		 --1.3.6.1.4.1.2011.6.139.11.1.17.1.42
		hw5gRadioApEDCABKAckPolicy OBJECT-TYPE
			SYNTAX INTEGER
				{
				normal(1),
				noAck(2)
				}
			MAX-ACCESS read-write
			STATUS current
			DESCRIPTION 
				"This object indicates the EDCA parameter AckPolicy for BK services on APs. The default value is 1."
			::= { hw5gRadioProfileEntry 42 }

		 --1.3.6.1.4.1.2011.6.139.11.1.17.1.43
		hw5gRadioWmmSwitch OBJECT-TYPE
			SYNTAX INTEGER
				{
				disable(1) ,
				enable(2)
				}
			MAX-ACCESS read-write
			STATUS current
			DESCRIPTION 
				"This object indicates the status of the WMM function. The default value is 2."
			::= { hw5gRadioProfileEntry 43 }

		 --1.3.6.1.4.1.2011.6.139.11.1.17.1.44
		hw5gRadioRtsCtsThreshold OBJECT-TYPE
			SYNTAX Unsigned32 (64..2347)
			MAX-ACCESS read-write
			STATUS current
			DESCRIPTION
				"This object indicates the request To Send/Clear To Send (RTS/CTS) threshold. If the length of a frame to be sent by the MAC Layer exceeds this threshold, an RTS frame needs to be sent before this frame. The default value is 1400 bytes(from V2R8C10; The default value is 2347 before V2R8C10.)."
			::= { hw5gRadioProfileEntry 44 }

		 --1.3.6.1.4.1.2011.6.139.11.1.17.1.45
		hw5gRadioRtsCtsMode OBJECT-TYPE
			SYNTAX INTEGER
				{
				disable(1) ,
				ctsToSelf(2)  ,
				rtsCts(3)
				}
			MAX-ACCESS read-write
			STATUS current
			DESCRIPTION
				"This object indicates the RTS-CTS mode set for the specified radio profile. The default value is 3(from V2R8C10; The default value is 2 before V2R8C10.). In V200R019C10 and later versions, 2 is not supported and will switch to 3 automatically."
			::= { hw5gRadioProfileEntry 45 }

		 --1.3.6.1.4.1.2011.6.139.11.1.17.1.46
		hw5gRadioPowerAutoAdjustSwitch OBJECT-TYPE
			SYNTAX INTEGER
				{
				disable(1) ,
				enable(2)
				}
			MAX-ACCESS read-write
			STATUS current
			DESCRIPTION 
				"This object indicates the status of the user-by-user power control function. The default value is 1."
			::= { hw5gRadioProfileEntry 46 }

		 --1.3.6.1.4.1.2011.6.139.11.1.17.1.47
		hw5gRadioBeamformingSwitch OBJECT-TYPE
			SYNTAX INTEGER
				{
				disable(1) ,
				enable(2)
				}
			MAX-ACCESS read-write
			STATUS current
			DESCRIPTION 
				"This object indicates the status of the beamforming function. The default value is 1."
			::= { hw5gRadioProfileEntry 47 }

		 --1.3.6.1.4.1.2011.6.139.11.1.17.1.48
		hw5gRadioWifiLight OBJECT-TYPE
			SYNTAX INTEGER
				{
				signalStrength(1) ,
				traffic(2)
				}
			MAX-ACCESS read-write
			STATUS current
			DESCRIPTION 
				"This object indicates information reflected by the blinking frequency of the Wireless LED on an AP. The default value is 1 NOTE ?	If Mesh is enabled on an AP, the Wireless indicator blinking frequency reflects the signal strength of the AP with the weakest signal among received signals from all neighboring APs.?	If WDS is enabled on an AP, the the Wireless indicator blinking frequency reflects the signal strength of the connected WDS AP.?	For a Leaf AP, the Wireless indicator blinking frequency reflects the signal strength of the connected Middle AP.?	For a Middle AP, the Wireless indicator blinking frequency reflects the signal strength of the connected Root AP.?	For a root AP, the Wireless indicator blinking frequency reflects the signal strength of the connected Middle AP with the weakest signal.?	If WDS or Mesh is not enabled on an AP, the Wireless indicator blinking frequency reflects the service traffic volume on the radio."
			::= { hw5gRadioProfileEntry 48 }

		 --1.3.6.1.4.1.2011.6.139.11.1.17.1.49
		hw5gRadioChannelSwitchAnnouncementSwitch OBJECT-TYPE
			SYNTAX INTEGER
				{
				disable(1) ,
				enable(2)
				}
			MAX-ACCESS read-write
			STATUS current
			DESCRIPTION 
				"This object indicates the status of the channel switchover announcement function. The default value is 2."
			::= { hw5gRadioProfileEntry 49 }

		 --1.3.6.1.4.1.2011.6.139.11.1.17.1.50
		hw5gRadioChannelSwitchMode OBJECT-TYPE
			SYNTAX INTEGER
				{
				continueTransmitting(1) ,
				stopTransmitting(2)
				}
			MAX-ACCESS read-write
			STATUS current
			DESCRIPTION 
				"This object indicates the channel switch announcement mode. The default value is 1."
			::= { hw5gRadioProfileEntry 50 }

		 --1.3.6.1.4.1.2011.6.139.11.1.17.1.51
		hw5gRadioAutoOffServiceSwitch OBJECT-TYPE
			SYNTAX INTEGER
				{
				disable(1) ,
				enable(2)
				}
			MAX-ACCESS read-write
			STATUS current
			DESCRIPTION 
				"This object indicates the status of the scheduled radio disabling function. The default value is 1."
			::= { hw5gRadioProfileEntry 51 }

		 --1.3.6.1.4.1.2011.6.139.11.1.17.1.52
		hw5gRadioAutoOffServiceStartTime OBJECT-TYPE
			SYNTAX OCTET STRING (SIZE (1..11))
			MAX-ACCESS read-write
			STATUS current
			DESCRIPTION 
				"This object indicates the start time for disabling the radio. The value is in the format of hh:mm:ss NOTE ?	hh specifies the hour. The value is an integer that ranges from 0 to 23.?	mm specifies the minute. The value is an integer that ranges from 0 to 59.?	ss specifies the second. The value is an integer that ranges from 0 to 59.."
			::= { hw5gRadioProfileEntry 52 }

		 --1.3.6.1.4.1.2011.6.139.11.1.17.1.53
		hw5gRadioAutoOffServiceEndTime OBJECT-TYPE
			SYNTAX OCTET STRING (SIZE (1..11))
			MAX-ACCESS read-write
			STATUS current
			DESCRIPTION 
				"This object indicates the end time for disabling of the radio. The value is in the format of hh:mm:ss. NOTE?	hh specifies the hour. The value is an integer that ranges from 0 to 23.?	mm specifies the minute. The value is an integer that ranges from 0 to 59.?	ss specifies the second. The value is an integer that ranges from 0 to 59."
			::= { hw5gRadioProfileEntry 53 }

		 --1.3.6.1.4.1.2011.6.139.11.1.17.1.54
		hw5gRadioInterferenceDetectSwitch OBJECT-TYPE
			SYNTAX INTEGER
				{
				disable(1) ,
				enable(2)
				}
			MAX-ACCESS read-write
			STATUS current
			DESCRIPTION 
				"This object indicates the status of the user-by-user power control function. The default value is 1."
			::= { hw5gRadioProfileEntry 54 }

		 --1.3.6.1.4.1.2011.6.139.11.1.17.1.55
		hw5gRadioInterferenceIntraFrequencyThreshold OBJECT-TYPE
			SYNTAX Unsigned32 (1..100)
			MAX-ACCESS read-write
			STATUS current
			DESCRIPTION 
				"This object indicates the alarm threshold for co-channel interference, namely, the percentage of the co-channel interference power against the maximum power. The default value is 50. "
			::= { hw5gRadioProfileEntry 55 }

		 --1.3.6.1.4.1.2011.6.139.11.1.17.1.56
		hw5gRadioInterferenceAdjacentFrequencyThreshold OBJECT-TYPE
			SYNTAX Unsigned32 (1..100)
			MAX-ACCESS read-write
			STATUS current
			DESCRIPTION 
				"This object indicates the alarm threshold for adjacent-channel interference, namely, the percentage of the adjacent-channel interference power against the maximum power. The default value is 50."
			::= { hw5gRadioProfileEntry 56 }

		 --1.3.6.1.4.1.2011.6.139.11.1.17.1.57
		hw5gRadioInterferenceStationThreshold OBJECT-TYPE
			SYNTAX Unsigned32 (1..256)
			MAX-ACCESS read-write
			STATUS current
			DESCRIPTION 
				"This object indicates the alarm threshold for adjacent-channel interference. When the number of the STAs detected exceeds the specified alarm threshold, the AP reports alarms to the AC. The default value is 32."
			::= { hw5gRadioProfileEntry 57 }

		 --1.3.6.1.4.1.2011.6.139.11.1.17.1.58
		hw5gRadioRrmProfile OBJECT-TYPE
			SYNTAX OCTET STRING (SIZE (1..35))
			MAX-ACCESS read-write
			STATUS current
			DESCRIPTION 
				"This object indicates the bound RRM profile."
			::= { hw5gRadioProfileEntry 58 }

		 --1.3.6.1.4.1.2011.6.139.11.1.17.1.59
		hw5gRadioAirScanProfile OBJECT-TYPE
			SYNTAX OCTET STRING (SIZE (1..35))
			MAX-ACCESS read-write
			STATUS current
			DESCRIPTION 
				"This object indicates the bound air scan profile."
			::= { hw5gRadioProfileEntry 59 }

		 --1.3.6.1.4.1.2011.6.139.11.1.17.1.60
		hw5gRadioProfileRowStatus OBJECT-TYPE
			SYNTAX RowStatus
			MAX-ACCESS read-write
			STATUS current
			DESCRIPTION 
				"This object indicates the row status of this table. ROWSTATUS_CREATEANDFLOW and ROWSTATUS_DESTROY are commonly used.?	ROWSTATUS_UNDEFINED: undefined?	ROWSTATUS_ACTIVE: active?	ROWSTATUS_NOTINSERVICE: notInService?	ROWSTATUS_NOTREADY: notReady?	ROWSTATUS_CREATEANDFLOW: createAndGo?	ROWSTATUS_CREATEANDWAIT: createAndWait?	ROWSTATUS_DESTROY: destroy."
			::= { hw5gRadioProfileEntry 60 }

		-- 1.3.6.1.4.1.2011.6.139.11.1.17.1.61
		hw5gRadioProfileUtmostPowerSwitch OBJECT-TYPE
			SYNTAX INTEGER
				{
				disable(1),
				auto(2),
				enable(3)
				}
			MAX-ACCESS read-write
			STATUS current
			DESCRIPTION
				"This object indicates the switch for the function of sending packets at maximum power, the default value is 2(auto)."
			::= { hw5gRadioProfileEntry 61 }
				
		-- 1.3.6.1.4.1.2011.6.139.11.1.17.1.63
		hw5gRadioProfileRadioType OBJECT-TYPE
			SYNTAX INTEGER
				{
				dot11a(2),
				dot11n(6),
				dot11ac(14),
				dot11ax(16)
				}
			MAX-ACCESS read-write
			STATUS current
			DESCRIPTION
				"This object indicates the type of radio. The default value is 16. "
			::= { hw5gRadioProfileEntry 63 }

		-- 1.3.6.1.4.1.2011.6.139.11.1.17.1.64
		hw5gRadioProfileSmartAntennaEnable OBJECT-TYPE
			SYNTAX INTEGER
				{
				default(1),
				enable(2),
				disable(3)
				}
			MAX-ACCESS read-write
			STATUS current
			DESCRIPTION
				"This object indicates the status of the smart antenna switch. The default value is 1."
			DEFVAL { default }
			::= { hw5gRadioProfileEntry 64 }

		-- 1.3.6.1.4.1.2011.6.139.11.1.17.1.65
		hw5gRadioProfileMuMIMOEnable OBJECT-TYPE
			SYNTAX INTEGER
				{
				disable(1),
				enable(2)
				}
			MAX-ACCESS read-write
			STATUS current
			DESCRIPTION
				"This object indicates the status of the MU MIMO switch. The default value is 1."
			DEFVAL { disable }
			::= { hw5gRadioProfileEntry 65 }
			
		-- 1.3.6.1.4.1.2011.6.139.11.1.17.1.66
		hw5gRadioProfileTxChainNum OBJECT-TYPE
			SYNTAX Unsigned32 (1..4)
			MAX-ACCESS read-write
			STATUS current
			DESCRIPTION
				"This object indicates the number of the TX chain. The default value is 4."
			DEFVAL { 4 }
			::= { hw5gRadioProfileEntry 66 }
			
		-- 1.3.6.1.4.1.2011.6.139.11.1.17.1.67
		hw5gRadioProfileRxChainNum OBJECT-TYPE
			SYNTAX Unsigned32 (1..4)
			MAX-ACCESS read-write
			STATUS current
			DESCRIPTION
				"This object indicates the number of the RX chain. The default value is 4."
			DEFVAL { 4 }
			::= { hw5gRadioProfileEntry 67 }
		
		-- 1.3.6.1.4.1.2011.6.139.11.1.17.1.68
		hw5gRadioProfileAutoOffTimeRange OBJECT-TYPE
			SYNTAX OCTET STRING (SIZE (0..32))
			MAX-ACCESS read-write
			STATUS current
			DESCRIPTION
				"This object indicates the time range for disabling the radio."
			::= { hw5gRadioProfileEntry 68 }
			
		-- 1.3.6.1.4.1.2011.6.139.11.1.17.1.69
		hw5gRadioAgileAntennaPolarSwitch OBJECT-TYPE
			SYNTAX INTEGER
				{
				disable(1),
				enable(2)
				}
			MAX-ACCESS read-write
			STATUS current
			DESCRIPTION
				"This object indicates the status of the agile antenna polarization. The default value is 1."
			::= { hw5gRadioProfileEntry 69 }

		
		-- 1.3.6.1.4.1.2011.6.139.11.1.17.1.70
		hw5gRadioProfileCCAThreshold OBJECT-TYPE
			SYNTAX Integer32 (-85..-40 | 0)
			MAX-ACCESS read-write
			STATUS current
			DESCRIPTION
				"This object indicates the value of the CCA threshold. The default value is 0."
			DEFVAL { 0 }
			::= { hw5gRadioProfileEntry 70 }

		-- 1.3.6.1.4.1.2011.6.139.11.1.17.1.71
		hw5gRadioProfileSmartAntennaLowPerThreshold OBJECT-TYPE
			SYNTAX Unsigned32 (10|20|30)
			MAX-ACCESS read-write
			STATUS current
			DESCRIPTION
				"This object indicates the value of the smart antenna low per threshold. The default value is 20."
			DEFVAL { 20 }	
			::= { hw5gRadioProfileEntry 71 }

		-- 1.3.6.1.4.1.2011.6.139.11.1.17.1.72
		hw5gRadioProfileSmartAntennaHighPerThreshold OBJECT-TYPE
			SYNTAX Unsigned32 (50|60|70|80|90)
			MAX-ACCESS read-write
			STATUS current
			DESCRIPTION
				"This object indicates the value of the smart antenna high per threshold. The default value is 80."
			DEFVAL { 80 }				
			::= { hw5gRadioProfileEntry 72 }

		-- 1.3.6.1.4.1.2011.6.139.11.1.17.1.73
		hw5gRadioProfileSmartAntennaTrainingInterval OBJECT-TYPE
			SYNTAX Unsigned32 (10..600 | 0)
			MAX-ACCESS read-write
			STATUS current
			DESCRIPTION
				"This object indicates the value of the smart antenna training interval. The default value is 0."
			DEFVAL { 0 }				
			::= { hw5gRadioProfileEntry 73 }

		-- 1.3.6.1.4.1.2011.6.139.11.1.17.1.74
		hw5gRadioProfileSmartAntennaTrainingMPDUNum OBJECT-TYPE
			SYNTAX Unsigned32 (10..1000)
			MAX-ACCESS read-write
			STATUS current
			DESCRIPTION
				"This object indicates the value of the smart antenna training MPDU number. The default value is 640."
			DEFVAL { 640 }				
			::= { hw5gRadioProfileEntry 74 }

		-- 1.3.6.1.4.1.2011.6.139.11.1.17.1.75
		hw5gRadioProfileSmartAntThruputTrainThreshold OBJECT-TYPE
			SYNTAX Unsigned32 (10|20|30|40|50)
			MAX-ACCESS read-write
			STATUS current
			DESCRIPTION
				"This object indicates the value of the smart antenna throughput trigger training threshold. The default value is 10."
			DEFVAL { 10 }				
			::= { hw5gRadioProfileEntry 75 }	

			-- 1.3.6.1.4.1.2011.6.139.11.1.17.1.76
		hw5gRadioDot11axGuardIntervalMode OBJECT-TYPE
			SYNTAX INTEGER
				{
				gi0dot8(1),
				gi1dot6(2),
				gi3dot2(3)
				}
			MAX-ACCESS read-write
			STATUS current
			DESCRIPTION
				"This object indicates the dot11ax GI mode. The default value is 1."
			::= { hw5gRadioProfileEntry 76 }		
        -- 1.3.6.1.4.1.2011.6.139.11.1.17.1.77
     	hw5gRadioHighwayBssid OBJECT-TYPE
			SYNTAX MacAddress
			MAX-ACCESS read-write
			STATUS current
			DESCRIPTION
				"This object indicates the highway bssid."
			::= { hw5gRadioProfileEntry 77 }
		
		-- 1.3.6.1.4.1.2011.6.139.11.1.17.1.78
		hw5gRadioAutonavigationBeaconInterval OBJECT-TYPE
			SYNTAX Unsigned32 (60..100)
			MAX-ACCESS read-write
			STATUS current
			DESCRIPTION
				"This object indicates a autonavigation beacon interval. The default value is 60. It is expressed in ms."
			::= { hw5gRadioProfileEntry 78 }
		-- 1.3.6.1.4.1.2011.6.139.11.1.17.1.79
		hw5gRadioVipUserBandwidthReservationRatio OBJECT-TYPE
			SYNTAX Unsigned32 (0..100)
			MAX-ACCESS read-write
			STATUS current
			DESCRIPTION
				"This object indicates the proportion of reserved bandwidth for VIP users. The default value is 20."
			::= { hw5gRadioProfileEntry 79 }
			
		-- 1.3.6.1.4.1.2011.6.139.11.1.17.1.80
		hw5GRadioRu26ToleranceSwitch OBJECT-TYPE
			SYNTAX INTEGER
				{
				disable(1),
				enable(2)
				}
			MAX-ACCESS read-write
			STATUS current
			DESCRIPTION
				"This object indicates the status of ru26-tolerance switch. The default value is 2."
			::= { hw5gRadioProfileEntry 80 }
			
		-- 1.3.6.1.4.1.2011.6.139.11.1.18
		hwRrmProfileTable OBJECT-TYPE
			SYNTAX SEQUENCE OF HwRrmProfileEntry 
			MAX-ACCESS not-accessible
			STATUS current
			DESCRIPTION 
				"This table is used to configure radio resource management parameters, including parameters related to band steering, dynamic load balancing, smart roaming, and UAC."
			::= { hwWlanConfigObjects 18 }

		--1.3.6.1.4.1.2011.6.139.11.1.18.1
		hwRrmProfileEntry OBJECT-TYPE
			SYNTAX HwRrmProfileEntry 
			MAX-ACCESS not-accessible
			STATUS current
			DESCRIPTION 
				"The index of this table is hwRrmProfileName."
			INDEX { hwRrmProfileName }
			::= { hwRrmProfileTable 1 }


		HwRrmProfileEntry ::=
			SEQUENCE {				
				hwRrmProfileName
					OCTET STRING,
				hwRrmAutoChannelSelectSwitch
					INTEGER,
				hwRrmAutoTxPowerSelectSwitch
					INTEGER,
				hwRrmErrRateThreshold
					Unsigned32,
				hwRrmAirtimeFairSchduleSwitch
					INTEGER,
				hwRrmDynamicEdcaSwitch
					INTEGER,
				hwRrmUacLimitClientSnrSwitch
					INTEGER,
				hwRrmUacClientSnrThreshold
					Unsigned32,
				hwRrmUacPolicySwitch
					INTEGER,
				hwRrmUacPolicyType
					INTEGER,
				hwRrmUacClientNumAccessThreshold
					Unsigned32,
				hwRrmUacClientNumRoamThreshold
					Unsigned32,
				hwRrmUacReachThresholdHideSsidSwitch
					INTEGER,
				hwRrmBandSteerDenyThreshold
					Unsigned32,
				hwRrmBandSteerLbClientThreshold
					Unsigned32,
				hwRrmBandSteerLbGapThreshold
					Unsigned32,
				hwRrmBandSteerClientBandsExpire
					Unsigned32,
				hwRrmLoadBalanceSwitch
					INTEGER,
				hwRrmLoadBalanceClientThreshold
					Unsigned32,
				hwRrmLoadBalanceGapThreshold
					Unsigned32,
				hwRrmLoadBalanceDenyThreshold
					Unsigned32,
				hwRrmSmartRoamCheckType
					INTEGER,
				hwRrmSmartRoamSwitch
					INTEGER,
				hwRrmSmartRoamSnrThreshold
					Unsigned32,
				hwRrmSmartRoamRateThreshold
					Unsigned32,
				hwRrmSmartRoamSnrHighLevelMargin
					Unsigned32,
				hwRrmSmartRoamSnrLowLevelMargin
					Unsigned32,
				hwRrmSmartRoamSnrCheckInterval
					Unsigned32,
				hwRrmSmartRoamUnableRoamExpireTime
					Unsigned32,
				hwRrmProfileRowStatus
					RowStatus,
				hwRrmUacChannelUtiAccessThreshold
					Unsigned32,
				hwRrmUacChannelUtiRoamThreshold
					Unsigned32,
				hwRrmSmartRoamQuickKickoffRateThr
					Unsigned32,
				hwRrmSmartRoamQuickKickoffSnrThr
					Unsigned32,
				hwRrmBandSteerSNRThreshold
				    Integer32,
				hwRrmLoadBalanceMode
					INTEGER,
				hwRrmLoadBalanceChUtilGapThreshold
					Unsigned32,
				hwRrmLoadBalanceChUtilStartThreshold
					Unsigned32,
				hwRrmCalibrateCoverageThr
					Integer32,
				hwRrmCalibrateMaxTxPwr
					Unsigned32,
				hwRrmCalibrateMinTxPwr
					Unsigned32,
                                hwRrmCalibrateNoiseFloorThr
					Integer32,
				hwRrmDFSSmartSelectionSwitch
					INTEGER,
				hwRrmDFSRecoverDelayTime
					Integer32,
				hwRrmSmartRoamQuickKickoffSNRCheckInterval
					Integer32,
				hwRrmSmartRoamQuickKickoffSNRPNObserveTime
					Integer32,
				hwRrmSmartRoamQuickKickoffSNRPNQualifyTime
					Integer32,
				hwRrmErrRateCheckInterval  
					Integer32,
				hwRrmErrRateCheckTrafficThreshold
					Integer32,
				hwRrmLoadBalanceRssiThreshold
	                		Integer32,
				hwSfnRoamCheckHighThreshold
					Integer32,
				hwSfnRoamCheckLowThreshold
					Integer32,
				hwSfnRoamCheckRssiAccumulateThreshold
					Integer32,
				hwSfnRoamCheckStaHoldingTimes
					Integer32,
				hwSfnRoamCheckGapRssiThreshold
					Integer32,
				hwSfnRoamCheckBetterSnrTimes
					Integer32,
				hwSfnRoamCheckInterval
					Integer32,
				hwSfnRoamReportInterval
					Integer32,
				hwRrmMultimediaAirOptimize
					INTEGER,
				hwRrmHighDensityAmcOptimizeSwitch
					INTEGER,
				hwRrmMultimediaOptimizedThresholdVoice
					Unsigned32,
				hwRrmMultimediaOptimizedThresholdVideo
					Unsigned32,
				hwRrmSmartRoamQuickKickoffSwitch
					INTEGER,
				hwRrmSmartRoamQuickKickoffCheckType
					INTEGER,
				hwRrmLoadBalanceGapStaNumThreshold
					Integer32,
				hwRrmLbProbeReportInterval
					Unsigned32,
				hwRrmLbDeauthFailTime
					Unsigned32,
				hwRrmLbBtmFailTime
					Unsigned32,
				hwRrmLbSteerRestrictTime
					Unsigned32,
				hwRrmLbSteerProbeRestrictThreshold
					Unsigned32,
				hwRrmLbSteerAuthRestrictThreshold
					Unsigned32,
				hwRrmLbRssiDiffGap
					Unsigned32,
				hwRrmSmartRoamAdvancedScan
					INTEGER,    
				hwRrmSmartRoamQuickKickoffBackOffTime
					Unsigned32,
				hwRrmDynamicEdcaThresholdBE
					Unsigned32,
				hwRrmCalibrate5gMaxTxPwr
					Unsigned32,
				hwRrmCalibrate5gMinTxPwr
					Unsigned32,
 				hwRrmTpcRequestSwitch
 					INTEGER,
 				hwRrmLinkMeasurementSwitch
 					INTEGER,
 				hwRrmInterferenceImmuneSwitch
 					INTEGER,
 				hwRrmBssColorSwitch
 					INTEGER,
 				hwRrmSpatialReuseSwitch
 					INTEGER
			 }

		 --1.3.6.1.4.1.2011.6.139.11.1.18.1.1
		hwRrmProfileName OBJECT-TYPE
			SYNTAX OCTET STRING (SIZE (1..35))
			MAX-ACCESS not-accessible
			STATUS current
			DESCRIPTION 
				"This object indicates the name of the RRM profile. It is the index of the table."
			::= { hwRrmProfileEntry 1 }

		 --1.3.6.1.4.1.2011.6.139.11.1.18.1.2
		hwRrmAutoChannelSelectSwitch OBJECT-TYPE
			SYNTAX INTEGER
				{
				disable(1) ,
				enable(2)
				}
			MAX-ACCESS read-write
			STATUS current
			DESCRIPTION 
				"This object indicates the status of the automatic channel selection function. The default value is 2."
			::= { hwRrmProfileEntry 2 }

		 --1.3.6.1.4.1.2011.6.139.11.1.18.1.3
		hwRrmAutoTxPowerSelectSwitch OBJECT-TYPE
			SYNTAX INTEGER
				{
				disable(1) ,
				enable(2)
				}
			MAX-ACCESS read-write
			STATUS current
			DESCRIPTION 
				"This object indicates the status of the automatic power selection function. The default value is 2."
			::= { hwRrmProfileEntry 3 }

		 --1.3.6.1.4.1.2011.6.139.11.1.18.1.4
		hwRrmErrRateThreshold OBJECT-TYPE
			SYNTAX Unsigned32 (20..100)
			MAX-ACCESS read-write
			STATUS current
			DESCRIPTION
				"This object indicate the error packet threshold triggering the automatic channel or power selection function. The default value is 60. It is expressed in percentage."
			::= { hwRrmProfileEntry 4 }

		 --1.3.6.1.4.1.2011.6.139.11.1.18.1.5
		hwRrmAirtimeFairSchduleSwitch OBJECT-TYPE
			SYNTAX INTEGER
				{
				disable(1) ,
				enable(2)
				}
			MAX-ACCESS read-write
			STATUS current
			DESCRIPTION 
				"This object indicates the status of the airtime scheduling function. The default value is 1."
			::= { hwRrmProfileEntry 5 }

		 --1.3.6.1.4.1.2011.6.139.11.1.18.1.6
		hwRrmDynamicEdcaSwitch OBJECT-TYPE
			SYNTAX INTEGER
				{
				disable(1) ,
				enable(2)
				}
			MAX-ACCESS read-write
			STATUS current
			DESCRIPTION
				"This object indicates the status of the dynamic EDCA parameter adjustment function. The default value is 1."
			::= { hwRrmProfileEntry 6 }

		 --1.3.6.1.4.1.2011.6.139.11.1.18.1.7
		hwRrmUacLimitClientSnrSwitch OBJECT-TYPE
			SYNTAX INTEGER
				{
				disable(1) ,
				enable(2)
				}
			MAX-ACCESS read-write
			STATUS current
			DESCRIPTION 
				"This object indicates the status of the rejecting access from terminals with weak signals function. The default value is 1."
			::= { hwRrmProfileEntry 7 }

		 --1.3.6.1.4.1.2011.6.139.11.1.18.1.8
		hwRrmUacClientSnrThreshold OBJECT-TYPE
			SYNTAX Unsigned32 (5..45 | 255)
			MAX-ACCESS read-write
			STATUS current
			DESCRIPTION
				"This object indicates the SNR threshold for rejecting access from terminals. The default value is 15(from V2R8C10; The default value is 20 before V2R8C10.). The value ranges from 5 to 25 from V200R010C00 and 5 to 75 before V200R010C00. It is expressed in dB. "
			::= { hwRrmProfileEntry 8 }

		 --1.3.6.1.4.1.2011.6.139.11.1.18.1.9
		hwRrmUacPolicySwitch OBJECT-TYPE
			SYNTAX INTEGER
				{
				disable(1) ,
				enable(2)
				}
			MAX-ACCESS read-write
			STATUS current
			DESCRIPTION 
				"This object indicates the status of the UAC policy function. The default value is 1."
			::= { hwRrmProfileEntry 9 }

		 --1.3.6.1.4.1.2011.6.139.11.1.18.1.10
		hwRrmUacPolicyType OBJECT-TYPE
			SYNTAX INTEGER
				{
				users(1) ,
				channelUtilization(2),
				unknown(255)
				}
			MAX-ACCESS read-write
			STATUS current
			DESCRIPTION 
				"This object indicates the UAC policy. The default value is 1."
			::= { hwRrmProfileEntry 10 }

		 --1.3.6.1.4.1.2011.6.139.11.1.18.1.11
		hwRrmUacClientNumAccessThreshold OBJECT-TYPE
			SYNTAX Unsigned32 (1..512)
			MAX-ACCESS read-write
			STATUS current
			DESCRIPTION 
				"Description."
			::= { hwRrmProfileEntry 11 }

		 --1.3.6.1.4.1.2011.6.139.11.1.18.1.12
		hwRrmUacClientNumRoamThreshold OBJECT-TYPE
			SYNTAX Unsigned32 (1..512)
			MAX-ACCESS read-write
			STATUS current
			DESCRIPTION 
				"Description."
			::= { hwRrmProfileEntry 12 }

		 --1.3.6.1.4.1.2011.6.139.11.1.18.1.13
		hwRrmUacReachThresholdHideSsidSwitch OBJECT-TYPE
			SYNTAX INTEGER
				{
				advertiseSSID(1),
                                                                             hideSSID(2),
                                                                             replaceBasedOnPriority(3)
				}
			MAX-ACCESS read-write
			STATUS current
			DESCRIPTION 
				"This object indicates the disposal method when the value of UAC reaches the specified threshold. The default value is 1."
			::= { hwRrmProfileEntry 13 }

		 --1.3.6.1.4.1.2011.6.139.11.1.18.1.14
		hwRrmBandSteerDenyThreshold OBJECT-TYPE
			SYNTAX Unsigned32 (0..10)
			MAX-ACCESS read-write
			STATUS current
			DESCRIPTION 
				"This object indicates the maximum number of times the band steering function rejects association requests from terminals. The default value is 0."
			::= { hwRrmProfileEntry 14 }

		 --1.3.6.1.4.1.2011.6.139.11.1.18.1.15
		hwRrmBandSteerLbClientThreshold OBJECT-TYPE
			SYNTAX Unsigned32 (0..100)
			MAX-ACCESS read-write
			STATUS current
			DESCRIPTION
				"This object indicates the minimum number of terminals for triggering inter-band load balancing. The default value is 100."
			::= { hwRrmProfileEntry 15 }

		 --1.3.6.1.4.1.2011.6.139.11.1.18.1.16
		hwRrmBandSteerLbGapThreshold OBJECT-TYPE
			SYNTAX Unsigned32 (1..100)
			MAX-ACCESS read-write
			STATUS current
			DESCRIPTION
				"This object indicates the percentage threshold for access STAs on the 5 GHz radio. The default value is 90."
			::= { hwRrmProfileEntry 16 }

		 --1.3.6.1.4.1.2011.6.139.11.1.18.1.17
		hwRrmBandSteerClientBandsExpire OBJECT-TYPE
			SYNTAX Unsigned32 (10..65535)
			MAX-ACCESS read-write
			STATUS current
			DESCRIPTION
				"This object indicates the expiration condition for records of terminal supported bands. If the AP continuously receives probe messages from a terminal on the same band and the number of received probe messages exceeds the specified threshold, the records of terminal supported bands will be updated and the AP will consider that the terminal supports only this band. The default value is 35."
			::= { hwRrmProfileEntry 17 }

		 --1.3.6.1.4.1.2011.6.139.11.1.18.1.18
		hwRrmLoadBalanceSwitch OBJECT-TYPE
			SYNTAX INTEGER
				{
				disable(1) ,
				enable(2)
				}
			MAX-ACCESS read-write
			STATUS current
			DESCRIPTION 
				"This object indicates the status of the load balancing group function. The default value is 2."
			::= { hwRrmProfileEntry 18 }

		 --1.3.6.1.4.1.2011.6.139.11.1.18.1.19
		hwRrmLoadBalanceClientThreshold OBJECT-TYPE
			SYNTAX Unsigned32 (1..100)
			MAX-ACCESS read-write
			STATUS current
			DESCRIPTION 
				"This object indicates the percentage of terminals for triggering load balancing. The default value is 10. It is expressed in percentage."
			::= { hwRrmProfileEntry 19 }

		 --1.3.6.1.4.1.2011.6.139.11.1.18.1.20
		hwRrmLoadBalanceGapThreshold OBJECT-TYPE
			SYNTAX Unsigned32 (1..100)
			MAX-ACCESS read-write
			STATUS current
			DESCRIPTION 
				"This object indicates the load difference threshold for triggering load balancing, which is expressed in the number of terminals. The default value is 10."
			::= { hwRrmProfileEntry 20 }

		 --1.3.6.1.4.1.2011.6.139.11.1.18.1.21
		hwRrmLoadBalanceDenyThreshold OBJECT-TYPE
			SYNTAX Unsigned32 (1..10)
			MAX-ACCESS read-write
			STATUS current
			DESCRIPTION 
				"This object indicates the maximum number of times the load balancing function rejects association requests from terminals. The default value is 3."
			::= { hwRrmProfileEntry 21 }

		 --1.3.6.1.4.1.2011.6.139.11.1.18.1.22
		hwRrmSmartRoamCheckType OBJECT-TYPE
			SYNTAX INTEGER
				{
				checkSnr(1) ,
				checkRate(2),
				checkAll(3)
				}			
			MAX-ACCESS read-write
			STATUS current
			DESCRIPTION 
				"This object indicates whether STA active roaming is triggered by rate check or SNR check.The values are as follows:?	1: checkSnr?	2: checkRate?	3: checkAll."
			::= { hwRrmProfileEntry 22 }

		 --1.3.6.1.4.1.2011.6.139.11.1.18.1.23
		hwRrmSmartRoamSwitch OBJECT-TYPE
			SYNTAX INTEGER
				{
				disable(1) ,
				enable(2)
				}
			MAX-ACCESS read-write
			STATUS current
			DESCRIPTION
				"This object indicates the status of the smart roaming function. The default value is 2."
			::= { hwRrmProfileEntry 23 }

		 --1.3.6.1.4.1.2011.6.139.11.1.18.1.24
		hwRrmSmartRoamSnrThreshold OBJECT-TYPE
			SYNTAX Unsigned32 (15..45)
			MAX-ACCESS read-write
			STATUS current
			DESCRIPTION 
				"This object indicates the SNR threshold for triggering the smart roaming function. The default value is 20 dB."
			::= { hwRrmProfileEntry 24 }

		 --1.3.6.1.4.1.2011.6.139.11.1.18.1.25
		hwRrmSmartRoamRateThreshold OBJECT-TYPE
			SYNTAX Unsigned32 (1..100)
			MAX-ACCESS read-write
			STATUS current
			DESCRIPTION 
				"This object indicates the rate threshold for triggering the smart roaming function. It is expressed in the percentage against the maximum rate supported by the terminal. The default value is 0. It is expressed in percentage."
			::= { hwRrmProfileEntry 25 }

		 --1.3.6.1.4.1.2011.6.139.11.1.18.1.26
		hwRrmSmartRoamSnrHighLevelMargin OBJECT-TYPE
			SYNTAX Unsigned32 (10..20)
			MAX-ACCESS read-write
			STATUS current
			DESCRIPTION 
				"This object indicates the upper SNR difference threshold for triggering smart roaming. The default value is 15. It is expressed in dB."
			::= { hwRrmProfileEntry 26 }

		 --1.3.6.1.4.1.2011.6.139.11.1.18.1.27
		hwRrmSmartRoamSnrLowLevelMargin OBJECT-TYPE
			SYNTAX Unsigned32 (3..15)
			MAX-ACCESS read-write
			STATUS current
			DESCRIPTION 
				"This object indicates the lower SNR difference threshold for triggering smart roaming. The default value is 6. It is expressed in dB."
			::= { hwRrmProfileEntry 27 }

		 --1.3.6.1.4.1.2011.6.139.11.1.18.1.28
		hwRrmSmartRoamSnrCheckInterval OBJECT-TYPE
			SYNTAX Unsigned32 (3..30)
			MAX-ACCESS read-write
			STATUS current
			DESCRIPTION 
				"This object indicates the terminal SNR detection interval for smart roaming. The default value is 3. It is expressed in s."
			::= { hwRrmProfileEntry 28 }

		 --1.3.6.1.4.1.2011.6.139.11.1.18.1.29
		hwRrmSmartRoamUnableRoamExpireTime OBJECT-TYPE
			SYNTAX Unsigned32 (30..2880)
			MAX-ACCESS read-write
			STATUS current
			DESCRIPTION 
				"This object indicates the aging time of records that terminals are unable to roam. The default value is 240. It is expressed in minutes."
			::= { hwRrmProfileEntry 29 }

		 --1.3.6.1.4.1.2011.6.139.11.1.18.1.30
		hwRrmProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwRrmProfileEntry 30 }

		
		-- 1.3.6.1.4.1.2011.6.139.11.1.18.1.31
		hwRrmUacChannelUtiAccessThreshold OBJECT-TYPE
			SYNTAX Unsigned32 (1..100)
			MAX-ACCESS read-write
			STATUS current
			DESCRIPTION
				"Description."
			::= { hwRrmProfileEntry 31 }

		
		-- 1.3.6.1.4.1.2011.6.139.11.1.18.1.32
		hwRrmUacChannelUtiRoamThreshold OBJECT-TYPE
			SYNTAX Unsigned32 (1..100)
			MAX-ACCESS read-write
			STATUS current
			DESCRIPTION
				"Description."
			::= { hwRrmProfileEntry 32 }

		-- 1.3.6.1.4.1.2011.6.139.11.1.18.1.33
		hwRrmSmartRoamQuickKickoffRateThr OBJECT-TYPE
			SYNTAX Unsigned32 (1..100)
			MAX-ACCESS read-write
			STATUS current
			DESCRIPTION
				"Smart roam quick-kickoff rate threshold"
			::= { hwRrmProfileEntry 33 }
		
		-- 1.3.6.1.4.1.2011.6.139.11.1.18.1.34
		hwRrmSmartRoamQuickKickoffSnrThr OBJECT-TYPE
			SYNTAX Unsigned32 (5..45)
			MAX-ACCESS read-write
			STATUS current
			DESCRIPTION
				"Smart roam quick-kickoff SNR threshold"
			::= { hwRrmProfileEntry 34 }
			
		-- 1.3.6.1.4.1.2011.6.139.11.1.18.1.35
		hwRrmBandSteerSNRThreshold OBJECT-TYPE
			SYNTAX Integer32 (10..35)
			MAX-ACCESS read-write
			STATUS current            
			DESCRIPTION
				"Description."
			DEFVAL { 20 }
			::= { hwRrmProfileEntry 35 }
			
		-- 1.3.6.1.4.1.2011.6.139.11.1.18.1.36
		hwRrmLoadBalanceMode OBJECT-TYPE
			SYNTAX INTEGER
				{
				staNumber(1),
				channelUtilization(2)
				}
			MAX-ACCESS read-write
			STATUS current
			DESCRIPTION
				"This object indicates the mode for load balancing in a static load balancing group."
			DEFVAL { staNumber }
			::= { hwRrmProfileEntry 36 }
		
		-- 1.3.6.1.4.1.2011.6.139.11.1.18.1.37
		hwRrmLoadBalanceChUtilGapThreshold OBJECT-TYPE
			SYNTAX Unsigned32 (1..99)
			MAX-ACCESS read-write
			STATUS current
			DESCRIPTION
				"This object indicates the load difference threshold of a static load balancing group in channel-utilization mode."
			DEFVAL { 20 }
			::= { hwRrmProfileEntry 37 }
		
		-- 1.3.6.1.4.1.2011.6.139.11.1.18.1.38
		hwRrmLoadBalanceChUtilStartThreshold OBJECT-TYPE
			SYNTAX Unsigned32 (1..99)
			MAX-ACCESS read-write
			STATUS current
			DESCRIPTION
				"This object indicates the start threshold for load balancing in a static load balancing group in channel-utilization mode."
			DEFVAL { 50 }
			::= { hwRrmProfileEntry 38 }
			
		-- 1.3.6.1.4.1.2011.6.139.11.1.18.1.39
		hwRrmCalibrateCoverageThr OBJECT-TYPE
			SYNTAX Integer32 (-85..-35)
			MAX-ACCESS read-write
			STATUS current
			DESCRIPTION
				"Calibrate TPC coverage threshold."
			DEFVAL { -60 }
			::= { hwRrmProfileEntry 39 }
		
		-- 1.3.6.1.4.1.2011.6.139.11.1.18.1.40
		hwRrmCalibrateMaxTxPwr OBJECT-TYPE
			SYNTAX Unsigned32 (1..127)
			MAX-ACCESS read-write
			STATUS current
			DESCRIPTION
				"Calibrate maximum TX power."
			DEFVAL { 127 }
			::= { hwRrmProfileEntry 40 }
		
		-- 1.3.6.1.4.1.2011.6.139.11.1.18.1.41
		hwRrmCalibrateMinTxPwr OBJECT-TYPE
			SYNTAX Unsigned32 (1..127)
			MAX-ACCESS read-write
			STATUS current
			DESCRIPTION
				"Calibrate minimum TX power."
			DEFVAL { 9 }
			::= { hwRrmProfileEntry 41 }
			
		-- 1.3.6.1.4.1.2011.6.139.11.1.18.1.42
		hwRrmCalibrateNoiseFloorThr OBJECT-TYPE
			SYNTAX Integer32 (-95..0)
			MAX-ACCESS read-write
			STATUS current
			DESCRIPTION
				"Calibrate nose-floor threshold."
			DEFVAL { -75 }
			::= { hwRrmProfileEntry 42 }
	        
		-- 1.3.6.1.4.1.2011.6.139.11.1.18.1.43
		hwRrmDFSSmartSelectionSwitch OBJECT-TYPE
			SYNTAX INTEGER
				{
				disable(1),
				enable(2)
				}
			MAX-ACCESS read-write
			STATUS current
			DESCRIPTION
				"Description."
			::= { hwRrmProfileEntry 43 }
		
		-- 1.3.6.1.4.1.2011.6.139.11.1.18.1.44
		hwRrmDFSRecoverDelayTime OBJECT-TYPE
			SYNTAX Integer32 (0..2880)
			MAX-ACCESS read-write
			STATUS current
			DESCRIPTION
				"Description."
			DEFVAL { 0 }
			::= { hwRrmProfileEntry 44 }
		
		-- 1.3.6.1.4.1.2011.6.139.11.1.18.1.45
		hwRrmSmartRoamQuickKickoffSNRCheckInterval OBJECT-TYPE
			SYNTAX Integer32 (300..3000)
			MAX-ACCESS read-write
			STATUS current
			DESCRIPTION
				"Description."
			::= { hwRrmProfileEntry 45 }
		
		-- 1.3.6.1.4.1.2011.6.139.11.1.18.1.46
		hwRrmSmartRoamQuickKickoffSNRPNObserveTime OBJECT-TYPE
			SYNTAX Integer32 (1..10)
			MAX-ACCESS read-write
			STATUS current
			DESCRIPTION
				"Description."
			::= { hwRrmProfileEntry 46 }
		
		-- 1.3.6.1.4.1.2011.6.139.11.1.18.1.47
		hwRrmSmartRoamQuickKickoffSNRPNQualifyTime OBJECT-TYPE
			SYNTAX Integer32 (1..10)
			MAX-ACCESS read-write
			STATUS current
			DESCRIPTION
				"Description."
			::= { hwRrmProfileEntry 47 }

		-- 1.3.6.1.4.1.2011.6.139.11.1.18.1.48
		hwRrmErrRateCheckInterval OBJECT-TYPE
			SYNTAX Integer32 (1..10)
			MAX-ACCESS read-write
			STATUS current
			DESCRIPTION
				"Description."
			::= { hwRrmProfileEntry 48 }

		-- 1.3.6.1.4.1.2011.6.139.11.1.18.1.49
		hwRrmErrRateCheckTrafficThreshold OBJECT-TYPE
			SYNTAX Integer32 (1..20000)
			MAX-ACCESS read-write
			STATUS current
			DESCRIPTION
				"Description."
			::= { hwRrmProfileEntry 49 }

                                  -- 1.3.6.1.4.1.2011.6.139.11.1.18.1.50
		hwRrmLoadBalanceRssiThreshold OBJECT-TYPE
			SYNTAX Integer32 (-75..-55)
			MAX-ACCESS read-write
			STATUS current
			DESCRIPTION
				"This object indicates the load balance rssi threshold."
			::= { hwRrmProfileEntry 50 }
		
		-- 1.3.6.1.4.1.2011.6.139.11.1.18.1.51
		hwSfnRoamCheckHighThreshold OBJECT-TYPE
			SYNTAX Integer32 (-60..-45)
			MAX-ACCESS read-write
			STATUS current
			DESCRIPTION
				"This object indicates sfn roam check high-threshold ."
			DEFVAL { -55 }
			::= { hwRrmProfileEntry 51 }

		
		-- 1.3.6.1.4.1.2011.6.139.11.1.18.1.52
		hwSfnRoamCheckLowThreshold OBJECT-TYPE
			SYNTAX Integer32 (-70..-55)
			MAX-ACCESS read-write
			STATUS current
			DESCRIPTION
				"This object indicates sfn roam check low-threshold ."
			DEFVAL { -60 }
			::= { hwRrmProfileEntry 52 }

		
		-- 1.3.6.1.4.1.2011.6.139.11.1.18.1.53
		hwSfnRoamCheckRssiAccumulateThreshold OBJECT-TYPE
			SYNTAX Integer32 (1..32)
			MAX-ACCESS read-write
			STATUS current
			DESCRIPTION
				"This object indicates sfn roam check rssi Accumulate Threshold ."
			DEFVAL { 8 }
			::= { hwRrmProfileEntry 53 }

		
		-- 1.3.6.1.4.1.2011.6.139.11.1.18.1.54
		hwSfnRoamCheckStaHoldingTimes OBJECT-TYPE
			SYNTAX Integer32 (1..32)
			MAX-ACCESS read-write
			STATUS current
			DESCRIPTION
				"This object indicates sfn roam check Sta HoldingTimes ."
			DEFVAL { 3 }
			::= { hwRrmProfileEntry 54 }

		
		-- 1.3.6.1.4.1.2011.6.139.11.1.18.1.55
		hwSfnRoamCheckGapRssiThreshold OBJECT-TYPE
			SYNTAX Integer32 (1..32)
			MAX-ACCESS read-write
			STATUS current
			DESCRIPTION
				"This object indicates sfn roam check gap rssi Threshold."
			DEFVAL { 6 }
			::= { hwRrmProfileEntry 55 }

		
		-- 1.3.6.1.4.1.2011.6.139.11.1.18.1.56
		hwSfnRoamCheckBetterSnrTimes OBJECT-TYPE
			SYNTAX Integer32 (1..32)
			MAX-ACCESS read-write
			STATUS current
			DESCRIPTION
				"This object indicates sfn roam check Better Snr Times."
			DEFVAL { 2 }
			::= { hwRrmProfileEntry 56 }

		
		-- 1.3.6.1.4.1.2011.6.139.11.1.18.1.57
		hwSfnRoamCheckInterval OBJECT-TYPE
			SYNTAX Integer32 (300..1500)
			MAX-ACCESS read-write
			STATUS current
			DESCRIPTION
				"This object indicates sfn roam check Decision Interval ."
			DEFVAL { 700 }
			::= { hwRrmProfileEntry 57 }

		
		-- 1.3.6.1.4.1.2011.6.139.11.1.18.1.58
		hwSfnRoamReportInterval OBJECT-TYPE
			SYNTAX Integer32 (200..1000)
			MAX-ACCESS read-write
			STATUS current
			DESCRIPTION
				"This object indicates sfn roam check Snr Report Interval "
			DEFVAL { 400 }
			::= { hwRrmProfileEntry 58 }
		
		-- 1.3.6.1.4.1.2011.6.139.11.1.18.1.59
		hwRrmMultimediaAirOptimize OBJECT-TYPE
			SYNTAX INTEGER
				{
				disable(1),
				enable(2)
				}
			MAX-ACCESS read-write
			STATUS current
			DESCRIPTION
				"This object indicates multimedia optimized edca."
			DEFVAL { disable }
			::= { hwRrmProfileEntry 59 }

		-- 1.3.6.1.4.1.2011.6.139.11.1.18.1.60
		hwRrmHighDensityAmcOptimizeSwitch OBJECT-TYPE
			SYNTAX INTEGER
				{
				disable(1),
				enable(2)
				}
			MAX-ACCESS read-write
			STATUS current
			DESCRIPTION
				"This object indicates high density AMC optimize switch."
			DEFVAL { disable }
			::= { hwRrmProfileEntry 60 }
		
		-- 1.3.6.1.4.1.2011.6.139.11.1.18.1.61
		hwRrmMultimediaOptimizedThresholdVoice OBJECT-TYPE
			SYNTAX Unsigned32 (10..1000)
			MAX-ACCESS read-write
			STATUS current
			DESCRIPTION
				"This object indicates multimedia optimized edca adaptive voice threshold."
			DEFVAL { 30 }
			::= { hwRrmProfileEntry 61 }
		
		-- 1.3.6.1.4.1.2011.6.139.11.1.18.1.62
		hwRrmMultimediaOptimizedThresholdVideo OBJECT-TYPE
			SYNTAX Unsigned32 (10..1000)
			MAX-ACCESS read-write
			STATUS current
			DESCRIPTION
				"This object indicates multimedia optimized edca adaptive video threshold."
			DEFVAL { 100 }
			::= { hwRrmProfileEntry 62 }
		
		-- 1.3.6.1.4.1.2011.6.139.11.1.18.1.63
		hwRrmSmartRoamQuickKickoffSwitch OBJECT-TYPE
			SYNTAX INTEGER
				{
				disable(1),
				enable(2)
				}
			MAX-ACCESS read-write
			STATUS current
			DESCRIPTION
				"This object the status of the smart roam quick-kickoff function. The default value is 2."
			DEFVAL { enable }
			::= { hwRrmProfileEntry 63 }

		
		-- 1.3.6.1.4.1.2011.6.139.11.1.18.1.64
		hwRrmSmartRoamQuickKickoffCheckType OBJECT-TYPE
			SYNTAX INTEGER
				{
				checkSnr(1),
				checkRate(2),
				checkAll(3)
				}
			MAX-ACCESS read-write
			STATUS current
			DESCRIPTION
				"This object indicates the check mode for determining whether to quickly disconnect STAs. The default value is 1."
			DEFVAL { checkSnr }
			::= { hwRrmProfileEntry 64 }
			
			
		-- 1.3.6.1.4.1.2011.6.139.11.1.18.1.65
		hwRrmLoadBalanceGapStaNumThreshold OBJECT-TYPE
			SYNTAX Integer32 (1..20)
			MAX-ACCESS read-write
			STATUS current
			DESCRIPTION
				"This object indicates the load difference threshold for triggering dynamic load balancing based on the number of STAs. The value 0 indicates that load balancing is based on the percentage of STAs."
			::= { hwRrmProfileEntry 65 }
			
		-- 1.3.6.1.4.1.2011.6.139.11.1.18.1.66
		hwRrmLbProbeReportInterval OBJECT-TYPE
			SYNTAX Unsigned32 (30..300)
			MAX-ACCESS read-write
			STATUS current
			DESCRIPTION
				"This object indicates the interval for reporting Probe frames. The default value is 120, in seconds."
			::= { hwRrmProfileEntry 66 }
			
		-- 1.3.6.1.4.1.2011.6.139.11.1.18.1.67
		hwRrmLbDeauthFailTime OBJECT-TYPE
			SYNTAX Unsigned32 (0..5)
			MAX-ACCESS read-write
			STATUS current
			DESCRIPTION
				"This object indicates the number of attempts to steer STAs in Deauthentication mode. The default value is 2."
			::= { hwRrmProfileEntry 67 }
			
		-- 1.3.6.1.4.1.2011.6.139.11.1.18.1.68
		hwRrmLbBtmFailTime OBJECT-TYPE
			SYNTAX Unsigned32 (0..10)
			MAX-ACCESS read-write
			STATUS current
			DESCRIPTION
				"This object indicates the number of attempts to steer STAs in BTM mode. The default value is 5."
			::= { hwRrmProfileEntry 68 }
			
		-- 1.3.6.1.4.1.2011.6.139.11.1.18.1.69
		hwRrmLbSteerRestrictTime OBJECT-TYPE
			SYNTAX Unsigned32 (0..10)
			MAX-ACCESS read-write
			STATUS current
			DESCRIPTION
				"This object indicates the time for suppressing STA association with non-target APs during STA steering. The default value is 5, in seconds."
			::= { hwRrmProfileEntry 69 }
			
		-- 1.3.6.1.4.1.2011.6.139.11.1.18.1.70
		hwRrmLbSteerProbeRestrictThreshold OBJECT-TYPE
			SYNTAX Unsigned32 (0..10)
			MAX-ACCESS read-write
			STATUS current
			DESCRIPTION
				"This object indicates the number of times non-target APs suppress STA Probe frames during STA steering. The default value is 5."
			::= { hwRrmProfileEntry 70 }
			
		-- 1.3.6.1.4.1.2011.6.139.11.1.18.1.71
		hwRrmLbSteerAuthRestrictThreshold OBJECT-TYPE
			SYNTAX Unsigned32 (0..5)
			MAX-ACCESS read-write
			STATUS current
			DESCRIPTION
				"This object indicates the number of times non-target APs suppress STA Probe frames during STA steering. The default value is 0."
			::= { hwRrmProfileEntry 71 }
			
		-- 1.3.6.1.4.1.2011.6.139.11.1.18.1.72
		hwRrmLbRssiDiffGap OBJECT-TYPE
			SYNTAX Unsigned32 (0..15)
			MAX-ACCESS read-write
			STATUS current
			DESCRIPTION
				"This object indicates the threshold of the RSSI gap between the associated radio and target radio. The default value is 5, in dB.."
			::= { hwRrmProfileEntry 72 }
			
		-- 1.3.6.1.4.1.2011.6.139.11.1.18.1.73
		hwRrmSmartRoamAdvancedScan OBJECT-TYPE
			SYNTAX INTEGER
				{
				disable(1),
				enable(2)
				}
			MAX-ACCESS read-write
			STATUS current
			DESCRIPTION
				"This object indicates the switch of advanced scan."
			::= { hwRrmProfileEntry 73 }
			
		-- 1.3.6.1.4.1.2011.6.139.11.1.18.1.74
		hwRrmSmartRoamQuickKickoffBackOffTime OBJECT-TYPE
			SYNTAX Unsigned32 (1..600)
			MAX-ACCESS read-write
			STATUS current
			DESCRIPTION
				"This object indicates the back-off time of kick off."
			::= { hwRrmProfileEntry 74 }																							
		-- 1.3.6.1.4.1.2011.6.139.11.1.18.1.75
		hwRrmDynamicEdcaThresholdBE OBJECT-TYPE
			SYNTAX Unsigned32 (1..1000)
			MAX-ACCESS read-write
			STATUS current
			DESCRIPTION
				"This object indicates the restrict threshold of edca."
			DEFVAL { 6 }
			::= { hwRrmProfileEntry 75 }
		-- 1.3.6.1.4.1.2011.6.139.11.1.18.1.76
		hwRrmCalibrate5gMaxTxPwr OBJECT-TYPE
			SYNTAX Unsigned32 (1..127)
			MAX-ACCESS read-write
			STATUS current
			DESCRIPTION
				"Calibrate 5g maximum TX power."
			DEFVAL { 127 }
			::= { hwRrmProfileEntry 76 }
		-- 1.3.6.1.4.1.2011.6.139.11.1.18.1.77
		hwRrmCalibrate5gMinTxPwr OBJECT-TYPE
			SYNTAX Unsigned32 (1..127)
			MAX-ACCESS read-write
			STATUS current
			DESCRIPTION
				"Calibrate 5g minimum TX power."
			DEFVAL { 12 }
			::= { hwRrmProfileEntry 77 }
		-- 1.3.6.1.4.1.2011.6.139.11.1.18.1.78
		hwRrmTpcRequestSwitch OBJECT-TYPE
			SYNTAX INTEGER
				{
				disable(1),
				enable(2)
				}
			MAX-ACCESS read-write
			STATUS current
			DESCRIPTION
				"This object indicates the status of the tpc request function. The default value is 1."
			DEFVAL { disable }
			::= { hwRrmProfileEntry 78 }
		-- 1.3.6.1.4.1.2011.6.139.11.1.18.1.79
		hwRrmLinkMeasurementSwitch OBJECT-TYPE
			SYNTAX INTEGER
				{
				disable(1),
				enable(2)
				}
			MAX-ACCESS read-write
			STATUS current
			DESCRIPTION
				"This object indicates the status of the link measurement function. The default value is 2."
			DEFVAL { enable }
			::= { hwRrmProfileEntry 79 }
		-- 1.3.6.1.4.1.2011.6.139.11.1.18.1.80
		hwRrmInterferenceImmuneSwitch OBJECT-TYPE
			SYNTAX INTEGER
				{
				disable(1),
				enable(2)
				}
			MAX-ACCESS read-write
			STATUS current
			DESCRIPTION
				"This object indicates the status of the interference immune function. The default value is 2."
			DEFVAL { enable }
			::= { hwRrmProfileEntry 80 }

		-- 1.3.6.1.4.1.2011.6.139.11.1.18.1.81
		hwRrmBssColorSwitch OBJECT-TYPE
			SYNTAX INTEGER
				{
				disable(1),
				enable(2)
				}
			MAX-ACCESS read-write
			STATUS current
			DESCRIPTION
				"This object indicates the status of the bss color function. The default value is 2."
			DEFVAL { enable }
			::= { hwRrmProfileEntry 81 }

		-- 1.3.6.1.4.1.2011.6.139.11.1.18.1.82
		hwRrmSpatialReuseSwitch OBJECT-TYPE
			SYNTAX INTEGER
				{
				disable(1),
				enable(2)
				}
			MAX-ACCESS read-write
			STATUS current
			DESCRIPTION
				"This object indicates the status of the spatial reuse function. The default value is 2."
			DEFVAL { enable }
			::= { hwRrmProfileEntry 82 }
		-- 1.3.6.1.4.1.2011.6.139.11.1.19
		hwAirScanProfileTable OBJECT-TYPE
			SYNTAX SEQUENCE OF HwAirScanProfileEntry 
			MAX-ACCESS not-accessible
			STATUS current
			DESCRIPTION 
				"This table is used to configure air scan intervals, duration, and scan channel sets."
			::= { hwWlanConfigObjects 19 }

		--1.3.6.1.4.1.2011.6.139.11.1.19.1
		hwAirScanProfileEntry OBJECT-TYPE
			SYNTAX HwAirScanProfileEntry 
			MAX-ACCESS not-accessible
			STATUS current
			DESCRIPTION 
				"The index of this table is hwAirScanProfileName."
			INDEX { hwAirScanProfileName }
			::= { hwAirScanProfileTable 1 }


		HwAirScanProfileEntry ::=
			SEQUENCE {				
				hwAirScanProfileName
					OCTET STRING,
				hwAirScanPeriod
					Unsigned32,
				hwAirScanInterval
					Unsigned32,
				hwAirScanChannelSet
					INTEGER,
				hwAirScanProfilRowStatus
					RowStatus,
				hwAirScanVoiceAware
					INTEGER,
				hwAirScanVideoAware
					INTEGER,
				hwAirScanSwitch
					INTEGER,
				hwAirScanEnhancement
					INTEGER
			 }

		 --1.3.6.1.4.1.2011.6.139.11.1.19.1.1
		hwAirScanProfileName OBJECT-TYPE
			SYNTAX OCTET STRING (SIZE (1..35))
			MAX-ACCESS not-accessible
			STATUS current
			DESCRIPTION 
				"This object indicates the name of an air scan profile. It is the index of the table."
			::= { hwAirScanProfileEntry 1 }

		 --1.3.6.1.4.1.2011.6.139.11.1.19.1.2
		hwAirScanPeriod OBJECT-TYPE
			SYNTAX Unsigned32 (60..100)
			MAX-ACCESS read-write
			STATUS current
			DESCRIPTION 
				"This object indicates the air scan period. The default value is 60. It is expressed in ms."
			::= { hwAirScanProfileEntry 2 }

		 --1.3.6.1.4.1.2011.6.139.11.1.19.1.3
		hwAirScanInterval OBJECT-TYPE
			SYNTAX Unsigned32 (300..600000)
			MAX-ACCESS read-write
			STATUS current
			DESCRIPTION 
				"This object indicates the scan interval. The default value is 10000. The unit is 1ms."
			::= { hwAirScanProfileEntry 3 }

		 --1.3.6.1.4.1.2011.6.139.11.1.19.1.4
		hwAirScanChannelSet OBJECT-TYPE
			SYNTAX INTEGER
				{
				countryChannel(1),
				dcaChannel(2),
				workChannel(3)
				}
			MAX-ACCESS read-write
			STATUS current
			DESCRIPTION 
				"This object indicates the scan channel set. The default value is 1."
			::= { hwAirScanProfileEntry 4 }

			--1.3.6.1.4.1.2011.6.139.11.1.19.1.5
		hwAirScanProfilRowStatus OBJECT-TYPE
			SYNTAX RowStatus
			MAX-ACCESS read-write
			STATUS current
			DESCRIPTION 
				"This object indicates the row status of this table. ROWSTATUS_CREATEANDFLOW and ROWSTATUS_DESTROY are commonly used.?	ROWSTATUS_UNDEFINED: undefined?	ROWSTATUS_ACTIVE: active?	ROWSTATUS_NOTINSERVICE: notInService?	ROWSTATUS_NOTREADY: notReady?	ROWSTATUS_CREATEANDFLOW: createAndGo?	ROWSTATUS_CREATEANDWAIT: createAndWait?	ROWSTATUS_DESTROY: destroy."
			::= { hwAirScanProfileEntry 5 }
			
		 --1.3.6.1.4.1.2011.6.139.11.1.19.1.6
		hwAirScanVoiceAware OBJECT-TYPE
			SYNTAX INTEGER
				{
				disable(1),
				enable(2)
				}
			MAX-ACCESS read-write
			STATUS current
			DESCRIPTION 
				"This object indicates the voice aware set. The default value is enable."
			::= { hwAirScanProfileEntry 6 }

		 --1.3.6.1.4.1.2011.6.139.11.1.19.1.7
		hwAirScanVideoAware OBJECT-TYPE
			SYNTAX INTEGER
				{
				disable(1),
				enable(2)
				}
			MAX-ACCESS read-write
			STATUS current
			DESCRIPTION 
				"This object indicates the video aware set. The default value is enable."
			::= { hwAirScanProfileEntry 7 }
	
    -- 1.3.6.1.4.1.2011.6.139.11.1.19.1.8
		hwAirScanSwitch OBJECT-TYPE
			SYNTAX INTEGER
				{
				disable(1),
				enable(2)
				}
			MAX-ACCESS read-write
			STATUS current
			DESCRIPTION
				"This object indicates the scan switch status. The default value is enable."
			::= { hwAirScanProfileEntry 8 }	

                -- 1.3.6.1.4.1.2011.6.139.11.1.19.1.9
		hwAirScanEnhancement OBJECT-TYPE
			SYNTAX INTEGER
				{
				disable(1),
				enable(2)
				}
			MAX-ACCESS read-write
			STATUS current
			DESCRIPTION
				"This object indicates the scan enhancement status. The default value is disable."
			::= { hwAirScanProfileEntry 9 }	

		-- 1.3.6.1.4.1.2011.6.139.11.1.20
		hwVapProfileTable OBJECT-TYPE
			SYNTAX SEQUENCE OF HwVapProfileEntry 
			MAX-ACCESS not-accessible
			STATUS current
			DESCRIPTION 
				"This table is used to configure and query VAP profile parameters."
			::= { hwWlanConfigObjects 20 }

		--1.3.6.1.4.1.2011.6.139.11.1.20.1
		hwVapProfileEntry OBJECT-TYPE
			SYNTAX HwVapProfileEntry 
			MAX-ACCESS not-accessible
			STATUS current
			DESCRIPTION 
				"The index of this table is hwVapProfileName."
			INDEX { hwVapProfileName }
			::= { hwVapProfileTable 1 }


		HwVapProfileEntry ::=
			SEQUENCE {				
				hwVapProfileName
					OCTET STRING,
				hwVapForwardMode
					INTEGER,
				hwVapTunnelForwardProtocol
					Unsigned32,
				hwVapServiceSwitch
					INTEGER,
				hwVapAutoOffStartTime
					OCTET STRING,
				hwVapAutoOffEndTime
					OCTET STRING,
				hwVapTemporaryManagementSwitch
					INTEGER,
				hwVapServiceVlan
					Unsigned32,
				hwVapVlanPool
					OCTET STRING,
				hwVapType
					INTEGER,
				hwVapStaAccessMode
					INTEGER,
				hwVapStaAccessModePorfile
					OCTET STRING,
				hwVapRoamHomeAgent
					INTEGER,
				hwVapRoamVlanMobilityGroup
					Unsigned32,
				hwVapRoamLayer3Switch
					INTEGER,
				hwVapBandSteerSwitch
					INTEGER,
				hwVapLearnIpv4Address
					INTEGER,
				hwVapLearnIpv6Address
					INTEGER,
				hwVapLearnIpv4AddressStrict
					INTEGER,
				hwVapIpBindCheck
					INTEGER,
				hwVapArpBindCheck
					INTEGER,
				hwVapOptinon82InsertSwitch
					INTEGER,
				hwVapOptinon82InsertRidFormat
					INTEGER,
				hwVapDhcpTrustPort
					INTEGER,
				hwVapNdTrustPort
					INTEGER,
				hwVapSecurityProfile
					OCTET STRING,
				hwVapTrafficProfile
					OCTET STRING,
				hwVapSsidProfile
					OCTET STRING,
				hwVapAuthenticationProfile
					OCTET STRING,
				hwVapSacProfile
					OCTET STRING,
				hwVapProfileRowStatus
					RowStatus,
				hwVapUserProfile
					OCTET STRING,
				hwVapHotspot2Profile
					OCTET STRING,
				hwSoftgreProfile
					OCTET STRING,
				hwVapOptinon82RidUserDefined
					OCTET STRING,
				hwVapOptinon82RidMacFormat
					INTEGER,
				hwVapOptinon82InsertCidFormat
					INTEGER,
				hwVapOptinon82CidUserDefined
					OCTET STRING,
				hwVapOptinon82CidMacFormat
					INTEGER,
				hwVapUccProfile
					OCTET STRING,
				hwVapAntiAttackBroadcastFloodSwitch
					INTEGER,
				hwVapAntiAttackBroadcastFloodStaRateThreshold
					Unsigned32,
				hwVapAntiAttackBroadcastFloodBlacklistSwitch
					INTEGER,
				hwVapLearnIpv6AddressStrict
					INTEGER,
				hwVapAntiAttackARPFloodSwitch
					INTEGER,
				hwVapAntiAttackARPFloodStaRateThreshold
					Unsigned32,
				hwVapAntiAttackARPFloodBlacklistSwitch
					INTEGER,
				hwVapAntiAttackNDFloodSwitch
					INTEGER,
				hwVapAntiAttackNDFloodStaRateThreshold
					Unsigned32,
				hwVapAntiAttackNDFloodBlacklistSwitch
					INTEGER,
				hwVapAntiAttackIGMPFloodSwitch
					INTEGER,
				hwVapAntiAttackIGMPFloodStaRateThreshold
					Unsigned32,
				hwVapAntiAttackIGMPFloodBlacklistSwitch
					INTEGER,
				hwVapDefenceProfile
					OCTET STRING,
				hwVapTimeRange
					OCTET STRING,
				hwVapPermitVlanList
					OCTET STRING, 
				hwVapSfnRoamSwitch		
					INTEGER,
				hwVapStaNetworkDetectSwitch
					INTEGER,   		
				hwVapLearnIpv4AddressIpconflictuncheck  
					INTEGER,  
				hwVapLearnIpv6AddressIpconflictuncheck  
					INTEGER,
				hwVapRadiusTemplate
					OCTET STRING,
				hwVapBackUpState
					INTEGER,
				hwVapBackUpMode
					INTEGER,
				hwVapRadiusState
					INTEGER,
				hwVapKeepServiceSwitch 
					INTEGER,
				hwVapNaviACID
					Unsigned32,
				hwVapNaviACWlanId
					Unsigned32,
				hwVapHighwayEnable
				    INTEGER,
				hwVapServiceExpAnalysisSwitch
					INTEGER,
				hwVapServiceExpAnalysisSnoopingPort
					Unsigned32,
				hwVapAutonavigationRoamOptimizeSwitch
					INTEGER,
				hwVapMdnsPolicyLocalACSwitch
					INTEGER,
				hwVapProfileMdnsSnooping
					INTEGER,
				hwVapSplitTunnelAcl
					Unsigned32,
				hwVapSplitTunnelAclIPv6
					Unsigned32,
				hwVapApZoneName
					OCTET STRING,
				hwVapRadio
					Unsigned32,
				hwVapProfileMuBaTriggerMode
					INTEGER
			 }


		 --1.3.6.1.4.1.2011.6.139.11.1.20.1.1
		hwVapProfileName OBJECT-TYPE
			SYNTAX OCTET STRING (SIZE (1..35))
			MAX-ACCESS not-accessible
			STATUS current
			DESCRIPTION 
				"This object indicates the name of a VAP profile. It is the index of the table."
			::= { hwVapProfileEntry 1 }

		 --1.3.6.1.4.1.2011.6.139.11.1.20.1.2
		hwVapForwardMode OBJECT-TYPE
			SYNTAX INTEGER
				{
				unknown(1),
				directForward(2),
				tunnel(3),
				softgre(4)
				}
			MAX-ACCESS read-write
			STATUS current
			DESCRIPTION 
				"This object indicates the service forwarding mode. The default value is 2."
			::= { hwVapProfileEntry 2 }

		 --1.3.6.1.4.1.2011.6.139.11.1.20.1.3
		hwVapTunnelForwardProtocol OBJECT-TYPE
			SYNTAX Unsigned32
			MAX-ACCESS read-write
			STATUS current
			DESCRIPTION 
				"This object indicates the format of packets forwarded by tunnel. The default value is 0xd.?	bit0: dot1x?	bit1: dhcp?	bit2: http?	bit3: wapi?	bit4: mdns."
			::= { hwVapProfileEntry 3 }

		 --1.3.6.1.4.1.2011.6.139.11.1.20.1.4
		hwVapServiceSwitch OBJECT-TYPE
			SYNTAX INTEGER
				{
				disable(1) ,
				enable(2)
				}
			MAX-ACCESS read-write
			STATUS current
			DESCRIPTION 
				"This object indicates the status of the VAP service function. The default value is 2."
			::= { hwVapProfileEntry 4 }

		 --1.3.6.1.4.1.2011.6.139.11.1.20.1.5
		hwVapAutoOffStartTime OBJECT-TYPE
			SYNTAX OCTET STRING (SIZE (1..11))
			MAX-ACCESS read-write
			STATUS current
			DESCRIPTION 
				"This object indicates the start time of VAP profile. The format is HH:MM:SS."
			::= { hwVapProfileEntry 5 }

		 --1.3.6.1.4.1.2011.6.139.11.1.20.1.6
		hwVapAutoOffEndTime OBJECT-TYPE
			SYNTAX OCTET STRING (SIZE (1..11))
			MAX-ACCESS read-write
			STATUS current
			DESCRIPTION 
				"This object indicates the end time of VAP profile. The format is HH:MM:SS."
			::= { hwVapProfileEntry 6 }

		 --1.3.6.1.4.1.2011.6.139.11.1.20.1.7
		hwVapTemporaryManagementSwitch OBJECT-TYPE
			SYNTAX INTEGER
				{
				disable(1) ,
				enable(2)
				}
			MAX-ACCESS read-write
			STATUS current
			DESCRIPTION 
				"If this parameter is set to 2, the VAP automatically becomes the management VAP for offline APs after the AP is disconnected. It can still send signals so that maintenance personnel can access it to identify faults (the security mode is the non-authentication security mode and the SSID will be hidden). The default value is 1."
			::= { hwVapProfileEntry 7 }

		 --1.3.6.1.4.1.2011.6.139.11.1.20.1.8
		hwVapServiceVlan OBJECT-TYPE
			SYNTAX Unsigned32 (1..4094)
			MAX-ACCESS read-write
			STATUS current
			DESCRIPTION 
				"This object indicates the service VLAN for the VAP. The default value is 1."
			::= { hwVapProfileEntry 8 }

		 --1.3.6.1.4.1.2011.6.139.11.1.20.1.9
		hwVapVlanPool OBJECT-TYPE
			SYNTAX OCTET STRING (SIZE (0..31))
			MAX-ACCESS read-write
			STATUS current
			DESCRIPTION 
				"This object indicates the VLAN pool to which the VAP is bound."
			::= { hwVapProfileEntry 9 }

		 --1.3.6.1.4.1.2011.6.139.11.1.20.1.10
		hwVapType OBJECT-TYPE
			SYNTAX INTEGER
				{
				service(1) ,
				managementAp(2),
				managementAc(3),
				serviceBackupApOffline(4),
				radiusdownBackup(5),
				serviceNaviAc(6),
				managementLeaderAp(7)
				}
			MAX-ACCESS read-write
			STATUS current
			DESCRIPTION 
				"This object indicates the VAP type. The default value is 1."
			::= { hwVapProfileEntry 10 }

		 --1.3.6.1.4.1.2011.6.139.11.1.20.1.11
		hwVapStaAccessMode OBJECT-TYPE
			SYNTAX INTEGER
				{
				disable(1),
				blacklist(2),
				whitelist(3)
				}
			MAX-ACCESS read-write
			STATUS current
			DESCRIPTION 
				"This object indicates the access mode. The default value is 1."
			::= { hwVapProfileEntry 11 }

		 --1.3.6.1.4.1.2011.6.139.11.1.20.1.12
		hwVapStaAccessModePorfile OBJECT-TYPE
			SYNTAX OCTET STRING (SIZE (0..35))
			MAX-ACCESS read-write
			STATUS current
			DESCRIPTION 
				"This object indicates blacklist and whitelist profiles."
			::= { hwVapProfileEntry 12 }

		 --1.3.6.1.4.1.2011.6.139.11.1.20.1.13
		hwVapRoamHomeAgent OBJECT-TYPE
			SYNTAX INTEGER
				{
				ap(1),
				ac(2)
				}
			MAX-ACCESS read-write
			STATUS current
			DESCRIPTION 
				"This object indicates the tunnel endpoint for inter-Layer 3 roaming. The default value is 1.."
			::= { hwVapProfileEntry 13 }

		 --1.3.6.1.4.1.2011.6.139.11.1.20.1.14
		hwVapRoamVlanMobilityGroup OBJECT-TYPE
			SYNTAX Unsigned32 (1..4094)
			MAX-ACCESS read-write
			STATUS current
			DESCRIPTION 
				"This object indicates the VLAN group for roaming. For the same VLAN, if the VAP is in different VLAN groups for roaming, the roaming is also inter-Layer 3 roaming. The default value is 1.."
			::= { hwVapProfileEntry 14 }

		 --1.3.6.1.4.1.2011.6.139.11.1.20.1.15
		hwVapRoamLayer3Switch OBJECT-TYPE
			SYNTAX INTEGER
				{
				disable(1) ,
				enable(2)
				}
			MAX-ACCESS read-write
			STATUS current
			DESCRIPTION 
				"This object indicates the status of the Layer 3 roaming function. The default value is 2."
			::= { hwVapProfileEntry 15 }

		 --1.3.6.1.4.1.2011.6.139.11.1.20.1.16
		hwVapBandSteerSwitch OBJECT-TYPE
			SYNTAX INTEGER
				{
				disable(1) ,
				enable(2)
				}
			MAX-ACCESS read-write
			STATUS current
			DESCRIPTION 
				"This object indicates the status of the band steering function. The default value is 2."
			::= { hwVapProfileEntry 16 }

		 --1.3.6.1.4.1.2011.6.139.11.1.20.1.17
		hwVapLearnIpv4Address OBJECT-TYPE
			SYNTAX INTEGER
				{
				disable(1) ,
				enable(2)
				}
			MAX-ACCESS read-write
			STATUS current
			DESCRIPTION 
				"This object indicates the status of the IPv4 address learning function. The default value is 2."
			::= { hwVapProfileEntry 17 }

		 --1.3.6.1.4.1.2011.6.139.11.1.20.1.18
		hwVapLearnIpv6Address OBJECT-TYPE
			SYNTAX INTEGER
				{
				disable(1) ,
				enable(2)
				}
			MAX-ACCESS read-write
			STATUS current
			DESCRIPTION 
				"This object indicates the status of the IPv6 address learning function. The default value is 2."
			::= { hwVapProfileEntry 18 }

		 --1.3.6.1.4.1.2011.6.139.11.1.20.1.19
		hwVapLearnIpv4AddressStrict OBJECT-TYPE
			SYNTAX INTEGER
				{
				disable(1) ,
				enable(2) ,
				enableBlacklist(3)
				}
			MAX-ACCESS read-write
			STATUS current
			DESCRIPTION 
				"This object indicates the status of the strict address learning (only through the DHCP) function. The default value is 1."
			::= { hwVapProfileEntry 19 }

		 --1.3.6.1.4.1.2011.6.139.11.1.20.1.20
		hwVapIpBindCheck OBJECT-TYPE
			SYNTAX INTEGER
				{
				disable(1) ,
				enable(2)
				}
			MAX-ACCESS read-write
			STATUS current
			DESCRIPTION 
				"This object indicates the status of the IP binding relationship check function. The default value is 1."
			::= { hwVapProfileEntry 20 }

		 --1.3.6.1.4.1.2011.6.139.11.1.20.1.21
		hwVapArpBindCheck OBJECT-TYPE
			SYNTAX INTEGER
				{
				disable(1) ,
				enable(2)
				}
			MAX-ACCESS read-write
			STATUS current
			DESCRIPTION 
				"This object indicates the status of the ARP binding relationship check function. The default value is 1."
			::= { hwVapProfileEntry 21 }

		 --1.3.6.1.4.1.2011.6.139.11.1.20.1.22
		hwVapOptinon82InsertSwitch OBJECT-TYPE
			SYNTAX INTEGER
				{
				disable(1) ,
				enable(2)
				}
			MAX-ACCESS read-write
			STATUS current
			DESCRIPTION 
				"This object indicates the status of the function of appending the Option 82 field to DHCP messages. The default value is 1."
			::= { hwVapProfileEntry 22 }

		 --1.3.6.1.4.1.2011.6.139.11.1.20.1.23
		hwVapOptinon82InsertRidFormat OBJECT-TYPE
			SYNTAX INTEGER
				{
				apMac(1),
				apMacSsid(2),
				userDefined(3),
				apName(4),
				apNameSsid(5),
				apLocation(6),
				apLocationSsid(7)
				}
			MAX-ACCESS read-write
			STATUS current
			DESCRIPTION
				"This object indicates the format of remote-id(RID) in the Option 82 field to DHCP messages. The default value is 1."
			::= { hwVapProfileEntry 23 }

		 --1.3.6.1.4.1.2011.6.139.11.1.20.1.24
		hwVapDhcpTrustPort OBJECT-TYPE
			SYNTAX INTEGER
				{
				disable(1) ,
				enable(2)
				}
			MAX-ACCESS read-write
			STATUS current
			DESCRIPTION 
				"This object indicates the status of the radio interface DHCP trust function. The default value is 1."
			::= { hwVapProfileEntry 24 }

		 --1.3.6.1.4.1.2011.6.139.11.1.20.1.25
		hwVapNdTrustPort OBJECT-TYPE
			SYNTAX INTEGER
				{
				disable(1) ,
				enable(2)
				}
			MAX-ACCESS read-write
			STATUS current
			DESCRIPTION 
				"This object indicates the status of the radio interface ND trust function. The default value is 1."
			::= { hwVapProfileEntry 25 }

		 --1.3.6.1.4.1.2011.6.139.11.1.20.1.26
		hwVapSecurityProfile OBJECT-TYPE
			SYNTAX OCTET STRING (SIZE (1..35))
			MAX-ACCESS read-write
			STATUS current
			DESCRIPTION 
				"The object indicates the security profile that is bound to the VAP. The default value is default."
			::= { hwVapProfileEntry 26 }

		 --1.3.6.1.4.1.2011.6.139.11.1.20.1.27
		hwVapTrafficProfile OBJECT-TYPE
			SYNTAX OCTET STRING (SIZE (1..35))
			MAX-ACCESS read-write
			STATUS current
			DESCRIPTION 
				"The object indicates the traffic profile that is bound to the VAP. The default value is default."
			::= { hwVapProfileEntry 27 }

		 --1.3.6.1.4.1.2011.6.139.11.1.20.1.28
		hwVapSsidProfile OBJECT-TYPE
			SYNTAX OCTET STRING (SIZE (1..35))
			MAX-ACCESS read-write
			STATUS current
			DESCRIPTION 
				"The object indicates the SSID profile that is bound to the VAP. The default value is default."
			::= { hwVapProfileEntry 28 }

		 --1.3.6.1.4.1.2011.6.139.11.1.20.1.29
		hwVapAuthenticationProfile OBJECT-TYPE
			SYNTAX OCTET STRING (SIZE (0..35))
			MAX-ACCESS read-write
			STATUS current
			DESCRIPTION 
				"The object indicates the authentication profile that is bound to the VAP. The default value is default."
			::= { hwVapProfileEntry 29 }

		 --1.3.6.1.4.1.2011.6.139.11.1.20.1.30
		hwVapSacProfile OBJECT-TYPE
			SYNTAX OCTET STRING (SIZE (0..35))
			MAX-ACCESS read-write
			STATUS current
			DESCRIPTION 
				"The object indicates the SAC profile that is bound to the VAP."
			::= { hwVapProfileEntry 30 }

		 --1.3.6.1.4.1.2011.6.139.11.1.20.1.31
		hwVapProfileRowStatus OBJECT-TYPE
			SYNTAX RowStatus
			MAX-ACCESS read-write
			STATUS current
			DESCRIPTION 
				"This object indicates the row status of this table. ROWSTATUS_CREATEANDFLOW and ROWSTATUS_DESTROY are commonly used.?	ROWSTATUS_UNDEFINED: undefined?	ROWSTATUS_ACTIVE: active?	ROWSTATUS_NOTINSERVICE: notInService?	ROWSTATUS_NOTREADY: notReady?	ROWSTATUS_CREATEANDFLOW: createAndGo?	ROWSTATUS_CREATEANDWAIT: createAndWait?	ROWSTATUS_DESTROY: destroy."
			::= { hwVapProfileEntry 31 }

		
		-- 1.3.6.1.4.1.2011.6.139.11.1.20.1.32
		hwVapUserProfile OBJECT-TYPE
			SYNTAX OCTET STRING (SIZE (0..35))
			MAX-ACCESS read-write
			STATUS current
			DESCRIPTION
				"The object indicates the user profile that is bound to the VAP."
			::= { hwVapProfileEntry 32 }

		
		-- 1.3.6.1.4.1.2011.6.139.11.1.20.1.33
		hwVapHotspot2Profile OBJECT-TYPE
			SYNTAX OCTET STRING (SIZE (0..35))
			MAX-ACCESS read-write
			STATUS current
			DESCRIPTION
				"The object indicates the Hotspot2.0 profile that is bound to the VAP."
			::= { hwVapProfileEntry 33 }

		
		-- 1.3.6.1.4.1.2011.6.139.11.1.20.1.34
		hwSoftgreProfile OBJECT-TYPE
			SYNTAX OCTET STRING (SIZE (0..35))
			MAX-ACCESS read-write
			STATUS current
			DESCRIPTION
				"The object indicates the Softgre profile that is bound to the VAP."
			::= { hwVapProfileEntry 34 }
			
		 --1.3.6.1.4.1.2011.6.139.11.1.20.1.35
		hwVapOptinon82RidUserDefined OBJECT-TYPE
			SYNTAX OCTET STRING (SIZE (1..255))
			MAX-ACCESS read-write
			STATUS current
			DESCRIPTION 
				"This object indicates the user-defined format of remote-id(RID) in the Option 82 field to DHCP messages."
			::= { hwVapProfileEntry 35 }

		 --1.3.6.1.4.1.2011.6.139.11.1.20.1.36
		hwVapOptinon82RidMacFormat OBJECT-TYPE
			SYNTAX INTEGER
				{
				default(0),
				normal(1) ,
				compact(2),
				hex(3)
				}
			MAX-ACCESS read-write
			STATUS current
			DESCRIPTION 
				"This object indicates the AP MAC address format of remote-id(RID) in the Option 82 field to DHCP messages. The default value is 0."
			::= { hwVapProfileEntry 36 }
			
		 --1.3.6.1.4.1.2011.6.139.11.1.20.1.37
		hwVapOptinon82InsertCidFormat OBJECT-TYPE
			SYNTAX INTEGER
				{
				apMac(1),
				apMacSsid(2),
				userDefined(3),
				apName(4),
				apNameSsid(5),
				apLocation(6),
				apLocationSsid(7)
				}
			MAX-ACCESS read-write
			STATUS current
			DESCRIPTION 
				"This object indicates the format of circuit-id(CID) in the Option 82 field to DHCP messages. The default value is 1."
			::= { hwVapProfileEntry 37 }
			
			
		 --1.3.6.1.4.1.2011.6.139.11.1.20.1.38
		hwVapOptinon82CidUserDefined OBJECT-TYPE
			SYNTAX OCTET STRING (SIZE (1..255))
			MAX-ACCESS read-write
			STATUS current
			DESCRIPTION 
				"This object indicates the user-defined format of circuit-id(CID) in the Option 82 field to DHCP messages."
			::= { hwVapProfileEntry 38 }

		 --1.3.6.1.4.1.2011.6.139.11.1.20.1.39
		hwVapOptinon82CidMacFormat OBJECT-TYPE
			SYNTAX INTEGER
				{
				default(0),
				normal(1) ,
				compact(2),
				hex(3)
				}
			MAX-ACCESS read-write
			STATUS current
			DESCRIPTION 
				"This object indicates the AP MAC address format of circuit-id(CID) in the Option 82 field to DHCP messages. The default value is 0."
			::= { hwVapProfileEntry 39 }

                 --1.3.6.1.4.1.2011.6.139.11.1.20.1.40
		hwVapUccProfile OBJECT-TYPE
			SYNTAX OCTET STRING (SIZE (0..35))
			MAX-ACCESS read-write
			STATUS current
			DESCRIPTION 
				"The object indicates the UCC profile that is bound to the VAP."
			::= { hwVapProfileEntry 40 }
		
		-- 1.3.6.1.4.1.2011.6.139.11.1.20.1.41
		hwVapAntiAttackBroadcastFloodSwitch OBJECT-TYPE
			SYNTAX INTEGER
				{
				disable(1),
				enable(2)
				}
			MAX-ACCESS read-write
			STATUS current
			DESCRIPTION
				"This object indicates the status of the VAP anti-attack braoadcast flood function. The default value is 2."
			::= { hwVapProfileEntry 41 }
		
		-- 1.3.6.1.4.1.2011.6.139.11.1.20.1.42
		hwVapAntiAttackBroadcastFloodStaRateThreshold OBJECT-TYPE
			SYNTAX Unsigned32 (5..5000)
			MAX-ACCESS read-write
			STATUS current
			DESCRIPTION
				"This object indicates the anti-attack braoadcast flood sta-rate-threshold for the VAP. The default value is 10."
			::= { hwVapProfileEntry 42 }
			
		-- 1.3.6.1.4.1.2011.6.139.11.1.20.1.43
		hwVapAntiAttackBroadcastFloodBlacklistSwitch OBJECT-TYPE
			SYNTAX INTEGER
				{
				disable(1),
				enable(2)
				}
			MAX-ACCESS read-write
			STATUS current
			DESCRIPTION
				"This object indicates the status of the VAP anti-attack braoadcast flood blacklist function. The default value is 1."
			::= { hwVapProfileEntry 43 }
		
		-- 1.3.6.1.4.1.2011.6.139.11.1.20.1.44
		hwVapLearnIpv6AddressStrict OBJECT-TYPE
			SYNTAX INTEGER
				{
				disable(1),
				enable(2),
				enableBlacklist(3)
				}
			MAX-ACCESS read-write
			STATUS current
			DESCRIPTION
				"This object indicates the status of the strict address learning (only through the DHCPv6) function. The default value is 1."
			::= { hwVapProfileEntry 44 }
			
		-- 1.3.6.1.4.1.2011.6.139.11.1.20.1.45
		hwVapAntiAttackARPFloodSwitch OBJECT-TYPE
			SYNTAX INTEGER
				{
				disable(1),
				enable(2)
				}
			MAX-ACCESS read-write
			STATUS current
			DESCRIPTION
				"This object indicates the status of the VAP anti-attack ARP flood function. The default value is 2."
			::= { hwVapProfileEntry 45 }
			
		-- 1.3.6.1.4.1.2011.6.139.11.1.20.1.46
		hwVapAntiAttackARPFloodStaRateThreshold OBJECT-TYPE
			SYNTAX Unsigned32 (1..500)
			MAX-ACCESS read-write
			STATUS current
			DESCRIPTION
				"This object indicates the anti-attack ARP flood sta-rate-threshold for the VAP. The default value is 5."
			::= { hwVapProfileEntry 46 }

		-- 1.3.6.1.4.1.2011.6.139.11.1.20.1.47
		hwVapAntiAttackARPFloodBlacklistSwitch OBJECT-TYPE
			SYNTAX INTEGER
				{
				disable(1),
				enable(2)
				}
			MAX-ACCESS read-write
			STATUS current
			DESCRIPTION
				"This object indicates the status of the VAP anti-attack ARP flood blacklist function. The default value is 1."
			::= { hwVapProfileEntry 47 }

		-- 1.3.6.1.4.1.2011.6.139.11.1.20.1.48
		hwVapAntiAttackNDFloodSwitch OBJECT-TYPE
			SYNTAX INTEGER
				{
				disable(1),
				enable(2)
				}
			MAX-ACCESS read-write
			STATUS current
			DESCRIPTION
				"This object indicates the status of the VAP anti-attack ND flood function. The default value is 2."
			::= { hwVapProfileEntry 48 }

		-- 1.3.6.1.4.1.2011.6.139.11.1.20.1.49
		hwVapAntiAttackNDFloodStaRateThreshold OBJECT-TYPE
			SYNTAX Unsigned32 (1..500)
			MAX-ACCESS read-write
			STATUS current
			DESCRIPTION
				"This object indicates the anti-attack ND flood sta-rate-threshold for the VAP. The default value is 16."
			::= { hwVapProfileEntry 49 }

		-- 1.3.6.1.4.1.2011.6.139.11.1.20.1.50
		hwVapAntiAttackNDFloodBlacklistSwitch OBJECT-TYPE
			SYNTAX INTEGER
				{
				disable(1),
				enable(2)
				}
			MAX-ACCESS read-write
			STATUS current
			DESCRIPTION
				"This object indicates the status of the VAP anti-attack ND flood blacklist function. The default value is 1."
			::= { hwVapProfileEntry 50 }

		-- 1.3.6.1.4.1.2011.6.139.11.1.20.1.51
		hwVapAntiAttackIGMPFloodSwitch OBJECT-TYPE
			SYNTAX INTEGER
				{
				disable(1),
				enable(2)
				}
			MAX-ACCESS read-write
			STATUS current
			DESCRIPTION
				"This object indicates the status of the VAP anti-attack IGMP flood function. The default value is 2."
			::= { hwVapProfileEntry 51 }

		-- 1.3.6.1.4.1.2011.6.139.11.1.20.1.52
		hwVapAntiAttackIGMPFloodStaRateThreshold OBJECT-TYPE
			SYNTAX Unsigned32 (1..500)
			MAX-ACCESS read-write
			STATUS current
			DESCRIPTION
				"This object indicates the anti-attack IGMP flood sta-rate-threshold for the VAP. The default value is 4."
			::= { hwVapProfileEntry 52 }

		-- 1.3.6.1.4.1.2011.6.139.11.1.20.1.53
		hwVapAntiAttackIGMPFloodBlacklistSwitch OBJECT-TYPE
			SYNTAX INTEGER
				{
				disable(1),
				enable(2)
				}
			MAX-ACCESS read-write
			STATUS current
			DESCRIPTION
				"This object indicates the status of the VAP anti-attack IGMP flood blacklist function. The default value is 1."
			::= { hwVapProfileEntry 53 }

		 --1.3.6.1.4.1.2011.6.139.11.1.20.1.54
		hwVapDefenceProfile OBJECT-TYPE
			SYNTAX OCTET STRING (SIZE (0..32))
			MAX-ACCESS read-write
			STATUS current
			DESCRIPTION 
				"The object indicates the Defence profile that is bound to the VAP. "
			::= { hwVapProfileEntry 54 }	
			
		 --1.3.6.1.4.1.2011.6.139.11.1.20.1.55
		hwVapTimeRange OBJECT-TYPE
			SYNTAX OCTET STRING (SIZE (0..32))
			MAX-ACCESS read-write
			STATUS current
			DESCRIPTION 
				"The object indicates the TimeRange ."
			::= { hwVapProfileEntry 55 }	
		
		 --1.3.6.1.4.1.2011.6.139.11.1.20.1.56
		hwVapPermitVlanList OBJECT-TYPE
			SYNTAX OCTET STRING (SIZE (0..1024))
			MAX-ACCESS read-write
			STATUS current
			DESCRIPTION 
				"This object indicates the PermitVlanList. The default value is 0."
			::= { hwVapProfileEntry 56 }

		 --1.3.6.1.4.1.2011.6.139.11.1.20.1.57
		 hwVapSfnRoamSwitch OBJECT-TYPE
		  	SYNTAX INTEGER
				{
				disable(1),
				enable(2)
				}
			MAX-ACCESS read-write
			STATUS current
			DESCRIPTION
				"This object indicates the status of the SFN Roam function. The default value is 1."
			::= { hwVapProfileEntry 57 }			
	
	     --1.3.6.1.4.1.2011.6.139.11.1.20.1.58
		 hwVapStaNetworkDetectSwitch OBJECT-TYPE
		  	SYNTAX INTEGER
				{
				disable(1),
				enable(2)
				}
			MAX-ACCESS read-write
			STATUS current
			DESCRIPTION
				"This object indicates the status of sta network reachable detect function. The default value is 2."
			::= { hwVapProfileEntry 58 }
			
		 --1.3.6.1.4.1.2011.6.139.11.1.20.1.59
		 hwVapLearnIpv4AddressIpconflictuncheck OBJECT-TYPE
		  	SYNTAX INTEGER
				{
				disable(1),
				enable(2)
				}
			MAX-ACCESS read-write
			STATUS current
			DESCRIPTION
				"This object indicates the status of the IPv4 address conflict check function. The default value is 1."
			::= { hwVapProfileEntry 59 }

	     --1.3.6.1.4.1.2011.6.139.11.1.20.1.60
		 hwVapLearnIpv6AddressIpconflictuncheck OBJECT-TYPE
		  	SYNTAX INTEGER
				{
				disable(1),
				enable(2)
				}
			MAX-ACCESS read-write
			STATUS current
			DESCRIPTION
				"This object indicates the status of the IPv6 address conflict check function. The default value is 1."
			::= { hwVapProfileEntry 60 }

	     --1.3.6.1.4.1.2011.6.139.11.1.20.1.61
		 hwVapRadiusTemplate OBJECT-TYPE
		  	SYNTAX OCTET STRING (SIZE (0..32))
			MAX-ACCESS read-write
			STATUS current
			DESCRIPTION
				"This object indicates the name of radius-server template."
			::= { hwVapProfileEntry 61 }

	     --1.3.6.1.4.1.2011.6.139.11.1.20.1.62
		 hwVapBackUpState OBJECT-TYPE
		  	SYNTAX INTEGER
				{
				off(1),
				on(2),
				invalid(3)
				}
			MAX-ACCESS read-write
			STATUS current
			DESCRIPTION
				"This object indicates the state of the radiusdownBackup vap."
			::= { hwVapProfileEntry 62 }

	     --1.3.6.1.4.1.2011.6.139.11.1.20.1.63
		 hwVapBackUpMode OBJECT-TYPE
		  	SYNTAX INTEGER
				{
				manual(1),
				auto(2),
				invalid(3)
				}
			MAX-ACCESS read-only
			STATUS current
			DESCRIPTION
				"This object indicates the mode of the switch which triges vap on or off."
			::= { hwVapProfileEntry 63 }

	     --1.3.6.1.4.1.2011.6.139.11.1.20.1.64
		 hwVapRadiusState OBJECT-TYPE
		  	SYNTAX INTEGER
				{
				up(1),
				down(2),
				invalid(3)
				}
			MAX-ACCESS read-only
			STATUS current
			DESCRIPTION
				"This object indicates the state of radius server."
			::= { hwVapProfileEntry 64 }
			
	     --1.3.6.1.4.1.2011.6.139.11.1.20.1.65
		 hwVapKeepServiceSwitch OBJECT-TYPE
		  	SYNTAX INTEGER
				{
				enable(1),
				disable(2),
				allowaccess(3),
				allowAccessAlsoNoauth(4)
				}
			MAX-ACCESS read-write
			STATUS current
			DESCRIPTION
				"This object indicates the status of vap keep service function. The default value is 2."
			::= { hwVapProfileEntry 65 }


		-- 1.3.6.1.4.1.2011.6.139.11.1.20.1.66
		hwVapNaviACID OBJECT-TYPE
			SYNTAX Unsigned32 (4294967295 | 0..15)
			MAX-ACCESS read-write
			STATUS current
			DESCRIPTION
				"This object indicates the AC index."
			::= { hwVapProfileEntry 66 }

		
		-- 1.3.6.1.4.1.2011.6.139.11.1.20.1.67
		hwVapNaviACWlanId OBJECT-TYPE
			SYNTAX Unsigned32 (4294967295 | 1..16)
			MAX-ACCESS read-write
			STATUS current
			DESCRIPTION
				"This object indicates the wlan index."
			::= { hwVapProfileEntry 67 }

                 --1.3.6.1.4.1.2011.6.139.11.1.20.1.68
		 hwVapHighwayEnable OBJECT-TYPE
		  	SYNTAX INTEGER
				{
				disable(1),
				enable(2)
	         	}
			MAX-ACCESS read-write
			STATUS current
			DESCRIPTION
				"This object indicates the status of vap highway status. The default value is 1."
			::= { hwVapProfileEntry 68 }
                 --1.3.6.1.4.1.2011.6.139.11.1.20.1.69
		 hwVapServiceExpAnalysisSwitch OBJECT-TYPE
		  	SYNTAX INTEGER
				{
				disable(1),
				enable(2)
	         	}
			MAX-ACCESS read-write
			STATUS current
			DESCRIPTION
				"This object indicates the status of service experience analysis. The default value is 1."
			::= { hwVapProfileEntry 69}
		 --1.3.6.1.4.1.2011.6.139.11.1.20.1.70
		 hwVapServiceExpAnalysisSnoopingPort OBJECT-TYPE
		  	SYNTAX Unsigned32 (1..65535)
			MAX-ACCESS read-write
			STATUS current
			DESCRIPTION
				"This object indicates SIP snooping port. The default value is 5060."
			::= { hwVapProfileEntry 70 }
		--1.3.6.1.4.1.2011.6.139.11.1.20.1.71
		 hwVapAutonavigationRoamOptimizeSwitch OBJECT-TYPE
		  	SYNTAX INTEGER
				{
				disable(1),
				enable(2)
				}
			MAX-ACCESS read-write
			STATUS current
			DESCRIPTION
				"This object indicates whether to enable autonavigation roaming optimization."
			::= { hwVapProfileEntry 71 }
			
		--1.3.6.1.4.1.2011.6.139.11.1.20.1.72
		 hwVapMdnsPolicyLocalACSwitch OBJECT-TYPE
		  	SYNTAX INTEGER
				{
				disable(1),
				enable(2)
				}
			MAX-ACCESS read-write
			STATUS current
			DESCRIPTION
				"This object indicates the status of vap MDNS policy on local ac. The default value is 1."
			::= { hwVapProfileEntry 72 }

		-- 1.3.6.1.4.1.2011.6.139.11.1.20.1.73
		hwVapProfileMdnsSnooping OBJECT-TYPE
			SYNTAX INTEGER
				{
				disable(1),
				enable(2)
				}
			MAX-ACCESS read-write
			STATUS current
			DESCRIPTION
				"This object indicates the switch of MDNS snooping. The default value is 1."
			::= { hwVapProfileEntry 73 }
			
                -- 1.3.6.1.4.1.2011.6.139.11.1.20.1.74
		hwVapSplitTunnelAcl OBJECT-TYPE
			SYNTAX Unsigned32 (3000..3031)
			MAX-ACCESS read-write
			STATUS current
			DESCRIPTION
				"This object indicates configure of split tunnel ACL."
			::= { hwVapProfileEntry 74 }

                -- 1.3.6.1.4.1.2011.6.139.11.1.20.1.75
		hwVapSplitTunnelAclIPv6 OBJECT-TYPE
			SYNTAX Unsigned32 (3000..3031)
			MAX-ACCESS read-write
			STATUS current
			DESCRIPTION
				"This object indicates configure of split tunnel IPv6 ACL."
			::= { hwVapProfileEntry 75 }

		--1.3.6.1.4.1.2011.6.139.11.1.20.1.76
		hwVapApZoneName OBJECT-TYPE
		  	SYNTAX OCTET STRING (SIZE (0..35))
			MAX-ACCESS read-write
			STATUS current
			DESCRIPTION
				"This object indicates the zone name of vap."
			::= { hwVapProfileEntry 76 }
		
		--1.3.6.1.4.1.2011.6.139.11.1.20.1.77
		hwVapRadio OBJECT-TYPE
		  	SYNTAX Unsigned32 (0..2 | 255)
			MAX-ACCESS read-write
			STATUS current
			DESCRIPTION
				"This object indicates the radio that vap takes effect. The default value is 255."
			::= { hwVapProfileEntry 77 }

		--1.3.6.1.4.1.2011.6.139.11.1.20.1.78
		hwVapProfileMuBaTriggerMode OBJECT-TYPE
			SYNTAX INTEGER
				{
				basictrigger(1),
				mubar(2)
				}
			MAX-ACCESS read-write
			STATUS current
			DESCRIPTION
				"This object indicates the trigger mode of sending MU-BA. The default value is 2."
			::= { hwVapProfileEntry 78 }

		-- 1.3.6.1.4.1.2011.6.139.11.1.21
		hwSsidProfileTable OBJECT-TYPE
			SYNTAX SEQUENCE OF HwSsidProfileEntry 
			MAX-ACCESS not-accessible
			STATUS current
			DESCRIPTION 
				"This table is used to configure and query SSID profile parameters."
			::= { hwWlanConfigObjects 21 }

		--1.3.6.1.4.1.2011.6.139.11.1.21.1
		hwSsidProfileEntry OBJECT-TYPE
			SYNTAX HwSsidProfileEntry 
			MAX-ACCESS not-accessible
			STATUS current
			DESCRIPTION 
				"The index of this table is hwSsidProfileName."
			INDEX { hwSsidProfileName }
			::= { hwSsidProfileTable 1 }


		HwSsidProfileEntry ::=
			SEQUENCE {				
				hwSsidProfileName
					OCTET STRING,
				hwSsidText
					OCTET STRING,
				hwSsidHide
					INTEGER,
				hwSsidAssocTimeout
					Unsigned32,
				hwSsidMaxStaNum
					Unsigned32,
				hwSsidLegacyStaSwitch
					INTEGER,
				hwSsidDtimInterval
					Unsigned32,
				hwSsidClientEdcaVoiceECWmax
					Unsigned32,
				hwSsidClientEdcaVoiceECWmin
					Unsigned32,
				hwSsidClientEdcaVoiceAIFSN
					Unsigned32,
				hwSsidClientEdcaVoiceTXOPLimit
					Unsigned32,
				hwSsidClientEdcaVideoECWmax
					Unsigned32,
				hwSsidClientEdcaVideoECWmin
					Unsigned32,
				hwSsidClientEdcaVideoAIFSN
					Unsigned32,
				hwSsidClientEdcaVideoTXOPLimit
					Unsigned32,
				hwSsidClientEdcaBeECWmax
					Unsigned32,
				hwSsidClientEdcaBeECWmin
					Unsigned32,
				hwSsidClientEdcaBeAIFSN
					Unsigned32,
				hwSsidClientEdcaBeTXOPLimit
					Unsigned32,
				hwSsidClientEdcaBkECWmax
					Unsigned32,
				hwSsidClientEdcaBkECWmin
					Unsigned32,
				hwSsidClientEdcaBkAIFSN
					Unsigned32,
				hwSsidClientEdcaBkTXOPLimit
					Unsigned32,
				hwSsidInboundCarCir
					Unsigned32,
				hwSsidInboundCarPir
					Unsigned32,
				hwSsidInboundCarCbs
					Unsigned32,
				hwSsidInboundCarPbs
					Unsigned32,
				hwSsidOutboundCarCir
					Unsigned32,
				hwSsidOutboundCarPir
					Unsigned32,
				hwSsidOutboundCarCbs
					Unsigned32,
				hwSsidOutboundCarPbs
					Unsigned32,
				hwSsidProfileRowStatus
					RowStatus,
				hwSsidHideWhileReachMaxSta
					INTEGER,
				hwSsidBeacon2gRate
					INTEGER,
				hwSsidBeacon5gRate
					INTEGER,
				hwSsidDenyBroadcastProbe
					INTEGER,
				hwSsidProbeResponseRetry
					Unsigned32,
				hwSsidUapsd
					INTEGER,
				hwSsidActiveDullClient
					INTEGER,
				hwSsidMuMIMOSwitch
					INTEGER,
				hwSsidProfile80211rEnable
					INTEGER,
				hwSsidProfile80211rMode
					INTEGER,
				hwSsidProfile80211rReassociateTimeout
					Integer32,
				hwSsidQbssLoadSwitch
					INTEGER,
				hwSsidSingleTxchainSwitch
					INTEGER,
				hwSsidMuMIMOOptimizeSwitch
					INTEGER,
				hwSsidAdvertiseApNameSwitch 
					INTEGER,
				hwSsidServiceGuarantee
					INTEGER,
                                                                             hwSsidInterAcRoamSwitch 
					INTEGER,
				hwSsidVhtTxNssCount
					Unsigned32,
				hwSsidVhtRxNssCount
					Unsigned32,
				hwSsidVhtTxMcsMap
					Unsigned32,
 				hwSsidVhtRxMcsMap
					Unsigned32,
				hwSsidHETxNssCount
					Unsigned32,
				hwSsidHERxNssCount
					Unsigned32,
				hwSsidHETxMcsMap
					Unsigned32,
				hwSsidHERxMcsMap
					Unsigned32,
				hwSsidBeamformingSwitch
					INTEGER,
				hwSsidProfilePartialMumimoDownlinkSwitch
					INTEGER,
				hwSsidProfileOfdmaDownlinkSwitch
					INTEGER,
				hwSsidProfileOfdmaUplinkSwitch
					INTEGER,
				hwSsidTwtSwitch
					INTEGER,
				hwSsidProfile80211rPrivateSwitch
					INTEGER
			 }

		 --1.3.6.1.4.1.2011.6.139.11.1.21.1.1
		hwSsidProfileName OBJECT-TYPE
			SYNTAX OCTET STRING (SIZE (1..35))
			MAX-ACCESS not-accessible
			STATUS current
			DESCRIPTION 
				"This object indicates the name of a VAP profile. It is the index of the table."
			::= { hwSsidProfileEntry 1 }

		 --1.3.6.1.4.1.2011.6.139.11.1.21.1.2
		hwSsidText OBJECT-TYPE
			SYNTAX OCTET STRING (SIZE (1..32))
			MAX-ACCESS read-write
			STATUS current
			DESCRIPTION 
				"This object indicates the SSID character string. The default value is HUAWEI-WLAN."
			::= { hwSsidProfileEntry 2 }

		 --1.3.6.1.4.1.2011.6.139.11.1.21.1.3
		hwSsidHide OBJECT-TYPE
			SYNTAX INTEGER
				{
				disable(1) ,
				enable(2)
				}
			MAX-ACCESS read-write
			STATUS current
			DESCRIPTION 
				"This object indicates whether to enable SSID hiding. The default value is 1."
			::= { hwSsidProfileEntry 3 }

		 --1.3.6.1.4.1.2011.6.139.11.1.21.1.4
		hwSsidAssocTimeout OBJECT-TYPE
			SYNTAX Unsigned32 (1..30)
			MAX-ACCESS read-write
			STATUS current
			DESCRIPTION 
				"This object indicates the association timeout period of a user. The default value is 5 minutes."
			::= { hwSsidProfileEntry 4 }

		 --1.3.6.1.4.1.2011.6.139.11.1.21.1.5
		hwSsidMaxStaNum OBJECT-TYPE
			SYNTAX Unsigned32 (1..512)
			MAX-ACCESS read-write
			STATUS current
			DESCRIPTION 
				"The object indicates the number of access users on a VAP. The default value is 64."
			::= { hwSsidProfileEntry 5 }

		 --1.3.6.1.4.1.2011.6.139.11.1.21.1.6
		hwSsidLegacyStaSwitch OBJECT-TYPE
			SYNTAX INTEGER
				{
				disable(1) ,
				enable(2) ,
				onlyDot11bDisable(3)
				}
			MAX-ACCESS read-write
			STATUS current
			DESCRIPTION 
				"This object indicates whether to allow access from legacy terminals. The default value is 2."
			::= { hwSsidProfileEntry 6 }

		 --1.3.6.1.4.1.2011.6.139.11.1.21.1.7
		hwSsidDtimInterval OBJECT-TYPE
			SYNTAX Unsigned32 (1..255)
			MAX-ACCESS read-write
			STATUS current
			DESCRIPTION 
				"This object indicates the DTIM interval. The default value is 1."
			::= { hwSsidProfileEntry 7 }

		 --1.3.6.1.4.1.2011.6.139.11.1.21.1.8
		hwSsidClientEdcaVoiceECWmax OBJECT-TYPE
			SYNTAX Unsigned32 (0..15)
			MAX-ACCESS read-write
			STATUS current
			DESCRIPTION 
				"This object indicates the ECWmax value, which determines the average avoidance time. The value of this object is the ECWmax value of the AC_VO queue on the station. The default value is 3."
			::= { hwSsidProfileEntry 8 }

		 --1.3.6.1.4.1.2011.6.139.11.1.21.1.9
		hwSsidClientEdcaVoiceECWmin OBJECT-TYPE
			SYNTAX Unsigned32 (0..15)
			MAX-ACCESS read-write
			STATUS current
			DESCRIPTION 
				"This object indicates the ECWmin value, which determines the average avoidance time. The value of this object is the ECWmin value of the AC_VO queue on the station. The default value is 2."
			::= { hwSsidProfileEntry 9 }

		 --1.3.6.1.4.1.2011.6.139.11.1.21.1.10
		hwSsidClientEdcaVoiceAIFSN OBJECT-TYPE
			SYNTAX Unsigned32 (1..15)
			MAX-ACCESS read-write
			STATUS current
			DESCRIPTION 
				"This object indicates the AIFSN value, which determines the idle waiting time. The value of this object is the AIFSN value of the AC_VO queue on the station. The default value is 2. In V200R019C10 and later versions, 1 is not supported and will switch to 2 automatically."
			::= { hwSsidProfileEntry 10 }

		 --1.3.6.1.4.1.2011.6.139.11.1.21.1.11
		hwSsidClientEdcaVoiceTXOPLimit OBJECT-TYPE
			SYNTAX Unsigned32 (0..255)
			MAX-ACCESS read-write
			STATUS current
			DESCRIPTION 
				"This object indicates the TXOPLimit value, which determines the time for occupying the channel. The value of this object is the TXOPLimit value of the AC_VO queue on the station. The default value is 47."
			::= { hwSsidProfileEntry 11 }

		 --1.3.6.1.4.1.2011.6.139.11.1.21.1.12
		hwSsidClientEdcaVideoECWmax OBJECT-TYPE
			SYNTAX Unsigned32 (0..15)
			MAX-ACCESS read-write
			STATUS current
			DESCRIPTION 
				"This object indicates the ECWmax value, which determines the average avoidance time. The value of this object is the ECWmax value of the AC_VI queue on the station. The default value is 4."
			::= { hwSsidProfileEntry 12 }

		 --1.3.6.1.4.1.2011.6.139.11.1.21.1.13
		hwSsidClientEdcaVideoECWmin OBJECT-TYPE
			SYNTAX Unsigned32 (0..15)
			MAX-ACCESS read-write
			STATUS current
			DESCRIPTION 
				"This object indicates the ECWmin value, which determines the average avoidance time. The value of this object is the ECWmin value of the AC_VI queue on the station. The default value is 3."
			::= { hwSsidProfileEntry 13 }

		 --1.3.6.1.4.1.2011.6.139.11.1.21.1.14
		hwSsidClientEdcaVideoAIFSN OBJECT-TYPE
			SYNTAX Unsigned32 (1..15)
			MAX-ACCESS read-write
			STATUS current
			DESCRIPTION 
				"This object indicates the AIFSN value, which determines the idle waiting time. The value of this object is the AIFSN value of the AC_VI queue on the station. The default value is 2. In V200R019C10 and later versions, 1 is not supported and will switch to 2 automatically."
			::= { hwSsidProfileEntry 14 }

		 --1.3.6.1.4.1.2011.6.139.11.1.21.1.15
		hwSsidClientEdcaVideoTXOPLimit OBJECT-TYPE
			SYNTAX Unsigned32 (0..255)
			MAX-ACCESS read-write
			STATUS current
			DESCRIPTION 
				"This object indicates the TXOPLimit value, which determines the time for occupying the channel. The value of this object is the TXOPLimit value of the AC_VI queue on the station. The default value is 94."
			::= { hwSsidProfileEntry 15 }

		 --1.3.6.1.4.1.2011.6.139.11.1.21.1.16
		hwSsidClientEdcaBeECWmax OBJECT-TYPE
			SYNTAX Unsigned32 (0..15)
			MAX-ACCESS read-write
			STATUS current
			DESCRIPTION 
				"This object indicates the ECWmax value, which determines the average avoidance time. The value of this object is the ECWmax value of the AC_BE queue on the station. The default value is 10."
			::= { hwSsidProfileEntry 16 }

		 --1.3.6.1.4.1.2011.6.139.11.1.21.1.17
		hwSsidClientEdcaBeECWmin OBJECT-TYPE
			SYNTAX Unsigned32 (0..15)
			MAX-ACCESS read-write
			STATUS current
			DESCRIPTION 
				"This object indicates the ECWmin value, which determines the average avoidance time. The value of this object is the ECWmin value of the AC_BE queue on the station. The default value is 4."
			::= { hwSsidProfileEntry 17 }

		 --1.3.6.1.4.1.2011.6.139.11.1.21.1.18
		hwSsidClientEdcaBeAIFSN OBJECT-TYPE
			SYNTAX Unsigned32 (1..15)
			MAX-ACCESS read-write
			STATUS current
			DESCRIPTION 
				"This object indicates the AIFSN value, which determines the idle waiting time. The value of this object is the AIFSN value of the AC_BE queue on the station. The default value is 3. In V200R019C10 and later versions, 1 is not supported and will switch to 2 automatically."
			::= { hwSsidProfileEntry 18 }

		 --1.3.6.1.4.1.2011.6.139.11.1.21.1.19
		hwSsidClientEdcaBeTXOPLimit OBJECT-TYPE
			SYNTAX Unsigned32 (0..255)
			MAX-ACCESS read-write
			STATUS current
			DESCRIPTION 
				"This object indicates the TXOPLimit value, which determines the time for occupying the channel. The value of this object is the TXOPLimit value of the AC_BE queue on the station. The default value is 0."
			::= { hwSsidProfileEntry 19 }

		 --1.3.6.1.4.1.2011.6.139.11.1.21.1.20
		hwSsidClientEdcaBkECWmax OBJECT-TYPE
			SYNTAX Unsigned32 (0..15)
			MAX-ACCESS read-write
			STATUS current
			DESCRIPTION 
				"This object indicates the ECWmax value, which determines the average avoidance time. The value of this object is the ECWmax value of the AC_BK queue on the station. The default value is 10."
			::= { hwSsidProfileEntry 20 }

		 --1.3.6.1.4.1.2011.6.139.11.1.21.1.21
		hwSsidClientEdcaBkECWmin OBJECT-TYPE
			SYNTAX Unsigned32 (0..15)
			MAX-ACCESS read-write
			STATUS current
			DESCRIPTION 
				"This object indicates the ECWmin value, which determines the average avoidance time. The value of this object is the ECWmin value of the AC_BK queue on the station. The default value is 4."
			::= { hwSsidProfileEntry 21 }

		 --1.3.6.1.4.1.2011.6.139.11.1.21.1.22
		hwSsidClientEdcaBkAIFSN OBJECT-TYPE
			SYNTAX Unsigned32 (1..15)
			MAX-ACCESS read-write
			STATUS current
			DESCRIPTION 
				"This object indicates the AIFSN value, which determines the idle waiting time. The value of this object is the AIFSN value of the AC_BK queue on the station. The default value is 7. In V200R019C10 and later versions, 1 is not supported and will switch to 2 automatically."
			::= { hwSsidProfileEntry 22 }

		 --1.3.6.1.4.1.2011.6.139.11.1.21.1.23
		hwSsidClientEdcaBkTXOPLimit OBJECT-TYPE
			SYNTAX Unsigned32 (0..255)
			MAX-ACCESS read-write
			STATUS current
			DESCRIPTION 
				"This object indicates the TXOPLimit value, which determines the time for occupying the channel. The value of this object is the TXOPLimit value of the AC_BK queue on the station. The default value is 0."
			::= { hwSsidProfileEntry 23 }

		 --1.3.6.1.4.1.2011.6.139.11.1.21.1.24
		hwSsidInboundCarCir OBJECT-TYPE
			SYNTAX Unsigned32 (0..4294967295)
			MAX-ACCESS read-write
			STATUS current
			DESCRIPTION 
				"This object indicates the inbound committed information rate (CIR) of the SSID. The default value is 0 kbit/s. Invalid value is 1 to 63."
			::= { hwSsidProfileEntry 24 }

		 --1.3.6.1.4.1.2011.6.139.11.1.21.1.25
		hwSsidInboundCarPir OBJECT-TYPE
			SYNTAX Unsigned32 (0..4294967295)
			MAX-ACCESS read-write
			STATUS current
			DESCRIPTION 
				"This object indicates the inbound peak information rate (PIR) of the SSID. The default value is 0 kbit/s. Invalid value is 1 to 63."
			::= { hwSsidProfileEntry 25 }

		 --1.3.6.1.4.1.2011.6.139.11.1.21.1.26
		hwSsidInboundCarCbs OBJECT-TYPE
			SYNTAX Unsigned32 (0..4294967295)
			MAX-ACCESS read-write
			STATUS current
			DESCRIPTION 
				"This object indicates the inbound committed burst size (CBS) of the SSID. The default value is 0 bytes. Invalid value is 1 to 1499."
			::= { hwSsidProfileEntry 26 }

		 --1.3.6.1.4.1.2011.6.139.11.1.21.1.27
		hwSsidInboundCarPbs OBJECT-TYPE
			SYNTAX Unsigned32 (0..4294967295)
			MAX-ACCESS read-write
			STATUS current
			DESCRIPTION 
				"This object indicates the inbound peak burst size (PBS) of the SSID. The default value is 0 bytes. Invalid value is 1 to 1499."
			::= { hwSsidProfileEntry 27 }

		 --1.3.6.1.4.1.2011.6.139.11.1.21.1.28
		hwSsidOutboundCarCir OBJECT-TYPE
			SYNTAX Unsigned32 (0..4294967295)
			MAX-ACCESS read-write
			STATUS current
			DESCRIPTION 
				"This object indicates the outbound committed information rate (CIR) of the SSID. The default value is 0 kbit/s. Invalid value is 1 to 63."
			::= { hwSsidProfileEntry 28 }

		 --1.3.6.1.4.1.2011.6.139.11.1.21.1.29
		hwSsidOutboundCarPir OBJECT-TYPE
			SYNTAX Unsigned32 (0..4294967295)
			MAX-ACCESS read-write
			STATUS current
			DESCRIPTION 
				"This object indicates the outbound peak information rate (PIR) of the SSID. The default value is 0 kbit/s. Invalid value is 1 to 63."
			::= { hwSsidProfileEntry 29 }

		 --1.3.6.1.4.1.2011.6.139.11.1.21.1.30
		hwSsidOutboundCarCbs OBJECT-TYPE
			SYNTAX Unsigned32 (0..4294967295)
			MAX-ACCESS read-write
			STATUS current
			DESCRIPTION 
				"This object indicates the outbound committed burst size (CBS) of the SSID. The default value is 0 bytes. Invalid value is 1 to 1499."
			::= { hwSsidProfileEntry 30 }

		 --1.3.6.1.4.1.2011.6.139.11.1.21.1.31
		hwSsidOutboundCarPbs OBJECT-TYPE
			SYNTAX Unsigned32 (0..4294967295)
			MAX-ACCESS read-write
			STATUS current
			DESCRIPTION 
				"This object indicates the outbound peak burst size (PBS) of the SSID. The default value is 0 bytes. Invalid value is 1 to 1499."
			::= { hwSsidProfileEntry 31 }

		 --1.3.6.1.4.1.2011.6.139.11.1.21.1.32
		hwSsidProfileRowStatus OBJECT-TYPE
			SYNTAX RowStatus
			MAX-ACCESS read-write
			STATUS current
			DESCRIPTION 
				"Description."
			::= { hwSsidProfileEntry 32 }

		-- 1.3.6.1.4.1.2011.6.139.11.1.21.1.33
		hwSsidHideWhileReachMaxSta OBJECT-TYPE
			SYNTAX INTEGER
				{
				advertiseSSID(1),
				hideSSID(2),
				replaceBasedOnPriority(3)
				}
			MAX-ACCESS read-write
			STATUS current
			DESCRIPTION
				"This object indicates the disposal method when the number of stations reaches the specified threshold. The default value is 2."
			::= { hwSsidProfileEntry 33 }
			
		
			
		 --1.3.6.1.4.1.2011.6.139.11.1.21.1.34
		hwSsidBeacon2gRate OBJECT-TYPE
			SYNTAX INTEGER
				{
				one(1),
				two(2),
				five(5),
				six(6),
				nine(9),
				eleven(11),
				twelve(12),
				eighteen(18),
				twentyfour(24),
				thirtysix(36),
				fortyeight (48),
				fiftyfour(54)
				}
			MAX-ACCESS read-write
			STATUS current
			DESCRIPTION 
				"Description."
			::= { hwSsidProfileEntry 34 }
			
		 --1.3.6.1.4.1.2011.6.139.11.1.21.1.35
		hwSsidBeacon5gRate OBJECT-TYPE
			SYNTAX INTEGER
				{
				six(6),
				nine(9),
				twelve(12),
				eighteen(18),
				twentyfour(24),
				thirtysix(36),
				fortyeight (48),
				fiftyfour(54)
				}
			MAX-ACCESS read-write
			STATUS current
			DESCRIPTION 
				"Description."
			::= { hwSsidProfileEntry 35 }
			
		 --1.3.6.1.4.1.2011.6.139.11.1.21.1.36
		hwSsidDenyBroadcastProbe OBJECT-TYPE
			SYNTAX INTEGER
				{
				disable(1) ,
				enable(2)
				}
			MAX-ACCESS read-write
			STATUS current
			DESCRIPTION 
				"Description."
			::= { hwSsidProfileEntry 36 }

		  --1.3.6.1.4.1.2011.6.139.11.1.21.1.37
		hwSsidProbeResponseRetry OBJECT-TYPE
			SYNTAX  Unsigned32 (0..3)
			MAX-ACCESS read-write
			STATUS current
			DESCRIPTION 
				"Description."
			::= { hwSsidProfileEntry 37 }


		
		-- 1.3.6.1.4.1.2011.6.139.11.1.21.1.38
		hwSsidUapsd OBJECT-TYPE
			SYNTAX INTEGER
				{
				disable(1),
				enable(2)
				}
			MAX-ACCESS read-write
			STATUS current
			DESCRIPTION
				"Description."
			::= { hwSsidProfileEntry 38 }

		
		-- 1.3.6.1.4.1.2011.6.139.11.1.21.1.39
		hwSsidActiveDullClient OBJECT-TYPE
			SYNTAX INTEGER
				{
				disable(1),
				enable(2)
				}
			MAX-ACCESS read-write
			STATUS current
			DESCRIPTION
				"Description."
			::= { hwSsidProfileEntry 39 }
		
		-- 1.3.6.1.4.1.2011.6.139.11.1.21.1.40
		hwSsidMuMIMOSwitch OBJECT-TYPE
			SYNTAX INTEGER
				{
				disable(1),
				enable(2)
				}
			MAX-ACCESS read-write
			STATUS current
			DESCRIPTION
				"Description."
			::= { hwSsidProfileEntry 40 }

		-- 1.3.6.1.4.1.2011.6.139.11.1.21.1.41
		hwSsidProfile80211rEnable OBJECT-TYPE
			SYNTAX INTEGER
				{
				disable(1),
				enable(2)
				}
			MAX-ACCESS read-write
			STATUS current
			DESCRIPTION
				"This object indicates the switch of 802.11r."
			::= { hwSsidProfileEntry 41 }
		
		-- 1.3.6.1.4.1.2011.6.139.11.1.21.1.42
		hwSsidProfile80211rMode OBJECT-TYPE
			SYNTAX INTEGER
				{
				unknown(0),
				overtheair (1),
				overtheds(2)
				}
			MAX-ACCESS read-write
			STATUS current
			DESCRIPTION
				"This object indicates the mode of 802.11r."
			::= { hwSsidProfileEntry 42 }
		
		-- 1.3.6.1.4.1.2011.6.139.11.1.21.1.43
		hwSsidProfile80211rReassociateTimeout OBJECT-TYPE
			SYNTAX Integer32 (0..10)
			MAX-ACCESS read-write
			STATUS current
			DESCRIPTION
				"This object indicates the reassociate timeout of 802.11r."
			::= { hwSsidProfileEntry 43 }

		-- 1.3.6.1.4.1.2011.6.139.11.1.21.1.44
		hwSsidQbssLoadSwitch OBJECT-TYPE
			SYNTAX INTEGER
				{
				disable(1),
				enable(2)
				}
			MAX-ACCESS read-write
			STATUS current
			DESCRIPTION
				"This object indicates the qbss load switch of VAP."
			::= { hwSsidProfileEntry 44 }

		-- 1.3.6.1.4.1.2011.6.139.11.1.21.1.45
		hwSsidSingleTxchainSwitch OBJECT-TYPE
			SYNTAX INTEGER
				{
				disable(1),
				enable(2)
				}
			MAX-ACCESS read-write
			STATUS current
			DESCRIPTION
				"This object indicates the single txchain switch of VAP."
			::= { hwSsidProfileEntry 45 }

		-- 1.3.6.1.4.1.2011.6.139.11.1.21.1.46
		hwSsidMuMIMOOptimizeSwitch OBJECT-TYPE
			SYNTAX INTEGER
				{
				disable(1),
				enable(2)
				}
			MAX-ACCESS read-write
			STATUS current
			DESCRIPTION
				"Description."
			::= { hwSsidProfileEntry 46 }
			
		-- 1.3.6.1.4.1.2011.6.139.11.1.21.1.47
		hwSsidAdvertiseApNameSwitch OBJECT-TYPE
			SYNTAX INTEGER
				{
				disable(1),
				enable(2)
				}
			MAX-ACCESS read-write
			STATUS current
			DESCRIPTION
				"Description."
			::= { hwSsidProfileEntry 47 }
			
		-- 1.3.6.1.4.1.2011.6.139.11.1.21.1.48
		hwSsidServiceGuarantee OBJECT-TYPE
			SYNTAX INTEGER
				{
				performanceFirst(1),
				reliabilityFirst(2)
				}
			MAX-ACCESS read-write
			STATUS current
			DESCRIPTION
				"This object indicates the service guarantee switch of VAP."
			DEFVAL { performanceFirst }
			::= { hwSsidProfileEntry 48 }

                                       -- 1.3.6.1.4.1.2011.6.139.11.1.21.1.49
		hwSsidInterAcRoamSwitch OBJECT-TYPE
			SYNTAX INTEGER
				{
				enable(1),
				disable(2)
				}
			MAX-ACCESS read-write
			STATUS current
			DESCRIPTION
				"This object indicates the inter-ac roam switch of SSID."
			::= { hwSsidProfileEntry 49 }
		-- 1.3.6.1.4.1.2011.6.139.11.1.21.1.50
		hwSsidVhtTxNssCount OBJECT-TYPE
			SYNTAX Unsigned32 (1..8 | 255)
			MAX-ACCESS read-write
			STATUS current
			DESCRIPTION
				"This object indicates the maximum number of VHT TX spatial streams."
			::= { hwSsidProfileEntry 50 }
		-- 1.3.6.1.4.1.2011.6.139.11.1.21.1.51
		hwSsidVhtRxNssCount OBJECT-TYPE
			SYNTAX Unsigned32 (1..8 | 255)
			MAX-ACCESS read-write
			STATUS current
			DESCRIPTION
				"This object indicates the maximum number of VHT RX spatial streams."
			::= { hwSsidProfileEntry 51 }
		-- 1.3.6.1.4.1.2011.6.139.11.1.21.1.52
		hwSsidVhtTxMcsMap OBJECT-TYPE
			SYNTAX Unsigned32 (7..9 | 255)
			MAX-ACCESS read-write
			STATUS current
			DESCRIPTION
				"This object indicates the maximum VHT TX MCS value."
			::= { hwSsidProfileEntry 52 }
		-- 1.3.6.1.4.1.2011.6.139.11.1.21.1.53
		hwSsidVhtRxMcsMap OBJECT-TYPE
			SYNTAX Unsigned32 (7..9 | 255)
			MAX-ACCESS read-write
			STATUS current
			DESCRIPTION
				"This object indicates the maximum VHT RX MCS value."
			::= { hwSsidProfileEntry 53 }
		-- 1.3.6.1.4.1.2011.6.139.11.1.21.1.54
		hwSsidHETxNssCount OBJECT-TYPE
			SYNTAX Unsigned32 (1..8)
			MAX-ACCESS read-write
			STATUS current
			DESCRIPTION
				"This object indicates the maximum number of HE TX spatial streams."
			::= { hwSsidProfileEntry 54 }
		-- 1.3.6.1.4.1.2011.6.139.11.1.21.1.55
		hwSsidHERxNssCount OBJECT-TYPE
			SYNTAX Unsigned32 (1..8)
			MAX-ACCESS read-write
			STATUS current
			DESCRIPTION
				"This object indicates the maximum number of HE RX spatial streams."
			::= { hwSsidProfileEntry 55 }
		-- 1.3.6.1.4.1.2011.6.139.11.1.21.1.56
		hwSsidHETxMcsMap OBJECT-TYPE
			SYNTAX Unsigned32 (7 | 9 | 11)
			MAX-ACCESS read-write
			STATUS current
			DESCRIPTION
				"This object indicates the maximum HE TX MCS value."
			::= { hwSsidProfileEntry 56 }
		-- 1.3.6.1.4.1.2011.6.139.11.1.21.1.57
		hwSsidHERxMcsMap OBJECT-TYPE
			SYNTAX Unsigned32 (7 | 9 | 11)
			MAX-ACCESS read-write
			STATUS current
			DESCRIPTION
				"This object indicates the maximum HE RX MCS value."
			::= { hwSsidProfileEntry 57 }
		-- 1.3.6.1.4.1.2011.6.139.11.1.21.1.58
		hwSsidBeamformingSwitch OBJECT-TYPE
			SYNTAX INTEGER
				{
				disable (1),
				enable(2)
				}
			MAX-ACCESS read-write
			STATUS current
			DESCRIPTION
				"This object indicates the transmit beamforming switch of SSID. The default value is 2."
			::= { hwSsidProfileEntry 58 }
			
		-- 1.3.6.1.4.1.2011.6.139.11.1.21.1.59
		hwSsidProfilePartialMumimoDownlinkSwitch OBJECT-TYPE
			SYNTAX INTEGER
				{
				disable(1),
				enable(2)
				}
			MAX-ACCESS read-write
			STATUS current
			DESCRIPTION
				"This object indicates whether to enable the partial-mu-mimo downlink function. The default value is 2."
			::= { hwSsidProfileEntry 59 }
			
		-- 1.3.6.1.4.1.2011.6.139.11.1.21.1.60
		hwSsidProfileOfdmaDownlinkSwitch OBJECT-TYPE
			SYNTAX INTEGER
				{
				disable(1),
				enable(2)
				}
			MAX-ACCESS read-write
			STATUS current
			DESCRIPTION
				"This object indicates whether to enable the OFDMA downlink function. The default value is 2."
			::= { hwSsidProfileEntry 60 }
		
		-- 1.3.6.1.4.1.2011.6.139.11.1.21.1.61
		hwSsidProfileOfdmaUplinkSwitch OBJECT-TYPE
			SYNTAX INTEGER
				{
				disable(1),
				enable(2)
				}
			MAX-ACCESS read-write
			STATUS current
			DESCRIPTION
				"This object indicates whether to enable the OFDMA uplink function. The default value is 2."
			::= { hwSsidProfileEntry 61 }		
		
		-- 1.3.6.1.4.1.2011.6.139.11.1.21.1.62
		hwSsidTwtSwitch OBJECT-TYPE
			SYNTAX INTEGER
				{
				disable(1),
				enable(2)
				}
			MAX-ACCESS read-write
			STATUS current
			DESCRIPTION
				"This object indicates whether to enable the twt function. The default value is 1."
			::= { hwSsidProfileEntry 62 }		

		-- 1.3.6.1.4.1.2011.6.139.11.1.21.1.63
		hwSsidProfile80211rPrivateSwitch OBJECT-TYPE
			SYNTAX INTEGER
				{
				disable(1),
				enable(2)
				}
			MAX-ACCESS read-write
			STATUS current
			DESCRIPTION
				"This object indicates if 11r private is enabled. The default value is 1."
			::= { hwSsidProfileEntry 63 }

		-- 1.3.6.1.4.1.2011.6.139.11.1.22
		hwSecurityProfileTable OBJECT-TYPE
			SYNTAX SEQUENCE OF HwSecurityProfileEntry
			MAX-ACCESS not-accessible
			STATUS current
			DESCRIPTION
				"This table is used to describe the information of a security profile."
			::= { hwWlanConfigObjects 22 }

		--1.3.6.1.4.1.2011.6.139.11.1.22.1
		hwSecurityProfileEntry OBJECT-TYPE
			SYNTAX HwSecurityProfileEntry 
			MAX-ACCESS not-accessible
			STATUS current
			DESCRIPTION 
				"The index of this table is hwSecurityProfileName."
			INDEX { hwSecurityProfileName }
			::= { hwSecurityProfileTable 1 }


		HwSecurityProfileEntry ::=
			SEQUENCE {				
				hwSecurityProfileName
					OCTET STRING,
				hwSecurityPolicy
					INTEGER,
				hwSecurityWepEncrypt
					Unsigned32,
				hwSecurityWepPskMode
					Unsigned32,
				hwSecurityWepPsk1
					OCTET STRING,
				hwSecurityWepPsk2
					OCTET STRING,
				hwSecurityWepPsk3
					OCTET STRING,
				hwSecurityWepPsk4
					OCTET STRING,
				hwSecurityWepDefaultKeyId
					Unsigned32,
				hwSecurityWpaEncrypt
					INTEGER,
				hwSecurityWpaPskMode
					INTEGER,
				hwSecurityWpaPsk
					OCTET STRING,
				hwSecurityWpaPtkUpdateSwitch
					INTEGER,
				hwSecurityWpaPtkUpdateInterval
					Unsigned32,
				hwSecurityWapiPskMode
					INTEGER,
				hwSecurityWapiPsk
					OCTET STRING,
				hwSecurityWapiAsuIpAddress
					IpAddress,
				hwSecurityWapiIssuerCertFileName
					OCTET STRING,
				hwSecurityWapiAsuCertFileName
					OCTET STRING,
				hwSecurityWapiAcCertFileName
					OCTET STRING,
				hwSecurityWapiAcPrvKeyFileName
					OCTET STRING,
				hwSecurityWapiIssuerPfxPassword
					OCTET STRING,
				hwSecurityWapiAsuPfxPassword
					OCTET STRING,
				hwSecurityWapiAcPfxPassword
					OCTET STRING,
				hwSecurityWapiAcPrvKeyPassword
					OCTET STRING,
				hwSecurityWapiCertRetransCount
					Unsigned32,
				hwSecurityWapiBkThreshold
					Unsigned32,
				hwSecurityWapiBkLifetime
					Unsigned32,
				hwSecurityWapiUskUpdateMethod
					INTEGER,
				hwSecurityWapiMskUpdateMethod
					INTEGER,
				hwSecurityWapiUskUpdateInterval
					Unsigned32,
				hwSecurityWapiUskUpdatePackets
					Unsigned32,
				hwSecurityWapiUskRetansCount
					Unsigned32,
				hwSecurityWapiMskUpdateInterval
					Unsigned32,
				hwSecurityWapiMskUpdatePackets
					Unsigned32,
				hwSecurityWapiMskRetansCount
					Unsigned32,
				hwSecurityWapiSATimeout
					Unsigned32,
				hwSecurityPMF
					Unsigned32,
				hwSecurityProfileRowStatus
					RowStatus,
 				hwSecurityWepDot1xMode
					Unsigned32
			 }

		 --1.3.6.1.4.1.2011.6.139.11.1.22.1.1
		hwSecurityProfileName OBJECT-TYPE
			SYNTAX OCTET STRING (SIZE (1..35))
			MAX-ACCESS not-accessible
			STATUS current
			DESCRIPTION 
				"This object indicates the name of a security profile. It is the index of the table."
			::= { hwSecurityProfileEntry 1 }

         --1.3.6.1.4.1.2011.6.139.11.1.22.1.2
        hwSecurityPolicy OBJECT-TYPE
            SYNTAX INTEGER
                {
                wapiCert(1),
                wapiPsk(2),
                wpaDot1x(3),
                wpaPsk(4),
                wpa2Dot1x(5),
                wpa2Psk(6),
                wepShareKey(7),
                open(8),
                wpaWpa2Psk(9),
                wpaWpa2Dot1x(10),
                wepNoauth(11),
                wepDynamic(12),
                wpaPpsk(13),
                wpa2Ppsk(14),
                wpaWpa2Ppsk(15),
                wpa3Sae(16),
                wpa2Wpa3PskSae(17),
                wpa3Dot1x(18)
                }
            MAX-ACCESS read-write
            STATUS current
            DESCRIPTION
                "This object indicates the air interface authentication policy. The default value is 8(open)."
            ::= { hwSecurityProfileEntry 2 }

		 --1.3.6.1.4.1.2011.6.139.11.1.22.1.3
		hwSecurityWepEncrypt OBJECT-TYPE
			SYNTAX Unsigned32 (0..65535)
			MAX-ACCESS read-write
			STATUS current
			DESCRIPTION 
				"This object indicates the WEP encryption algorithm. The default value is 4369."
			::= { hwSecurityProfileEntry 3 }

		 --1.3.6.1.4.1.2011.6.139.11.1.22.1.4
		hwSecurityWepPskMode OBJECT-TYPE
			SYNTAX Unsigned32 (0..65535)
			MAX-ACCESS read-write
			STATUS current
			DESCRIPTION 
				"This object indicates that the WEP PSK mode is PassPhase or Hex. The default value is 4369."
			::= { hwSecurityProfileEntry 4 }

		 --1.3.6.1.4.1.2011.6.139.11.1.22.1.5
		hwSecurityWepPsk1 OBJECT-TYPE
			SYNTAX OCTET STRING (SIZE (1..68))
			MAX-ACCESS read-write
			STATUS current
			DESCRIPTION 
				"This object indicates the WEP PSK1."
			::= { hwSecurityProfileEntry 5 }

		 --1.3.6.1.4.1.2011.6.139.11.1.22.1.6
		hwSecurityWepPsk2 OBJECT-TYPE
			SYNTAX OCTET STRING (SIZE (1..68))
			MAX-ACCESS read-write
			STATUS current
			DESCRIPTION 
				"This object indicates the WEP PSK2."
			::= { hwSecurityProfileEntry 6 }

		 --1.3.6.1.4.1.2011.6.139.11.1.22.1.7
		hwSecurityWepPsk3 OBJECT-TYPE
			SYNTAX OCTET STRING (SIZE (1..68))
			MAX-ACCESS read-write
			STATUS current
			DESCRIPTION 
				"This object indicates the WEP PSK3."
			::= { hwSecurityProfileEntry 7 }

		 --1.3.6.1.4.1.2011.6.139.11.1.22.1.8
		hwSecurityWepPsk4 OBJECT-TYPE
			SYNTAX OCTET STRING (SIZE (1..68))
			MAX-ACCESS read-write
			STATUS current
			DESCRIPTION 
				"This object indicates the WEP PSK4."
			::= { hwSecurityProfileEntry 8 }

		 --1.3.6.1.4.1.2011.6.139.11.1.22.1.9
		hwSecurityWepDefaultKeyId OBJECT-TYPE
			SYNTAX Unsigned32 (1..4)
			MAX-ACCESS read-write
			STATUS current
			DESCRIPTION 
				"This object indicates the default key ID for WEP. The default value is 1."
			::= { hwSecurityProfileEntry 9 }

		 --1.3.6.1.4.1.2011.6.139.11.1.22.1.10
		hwSecurityWpaEncrypt OBJECT-TYPE
			SYNTAX INTEGER
				{
				unknown(0),
				wpaAes(1),
				wpaTkip(2),
				wpaAesTkip(3),
				wpaTkipWpa2Aes(4),
                                                                             wpaGcmp256(5)
				}
			MAX-ACCESS read-write
			STATUS current
			DESCRIPTION 
				"This object indicates the WPA/WPA2/WPA3 encryption algorithm."
			::= { hwSecurityProfileEntry 10 }

		 --1.3.6.1.4.1.2011.6.139.11.1.22.1.11
		hwSecurityWpaPskMode OBJECT-TYPE
			SYNTAX INTEGER
				{
				pskPassphase(1),
				pskHex(2)
				}
			MAX-ACCESS read-write
			STATUS current
			DESCRIPTION 
				"This object indicates whether the WPA PSK mode is PassPhase or Hex."
			::= { hwSecurityProfileEntry 11 }

		 --1.3.6.1.4.1.2011.6.139.11.1.22.1.12
		hwSecurityWpaPsk OBJECT-TYPE
			SYNTAX OCTET STRING (SIZE (0|6|8..108))
			MAX-ACCESS read-write
			STATUS current
			DESCRIPTION 
				"This object indicates the WPA/WPA2 PSK."
			::= { hwSecurityProfileEntry 12 }

		 --1.3.6.1.4.1.2011.6.139.11.1.22.1.13
		hwSecurityWpaPtkUpdateSwitch OBJECT-TYPE
			SYNTAX INTEGER
				{
				disable(1) ,
				enable(2)
				}
			MAX-ACCESS read-write
			STATUS current
			DESCRIPTION 
				"This object indicates the status of WPA PTK update function. The default value is 1."
			::= { hwSecurityProfileEntry 13 }

		 --1.3.6.1.4.1.2011.6.139.11.1.22.1.14
		hwSecurityWpaPtkUpdateInterval OBJECT-TYPE
			SYNTAX Unsigned32 (43200..86400)
			MAX-ACCESS read-write
			STATUS current
			DESCRIPTION 
				"This object indicates the WPA PTK update interval. The default value is 43200 seconds."
			::= { hwSecurityProfileEntry 14 }

		 --1.3.6.1.4.1.2011.6.139.11.1.22.1.15
		hwSecurityWapiPskMode OBJECT-TYPE
			SYNTAX INTEGER
				{
				pskPassphase(1),
				pskHex(2)
				}
			MAX-ACCESS read-write
			STATUS current
			DESCRIPTION
				"This object indicates the WAPI PSK mode. The default value is 1. 1:pskPassphase 2:pskHex."
			::= { hwSecurityProfileEntry 15 }
		

		-- 1.3.6.1.4.1.2011.6.139.11.1.22.1.16
		hwSecurityWapiPsk OBJECT-TYPE
			SYNTAX OCTET STRING (SIZE (0|6|8..108))
			MAX-ACCESS read-write
			STATUS current
			DESCRIPTION 
				"This object indicates the WAPI PSK."
			::= { hwSecurityProfileEntry 16 }
		

		-- 1.3.6.1.4.1.2011.6.139.11.1.22.1.17
		hwSecurityWapiAsuIpAddress OBJECT-TYPE
			SYNTAX IpAddress
			MAX-ACCESS read-write
			STATUS current
			DESCRIPTION
				"This object indicates the IP address of the WAPI ASU."
			::= { hwSecurityProfileEntry 17 }

		 --1.3.6.1.4.1.2011.6.139.11.1.22.1.18
		hwSecurityWapiIssuerCertFileName OBJECT-TYPE
			SYNTAX OCTET STRING (SIZE (0..255))
			MAX-ACCESS read-write
			STATUS current
			DESCRIPTION 
				"This object indicates the certificate file name of the WAPI issuer."
			::= { hwSecurityProfileEntry 18 }

		 --1.3.6.1.4.1.2011.6.139.11.1.22.1.19
		hwSecurityWapiAsuCertFileName OBJECT-TYPE
			SYNTAX OCTET STRING (SIZE (0..255))
			MAX-ACCESS read-write
			STATUS current
			DESCRIPTION 
				"This object indicate the certificate file name of the WAPI ASU."
			::= { hwSecurityProfileEntry 19 }

		 --1.3.6.1.4.1.2011.6.139.11.1.22.1.20
		hwSecurityWapiAcCertFileName OBJECT-TYPE
			SYNTAX OCTET STRING (SIZE (0..255))
			MAX-ACCESS read-write
			STATUS current
			DESCRIPTION 
				"This object indicate the certificate file name of the WAPI AC."
			::= { hwSecurityProfileEntry 20 }

		 --1.3.6.1.4.1.2011.6.139.11.1.22.1.21
		hwSecurityWapiAcPrvKeyFileName OBJECT-TYPE
			SYNTAX OCTET STRING (SIZE (0..255))
			MAX-ACCESS read-write
			STATUS current
			DESCRIPTION 
				"This object indicates the private key file name of the WAPI AC."
			::= { hwSecurityProfileEntry 21 }

		 --1.3.6.1.4.1.2011.6.139.11.1.22.1.22
		hwSecurityWapiIssuerPfxPassword OBJECT-TYPE
			SYNTAX OCTET STRING (SIZE (0..68))
			MAX-ACCESS read-write
			STATUS current
			DESCRIPTION 
				"This object indicates the WAPI issuer certificate key."
			::= { hwSecurityProfileEntry 22 }

		 --1.3.6.1.4.1.2011.6.139.11.1.22.1.23
		hwSecurityWapiAsuPfxPassword OBJECT-TYPE
			SYNTAX OCTET STRING (SIZE (0..68))
			MAX-ACCESS read-write
			STATUS current
			DESCRIPTION 
				"This object indicates the WAPI ASU certificate key."
			::= { hwSecurityProfileEntry 23 }

		 --1.3.6.1.4.1.2011.6.139.11.1.22.1.24
		hwSecurityWapiAcPfxPassword OBJECT-TYPE
			SYNTAX OCTET STRING (SIZE (0..68))
			MAX-ACCESS read-write
			STATUS current
			DESCRIPTION 
				"This object indicates the WAPI AC certificate key."
			::= { hwSecurityProfileEntry 24 }

		 --1.3.6.1.4.1.2011.6.139.11.1.22.1.25
		hwSecurityWapiAcPrvKeyPassword OBJECT-TYPE
			SYNTAX OCTET STRING (SIZE (0..68))
			MAX-ACCESS read-write
			STATUS current
			DESCRIPTION 
				"This object indicates the key for reading the AC private key file."
			::= { hwSecurityProfileEntry 25 }

		 --1.3.6.1.4.1.2011.6.139.11.1.22.1.26
		hwSecurityWapiCertRetransCount OBJECT-TYPE
			SYNTAX Unsigned32 (1..10)
			MAX-ACCESS read-write
			STATUS current
			DESCRIPTION 
				"This object indicates the number of retransmissions of WAPI certificate authentication packets. The default value is 3."
			::= { hwSecurityProfileEntry 26 }

		 --1.3.6.1.4.1.2011.6.139.11.1.22.1.27
		hwSecurityWapiBkThreshold OBJECT-TYPE
			SYNTAX Unsigned32 (1..100)
			MAX-ACCESS read-write
			STATUS current
			DESCRIPTION
				"This object indicates the WAPI BK lifetime percentage. The default value is 70."
			::= { hwSecurityProfileEntry 27 }
		

		-- 1.3.6.1.4.1.2011.6.139.11.1.22.1.28
		hwSecurityWapiBkLifetime OBJECT-TYPE
			SYNTAX Unsigned32 (600..604800)
			MAX-ACCESS read-write
			STATUS current
			DESCRIPTION
				"This object indicates the interval for updating the WAPI BK. The default value is 43200 seconds."
			::= { hwSecurityProfileEntry 28 }
		

		 --1.3.6.1.4.1.2011.6.139.11.1.22.1.29
		hwSecurityWapiUskUpdateMethod OBJECT-TYPE
			SYNTAX INTEGER
				{
				disabled(1) ,
				timeBased(2) ,
				packetBased(3) ,
				timepacketBased(4)
				}
			MAX-ACCESS read-write
			STATUS current
			DESCRIPTION 
				"This object indicates the WAPI USK update mode. The default value is 2."
			::= { hwSecurityProfileEntry 29 }

		 --1.3.6.1.4.1.2011.6.139.11.1.22.1.30
		hwSecurityWapiMskUpdateMethod OBJECT-TYPE
			SYNTAX INTEGER
				{
				disabled(1) ,
				timeBased(2) ,
				packetBased(3) ,
				timepacketBased(4)
				}
			MAX-ACCESS read-write
			STATUS current
			DESCRIPTION 
				"This object indicates the WAPI MSK update mode. The default value is 2."
			::= { hwSecurityProfileEntry 30 }

		 --1.3.6.1.4.1.2011.6.139.11.1.22.1.31
		hwSecurityWapiUskUpdateInterval OBJECT-TYPE
			SYNTAX Unsigned32 (600..604800)
			MAX-ACCESS read-write
			STATUS current
			DESCRIPTION 
				"This object indicates the time-based interval for updating the WAPI USK. The default value is 86400 seconds."
			::= { hwSecurityProfileEntry 31 }

		 --1.3.6.1.4.1.2011.6.139.11.1.22.1.32
		hwSecurityWapiUskUpdatePackets OBJECT-TYPE
			SYNTAX Unsigned32 (1..4200000)
			MAX-ACCESS read-write
			STATUS current
			DESCRIPTION 
				"This object indicates the number of packets that will trigger WAPI USK update. The default value is 10."
			::= { hwSecurityProfileEntry 32 }

		 --1.3.6.1.4.1.2011.6.139.11.1.22.1.33
		hwSecurityWapiUskRetansCount OBJECT-TYPE
			SYNTAX Unsigned32 (1..10)
			MAX-ACCESS read-write
			STATUS current
			DESCRIPTION 
				"This object indicates the maximum number of retransmissions of a WAPI USK negotiation packet. The default value is 3."
			::= { hwSecurityProfileEntry 33 }

		 --1.3.6.1.4.1.2011.6.139.11.1.22.1.34
		hwSecurityWapiMskUpdateInterval OBJECT-TYPE
			SYNTAX Unsigned32 (600..604800)
			MAX-ACCESS read-write
			STATUS current
			DESCRIPTION 
				"This object indicates the time-based interval for updating the WAPI MSK. The default value is 86400 seconds."
			::= { hwSecurityProfileEntry 34 }

		 --1.3.6.1.4.1.2011.6.139.11.1.22.1.35
		hwSecurityWapiMskUpdatePackets OBJECT-TYPE
			SYNTAX Unsigned32 (1..4200000)
			MAX-ACCESS read-write
			STATUS current
			DESCRIPTION 
				"This object indicates the number of packets that will trigger WAPI MSK update. The default value is 10."
			::= { hwSecurityProfileEntry 35 }

		 --1.3.6.1.4.1.2011.6.139.11.1.22.1.36
		hwSecurityWapiMskRetansCount OBJECT-TYPE
			SYNTAX Unsigned32 (1..10)
			MAX-ACCESS read-write
			STATUS current
			DESCRIPTION 
				"This object indicates the maximum number of retransmissions of a WAPI MSK negotiation packet. The default value is 3."
			::= { hwSecurityProfileEntry 36 }

		 --1.3.6.1.4.1.2011.6.139.11.1.22.1.37
		hwSecurityWapiSATimeout OBJECT-TYPE
			SYNTAX Unsigned32 (1..255)
			MAX-ACCESS read-write
			STATUS current
			DESCRIPTION 
				"This object indicates the timeout period of a WAPI-based security association (SA). The default value is 60 seconds."
			::= { hwSecurityProfileEntry 37 }

		 --1.3.6.1.4.1.2011.6.139.11.1.22.1.38
		hwSecurityPMF OBJECT-TYPE
			SYNTAX Unsigned32 (1..3)
			MAX-ACCESS read-write
			STATUS current
			DESCRIPTION
				"This object indicates the status of the PMF function. The default value is 1."
			::= { hwSecurityProfileEntry 38 }
		hwSecurityProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwSecurityProfileEntry 39 }

		 --1.3.6.1.4.1.2011.6.139.11.1.22.1.40
		hwSecurityWepDot1xMode OBJECT-TYPE
			SYNTAX Unsigned32
			MAX-ACCESS read-write
			STATUS current
			DESCRIPTION 
				"This object indicates that the WEP DOT1X key mode is wep40, wep104 or wep128. The default value is 0.bit0~3:key0;bit4~bit7:key1;bit8~bit11:key2;bit12~bit16:key3.0:invalid;1:wep40;2:wep104;3:wep128."
			::= { hwSecurityProfileEntry 40 }

		--1.3.6.1.4.1.2011.6.139.11.1.23
		hwAPTrafficProfileTable OBJECT-TYPE
			SYNTAX SEQUENCE OF HwAPTrafficProfileEntry 
			MAX-ACCESS not-accessible
			STATUS current
			DESCRIPTION 
				"This table is used to configure and query traffic profile parameters."
			::= { hwWlanConfigObjects 23 }

		--1.3.6.1.4.1.2011.6.139.11.1.23.1
		hwAPTrafficProfileEntry OBJECT-TYPE
			SYNTAX HwAPTrafficProfileEntry 
			MAX-ACCESS not-accessible
			STATUS current
			DESCRIPTION 
				"The index of this table is hwAPTrafficProfileName."
			INDEX { hwAPTrafficProfileName }
			::= { hwAPTrafficProfileTable 1 }


		HwAPTrafficProfileEntry ::=
			SEQUENCE {				
				hwAPTrafficProfileName
					OCTET STRING,
				hwAPTrafficProfilePriorityMapDnTrustMode
					INTEGER,
				hwAPTrafficProfilePriorityDscpDnMap80211e
					OCTET STRING,
				hwAPTrafficProfilePriority80211eUpMapDscp
					OCTET STRING,
				hwAPTrafficProfileUserIsolate
					INTEGER,
				hwAPTrafficProfileRateLimitClientUp
					Unsigned32,
				hwAPTrafficProfileRateLimitClientDn
					Unsigned32,
				hwAPTrafficProfileRateLimitVapUp
					Unsigned32,
				hwAPTrafficProfileRateLimitVapDn
					Unsigned32,
				hwAPTrafficProfileMldSnooping
					INTEGER,
				hwAPTrafficProfileIGMPSnooping
					INTEGER,
				hwAPTrafficProfileIGMPSnoopingReportSuppress
					INTEGER,
				hwAPTrafficProfileMcToUc
					INTEGER,
				hwAPTrafficProfileOptimizeSuppressionBc
					Unsigned32,
				hwAPTrafficProfileOptimizeSuppressionUc
					Unsigned32,
				hwAPTrafficProfileOptimizeSuppressionMc
					Unsigned32,
				hwAPTrafficProfileOptimizeTCPAdjustMSS
					Unsigned32,
				hwAPTrafficProfileOptimizeProxyARP
					INTEGER,
				hwAPTrafficProfileOptimizeProxyND
					INTEGER,
				hwAPTrafficProfileOptimizeUcSendARP
					INTEGER,
				hwAPTrafficProfileOptimizeUcSendND
					INTEGER,
				hwAPTrafficProfileOptimizeUcSendDHCP
					INTEGER,
				hwAPTrafficProfileOptimizeBcMcDenyAll
					INTEGER,
				hwAPTrafficProfileOptimizeStaBridgeForward
					INTEGER,
				hwAPTrafficProfileRowStatus
					RowStatus,
				hwAPTrafficProfilePriorityMapUpTrustMode
					INTEGER,
				hwAPTrafficProfilePriorityDscpUpMapDscp
					OCTET STRING,
				hwAPTrafficProfileOptimizeBcMcMismatchAct
					INTEGER,
				hwAPTrafficProfileMcToUcDynamicAdatptive
					INTEGER,
				hwAPTrafficProfileIGMPSnoopingMaxBandwidth
					Unsigned32,
				hwAPTrafficProfileIGMPSnoopingMaxUser
					Unsigned32,
				hwAPTrafficProfilePriorityDscpUpMap8021p
					OCTET STRING,
				hwAPTrafficProfilePriority80211eUpMap8021p
					OCTET STRING,
				hwAPTrafficProfilePriority8021pDnMap80211e
					OCTET STRING,
                hwAPTrafficProfilePriorityMapUpPayloadTrustMode
					INTEGER,
				hwAPTrafficProfileSvpVoice
					INTEGER,
				hwAPTrafficProfileRateLimitClientDynamic
					INTEGER,
				hwAPTrafficProfileRateLimitClientDynamicThr
					Unsigned32
			 }

		 --1.3.6.1.4.1.2011.6.139.11.1.23.1.1
		hwAPTrafficProfileName OBJECT-TYPE
			SYNTAX OCTET STRING (SIZE (1..35))
			MAX-ACCESS not-accessible
			STATUS current
			DESCRIPTION 
				"This object indicates the name of a traffic profile."
			::= { hwAPTrafficProfileEntry 1 }

		 --1.3.6.1.4.1.2011.6.139.11.1.23.1.2
		hwAPTrafficProfilePriorityMapDnTrustMode OBJECT-TYPE
			SYNTAX INTEGER
				{
				trustDSCP(1),
				trust8021P(2)
				}
			MAX-ACCESS read-write
			STATUS current
			DESCRIPTION 
				"This object indicates the downstream service priority mapping mode. The default value is 1."
			::= { hwAPTrafficProfileEntry 2 }

		 --1.3.6.1.4.1.2011.6.139.11.1.23.1.3
		hwAPTrafficProfilePriorityDscpDnMap80211e OBJECT-TYPE
			SYNTAX OCTET STRING (SIZE (1..256))
			MAX-ACCESS read-write
			STATUS current
			DESCRIPTION 
				"This object indicates the mapping relationship between 802.1p priorities of 802.3 packets and user priorities of 802.11 packets when data packets are sent to a downstream AP. DSCP values range from 0 to 63 and 802.11e priorities range from 0 to 7. Two mapped data are separated by a comma."
			::= { hwAPTrafficProfileEntry 3 }

		 --1.3.6.1.4.1.2011.6.139.11.1.23.1.4
		hwAPTrafficProfilePriority80211eUpMapDscp OBJECT-TYPE
			SYNTAX OCTET STRING (SIZE (1..256))
			MAX-ACCESS read-write
			STATUS current
			DESCRIPTION 
				"This object indicates the tunnel priority mappings when data packets are sent from APs to an AC. DSCP values range from 0 to 63 and 802.11e priorities range from 0 to 7. Two mapped data are separated by a comma."
			::= { hwAPTrafficProfileEntry 4 }

		 --1.3.6.1.4.1.2011.6.139.11.1.23.1.5
		hwAPTrafficProfileUserIsolate OBJECT-TYPE
			SYNTAX INTEGER
				{
				disable(1),
				l3Isolate(2),
				l2Isolate(3)
				}
			MAX-ACCESS read-write
			STATUS current
			DESCRIPTION 
				"This object indicates the user isolation mode. The default value is 1."
			::= { hwAPTrafficProfileEntry 5 }

		 --1.3.6.1.4.1.2011.6.139.11.1.23.1.6
		hwAPTrafficProfileRateLimitClientUp OBJECT-TYPE
			SYNTAX Unsigned32 (64..4294967295)
			MAX-ACCESS read-write
			STATUS current
			DESCRIPTION 
				"This object indicates the STA's uplink rate limit. The default value is 0xFFFFFFFF. It is expressed in kbit/s."
			::= { hwAPTrafficProfileEntry 6 }

		 --1.3.6.1.4.1.2011.6.139.11.1.23.1.7
		hwAPTrafficProfileRateLimitClientDn OBJECT-TYPE
			SYNTAX Unsigned32 (64..4294967295)
			MAX-ACCESS read-write
			STATUS current
			DESCRIPTION 
				"This object indicates the STA's downlink rate limit. The default value is 0xFFFFFFFF. It is expressed in kbit/s."
			::= { hwAPTrafficProfileEntry 7 }

		 --1.3.6.1.4.1.2011.6.139.11.1.23.1.8
		hwAPTrafficProfileRateLimitVapUp OBJECT-TYPE
			SYNTAX Unsigned32 (64..4294967295)
			MAX-ACCESS read-write
			STATUS current
			DESCRIPTION 
				"This object indicates the VAP's uplink rate limit. The default value is 0xFFFFFFFF. It is expressed in kbit/s."
			::= { hwAPTrafficProfileEntry 8 }

		 --1.3.6.1.4.1.2011.6.139.11.1.23.1.9
		hwAPTrafficProfileRateLimitVapDn OBJECT-TYPE
			SYNTAX Unsigned32 (64..4294967295)
			MAX-ACCESS read-write
			STATUS current
			DESCRIPTION 
				"This object indicates the VAP's downlink rate limit. The default value is 0xFFFFFFFF. It is expressed in kbit/s."
			::= { hwAPTrafficProfileEntry 9 }

		 --1.3.6.1.4.1.2011.6.139.11.1.23.1.10
		hwAPTrafficProfileMldSnooping OBJECT-TYPE
			SYNTAX INTEGER
				{
				disable(1) ,
				enable(2)
				}
			MAX-ACCESS read-write
			STATUS current
			DESCRIPTION 
				"This object indicates the status of the MLD snooping function. The default value is 1."
			::= { hwAPTrafficProfileEntry 10 }

		 --1.3.6.1.4.1.2011.6.139.11.1.23.1.11
		hwAPTrafficProfileIGMPSnooping OBJECT-TYPE
			SYNTAX INTEGER
				{
				disable(1) ,
				enable(2)
				}
			MAX-ACCESS read-write
			STATUS current
			DESCRIPTION 
				"This object indicates the status of the IGMP snooping function. The default value is 1."
			::= { hwAPTrafficProfileEntry 11 }

		 --1.3.6.1.4.1.2011.6.139.11.1.23.1.12
		hwAPTrafficProfileIGMPSnoopingReportSuppress OBJECT-TYPE
			SYNTAX INTEGER
				{
				disable(1) ,
				enable(2)
				}
			MAX-ACCESS read-write
			STATUS current
			DESCRIPTION 
				"This object indicates the status of the IGMP snooping report suppression function. The default value is 1."
			::= { hwAPTrafficProfileEntry 12 }

		 --1.3.6.1.4.1.2011.6.139.11.1.23.1.13
		hwAPTrafficProfileMcToUc OBJECT-TYPE
			SYNTAX INTEGER
				{
				disable(1) ,
				enable(2)
				}
			MAX-ACCESS read-write
			STATUS current
			DESCRIPTION 
				"This object indicates the status of the function of converting multicast to unicast. The default value is 1."
			::= { hwAPTrafficProfileEntry 13 }

		 --1.3.6.1.4.1.2011.6.139.11.1.23.1.14
		hwAPTrafficProfileOptimizeSuppressionBc OBJECT-TYPE
			SYNTAX Unsigned32 (0..14881000|4294967295)
			MAX-ACCESS read-write
			STATUS current
			DESCRIPTION 
				"This object indicates the information about broadcast storm suppression. The unit is pps. The default value is 0xFFFFFFFF, indicating that the broadcast storm suppression is not enabled."
			::= { hwAPTrafficProfileEntry 14 }

		 --1.3.6.1.4.1.2011.6.139.11.1.23.1.15
		hwAPTrafficProfileOptimizeSuppressionUc OBJECT-TYPE
			SYNTAX Unsigned32 (0..14881000|4294967295)
			MAX-ACCESS read-write
			STATUS current
			DESCRIPTION 
				"This object indicates the information about unknown unicast storm suppression. The unit is pps. The default value is 0xFFFFFFFF, indicating that the broadcast storm suppression is not enabled."
			::= { hwAPTrafficProfileEntry 15 }

		 --1.3.6.1.4.1.2011.6.139.11.1.23.1.16
		hwAPTrafficProfileOptimizeSuppressionMc OBJECT-TYPE
			SYNTAX Unsigned32 (0..14881000|4294967295)
			MAX-ACCESS read-write
			STATUS current
			DESCRIPTION 
				"This object indicates the information about multicast storm suppression. The unit is pps. The default value is 0xFFFFFFFF, indicating that the broadcast storm suppression is not enabled."
			::= { hwAPTrafficProfileEntry 16 }

		 --1.3.6.1.4.1.2011.6.139.11.1.23.1.17
		hwAPTrafficProfileOptimizeTCPAdjustMSS OBJECT-TYPE
			SYNTAX Unsigned32 (128..2048|4294967295)
			MAX-ACCESS read-write
			STATUS current
			DESCRIPTION 
				"This object indicates the information about the automatic MSS adjustment. The default value is 0xFFFFFFFF, indicating that this function is not enabled."
			::= { hwAPTrafficProfileEntry 17 }

		 --1.3.6.1.4.1.2011.6.139.11.1.23.1.18
		hwAPTrafficProfileOptimizeProxyARP OBJECT-TYPE
			SYNTAX INTEGER
				{
				disable(1) ,
				enable(2)
				}
			MAX-ACCESS read-write
			STATUS current
			DESCRIPTION 
				"This object indicates the status of the ARP proxy function. The default value is 1."
			::= { hwAPTrafficProfileEntry 18 }

		 --1.3.6.1.4.1.2011.6.139.11.1.23.1.19
		hwAPTrafficProfileOptimizeProxyND OBJECT-TYPE
			SYNTAX INTEGER
				{
				disable(1) ,
				enable(2)
				}
			MAX-ACCESS read-write
			STATUS current
			DESCRIPTION 
				"This object indicates the status of the ND proxy function. The default value is 1."
			::= { hwAPTrafficProfileEntry 19 }

		 --1.3.6.1.4.1.2011.6.139.11.1.23.1.20
		hwAPTrafficProfileOptimizeUcSendARP OBJECT-TYPE
			SYNTAX INTEGER
				{
				disable(1) ,
				enable(2)
				}
			MAX-ACCESS read-write
			STATUS current
			DESCRIPTION 
				"This object indicates the status of the unicast ARP function. The default value is 2."
			::= { hwAPTrafficProfileEntry 20 }

		 --1.3.6.1.4.1.2011.6.139.11.1.23.1.21
		hwAPTrafficProfileOptimizeUcSendND OBJECT-TYPE
			SYNTAX INTEGER
				{
				disable(1) ,
				enable(2)
				}
			MAX-ACCESS read-write
			STATUS current
			DESCRIPTION 
				"This object indicates the status of the unicast ND function. The default value is 2."
			::= { hwAPTrafficProfileEntry 21 }

		 --1.3.6.1.4.1.2011.6.139.11.1.23.1.22
		hwAPTrafficProfileOptimizeUcSendDHCP OBJECT-TYPE
			SYNTAX INTEGER
				{
				disable(1) ,
				enable(2)
				}
			MAX-ACCESS read-write
			STATUS current
			DESCRIPTION 
				"This object indicates the status of the unicast DHCP function. The default value is 1."
			::= { hwAPTrafficProfileEntry 22 }

		 --1.3.6.1.4.1.2011.6.139.11.1.23.1.23
		hwAPTrafficProfileOptimizeBcMcDenyAll OBJECT-TYPE
			SYNTAX INTEGER
				{
				disable(1) ,
				enable(2)
				}
			MAX-ACCESS read-write
			STATUS current
			DESCRIPTION 
				"After this function is enabled, other multicast packets, except for proxy response packets and multicast packets converted to unicast packets, are discarded. The default value is 1."
			::= { hwAPTrafficProfileEntry 23 }

		 --1.3.6.1.4.1.2011.6.139.11.1.23.1.24
		hwAPTrafficProfileOptimizeStaBridgeForward OBJECT-TYPE
			SYNTAX INTEGER
				{
				disable(1) ,
				enable(2)
				}
			MAX-ACCESS read-write
			STATUS current
			DESCRIPTION 
				"This object indicates the status of the STA bridge forwarding function. The default value is 2."
			::= { hwAPTrafficProfileEntry 24 }

		
		-- 1.3.6.1.4.1.2011.6.139.11.1.23.1.25
		hwAPTrafficProfileRowStatus OBJECT-TYPE
			SYNTAX RowStatus
			MAX-ACCESS read-create
			STATUS current
			DESCRIPTION
				"This object indicates the row status of this table. ROWSTATUS_CREATEANDFLOW and ROWSTATUS_DESTROY are commonly used."
			::= { hwAPTrafficProfileEntry 25 }

		
		-- 1.3.6.1.4.1.2011.6.139.11.1.23.1.26
		hwAPTrafficProfilePriorityMapUpTrustMode OBJECT-TYPE
			SYNTAX INTEGER
				{
				trust80211e(1),
				trustdscp(2)
				}
			MAX-ACCESS read-write
			STATUS current
			DESCRIPTION
				"This object indicates the tunnel priority mapping mode."
			::= { hwAPTrafficProfileEntry 26 }

		
		-- 1.3.6.1.4.1.2011.6.139.11.1.23.1.27
		hwAPTrafficProfilePriorityDscpUpMapDscp OBJECT-TYPE
			SYNTAX OCTET STRING (SIZE (1..256))
			MAX-ACCESS read-write
			STATUS current
			DESCRIPTION
				"This object indicates the mapping relationship between DSCP and DSCP. DSCP values range from 0 to 63. Two mapped data are separated by a comma."
			::= { hwAPTrafficProfileEntry 27 }
		
		-- 1.3.6.1.4.1.2011.6.139.11.1.23.1.28
		hwAPTrafficProfileOptimizeBcMcMismatchAct OBJECT-TYPE
			SYNTAX INTEGER
				{
				traverse(1),
				drop(2)
				}
			MAX-ACCESS read-write
			STATUS current
			DESCRIPTION
				"This object indicates the status of the bcmc unicast send mismacth action function. The default value is 2."
			::= { hwAPTrafficProfileEntry 28 }

		-- 1.3.6.1.4.1.2011.6.139.11.1.23.1.29
		hwAPTrafficProfileMcToUcDynamicAdatptive OBJECT-TYPE
			SYNTAX INTEGER
				{
				disable(1),
				enable(2)
				}
			MAX-ACCESS read-write
			STATUS current
			DESCRIPTION
				"This object indicates the status of the multicast to unicast dynamic adaptive function. The default value is 2."
			::= { hwAPTrafficProfileEntry 29 }

		-- 1.3.6.1.4.1.2011.6.139.11.1.23.1.30
		hwAPTrafficProfileIGMPSnoopingMaxBandwidth OBJECT-TYPE
			SYNTAX Unsigned32 (0..10000000)
			MAX-ACCESS read-write
			STATUS current
			DESCRIPTION
				"This object indicates the status of the IGMP snooping max bandwidth function. The invalid value is 0."
			::= { hwAPTrafficProfileEntry 30 }

		-- 1.3.6.1.4.1.2011.6.139.11.1.23.1.31
		hwAPTrafficProfileIGMPSnoopingMaxUser OBJECT-TYPE
			SYNTAX Unsigned32 (0..1000)
			MAX-ACCESS read-write
			STATUS current
			DESCRIPTION
				"This object indicates the status of the IGMP snooping max user function. The invalid value is 0."
			::= { hwAPTrafficProfileEntry 31 }
			
		-- 1.3.6.1.4.1.2011.6.139.11.1.23.1.32
		hwAPTrafficProfilePriorityDscpUpMap8021p OBJECT-TYPE
			SYNTAX OCTET STRING (SIZE (1..256))
			MAX-ACCESS read-write
			STATUS current
			DESCRIPTION
				"This object indicates the mapping relationship between DSCP and 802.1p. DSCP values range from 0 to 63. Two mapped data are separated by a comma."
			::= { hwAPTrafficProfileEntry 32 }
			
		-- 1.3.6.1.4.1.2011.6.139.11.1.23.1.33
		hwAPTrafficProfilePriority80211eUpMap8021p OBJECT-TYPE
			SYNTAX OCTET STRING (SIZE (1..256))
			MAX-ACCESS read-write
			STATUS current
			DESCRIPTION
				"This object indicates the mapping relationship between 802.11e and 802.1p. 802.11e values range from 0 to 7. Two mapped data are separated by a comma."
			::= { hwAPTrafficProfileEntry 33 }
			
		-- 1.3.6.1.4.1.2011.6.139.11.1.23.1.34
		hwAPTrafficProfilePriority8021pDnMap80211e OBJECT-TYPE
			SYNTAX OCTET STRING (SIZE (1..256))
			MAX-ACCESS read-write
			STATUS current
			DESCRIPTION
				"This object indicates the mapping relationship between 802.11e and 802.1p. 802.11e values range from 0 to 7. Two mapped data are separated by a comma."
			::= { hwAPTrafficProfileEntry 34 }

                -- 1.3.6.1.4.1.2011.6.139.11.1.23.1.35
		hwAPTrafficProfilePriorityMapUpPayloadTrustMode OBJECT-TYPE
			SYNTAX INTEGER
			{
				trust80211E(1),
				trustDSCP(2)
			}
			MAX-ACCESS read-write
			STATUS current
			DESCRIPTION
				"This object indicates the status of priority-map upstream trust. The default value is 1."
			::= { hwAPTrafficProfileEntry 35 }

		-- 1.3.6.1.4.1.2011.6.139.11.1.23.1.36
		hwAPTrafficProfileSvpVoice OBJECT-TYPE
			SYNTAX INTEGER
			{
				disable(1),
				enable(2)
			}
			MAX-ACCESS read-write
			STATUS current
			DESCRIPTION
				"This object indicates the status of the SVP voice function. The default value is 1."
			::= { hwAPTrafficProfileEntry 36 }
			
		-- 1.3.6.1.4.1.2011.6.139.11.1.23.1.37
		hwAPTrafficProfileRateLimitClientDynamic OBJECT-TYPE
			SYNTAX INTEGER
			{
				disable(1),
				enable(2)
			}
			MAX-ACCESS read-write
			STATUS current
			DESCRIPTION
				"This object indicates the rate limit switch of client. The default value is 2."
			::= { hwAPTrafficProfileEntry 37 }
			
		--1.3.6.1.4.1.2011.6.139.11.1.23.1.38
		hwAPTrafficProfileRateLimitClientDynamicThr OBJECT-TYPE
			SYNTAX Unsigned32 (8|16|32)
			MAX-ACCESS read-write
			STATUS current
			DESCRIPTION 
				"This object indicates the limit rate of client. Can only be configed with 8,16,32. The default value is 16. It is expressed in Mbps."
			::= { hwAPTrafficProfileEntry 38 }
			
		--1.3.6.1.4.1.2011.6.139.11.1.24
		hwAPTrafficProfileFilterTable OBJECT-TYPE
			SYNTAX SEQUENCE OF HwAPTrafficProfileFilterEntry 
			MAX-ACCESS not-accessible
			STATUS current
			DESCRIPTION 
				"This table is used to configure QoS filter information."
			::= { hwWlanConfigObjects 24 }

		--1.3.6.1.4.1.2011.6.139.11.1.24.1
		hwAPTrafficProfileFilterEntry OBJECT-TYPE
			SYNTAX HwAPTrafficProfileFilterEntry 
			MAX-ACCESS not-accessible
			STATUS current
			DESCRIPTION 
				"The indexes of this table are hwAPTrafficProfileName, hwAPTrafficProfileFilterType, and hwAPTrafficProfileFilterDirection."
			INDEX { hwAPTrafficProfileName, hwAPTrafficProfileFilterType,hwAPTrafficProfileFilterDirection  }
			::= { hwAPTrafficProfileFilterTable 1 }


		HwAPTrafficProfileFilterEntry ::=
			SEQUENCE {				
				hwAPTrafficProfileFilterDirection
					INTEGER,
				hwAPTrafficProfileFilterType
					INTEGER,
				hwAPTrafficProfileFilterACLID
					Integer32,
				hwAPTrafficProfileFilterRowStatus
					RowStatus 
			 }

		 --1.3.6.1.4.1.2011.6.139.11.1.24.1.1
		hwAPTrafficProfileFilterDirection OBJECT-TYPE
			SYNTAX INTEGER
				{
				inbound(1),
				outbound(2)
				}
			MAX-ACCESS not-accessible
			STATUS current
			DESCRIPTION 
				"This object indicates the ACL rule direction for packet filtering in a traffic profile. This parameter has no default value."
			::= { hwAPTrafficProfileFilterEntry 1 }

		 --1.3.6.1.4.1.2011.6.139.11.1.24.1.2
		hwAPTrafficProfileFilterType OBJECT-TYPE
			SYNTAX INTEGER
				{
				ipv4(1),
				ipv6(2),
				l2(3)
				}
			MAX-ACCESS not-accessible
			STATUS current
			DESCRIPTION 
				"This object indicates the ACL rule type for packet filtering in a traffic profile. This parameter has no default value."
			::= { hwAPTrafficProfileFilterEntry 2 }

		 --1.3.6.1.4.1.2011.6.139.11.1.24.1.3
		hwAPTrafficProfileFilterACLID OBJECT-TYPE
			SYNTAX Integer32 (3000..3031 | 4000..4031 | 6000..6031)
			MAX-ACCESS read-write
			STATUS current
			DESCRIPTION 
				"This object indicates the ACL rule for packet filtering in a traffic profile."
			::= { hwAPTrafficProfileFilterEntry 3 }

		 --1.3.6.1.4.1.2011.6.139.11.1.24.1.4
		hwAPTrafficProfileFilterRowStatus OBJECT-TYPE
			SYNTAX RowStatus
			MAX-ACCESS read-create
			STATUS current
			DESCRIPTION 
				"This object indicates the row status of this table. ROWSTATUS_CREATEANDFLOW and ROWSTATUS_DESTROY are commonly used."
			::= { hwAPTrafficProfileFilterEntry 4 }

		--1.3.6.1.4.1.2011.6.139.11.1.25
		hwWlanVlanPoolTable OBJECT-TYPE
			SYNTAX SEQUENCE OF HwWlanVlanPoolEntry 
			MAX-ACCESS not-accessible
			STATUS current
			DESCRIPTION 
				"This table is used to configure VLAN pools."
			::= { hwWlanConfigObjects 25 }

		--1.3.6.1.4.1.2011.6.139.11.1.25.1
		hwWlanVlanPoolEntry OBJECT-TYPE
			SYNTAX HwWlanVlanPoolEntry 
			MAX-ACCESS not-accessible
			STATUS current
			DESCRIPTION 
				"The index of this table is hwVlanPoolName."
			INDEX { hwVlanPoolName }
			::= { hwWlanVlanPoolTable 1 }


		HwWlanVlanPoolEntry ::=
			SEQUENCE {				
				hwVlanPoolName
					OCTET STRING,
				hwVlanPoolVlanlist
					OCTET STRING,
				hwVlanPoolAssignMethod
					INTEGER,
				hwVlanPoolRowStatus
					RowStatus 
			 }

		 --1.3.6.1.4.1.2011.6.139.11.1.25.1.1
		hwVlanPoolName OBJECT-TYPE
			SYNTAX OCTET STRING (SIZE (1..31))
			MAX-ACCESS not-accessible
			STATUS current
			DESCRIPTION 
				"This object indicates the VLAN pool name. It is the index of the table."
			::= { hwWlanVlanPoolEntry 1 }

		 --1.3.6.1.4.1.2011.6.139.11.1.25.1.2
		hwVlanPoolVlanlist OBJECT-TYPE
			SYNTAX OCTET STRING (SIZE (0..640))
			MAX-ACCESS read-write
			STATUS current
			DESCRIPTION 
				"This object indicates the VLAN list."
			::= { hwWlanVlanPoolEntry 2 }

		 --1.3.6.1.4.1.2011.6.139.11.1.25.1.3
		hwVlanPoolAssignMethod OBJECT-TYPE
			SYNTAX INTEGER
				{
				hash(1),
				even(2)
				}
			MAX-ACCESS read-write
			STATUS current
			DESCRIPTION 
				"This object indicates the VLAN pool allocation algorithm. The default value is 1."
			::= { hwWlanVlanPoolEntry 3 }

		 --1.3.6.1.4.1.2011.6.139.11.1.25.1.4
		hwVlanPoolRowStatus OBJECT-TYPE
			SYNTAX RowStatus
			MAX-ACCESS read-write
			STATUS current
			DESCRIPTION 
				"This object indicates the row status of this table. ROWSTATUS_CREATEANDFLOW and ROWSTATUS_DESTROY are commonly used."
			::= { hwWlanVlanPoolEntry 4 }

		--1.3.6.1.4.1.2011.6.139.11.1.26
		hwWlanStaWhitelistConfig OBJECT IDENTIFIER ::= { hwWlanConfigObjects 26 }
		hwWlanStaWhitelistProfileTable OBJECT-TYPE
			SYNTAX SEQUENCE OF HwWlanStaWhitelistProfileEntry
			MAX-ACCESS not-accessible
			STATUS current
			DESCRIPTION 
				"This table is used to create STA whitelist profiles."
			::= { hwWlanStaWhitelistConfig 1 }

		
		-- 1.3.6.1.4.1.2011.6.139.11.1.26.1.1
		hwWlanStaWhitelistProfileEntry OBJECT-TYPE
			SYNTAX HwWlanStaWhitelistProfileEntry
			MAX-ACCESS not-accessible
			STATUS current
			DESCRIPTION 
				"The index of this table is hwWlanStaWhitelistProfileName."
			INDEX { hwWlanStaWhitelistProfileName }
			::= { hwWlanStaWhitelistProfileTable 1 }

		
		HwWlanStaWhitelistProfileEntry ::=
			SEQUENCE { 
				hwWlanStaWhitelistProfileName
					OCTET STRING,
				hwWlanStaWhitelistProfileRowStatus
					RowStatus
			 }

		-- 1.3.6.1.4.1.2011.6.139.11.1.26.1.1.1
		hwWlanStaWhitelistProfileName OBJECT-TYPE
			SYNTAX OCTET STRING (SIZE (1..35))
			MAX-ACCESS not-accessible
			STATUS current
			DESCRIPTION 
				"This object indicates the name of a STA whitelist profile. It is the index of the table."
			::= { hwWlanStaWhitelistProfileEntry 1 }

		
		-- 1.3.6.1.4.1.2011.6.139.11.1.26.1.1.2
		hwWlanStaWhitelistProfileRowStatus OBJECT-TYPE
			SYNTAX RowStatus
			MAX-ACCESS read-write
			STATUS current
			DESCRIPTION
				"This object indicates the row status of this table."
			::= { hwWlanStaWhitelistProfileEntry 2 }

		
		-- 1.3.6.1.4.1.2011.6.139.11.1.26.2
		hwWlanStaWhitelistProfileConfigTable OBJECT-TYPE
			SYNTAX SEQUENCE OF HwWlanStaWhitelistProfileConfigEntry
			MAX-ACCESS not-accessible
			STATUS current
			DESCRIPTION
				"This table is used to configure STA whitelist profiles."
			::= { hwWlanStaWhitelistConfig 2 }

		
		-- 1.3.6.1.4.1.2011.6.139.11.1.26.2.1
		hwWlanStaWhitelistProfileConfigEntry OBJECT-TYPE
			SYNTAX HwWlanStaWhitelistProfileConfigEntry
			MAX-ACCESS not-accessible
			STATUS current
			DESCRIPTION
				"The indexes of this table are hwWlanStaWhitelistProfileName and hwWlanStaWhitelistStaMac."
			INDEX { hwWlanStaWhitelistStaMac, hwWlanStaWhitelistProfileName }
			::= { hwWlanStaWhitelistProfileConfigTable 1 }

		
		HwWlanStaWhitelistProfileConfigEntry ::=
			SEQUENCE { 
				hwWlanStaWhitelistStaMac
					MacAddress,
				hwWlanStaWhitelistRowStatus
					RowStatus,
				hwWlanStaWhitelistStaMacDescription
					OCTET STRING
			 }

		-- 1.3.6.1.4.1.2011.6.139.11.1.26.2.1.1
		hwWlanStaWhitelistStaMac OBJECT-TYPE
			SYNTAX MacAddress
			MAX-ACCESS not-accessible
			STATUS current
			DESCRIPTION
				"This object indicates the whitelist."
			::= { hwWlanStaWhitelistProfileConfigEntry 1 }

		
		-- 1.3.6.1.4.1.2011.6.139.11.1.26.2.1.2
		hwWlanStaWhitelistRowStatus OBJECT-TYPE
			SYNTAX RowStatus
			MAX-ACCESS read-write
			STATUS current
			DESCRIPTION
				"This object indicates the row status of this table. ROWSTATUS_CREATEANDFLOW and ROWSTATUS_DESTROY are commonly used."
			::= { hwWlanStaWhitelistProfileConfigEntry 2 }

		-- 1.3.6.1.4.1.2011.6.139.11.1.26.2.1.3
		hwWlanStaWhitelistStaMacDescription OBJECT-TYPE
			SYNTAX OCTET STRING (SIZE (0..80))
			MAX-ACCESS read-write
			STATUS current
			DESCRIPTION
				"This object indicates the description of the sta-mac."
			::= { hwWlanStaWhitelistProfileConfigEntry 3 }

-- 1.3.6.1.4.1.2011.6.139.11.1.26.3
		-- 1.3.6.1.4.1.2011.6.139.11.1.26.3
		hwWlanStaWhitelistProfileOuiTable OBJECT-TYPE
			SYNTAX SEQUENCE OF HwWlanStaWhitelistProfileOuiEntry
			MAX-ACCESS not-accessible
			STATUS current
			DESCRIPTION
				"This table is used to configure OUI of STA whitelist profiles."
			::= { hwWlanStaWhitelistConfig 3 }
--     1.3.6.1.4.1.2011.6.139.11.1.26.3.1
		hwWlanStaWhitelistProfileOuiEntry OBJECT-TYPE
			SYNTAX HwWlanStaWhitelistProfileOuiEntry
			MAX-ACCESS not-accessible
			STATUS current
			DESCRIPTION
				"The indexes of this table are hwWlanStaWhitelistProfileName and hwWlanStaWhitelistOui."
			INDEX { hwWlanStaWhitelistOui, hwWlanStaWhitelistProfileName }
			::= { hwWlanStaWhitelistProfileOuiTable 1 }
		HwWlanStaWhitelistProfileOuiEntry ::=
			SEQUENCE { 
				hwWlanStaWhitelistOui
					OCTET STRING,
				hwWlanStaWhitelistOuiRowStatus
					RowStatus,
				hwWlanStaWhitelistOuiDescription
					OCTET STRING
			 }
--     1.3.6.1.4.1.2011.6.139.11.1.26.3.1.1
		hwWlanStaWhitelistOui OBJECT-TYPE
			SYNTAX OCTET STRING (SIZE(1..8))
			MAX-ACCESS not-accessible
			STATUS current
			DESCRIPTION
				"This object indicates the index of the OUI whitelist in the sta whitelist profile. Its format is XX-XX-XX.XX is a hexadecimal number."
			::= { hwWlanStaWhitelistProfileOuiEntry 1 }
-- 1.3.6.1.4.1.2011.6.139.11.1.26.3.1.2
		hwWlanStaWhitelistOuiRowStatus OBJECT-TYPE
			SYNTAX RowStatus
			MAX-ACCESS read-write
			STATUS current
			DESCRIPTION
				"This object indicates the row status of this table. ROWSTATUS_CREATEANDFLOW and ROWSTATUS_DESTROY are commonly used."
			::= { hwWlanStaWhitelistProfileOuiEntry 2 }
-- 1.3.6.1.4.1.2011.6.139.11.1.26.3.1.3
		hwWlanStaWhitelistOuiDescription OBJECT-TYPE
			SYNTAX OCTET STRING (SIZE (0..80))
			MAX-ACCESS read-write
			STATUS current
			DESCRIPTION
				"This object indicates the description of the oui."
			::= { hwWlanStaWhitelistProfileOuiEntry 3 }
		
		-- 1.3.6.1.4.1.2011.6.139.11.1.27
		hwWlanStaBlacklistConfig OBJECT IDENTIFIER ::= { hwWlanConfigObjects 27 }

		
		-- 1.3.6.1.4.1.2011.6.139.11.1.27.1
		hwWlanStaBlacklistProfileTable OBJECT-TYPE
			SYNTAX SEQUENCE OF HwWlanStaBlacklistProfileEntry
			MAX-ACCESS not-accessible
			STATUS current
			DESCRIPTION
				"This table is used to create STA blacklist profiles."
			::= { hwWlanStaBlacklistConfig 1 }

		
		-- 1.3.6.1.4.1.2011.6.139.11.1.27.1.1
		hwWlanStaBlacklistProfileEntry OBJECT-TYPE
			SYNTAX HwWlanStaBlacklistProfileEntry
			MAX-ACCESS not-accessible
			STATUS current
			DESCRIPTION
				"The index of this table is hwWlanStaBlacklistProfileName."
			INDEX { hwWlanStaBlacklistProfileName }
			::= { hwWlanStaBlacklistProfileTable 1 }

		
		HwWlanStaBlacklistProfileEntry ::=
			SEQUENCE { 
				hwWlanStaBlacklistProfileName
					OCTET STRING,
				hwWlanStaBlacklistProfileRowStatus
					RowStatus
			 }

		-- 1.3.6.1.4.1.2011.6.139.11.1.27.1.1.1
		hwWlanStaBlacklistProfileName OBJECT-TYPE
			SYNTAX OCTET STRING (SIZE (1..35))
			MAX-ACCESS not-accessible
			STATUS current
			DESCRIPTION 
				"This object indicates the STA blacklist profile name. It is the index of the table."
			::= { hwWlanStaBlacklistProfileEntry 1 }

		
		-- 1.3.6.1.4.1.2011.6.139.11.1.27.1.1.2
		hwWlanStaBlacklistProfileRowStatus OBJECT-TYPE
			SYNTAX RowStatus
			MAX-ACCESS read-write
			STATUS current
			DESCRIPTION
				"This object indicates the row status of this table. ROWSTATUS_CREATEANDFLOW and ROWSTATUS_DESTROY are commonly used."
			::= { hwWlanStaBlacklistProfileEntry 2 }

		
		-- 1.3.6.1.4.1.2011.6.139.11.1.27.2
		hwWlanStaBlacklistProfileConfigTable OBJECT-TYPE
			SYNTAX SEQUENCE OF HwWlanStaBlacklistProfileConfigEntry
			MAX-ACCESS not-accessible
			STATUS current
			DESCRIPTION
				"This table is used to configure STA blacklist profiles."
			::= { hwWlanStaBlacklistConfig 2 }

		
		-- 1.3.6.1.4.1.2011.6.139.11.1.27.2.1
		hwWlanStaBlacklistProfileConfigEntry OBJECT-TYPE
			SYNTAX HwWlanStaBlacklistProfileConfigEntry
			MAX-ACCESS not-accessible
			STATUS current
			DESCRIPTION
				"The indexes of this table are hwWlanStaBlacklistProfileName and hwWlanStaBlacklistStaMac."
			INDEX { hwWlanStaBlacklistStaMac, hwWlanStaBlacklistProfileName }
			::= { hwWlanStaBlacklistProfileConfigTable 1 }

		
		HwWlanStaBlacklistProfileConfigEntry ::=
			SEQUENCE { 
				hwWlanStaBlacklistStaMac
					MacAddress,
				hwWlanStaBlacklistRowStatus
					RowStatus,
				hwWlanStaBlacklistStaMacDescription
					OCTET STRING
			 }

		-- 1.3.6.1.4.1.2011.6.139.11.1.27.2.1.1
		hwWlanStaBlacklistStaMac OBJECT-TYPE
			SYNTAX MacAddress
			MAX-ACCESS not-accessible
			STATUS current
			DESCRIPTION
				"This object indicates the blacklist."
			::= { hwWlanStaBlacklistProfileConfigEntry 1 }

		
		-- 1.3.6.1.4.1.2011.6.139.11.1.27.2.1.2
		hwWlanStaBlacklistRowStatus OBJECT-TYPE
			SYNTAX RowStatus
			MAX-ACCESS read-write
			STATUS current
			DESCRIPTION 
				"This object indicates the row status of this table. ROWSTATUS_CREATEANDFLOW and ROWSTATUS_DESTROY are commonly used."
			::= { hwWlanStaBlacklistProfileConfigEntry 2 }

		-- 1.3.6.1.4.1.2011.6.139.11.1.27.2.1.3
		hwWlanStaBlacklistStaMacDescription OBJECT-TYPE
			SYNTAX OCTET STRING (SIZE (0..80))
			MAX-ACCESS read-write
			STATUS current
			DESCRIPTION
				"This object indicates the description of the sta-mac."
			::= { hwWlanStaBlacklistProfileConfigEntry 3 }
		--1.3.6.1.4.1.2011.6.139.11.1.28
		hwWidsProfileTable OBJECT-TYPE
			SYNTAX SEQUENCE OF HwWidsProfileEntry 
			MAX-ACCESS not-accessible
			STATUS current
			DESCRIPTION 
				"This table is used to configure WIDS classify profiles, WIDS attack profiles, and WIDS contain profiles."
			::= { hwWlanConfigObjects 28 }

		--1.3.6.1.4.1.2011.6.139.11.1.28.1
		hwWidsProfileEntry OBJECT-TYPE
			SYNTAX HwWidsProfileEntry 
			MAX-ACCESS not-accessible
			STATUS current
			DESCRIPTION 
				"The index of this table is hwWidsProfileName."
			INDEX { hwWidsProfileName }
			::= { hwWidsProfileTable 1 }


		HwWidsProfileEntry ::=
			SEQUENCE {				
				hwWidsProfileName
					OCTET STRING,
				hwWidsProfileRowStatus
					RowStatus,
				hwWidsDeviceReportInterval
					Unsigned32,
				hwWidsDeviceSyncInterval
					Unsigned32,
				hwWidsSpoofProfile
					OCTET STRING,
				hwWidsWhitelistProfile
					OCTET STRING,
				hwWidsBruteForceDetectInterval
					Unsigned32,
				hwWidsBruteForceDetectThreshold
					Unsigned32,
				hwWidsBruteForceQuietTime
					Unsigned32,
				hwWidsFloodDetectInterval
					Unsigned32,
				hwWidsFloodDetectThreshold
					Unsigned32,
				hwWidsFloodQuietTime
					Unsigned32,
				hwWidsWeakIvQuietTime
					Unsigned32,
				hwWidsSpoofQuietTime
					Unsigned32,
				hwWidsDynamicBlackListSwitch
					INTEGER,
				hwWidsRogueContainModeBmp
					Unsigned32,
 				hwWidsStaWhitelistProfile
					OCTET STRING,
 				hwWidsContainMinRssi
					Integer32,
				hwWidsContainMinStaNum
					Unsigned32
			 }

		 --1.3.6.1.4.1.2011.6.139.11.1.28.1.1
		hwWidsProfileName OBJECT-TYPE
			SYNTAX OCTET STRING (SIZE (1..35))
			MAX-ACCESS not-accessible
			STATUS current
			DESCRIPTION 
				"This object indicates the name of a WIDS profile. It is the index of the table."
			::= { hwWidsProfileEntry 1 }

		
		-- 1.3.6.1.4.1.2011.6.139.11.1.28.1.5
		hwWidsProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwWidsProfileEntry 5 }

		

		-- 1.3.6.1.4.1.2011.6.139.11.1.28.1.6
		hwWidsDeviceReportInterval OBJECT-TYPE
			SYNTAX Unsigned32 (10..3600)
			MAX-ACCESS read-write
			STATUS current
			DESCRIPTION 
				"This object indicates the device detection reporting interval. The default value is 300 seconds. In V200R019C10 and later versions, the value range changes to 60-3600."
			::= { hwWidsProfileEntry 6 }

		 --1.3.6.1.4.1.2011.6.139.11.1.28.1.7
		hwWidsDeviceSyncInterval OBJECT-TYPE
			SYNTAX Unsigned32 (120..360)
			MAX-ACCESS read-write
			STATUS current
			DESCRIPTION 
				"This object indicates the interval for APs to report all device information to an AC. The default value is 360 minutes."
			::= { hwWidsProfileEntry 7 }

		 --1.3.6.1.4.1.2011.6.139.11.1.28.1.8
		hwWidsSpoofProfile OBJECT-TYPE
			SYNTAX OCTET STRING (SIZE (0..35))
			MAX-ACCESS read-write
			STATUS current
			DESCRIPTION 
				"This object indicates the name of a WIDS spoof profile."
			::= { hwWidsProfileEntry 8 }

		 --1.3.6.1.4.1.2011.6.139.11.1.28.1.9
		hwWidsWhitelistProfile OBJECT-TYPE
			SYNTAX OCTET STRING (SIZE (0..35))
			MAX-ACCESS read-write
			STATUS current
			DESCRIPTION 
				"This object indicates the name of a WIDS confident profile."
			::= { hwWidsProfileEntry 9 }

		

		-- 1.3.6.1.4.1.2011.6.139.11.1.28.1.10
		hwWidsBruteForceDetectInterval OBJECT-TYPE
			SYNTAX Unsigned32 (10..120)
			MAX-ACCESS read-write
			STATUS current
			DESCRIPTION 
				"This object indicates the interval for brute force attack detection. The default value is 60. It is expressed in s."
			::= { hwWidsProfileEntry 10 }

		 --1.3.6.1.4.1.2011.6.139.11.1.28.1.11
		hwWidsBruteForceDetectThreshold OBJECT-TYPE
			SYNTAX Unsigned32 (1..100)
			MAX-ACCESS read-write
			STATUS current
			DESCRIPTION 
				"This object indicates the threshold for the number of brute force attack attempts, namely, the threshold for the number of key negotiation failures within a detection period. If the number of brute-force attack attempts exceeds the threshold, the terminal initiates brute force attacks. The default value is 20."
			::= { hwWidsProfileEntry 11 }

		 --1.3.6.1.4.1.2011.6.139.11.1.28.1.12
		hwWidsBruteForceQuietTime OBJECT-TYPE
			SYNTAX Unsigned32 (60..36000)
			MAX-ACCESS read-write
			STATUS current
			DESCRIPTION 
				"This object indicates the quiet period for brute force attack alarm reporting. The default value is 600 seconds."
			::= { hwWidsProfileEntry 12 }

		

		-- 1.3.6.1.4.1.2011.6.139.11.1.28.1.13
		hwWidsFloodDetectInterval OBJECT-TYPE
			SYNTAX Unsigned32 (10..120)
			MAX-ACCESS read-write
			STATUS current
			DESCRIPTION 
				"This object indicates the flood attack detection interval. The default value is 10. It is expressed in s."
			::= { hwWidsProfileEntry 13 }

		 --1.3.6.1.4.1.2011.6.139.11.1.28.1.14
		hwWidsFloodDetectThreshold OBJECT-TYPE
			SYNTAX Unsigned32 (1..1000)
			MAX-ACCESS read-write
			STATUS current
			DESCRIPTION 
				"This object indicates the threshold for food attack detection. If the number of packets of the same type received within a detection period exceeds the threshold, flood attacks occur. The default value is 500."
			::= { hwWidsProfileEntry 14 }

		 --1.3.6.1.4.1.2011.6.139.11.1.28.1.15
		hwWidsFloodQuietTime OBJECT-TYPE
			SYNTAX Unsigned32 (60..36000)
			MAX-ACCESS read-write
			STATUS current
			DESCRIPTION 
				"This object indicates the quiet period for flood attack alarm reporting. The default value is 600 seconds."
			::= { hwWidsProfileEntry 15 }

		

		-- 1.3.6.1.4.1.2011.6.139.11.1.28.1.16
		hwWidsWeakIvQuietTime OBJECT-TYPE
			SYNTAX Unsigned32 (60..36000)
			MAX-ACCESS read-write
			STATUS current
			DESCRIPTION 
				"This object indicates the quiet period for weak IV attack alarm reporting. The default value is 600 seconds."
			::= { hwWidsProfileEntry 16 }

		
		-- 1.3.6.1.4.1.2011.6.139.11.1.28.1.17
		hwWidsSpoofQuietTime OBJECT-TYPE
			SYNTAX Unsigned32 (60..36000)
			MAX-ACCESS read-write
			STATUS current
			DESCRIPTION 
				"This object indicates the quiet period for spoofing attack alarm reporting. The default value is 600 seconds."
			::= { hwWidsProfileEntry 17 }

		 --1.3.6.1.4.1.2011.6.139.11.1.28.1.18
		hwWidsDynamicBlackListSwitch OBJECT-TYPE
			SYNTAX INTEGER
				{
				disable(1) ,
				enable(2)
				}
			MAX-ACCESS read-write
			STATUS current
			DESCRIPTION 
				"This object indicates the status of the dynamic blacklist function. The default value is 2."
			::= { hwWidsProfileEntry 18 }

		

		-- 1.3.6.1.4.1.2011.6.139.11.1.28.1.19
		hwWidsRogueContainModeBmp OBJECT-TYPE
			SYNTAX Unsigned32
			MAX-ACCESS read-write
			STATUS current
			DESCRIPTION 
				"This object indicates the bit map of rogue device countering types. The default value is 0."
			::= { hwWidsProfileEntry 19 }

		-- 1.3.6.1.4.1.2011.6.139.11.1.28.1.20
		hwWidsStaWhitelistProfile  OBJECT-TYPE
			SYNTAX OCTET STRING (SIZE (0..35))
			 MAX-ACCESS read-write
			 STATUS current
			DESCRIPTION
			                "This object indicates the name of a sta whitelist profile."
			 ::= { hwWidsProfileEntry 20 }
		--    1.3.6.1.4.1.2011.6.139.11.1.28.1.21
	                   hwWidsContainMinRssi OBJECT-TYPE
	                            SYNTAX Integer32 (-95..-50 | 0)
	                            MAX-ACCESS read-write
	                            STATUS current
	                            DESCRIPTION
	                                    "This object indicates min Rssi for contain."
	                            ::= { hwWidsProfileEntry 21 }
	
		--    1.3.6.1.4.1.2011.6.139.11.1.28.1.22
            	                   hwWidsContainMinStaNum OBJECT-TYPE
	                            SYNTAX Unsigned32 (1..10 | 0)
	                            MAX-ACCESS read-write
	                            STATUS current
	                            DESCRIPTION
	                                    "This object indicates min sta num for contain."
	                            ::= { hwWidsProfileEntry 22 }

		--  1.3.6.1.4.1.2011.6.139.11.1.29
		hwWlanPPSKTable OBJECT-TYPE
			SYNTAX SEQUENCE OF HwWlanPPSKEntry
			MAX-ACCESS not-accessible
			STATUS current
			DESCRIPTION
				"This table is used to add and delete PPSK."
			::={ hwWlanConfigObjects 29} 
        
		--  1.3.6.1.4.1.2011.6.139.11.1.29.1
		hwWlanPPSKEntry OBJECT-TYPE
			SYNTAX HwWlanPPSKEntry
			MAX-ACCESS not-accessible
			STATUS current
			DESCRIPTION
				"The index of this table is hwWlanPPSKUserName"
			INDEX { hwWlanPPSKUserName }
			::= { hwWlanPPSKTable 1 }
        
		HwWlanPPSKEntry ::=
			SEQUENCE {
				hwWlanPPSKUserName 
					OCTET STRING,
				hwWlanPPSKPskMode 
					INTEGER,
				hwWlanPPSKPskValue 
					OCTET STRING,
				hwWlanPPSKPskUserGroup 
					OCTET STRING,
				hwWlanPPSKExpireDate 
					TimeTicks,
				hwWlanPPSKExpireHour 
					Unsigned32,
				hwWlanPPSKSsid 
					OCTET STRING,
				hwWlanPPSKMaxDevice 
					Unsigned32,
				hwWlanPPSKBranchGroup 
					OCTET STRING,
				hwWlanPPSKStaMac 
					MacAddress,
				hwWlanPPSKVlan 
					Unsigned32,
				hwWlanPPSKRowStatus 
					RowStatus
			}        
            
		--  1.3.6.1.4.1.2011.6.139.11.1.29.1.1
		hwWlanPPSKUserName OBJECT-TYPE
			SYNTAX OCTET STRING  (SIZE (1..64))
			MAX-ACCESS read-write
			STATUS current
			DESCRIPTION
				"Ppsk user name"
			::= { hwWlanPPSKEntry 1 }
        
		--  1.3.6.1.4.1.2011.6.139.11.1.29.1.2
		hwWlanPPSKPskMode   OBJECT-TYPE
			SYNTAX  INTEGER
				{
				passPhrase(1),
				hex(2)
				}
			MAX-ACCESS read-write
			STATUS current
			DESCRIPTION
				"This object indicates the pre-shared key mode of this table."
			::= { hwWlanPPSKEntry 2 }
        
		--  1.3.6.1.4.1.2011.6.139.11.1.29.1.3
		hwWlanPPSKPskValue  OBJECT-TYPE
			SYNTAX  OCTET STRING (SIZE (8..108))
			MAX-ACCESS read-write
			STATUS current
			DESCRIPTION
				"This object indicates the pre-shared key value of this table."
			::= { hwWlanPPSKEntry 3 }
        
        
		--  1.3.6.1.4.1.2011.6.139.11.1.29.1.4
		hwWlanPPSKPskUserGroup  OBJECT-TYPE
			SYNTAX  OCTET STRING (SIZE (0..64))
			MAX-ACCESS read-write
			STATUS current
			DESCRIPTION
				"This object indicates the user group of this table."
			::= { hwWlanPPSKEntry 4 }
        
		--  1.3.6.1.4.1.2011.6.139.11.1.29.1.5
		hwWlanPPSKExpireDate    OBJECT-TYPE
			SYNTAX  TimeTicks
			MAX-ACCESS read-write
			STATUS current
			DESCRIPTION
				"This object indicates  the expire date of this table."
			::= { hwWlanPPSKEntry 5 }

		--  1.3.6.1.4.1.2011.6.139.11.1.29.1.6
		hwWlanPPSKExpireHour    OBJECT-TYPE
			SYNTAX  Unsigned32 (0..23)
			MAX-ACCESS read-write
			STATUS current
			DESCRIPTION
				"This object indicates  the expire hour of this table."
			::= { hwWlanPPSKEntry 6 }
        
		--  1.3.6.1.4.1.2011.6.139.11.1.29.1.7
		hwWlanPPSKSsid  OBJECT-TYPE
			SYNTAX  OCTET STRING  (SIZE (1..32))
			MAX-ACCESS read-write
			STATUS current
			DESCRIPTION
				"This object indicates  the ssid of this table."
			::= { hwWlanPPSKEntry 7 }
        
		--  1.3.6.1.4.1.2011.6.139.11.1.29.1.8
		hwWlanPPSKMaxDevice   OBJECT-TYPE
			SYNTAX  Unsigned32
			MAX-ACCESS read-write
			STATUS current
			DESCRIPTION
				"This object indicates the max device of this table."
			::= { hwWlanPPSKEntry 8 }
        
		--  1.3.6.1.4.1.2011.6.139.11.1.29.1.9
		hwWlanPPSKBranchGroup    OBJECT-TYPE
			SYNTAX  OCTET STRING  (SIZE (0..35))
			MAX-ACCESS read-write
			STATUS current
			DESCRIPTION
				"This object indicates the branch group of this table."
			::= { hwWlanPPSKEntry 9 }
        
		--  1.3.6.1.4.1.2011.6.139.11.1.29.1.10
		hwWlanPPSKStaMac    OBJECT-TYPE
			SYNTAX  MacAddress
			MAX-ACCESS read-write
			STATUS current
			DESCRIPTION
				"This object indicates  the station mac-address of this table."
			::= { hwWlanPPSKEntry 10 }
        
		--  1.3.6.1.4.1.2011.6.139.11.1.29.1.11
		hwWlanPPSKVlan  OBJECT-TYPE
			SYNTAX  Unsigned32  (0..4094)
			MAX-ACCESS read-write
			STATUS current
			DESCRIPTION
				"This object indicates the vlan of this table."
			::= { hwWlanPPSKEntry 11 }
            
                
		-- 1.3.6.1.4.1.2011.6.139.11.1.29.1.12
		hwWlanPPSKRowStatus OBJECT-TYPE
			SYNTAX RowStatus
			MAX-ACCESS read-write
			STATUS current
			DESCRIPTION
				"This object indicates the row status of this table."
			::= { hwWlanPPSKEntry 12 }

-- 1.3.6.1.4.1.2011.6.139.11.1.32
		-- 1.3.6.1.4.1.2011.6.139.11.1.32
		hwWidsSpoofProfileTable OBJECT-TYPE
			SYNTAX SEQUENCE OF HwWidsSpoofProfileEntry 
			MAX-ACCESS not-accessible
			STATUS current
			DESCRIPTION 
				"This table is used to configure matching rules for spoof APs."
			::= { hwWlanConfigObjects 32 }

		--1.3.6.1.4.1.2011.6.139.11.1.32.1
		hwWidsSpoofProfileEntry OBJECT-TYPE
			SYNTAX HwWidsSpoofProfileEntry 
			MAX-ACCESS not-accessible
			STATUS current
			DESCRIPTION 
				"The indexes of this table are hwWidsSpoofProfileName and hwWidsSpoofSsidRegex."
			INDEX { hwWidsSpoofProfileName, hwWidsSpoofSsidRegex }
			::= { hwWidsSpoofProfileTable 1 }


		HwWidsSpoofProfileEntry ::=
			SEQUENCE {				
				hwWidsSpoofProfileName
					OCTET STRING,
				hwWidsSpoofSsidRegex
					OCTET STRING,
				hwWidsSpoofProfileRowStatus
					RowStatus 
			 }

		 --1.3.6.1.4.1.2011.6.139.11.1.32.1.1
		hwWidsSpoofProfileName OBJECT-TYPE
			SYNTAX OCTET STRING (SIZE (1..35))
			MAX-ACCESS not-accessible
			STATUS current
			DESCRIPTION 
				"This object indicates the name of a WIDS spoof profile. It is the index of the table."
			::= { hwWidsSpoofProfileEntry 1 }

		 --1.3.6.1.4.1.2011.6.139.11.1.32.1.2
		hwWidsSpoofSsidRegex OBJECT-TYPE
			SYNTAX OCTET STRING (SIZE (1..48))
			MAX-ACCESS not-accessible
			STATUS current
			DESCRIPTION 
				"This object indicates the matching rules for spoofing SSIDs."
			::= { hwWidsSpoofProfileEntry 2 }

		 --1.3.6.1.4.1.2011.6.139.11.1.32.1.3
		hwWidsSpoofProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwWidsSpoofProfileEntry 3 }

		--1.3.6.1.4.1.2011.6.139.11.1.33
		hwWidsWhitelistProfileMacTable OBJECT-TYPE
			SYNTAX SEQUENCE OF HwWidsWhitelistProfileMacEntry 
			MAX-ACCESS not-accessible
			STATUS current
			DESCRIPTION 
				"This table is used to configure WIDS MAC whitelists."
			::= { hwWlanConfigObjects 33 }

		--1.3.6.1.4.1.2011.6.139.11.1.33.1
		hwWidsWhitelistProfileMacEntry OBJECT-TYPE
			SYNTAX HwWidsWhitelistProfileMacEntry 
			MAX-ACCESS not-accessible
			STATUS current
			DESCRIPTION 
				"The index of this table is hwWidsWhitelistProfileName."
			INDEX { hwWidsWhitelistProfileName, hwWidsWhitelistProfileMac }
			::= { hwWidsWhitelistProfileMacTable 1 }


		HwWidsWhitelistProfileMacEntry ::=
			SEQUENCE {				
				hwWidsWhitelistProfileName
					OCTET STRING,
				hwWidsWhitelistProfileMac
					MacAddress,
				hwWidsWhitelistProfileMacRowStatus
					RowStatus 
			 }

		 --1.3.6.1.4.1.2011.6.139.11.1.33.1.1
		hwWidsWhitelistProfileName OBJECT-TYPE
			SYNTAX OCTET STRING (SIZE (1..35))
			MAX-ACCESS not-accessible
			STATUS current
			DESCRIPTION 
				"This object indicates the name of a WIDS confident profile. It is the index of the table."
			::= { hwWidsWhitelistProfileMacEntry 1 }

		 --1.3.6.1.4.1.2011.6.139.11.1.33.1.2
		hwWidsWhitelistProfileMac OBJECT-TYPE
			SYNTAX MacAddress
			MAX-ACCESS not-accessible
			STATUS current
			DESCRIPTION 
				"This object indicates the MAC address whitelist."
			::= { hwWidsWhitelistProfileMacEntry 2 }

		 --1.3.6.1.4.1.2011.6.139.11.1.33.1.3
		hwWidsWhitelistProfileMacRowStatus OBJECT-TYPE
			SYNTAX RowStatus
			MAX-ACCESS read-write
			STATUS current
			DESCRIPTION 
				"This object indicates the row status of this table. ROWSTATUS_CREATEANDFLOW and ROWSTATUS_DESTROY are commonly used."
			::= { hwWidsWhitelistProfileMacEntry 3 }

		--1.3.6.1.4.1.2011.6.139.11.1.34
		hwWidsWhitelistProfileOuiTable OBJECT-TYPE
			SYNTAX SEQUENCE OF HwWidsWhitelistProfileOuiEntry 
			MAX-ACCESS not-accessible
			STATUS current
			DESCRIPTION 
				"This table is used to configure WIDS OUI whitelists."
			::= { hwWlanConfigObjects 34 }

		--1.3.6.1.4.1.2011.6.139.11.1.34.1
		hwWidsWhitelistProfileOuiEntry OBJECT-TYPE
			SYNTAX HwWidsWhitelistProfileOuiEntry 
			MAX-ACCESS not-accessible
			STATUS current
			DESCRIPTION 
				"The index of this table is hwWidsWhitelistProfileOui."
			INDEX { hwWidsWhitelistProfileName, hwWidsWhitelistProfileOui }
			::= { hwWidsWhitelistProfileOuiTable 1 }


		HwWidsWhitelistProfileOuiEntry ::=
			SEQUENCE {				
				hwWidsWhitelistProfileOui
					OCTET STRING,
				hwWidsWhitelistProfileOuiRowStatus
					RowStatus 
			 }

		 --1.3.6.1.4.1.2011.6.139.11.1.34.1.1
		hwWidsWhitelistProfileOui OBJECT-TYPE
			SYNTAX OCTET STRING (SIZE (1..8))
			MAX-ACCESS not-accessible
			STATUS current
			DESCRIPTION 
				"This object indicates the index of the OUI whitelist in the WIDS confident profile. Its format is XX-XX-XX. XX is a hexadecimal number."
			::= { hwWidsWhitelistProfileOuiEntry 1 }

		 --1.3.6.1.4.1.2011.6.139.11.1.34.1.2
		hwWidsWhitelistProfileOuiRowStatus OBJECT-TYPE
			SYNTAX RowStatus
			MAX-ACCESS read-write
			STATUS current
			DESCRIPTION 
				"This object indicates the row status of this table. ROWSTATUS_CREATEANDFLOW and ROWSTATUS_DESTROY are commonly used."
			::= { hwWidsWhitelistProfileOuiEntry 2 }

		--1.3.6.1.4.1.2011.6.139.11.1.35
		hwWidsWhitelistProfileSsidTable OBJECT-TYPE
			SYNTAX SEQUENCE OF HwWidsWhitelistProfileSsidEntry 
			MAX-ACCESS not-accessible
			STATUS current
			DESCRIPTION 
				"This table is used to configure WIDS SSID whitelists."
			::= { hwWlanConfigObjects 35 }

		--1.3.6.1.4.1.2011.6.139.11.1.35.1
		hwWidsWhitelistProfileSsidEntry OBJECT-TYPE
			SYNTAX HwWidsWhitelistProfileSsidEntry 
			MAX-ACCESS not-accessible
			STATUS current
			DESCRIPTION 
				"The index of this table is hwWidsWhitelistProfileSsid."
			INDEX { hwWidsWhitelistProfileName, hwWidsWhitelistProfileSsid }
			::= { hwWidsWhitelistProfileSsidTable 1 }


		HwWidsWhitelistProfileSsidEntry ::=
			SEQUENCE {				
				hwWidsWhitelistProfileSsid
					OCTET STRING,
				hwWidsWhitelistProfileSsidRowStatus
					RowStatus 
			 }

		 --1.3.6.1.4.1.2011.6.139.11.1.35.1.1
		hwWidsWhitelistProfileSsid OBJECT-TYPE
			SYNTAX OCTET STRING (SIZE (1..34))
			MAX-ACCESS not-accessible
			STATUS current
			DESCRIPTION
				"This object indicates the trusted SSIDs that are case-sensitive."
			::= { hwWidsWhitelistProfileSsidEntry 1 }

		
-- 1.3.6.1.4.1.2011.6.139.11.1.35.1.2
		-- 1.3.6.1.4.1.2011.6.139.11.1.35.1.2
		hwWidsWhitelistProfileSsidRowStatus OBJECT-TYPE
			SYNTAX RowStatus
			MAX-ACCESS read-write
			STATUS current
			DESCRIPTION
				"This object indicates the row status of this table. ROWSTATUS_CREATEANDFLOW and ROWSTATUS_DESTROY are commonly used."
			::= { hwWidsWhitelistProfileSsidEntry 2 }

		
-- 1.3.6.1.4.1.2011.6.139.11.1.36
		-- 1.3.6.1.4.1.2011.6.139.11.1.36
		hwWlanMeshProfileTable OBJECT-TYPE
			SYNTAX SEQUENCE OF HwWlanMeshProfileEntry
			MAX-ACCESS not-accessible
			STATUS current
			DESCRIPTION
				"This table is used to configure and query Mesh profile parameters."
			::= { hwWlanConfigObjects 36 }

		
-- 1.3.6.1.4.1.2011.6.139.11.1.36.1
		-- 1.3.6.1.4.1.2011.6.139.11.1.36.1
		hwWlanMeshProfileEntry OBJECT-TYPE
			SYNTAX HwWlanMeshProfileEntry
			MAX-ACCESS not-accessible
			STATUS current
			DESCRIPTION
				"The index of this table is hwWlanMeshProfileName."
			INDEX { hwWlanMeshProfileName }
			::= { hwWlanMeshProfileTable 1 }

		
		HwWlanMeshProfileEntry ::=
			SEQUENCE { 
				hwWlanMeshProfileName
					OCTET STRING,
				hwWlanMeshID
					OCTET STRING,
				hwWlanMeshDhcpTrustPort
					INTEGER,
				hwWlanMeshLinkReportInterval
					Unsigned32,
				hwWlanMeshMaxLinkNum
					Unsigned32,
				hwWlanMeshRssiThreshold
					Integer32,
				hwWlanMeshSecurityProfileName
					OCTET STRING,
				hwWlanMeshProfileHandoverProfileName
					OCTET STRING,
				hwWlanMeshFwaSwitch
					INTEGER,
				hwWlanMeshFwaEdcaMode
					INTEGER,
				hwWlanMeshProfileRowStatus
					RowStatus,
				hwWlanMeshClientEdcaVoiceECWmax
					Unsigned32,
				hwWlanMeshClientEdcaVoiceECWmin
					Unsigned32,
				hwWlanMeshClientEdcaVoiceAIFSN 
					Unsigned32,
				hwWlanMeshClientEdcaVoiceTXOPLimit
					Unsigned32,
				hwWlanMeshClientEdcaVideoECWmax 
					Unsigned32,
				hwWlanMeshClientEdcaVideoECWmin 
					Unsigned32,
				hwWlanMeshClientEdcaVideoAIFSN
					Unsigned32,
				hwWlanMeshClientEdcaVideoTXOPLimit
					Unsigned32,
				hwWlanMeshClientEdcaBeECWmax
					Unsigned32,
				hwWlanMeshClientEdcaBeECWmin
					Unsigned32,
				hwWlanMeshClientEdcaBeAIFSN
					Unsigned32,
				hwWlanMeshClientEdcaBeTXOPLimit
					Unsigned32,
				hwWlanMeshClientEdcaBkECWmax
					Unsigned32,
				hwWlanMeshClientEdcaBkECWmin
					Unsigned32,
				hwWlanMeshClientEdcaBkAIFSN
					Unsigned32,
				hwWlanMeshClientEdcaBkTXOPLimit
					Unsigned32,
				hwWlanMeshNdTrustPort
					INTEGER,
				hwWlanMeshLinkAgingTime
					Unsigned32,
				hwWlanMeshProfilePriorityMapTrustMode
					INTEGER,
				hwWlanMeshProfilePriorityDscpMap80211e
					OCTET STRING,
				hwWlanMeshProfileClientModeSwitch
					INTEGER,
				hwWlanMeshProfileBeacon2gRate
					INTEGER,
				hwWlanMeshProfileBeacon5gRate
					INTEGER,
				hwWlanMeshProfileSwitchProbeInterval
					Unsigned32
			 }

-- 1.3.6.1.4.1.2011.6.139.11.1.36.1.1
		-- 1.3.6.1.4.1.2011.6.139.11.1.36.1.1
		hwWlanMeshProfileName OBJECT-TYPE
			SYNTAX OCTET STRING (SIZE (1..35))
			MAX-ACCESS not-accessible
			STATUS current
			DESCRIPTION
				"This object indicates the name of a mesh profile. It is the index of the table."
			::= { hwWlanMeshProfileEntry 1 }

		
-- 1.3.6.1.4.1.2011.6.139.11.1.36.1.2
		-- 1.3.6.1.4.1.2011.6.139.11.1.36.1.2
		hwWlanMeshID OBJECT-TYPE
			SYNTAX OCTET STRING (SIZE (1..32))
			MAX-ACCESS read-write
			STATUS current
			DESCRIPTION
				"This object indicates the mesh ID. The value is a string of case-sensitive characters without question marks (and spaces. It cannot begin or end with double quotation marks. The default value is huaweimesh."
			::= { hwWlanMeshProfileEntry 2 }

		
-- 1.3.6.1.4.1.2011.6.139.11.1.36.1.3
		-- 1.3.6.1.4.1.2011.6.139.11.1.36.1.3
		hwWlanMeshDhcpTrustPort OBJECT-TYPE
			SYNTAX INTEGER
				{
				disable(1),
				enable(2)
				}
			MAX-ACCESS read-write
			STATUS current
			DESCRIPTION
				"This object indicates whether to enable the DHCP trusted port on an AP. The default value is 2."
			::= { hwWlanMeshProfileEntry 3 }

		
-- 1.3.6.1.4.1.2011.6.139.11.1.36.1.4
		-- 1.3.6.1.4.1.2011.6.139.11.1.36.1.4
		hwWlanMeshLinkReportInterval OBJECT-TYPE
			SYNTAX Unsigned32 (5..3600)
			MAX-ACCESS read-write
			STATUS current
			DESCRIPTION
				"This object indicates the interval for reporting mesh link information. The default value is 30 seconds."
			::= { hwWlanMeshProfileEntry 4 }

		
-- 1.3.6.1.4.1.2011.6.139.11.1.36.1.5
		-- 1.3.6.1.4.1.2011.6.139.11.1.36.1.5
		hwWlanMeshMaxLinkNum OBJECT-TYPE
			SYNTAX Unsigned32 (1..32)
			MAX-ACCESS read-write
			STATUS current
			DESCRIPTION
				"In FWA mode, the maximum number of Mesh links supported is 32,otherwise, it is 8"
			::= { hwWlanMeshProfileEntry 5 }

		
-- 1.3.6.1.4.1.2011.6.139.11.1.36.1.6
		-- 1.3.6.1.4.1.2011.6.139.11.1.36.1.6
		hwWlanMeshRssiThreshold OBJECT-TYPE
			SYNTAX Integer32 (-90..-20)
			MAX-ACCESS read-write
			STATUS current
			DESCRIPTION
				"This object indicates the valid RSSI threshold for a Mesh link route. The default value is -75 dBm."
			::= { hwWlanMeshProfileEntry 6 }

		
		-- 1.3.6.1.4.1.2011.6.139.11.1.36.1.8
		hwWlanMeshSecurityProfileName OBJECT-TYPE
			SYNTAX OCTET STRING (SIZE (1..35))
			MAX-ACCESS read-write
			STATUS current
			DESCRIPTION
				"The object indicates the bound security profile."
			::= { hwWlanMeshProfileEntry 8 }

		
-- 1.3.6.1.4.1.2011.6.139.11.1.36.1.9
		-- 1.3.6.1.4.1.2011.6.139.11.1.36.1.9
		hwWlanMeshProfileHandoverProfileName OBJECT-TYPE
			SYNTAX OCTET STRING (SIZE (0..35))
			MAX-ACCESS read-write
			STATUS current
			DESCRIPTION
				"The object indicates the bound handover profile."
			::= { hwWlanMeshProfileEntry 9 }

		
-- 1.3.6.1.4.1.2011.6.139.11.1.36.1.10
		-- 1.3.6.1.4.1.2011.6.139.11.1.36.1.10
		hwWlanMeshFwaSwitch OBJECT-TYPE
			SYNTAX INTEGER
				{
				disable(1),
				enable(2)
				}
			MAX-ACCESS read-write
			STATUS current
			DESCRIPTION
				"This object indicates the status of the FWA mode function. The default value is 1."
			::= { hwWlanMeshProfileEntry 10 }

		
-- 1.3.6.1.4.1.2011.6.139.11.1.36.1.11
		-- 1.3.6.1.4.1.2011.6.139.11.1.36.1.11
		hwWlanMeshFwaEdcaMode OBJECT-TYPE
			SYNTAX INTEGER
				{
				auto(1),
				manual(2)
				}
			MAX-ACCESS read-write
			STATUS current
			DESCRIPTION
				"This object indicates the EDCA mode in FWA mode. The default value is 1."
			::= { hwWlanMeshProfileEntry 11 }

		
-- 1.3.6.1.4.1.2011.6.139.11.1.36.1.12
		-- 1.3.6.1.4.1.2011.6.139.11.1.36.1.12
		hwWlanMeshProfileRowStatus OBJECT-TYPE
			SYNTAX RowStatus
			MAX-ACCESS read-write
			STATUS current
			DESCRIPTION
				"This object indicates the row status of this table. ROWSTATUS_CREATEANDFLOW and ROWSTATUS_DESTROY are commonly used."
			::= { hwWlanMeshProfileEntry 12 }

		
		-- 1.3.6.1.4.1.2011.6.139.11.1.36.1.13
		hwWlanMeshClientEdcaVoiceECWmax OBJECT-TYPE
			SYNTAX Unsigned32 (0..15)
			MAX-ACCESS read-write
			STATUS current
			DESCRIPTION
				"This object indicates the exponent form of the maximum contention window (ECWmax) for AC_VO packets. ECWmin and ECWmax determine the average backoff time."
			::= { hwWlanMeshProfileEntry 13 }

		
		-- 1.3.6.1.4.1.2011.6.139.11.1.36.1.14
		hwWlanMeshClientEdcaVoiceECWmin OBJECT-TYPE
			SYNTAX Unsigned32 (0..15)
			MAX-ACCESS read-write
			STATUS current
			DESCRIPTION
				"This object indicates the exponent form of the minimum contention window (ECWmin) for AC_VO packets. ECWmin and ECWmax determine the average backoff time."
			::= { hwWlanMeshProfileEntry 14 }

		
		-- 1.3.6.1.4.1.2011.6.139.11.1.36.1.15
		hwWlanMeshClientEdcaVoiceAIFSN  OBJECT-TYPE
			SYNTAX Unsigned32 (1..15)
			MAX-ACCESS read-write
			STATUS current
			DESCRIPTION
				"This object indicates the AIFSN for AC_VO packets,  which determines the channel idle time."
			::= { hwWlanMeshProfileEntry 15 }

		
		-- 1.3.6.1.4.1.2011.6.139.11.1.36.1.16
		hwWlanMeshClientEdcaVoiceTXOPLimit OBJECT-TYPE
			SYNTAX Unsigned32 (0..255)
			MAX-ACCESS read-write
			STATUS current
			DESCRIPTION
				"This object indicates the transmission opportunity limit (TXOPLimit) for AC_VO packets, which determines the maximum duration in which an STA can occupy a channel. A larger TXOPLimit value indicates a longer duration to occupy a channel."
			::= { hwWlanMeshProfileEntry 16 }

		
		-- 1.3.6.1.4.1.2011.6.139.11.1.36.1.17
		hwWlanMeshClientEdcaVideoECWmax  OBJECT-TYPE
			SYNTAX Unsigned32 (0..15)
			MAX-ACCESS read-write
			STATUS current
			DESCRIPTION
				"This object indicates the exponent form of the maximum contention window (ECWmax) for AC_VI packets. ECWmin and ECWmax determine the average backoff time."
			::= { hwWlanMeshProfileEntry 17 }

		
		-- 1.3.6.1.4.1.2011.6.139.11.1.36.1.18
		hwWlanMeshClientEdcaVideoECWmin  OBJECT-TYPE
			SYNTAX Unsigned32 (0..15)
			MAX-ACCESS read-write
			STATUS current
			DESCRIPTION
				"This object indicates the exponent form of the minimum contention window (ECWmin) for AC_VI packets. ECWmin and ECWmax determine the average backoff time."
			::= { hwWlanMeshProfileEntry 18 }

		
		-- 1.3.6.1.4.1.2011.6.139.11.1.36.1.19
		hwWlanMeshClientEdcaVideoAIFSN OBJECT-TYPE
			SYNTAX Unsigned32 (1..15)
			MAX-ACCESS read-write
			STATUS current
			DESCRIPTION
				"This object indicates the AIFSN for AC_VI packets,  which determines the channel idle time."
			::= { hwWlanMeshProfileEntry 19 }

		
		-- 1.3.6.1.4.1.2011.6.139.11.1.36.1.20
		hwWlanMeshClientEdcaVideoTXOPLimit OBJECT-TYPE
			SYNTAX Unsigned32 (0..255)
			MAX-ACCESS read-write
			STATUS current
			DESCRIPTION
				"This object indicates the transmission opportunity limit (TXOPLimit) for AC_VI packets, which determines the maximum duration in which an STA can occupy a channel. A larger TXOPLimit value indicates a longer duration to occupy a channel."
			::= { hwWlanMeshProfileEntry 20 }

		
		-- 1.3.6.1.4.1.2011.6.139.11.1.36.1.21
		hwWlanMeshClientEdcaBeECWmax OBJECT-TYPE
			SYNTAX Unsigned32 (0..15)
			MAX-ACCESS read-write
			STATUS current
			DESCRIPTION
				"This object indicates the exponent form of the maximum contention window (ECWmax) for AC_BE packets. ECWmin and ECWmax determine the average backoff time."
			::= { hwWlanMeshProfileEntry 21 }

		
		-- 1.3.6.1.4.1.2011.6.139.11.1.36.1.22
		hwWlanMeshClientEdcaBeECWmin OBJECT-TYPE
			SYNTAX Unsigned32 (0..15)
			MAX-ACCESS read-write
			STATUS current
			DESCRIPTION
				"This object indicates the exponent form of the minimum contention window (ECWmin) for AC_BE packets. ECWmin and ECWmax determine the average backoff time."
			::= { hwWlanMeshProfileEntry 22 }

		
		-- 1.3.6.1.4.1.2011.6.139.11.1.36.1.23
		hwWlanMeshClientEdcaBeAIFSN OBJECT-TYPE
			SYNTAX Unsigned32 (1..15)
			MAX-ACCESS read-write
			STATUS current
			DESCRIPTION
				"This object indicates the AIFSN for AC_BE packets,  which determines the channel idle time."
			::= { hwWlanMeshProfileEntry 23 }

		
		-- 1.3.6.1.4.1.2011.6.139.11.1.36.1.24
		hwWlanMeshClientEdcaBeTXOPLimit OBJECT-TYPE
			SYNTAX Unsigned32 (0..255)
			MAX-ACCESS read-write
			STATUS current
			DESCRIPTION
				"This object indicates the transmission opportunity limit (TXOPLimit) for AC_BE packets, which determines the maximum duration in which an STA can occupy a channel. A larger TXOPLimit value indicates a longer duration to occupy a channel."
			::= { hwWlanMeshProfileEntry 24 }

		
		-- 1.3.6.1.4.1.2011.6.139.11.1.36.1.25
		hwWlanMeshClientEdcaBkECWmax OBJECT-TYPE
			SYNTAX Unsigned32 (0..15)
			MAX-ACCESS read-write
			STATUS current
			DESCRIPTION
				"This object indicates the exponent form of the maximum contention window (ECWmax) for AC_BK packets. ECWmin and ECWmax determine the average backoff time."
			::= { hwWlanMeshProfileEntry 25 }

		
		-- 1.3.6.1.4.1.2011.6.139.11.1.36.1.26
		hwWlanMeshClientEdcaBkECWmin OBJECT-TYPE
			SYNTAX Unsigned32 (0..15)
			MAX-ACCESS read-write
			STATUS current
			DESCRIPTION
				"This object indicates the exponent form of the minimum contention window (ECWmin) for AC_BK packets. ECWmin and ECWmax determine the average backoff time."
			::= { hwWlanMeshProfileEntry 26 }

		
		-- 1.3.6.1.4.1.2011.6.139.11.1.36.1.27
		hwWlanMeshClientEdcaBkAIFSN OBJECT-TYPE
			SYNTAX Unsigned32 (1..15)
			MAX-ACCESS read-write
			STATUS current
			DESCRIPTION
				"This object indicates the AIFSN for AC_BK packets,  which determines the channel idle time."
			::= { hwWlanMeshProfileEntry 27 }

		
		-- 1.3.6.1.4.1.2011.6.139.11.1.36.1.28
		hwWlanMeshClientEdcaBkTXOPLimit OBJECT-TYPE
			SYNTAX Unsigned32 (0..255)
			MAX-ACCESS read-write
			STATUS current
			DESCRIPTION
				"This object indicates the transmission opportunity limit (TXOPLimit) for AC_BK packets, which determines the maximum duration in which an STA can occupy a channel. A larger TXOPLimit value indicates a longer duration to occupy a channel."
			::= { hwWlanMeshProfileEntry 28 }

		
		-- 1.3.6.1.4.1.2011.6.139.11.1.36.1.29
		hwWlanMeshNdTrustPort OBJECT-TYPE
			SYNTAX INTEGER
				{
				disable(1),
				enable(2)
				}
			MAX-ACCESS read-write
			STATUS current
			DESCRIPTION
				"This object indicates whether to enable the ND trusted port on an AP. The default value is 2."
			::= { hwWlanMeshProfileEntry 29 }
			
			
		-- 1.3.6.1.4.1.2011.6.139.11.1.36.1.30
		hwWlanMeshLinkAgingTime OBJECT-TYPE
			SYNTAX Unsigned32 (5..60)
			MAX-ACCESS read-write
			STATUS current
			DESCRIPTION
				"This object indicates the mesh aging time."
			::= { hwWlanMeshProfileEntry 30 }
			
		-- 1.3.6.1.4.1.2011.6.139.11.1.36.1.31
		hwWlanMeshProfilePriorityMapTrustMode OBJECT-TYPE
			SYNTAX INTEGER
				{
				trustDSCP(1),
				trust8021P(2)
				}
			MAX-ACCESS read-write
			STATUS current
			DESCRIPTION
				"Description."
			::= { hwWlanMeshProfileEntry 31 }

		
		-- 1.3.6.1.4.1.2011.6.139.11.1.36.1.32
		hwWlanMeshProfilePriorityDscpMap80211e OBJECT-TYPE
			SYNTAX OCTET STRING (SIZE (1..256))
			MAX-ACCESS read-write
			STATUS current
			DESCRIPTION
				"Description."
			::= { hwWlanMeshProfileEntry 32 }

		-- 1.3.6.1.4.1.2011.6.139.11.1.36.1.33
		hwWlanMeshProfileClientModeSwitch OBJECT-TYPE
			SYNTAX INTEGER
				{
				disable(1),
				enable(2)
				}
			MAX-ACCESS read-write
			STATUS current
			DESCRIPTION
				"This object indicates the status of the Mesh client mode function. The default value is 1."
			::= { hwWlanMeshProfileEntry 33 }
			
		-- 1.3.6.1.4.1.2011.6.139.11.1.36.1.34
		hwWlanMeshProfileBeacon2gRate OBJECT-TYPE
			SYNTAX INTEGER
				{
				one(1),
				two(2),
				five(5),
				six(6),
				nine(9),
				eleven(11),
				twelve(12),
				eighteen(18),
				twentyfour(24),
				thirtysix(36),
				fortyeight(48),
				fiftyfour(54)
				}
			MAX-ACCESS read-write
			STATUS current
			DESCRIPTION
				"This object indicates the mesh 2g beacon rate. The default value is 1."
			::= { hwWlanMeshProfileEntry 34 }

		-- 1.3.6.1.4.1.2011.6.139.11.1.36.1.35
		hwWlanMeshProfileBeacon5gRate OBJECT-TYPE
			SYNTAX INTEGER
				{
				six(6),
				nine(9),
				twelve(12),
				eighteen(18),
				twentyfour(24),
				thirtysix(36),
				fortyeight(48),
				fiftyfour(54)
				}
			MAX-ACCESS read-write
			STATUS current
			DESCRIPTION
				"This object indicates the mesh 5g beacon rate. The default value is 6."
			::= { hwWlanMeshProfileEntry 35 }

		-- 1.3.6.1.4.1.2011.6.139.11.1.36.1.36
		hwWlanMeshProfileSwitchProbeInterval OBJECT-TYPE
			SYNTAX Unsigned32 (10..300)
			MAX-ACCESS read-write
			STATUS current
			DESCRIPTION
				"This object indicates the mesh profile switch probe interval. The default value is 60."
			DEFVAL { 60 }
			::= { hwWlanMeshProfileEntry 36 }
			
-- 1.3.6.1.4.1.2011.6.139.11.1.37
		hwWlanMeshWhitelistProfileTable OBJECT-TYPE
			SYNTAX SEQUENCE OF HwWlanMeshWhitelistProfileEntry
			MAX-ACCESS not-accessible
			STATUS current
			DESCRIPTION
				"This table describes the Mesh whitelist profile."
			::= { hwWlanConfigObjects 37 }

		
-- 1.3.6.1.4.1.2011.6.139.11.1.37.1
		-- 1.3.6.1.4.1.2011.6.139.11.1.37.1
		hwWlanMeshWhitelistProfileEntry OBJECT-TYPE
			SYNTAX HwWlanMeshWhitelistProfileEntry
			MAX-ACCESS not-accessible
			STATUS current
			DESCRIPTION
				"The index of this table is hwWlanMeshWhitelistProfileName."
			INDEX { hwWlanMeshWhitelistProfileName }
			::= { hwWlanMeshWhitelistProfileTable 1 }

		
		HwWlanMeshWhitelistProfileEntry ::=
			SEQUENCE { 
				hwWlanMeshWhitelistProfileName
					OCTET STRING,
				hwWlanMeshWhitelistProfileRowStatus
					RowStatus
			 }

-- 1.3.6.1.4.1.2011.6.139.11.1.37.1.1
		-- 1.3.6.1.4.1.2011.6.139.11.1.37.1.1
		hwWlanMeshWhitelistProfileName OBJECT-TYPE
			SYNTAX OCTET STRING (SIZE (1..35))
			MAX-ACCESS not-accessible
			STATUS current
			DESCRIPTION
				"This object indicates the name of a mesh profile."
			::= { hwWlanMeshWhitelistProfileEntry 1 }

		
-- 1.3.6.1.4.1.2011.6.139.11.1.37.1.2
		-- 1.3.6.1.4.1.2011.6.139.11.1.37.1.2
		hwWlanMeshWhitelistProfileRowStatus OBJECT-TYPE
			SYNTAX RowStatus
			MAX-ACCESS read-write
			STATUS current
			DESCRIPTION
				"This object indicates the row status of this table. ROWSTATUS_CREATEANDFLOW and ROWSTATUS_DESTROY are commonly used."
			::= { hwWlanMeshWhitelistProfileEntry 2 }

		
-- 1.3.6.1.4.1.2011.6.139.11.1.38
		-- 1.3.6.1.4.1.2011.6.139.11.1.38
		hwWlanMeshWhitelistProfileConfigTable OBJECT-TYPE
			SYNTAX SEQUENCE OF HwWlanMeshWhitelistProfileConfigEntry
			MAX-ACCESS not-accessible
			STATUS current
			DESCRIPTION
				"This table describes Mesh whitelists in the Mesh whitelist profile."
			::= { hwWlanConfigObjects 38 }

		
-- 1.3.6.1.4.1.2011.6.139.11.1.38.1
		-- 1.3.6.1.4.1.2011.6.139.11.1.38.1
		hwWlanMeshWhitelistProfileConfigEntry OBJECT-TYPE
			SYNTAX HwWlanMeshWhitelistProfileConfigEntry
			MAX-ACCESS not-accessible
			STATUS current
			DESCRIPTION
				"Indexes of this table are hwWlanMeshWhitelistProfileName and hwWlanMeshWhitelistPeerApMac."
			INDEX { hwWlanMeshWhitelistProfileName,hwWlanMeshWhitelistPeerApMac }
			::= { hwWlanMeshWhitelistProfileConfigTable 1 }


		HwWlanMeshWhitelistProfileConfigEntry ::=
			SEQUENCE {				
				hwWlanMeshWhitelistPeerApMac
					MacAddress,
				hwWlanMeshWhitelistRowStatus
					RowStatus
			 }

		 --1.3.6.1.4.1.2011.6.139.11.1.38.1.1
		hwWlanMeshWhitelistPeerApMac OBJECT-TYPE
			SYNTAX MacAddress
			MAX-ACCESS not-accessible
			STATUS current
			DESCRIPTION 
				"This object indicates the whitelist."
			::= { hwWlanMeshWhitelistProfileConfigEntry 1 }

		 --1.3.6.1.4.1.2011.6.139.11.1.38.1.2
		hwWlanMeshWhitelistRowStatus OBJECT-TYPE
			SYNTAX RowStatus
			MAX-ACCESS read-write
			STATUS current
			DESCRIPTION 
				"This object indicates the row status of this table. ROWSTATUS_CREATEANDFLOW and ROWSTATUS_DESTROY are commonly used."
			::= { hwWlanMeshWhitelistProfileConfigEntry 2 }

		--1.3.6.1.4.1.2011.6.139.11.1.39
		hwWlanMeshHandoverProfileTable OBJECT-TYPE
			SYNTAX SEQUENCE OF HwWlanMeshHandoverProfileEntry 
			MAX-ACCESS not-accessible
			STATUS current
			DESCRIPTION 
				"This table is used to configure and query Mesh handover profile parameters."
			::= { hwWlanConfigObjects 39 }

		--1.3.6.1.4.1.2011.6.139.11.1.39.1
		hwWlanMeshHandoverProfileEntry OBJECT-TYPE
			SYNTAX HwWlanMeshHandoverProfileEntry 
			MAX-ACCESS not-accessible
			STATUS current
			DESCRIPTION 
				"The index of this table is hwWlanMeshHandoverProfileName."
			INDEX { hwWlanMeshHandoverProfileName }
			::= { hwWlanMeshHandoverProfileTable 1 }


		HwWlanMeshHandoverProfileEntry ::=
			SEQUENCE {				
				hwWlanMeshHandoverProfileName
					OCTET STRING,
				hwWlanMeshHOLinkProbeInterval
					Unsigned32,
				hwWlanMeshHOMinRssiThreshold
					Integer32,
				hwWlanMeshHOMaxRssiThreshold
					Integer32,
				hwWlanMeshHOLinkHoldPeriod
					Unsigned32,
				hwWlanMeshHORssiMargin
					Unsigned32,
				hwWlanMeshHOLocationBasedAlgorithmEnable
					INTEGER,
				hwWlanMeshHOMovingDirection
					INTEGER,
				hwWlanMeshHOPNCriteriaObserveTime
					Unsigned32,
				hwWlanMeshHOPNCriteriaQualifyTime
					Unsigned32,
				hwWlanMeshUrgentHandoverLowRateThreshold
					Unsigned32,
				hwWlanMeshUrgentHandoverLowRatePeriod
					Unsigned32,
				hwWlanMeshUrgentHandoverPunishmentPeriod
					Unsigned32,
				hwWlanMeshUrgentHandoverPunishmentRssi
					Unsigned32,
				hwWlanMeshHandoverProfileRowStatus
					RowStatus 
			 }

		 --1.3.6.1.4.1.2011.6.139.11.1.39.1.1
		hwWlanMeshHandoverProfileName OBJECT-TYPE
			SYNTAX OCTET STRING (SIZE (1..35))
			MAX-ACCESS not-accessible
			STATUS current
			DESCRIPTION 
				"This object indicates the name of a mesh profile. It is the index of the table."
			::= { hwWlanMeshHandoverProfileEntry 1 }

		 --1.3.6.1.4.1.2011.6.139.11.1.39.1.2
		hwWlanMeshHOLinkProbeInterval OBJECT-TYPE
			SYNTAX Unsigned32 (50..6000)
			MAX-ACCESS read-write
			STATUS current
			DESCRIPTION 
				"Description."
			::= { hwWlanMeshHandoverProfileEntry 2 }

		 --1.3.6.1.4.1.2011.6.139.11.1.39.1.3
		hwWlanMeshHOMinRssiThreshold OBJECT-TYPE
			SYNTAX Integer32 (-90..-20)
			MAX-ACCESS read-write
			STATUS current
			DESCRIPTION 
				"Description."
			::= { hwWlanMeshHandoverProfileEntry 3 }

		 --1.3.6.1.4.1.2011.6.139.11.1.39.1.4
		hwWlanMeshHOMaxRssiThreshold OBJECT-TYPE
			SYNTAX Integer32 (-90..0)
			MAX-ACCESS read-write
			STATUS current
			DESCRIPTION 
				"Description."
			::= { hwWlanMeshHandoverProfileEntry 4 }

		 --1.3.6.1.4.1.2011.6.139.11.1.39.1.5
		hwWlanMeshHOLinkHoldPeriod OBJECT-TYPE
			SYNTAX Unsigned32 (1000..60000)
			MAX-ACCESS read-write
			STATUS current
			DESCRIPTION 
				"Description."
			::= { hwWlanMeshHandoverProfileEntry 5 }

		 --1.3.6.1.4.1.2011.6.139.11.1.39.1.6
		hwWlanMeshHORssiMargin OBJECT-TYPE
			SYNTAX Unsigned32 (1..70)
			MAX-ACCESS read-write
			STATUS current
			DESCRIPTION 
				"Description."
			::= { hwWlanMeshHandoverProfileEntry 6 }

		 --1.3.6.1.4.1.2011.6.139.11.1.39.1.7
		hwWlanMeshHOLocationBasedAlgorithmEnable OBJECT-TYPE
			SYNTAX INTEGER
				{
				disable(1) ,
				enable(2)
				}
			MAX-ACCESS read-write
			STATUS current
			DESCRIPTION 
				"Description."
			::= { hwWlanMeshHandoverProfileEntry 7 }

		 --1.3.6.1.4.1.2011.6.139.11.1.39.1.8
		hwWlanMeshHOMovingDirection OBJECT-TYPE
			SYNTAX INTEGER
				{
				forward(1),
				backward(2),
				undetermined(3)
				}
			MAX-ACCESS read-write
			STATUS current
			DESCRIPTION 
				"Description."
			::= { hwWlanMeshHandoverProfileEntry 8 }

		 --1.3.6.1.4.1.2011.6.139.11.1.39.1.9
		hwWlanMeshHOPNCriteriaObserveTime OBJECT-TYPE
			SYNTAX Unsigned32 (1..10)
			MAX-ACCESS read-write
			STATUS current
			DESCRIPTION 
				"Description."
			::= { hwWlanMeshHandoverProfileEntry 9 }

		 --1.3.6.1.4.1.2011.6.139.11.1.39.1.10
		hwWlanMeshHOPNCriteriaQualifyTime OBJECT-TYPE
			SYNTAX Unsigned32 (1..10)
			MAX-ACCESS read-write
			STATUS current
			DESCRIPTION 
				"Description."
			::= { hwWlanMeshHandoverProfileEntry 10 }

		 --1.3.6.1.4.1.2011.6.139.11.1.39.1.11
		hwWlanMeshUrgentHandoverLowRateThreshold OBJECT-TYPE
			SYNTAX Unsigned32 (1..1300)
			MAX-ACCESS read-write
			STATUS current
			DESCRIPTION 
				"Description."
			::= { hwWlanMeshHandoverProfileEntry 11 }

		 --1.3.6.1.4.1.2011.6.139.11.1.39.1.12
		hwWlanMeshUrgentHandoverLowRatePeriod OBJECT-TYPE
			SYNTAX Unsigned32 (0..10000)
			MAX-ACCESS read-write
			STATUS current
			DESCRIPTION 
				"Description."
			::= { hwWlanMeshHandoverProfileEntry 12 }

		 --1.3.6.1.4.1.2011.6.139.11.1.39.1.13
		hwWlanMeshUrgentHandoverPunishmentPeriod OBJECT-TYPE
			SYNTAX Unsigned32 (0..10000)
			MAX-ACCESS read-write
			STATUS current
			DESCRIPTION 
				"Description."
			::= { hwWlanMeshHandoverProfileEntry 13 }

		 --1.3.6.1.4.1.2011.6.139.11.1.39.1.14
		hwWlanMeshUrgentHandoverPunishmentRssi OBJECT-TYPE
			SYNTAX Unsigned32 (0..50)
			MAX-ACCESS read-write
			STATUS current
			DESCRIPTION 
				"Description."
			::= { hwWlanMeshHandoverProfileEntry 14 }

		 --1.3.6.1.4.1.2011.6.139.11.1.39.1.15
		hwWlanMeshHandoverProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwWlanMeshHandoverProfileEntry 15 }

		--1.3.6.1.4.1.2011.6.139.11.1.40
		hwWdsProfileTable OBJECT-TYPE
			SYNTAX SEQUENCE OF HwWdsProfileEntry 
			MAX-ACCESS not-accessible
			STATUS current
			DESCRIPTION 
				"This table is used to configure and query WDS profile parameters."
			::= { hwWlanConfigObjects 40 }

		--1.3.6.1.4.1.2011.6.139.11.1.40.1
		hwWdsProfileEntry OBJECT-TYPE
			SYNTAX HwWdsProfileEntry 
			MAX-ACCESS not-accessible
			STATUS current
			DESCRIPTION 
				"The index of this table is hwWdsProfileName."
			INDEX { hwWdsProfileName }
			::= { hwWdsProfileTable 1 }


		HwWdsProfileEntry ::=
			SEQUENCE {				
				hwWdsProfileName
					OCTET STRING,
				hwWdsName
					OCTET STRING,
				hwWdsMode
					INTEGER,
				hwWdsDhcpTrustPort
					INTEGER,
				hwWdsVlanTagged
					OCTET STRING,
				hwWdsSecurityProfileName
					OCTET STRING,
				hwWdsProfileRowStatus
					RowStatus,
				hwWdsNdTrustPort
					INTEGER,
				hwWdsProfilePriorityMapTrustMode
					INTEGER,
				hwWdsProfilePriorityDscpMap80211e
					OCTET STRING,
				hwWdsMuMIMOSwitch
					INTEGER,
				hwWdsProfileBeacon2gRate
					INTEGER,
				hwWdsProfileBeacon5gRate
					INTEGER
			 }

		 --1.3.6.1.4.1.2011.6.139.11.1.40.1.1
		hwWdsProfileName OBJECT-TYPE
			SYNTAX OCTET STRING (SIZE (1..35))
			MAX-ACCESS not-accessible
			STATUS current
			DESCRIPTION 
				"This object indicates the name of a WDS profile. It is the index of the table."
			::= { hwWdsProfileEntry 1 }

		
		-- 1.3.6.1.4.1.2011.6.139.11.1.40.1.2
		hwWdsName OBJECT-TYPE
			SYNTAX OCTET STRING (SIZE (1..32))
			MAX-ACCESS read-write
			STATUS current
			DESCRIPTION
				"This object indicates the WDS identifier. The value is a string of case-sensitive characters without question marks and spaces. It cannot begin or end with double quotation marks.
                                The default value is huaweiwds."
			DEFVAL { "HUAWEI-WLAN-WDS" }
			::= { hwWdsProfileEntry 2 }

		
		-- 1.3.6.1.4.1.2011.6.139.11.1.40.1.3
		hwWdsMode OBJECT-TYPE
			SYNTAX INTEGER
				{ 
				middle(1),
				root(2),
				leaf(3)
				}
			MAX-ACCESS read-write
			STATUS current
			DESCRIPTION 
				"This object indicates the mode of the WDS. The default value is 3."
			::= { hwWdsProfileEntry 3 }

		-- 1.3.6.1.4.1.2011.6.139.11.1.40.1.4
		hwWdsDhcpTrustPort OBJECT-TYPE
			SYNTAX INTEGER
				{
				disable(1) ,
				enable(2)
				}
			MAX-ACCESS read-write
			STATUS current
			DESCRIPTION 
				"This object indicates whether to enable the DHCP trusted port on an AP. The default value is 2."
			::= { hwWdsProfileEntry 4 }


		-- 1.3.6.1.4.1.2011.6.139.11.1.40.1.5
		hwWdsVlanTagged OBJECT-TYPE
			SYNTAX OCTET STRING
			MAX-ACCESS read-write
			STATUS current
			DESCRIPTION 
				"This object indicates the tagged VLAN in a bridge profile. It is used to add one or a group of VLANs to the WDS bridge profile in tagged mode. By default, no VLAN is configured in the WDS bridge profile."
			::= { hwWdsProfileEntry 5 }


		-- 1.3.6.1.4.1.2011.6.139.11.1.40.1.6
		hwWdsSecurityProfileName OBJECT-TYPE
			SYNTAX OCTET STRING (SIZE (1..35))
			MAX-ACCESS read-write
			STATUS current
			DESCRIPTION 
				"The object indicates the bound security profile."
			::= { hwWdsProfileEntry 6 }


		-- 1.3.6.1.4.1.2011.6.139.11.1.40.1.8
		hwWdsProfileRowStatus OBJECT-TYPE
			SYNTAX RowStatus
			MAX-ACCESS read-write
			STATUS current
			DESCRIPTION 
				"This object indicates the row status of this table. ROWSTATUS_CREATEANDFLOW and ROWSTATUS_DESTROY are commonly used.ROWSTATUS_UNDEFINED: undefined ROWSTATUS_ACTIVE: active ROWSTATUS_NOTINSERVICE: notInService ROWSTATUS_NOTREADY: notReady ROWSTATUS_CREATEANDFLOW: createAndGoROWSTATUS_CREATEANDWAIT: createAndWaitROWSTATUS_DESTROY: destroy"
			::= { hwWdsProfileEntry 8 }

		
		-- 1.3.6.1.4.1.2011.6.139.11.1.40.1.9
		hwWdsNdTrustPort OBJECT-TYPE
			SYNTAX INTEGER
				{
				disable(1),
				enable(2)
				}
			MAX-ACCESS read-write
			STATUS current
			DESCRIPTION
				"This object indicates whether to enable the ND trusted port on an AP. The default value is 2."
			DEFVAL { enable }
			::= { hwWdsProfileEntry 9 }

		
		-- 1.3.6.1.4.1.2011.6.139.11.1.40.1.10
		hwWdsProfilePriorityMapTrustMode OBJECT-TYPE
			SYNTAX INTEGER
				{
				trustDSCP(1),
				trust8021P(2)
				}
			MAX-ACCESS read-write
			STATUS current
			DESCRIPTION
				"Description."
			::= { hwWdsProfileEntry 10 }

		
		-- 1.3.6.1.4.1.2011.6.139.11.1.40.1.11
		hwWdsProfilePriorityDscpMap80211e OBJECT-TYPE
			SYNTAX OCTET STRING (SIZE (1..256))
			MAX-ACCESS read-write
			STATUS current
			DESCRIPTION
				"Description."
			::= { hwWdsProfileEntry 11 }

		-- 1.3.6.1.4.1.2011.6.139.11.1.40.1.12
		hwWdsMuMIMOSwitch OBJECT-TYPE
			SYNTAX INTEGER
				{
				disable(1),
				enable(2)
				}
			MAX-ACCESS read-write
			STATUS current
			DESCRIPTION
				"Description."
			::= { hwWdsProfileEntry 12 }

		-- 1.3.6.1.4.1.2011.6.139.11.1.40.1.13
		hwWdsProfileBeacon2gRate OBJECT-TYPE
			SYNTAX INTEGER
				{
				one(1),
				two(2),
				five(5),
				six(6),
				nine(9),
				eleven(11),
				twelve(12),
				eighteen(18),
				twentyfour(24),
				thirtysix(36),
				fortyeight(48),
				fiftyfour(54)
				}
			MAX-ACCESS read-write
			STATUS current
			DESCRIPTION
				"This object indicates the wds 2g beacon rate. The default value is 1."
			::= { hwWdsProfileEntry 13 }

		-- 1.3.6.1.4.1.2011.6.139.11.1.40.1.14
		hwWdsProfileBeacon5gRate OBJECT-TYPE
			SYNTAX INTEGER
				{
				six(6),
				nine(9),
				twelve(12),
				eighteen(18),
				twentyfour(24),
				thirtysix(36),
				fortyeight(48),
				fiftyfour(54)
				}
			MAX-ACCESS read-write
			STATUS current
			DESCRIPTION
				"This object indicates the wds 5g beacon rate. The default value is 6."
			::= { hwWdsProfileEntry 14 }

		--1.3.6.1.4.1.2011.6.139.11.1.41
		hwWdsWhitelistProfileTable OBJECT-TYPE
			SYNTAX SEQUENCE OF HwWdsWhitelistProfileEntry 
			MAX-ACCESS not-accessible
			STATUS current
			DESCRIPTION 
				"Description."
			::= { hwWlanConfigObjects 41 }

		--1.3.6.1.4.1.2011.6.139.11.1.41.1
		hwWdsWhitelistProfileEntry OBJECT-TYPE
			SYNTAX HwWdsWhitelistProfileEntry 
			MAX-ACCESS not-accessible
			STATUS current
			DESCRIPTION 
				"Description."
			INDEX { hwWdsWhitelistProfileName }
			::= { hwWdsWhitelistProfileTable 1 }


		HwWdsWhitelistProfileEntry ::=
			SEQUENCE {				
				hwWdsWhitelistProfileName
					OCTET STRING,
				hwWdsWhitelistProfileRowStatus
					RowStatus 
			 }

		 --1.3.6.1.4.1.2011.6.139.11.1.41.1.1
		hwWdsWhitelistProfileName OBJECT-TYPE
			SYNTAX OCTET STRING (SIZE (1..35))
			MAX-ACCESS not-accessible
			STATUS current
			DESCRIPTION 
				"Description."
			::= { hwWdsWhitelistProfileEntry 1 }

		 --1.3.6.1.4.1.2011.6.139.11.1.41.1.2
		hwWdsWhitelistProfileRowStatus OBJECT-TYPE
			SYNTAX RowStatus
			MAX-ACCESS read-write
			STATUS current
			DESCRIPTION 
				"Description."
			::= { hwWdsWhitelistProfileEntry 2 }

		--1.3.6.1.4.1.2011.6.139.11.1.42
		hwWdsWhitelistTable OBJECT-TYPE
			SYNTAX SEQUENCE OF HwWdsWhitelistEntry 
			MAX-ACCESS not-accessible
			STATUS current
			DESCRIPTION 
				"Description."
			::= { hwWlanConfigObjects 42 }

		--1.3.6.1.4.1.2011.6.139.11.1.42.1
		hwWdsWhitelistEntry OBJECT-TYPE
			SYNTAX HwWdsWhitelistEntry 
			MAX-ACCESS not-accessible
			STATUS current
			DESCRIPTION 
				"Description."
			INDEX { hwWdsWhitelistProfileName, hwWdsWhitelistPeerApMac }
			::= { hwWdsWhitelistTable 1 }


		HwWdsWhitelistEntry ::=
			SEQUENCE {				
				hwWdsWhitelistPeerApMac
					MacAddress,
				hwWdsWhitelistRowStatus
					RowStatus 
			 }

		 --1.3.6.1.4.1.2011.6.139.11.1.42.1.1
		hwWdsWhitelistPeerApMac OBJECT-TYPE
			SYNTAX MacAddress
			MAX-ACCESS not-accessible
			STATUS current
			DESCRIPTION 
				"Description."
			::= { hwWdsWhitelistEntry 1 }

		 --1.3.6.1.4.1.2011.6.139.11.1.42.1.2
		hwWdsWhitelistRowStatus OBJECT-TYPE
			SYNTAX RowStatus
			MAX-ACCESS read-write
			STATUS current
			DESCRIPTION 
				"Description."
			::= { hwWdsWhitelistEntry 2 }

		--1.3.6.1.4.1.2011.6.139.11.1.43
		hwLocationProfileTable OBJECT-TYPE
			SYNTAX SEQUENCE OF HwLocationProfileEntry 
			MAX-ACCESS not-accessible
			STATUS current
			DESCRIPTION 
				"This table is used to configure terminal location and tag location."
			::= { hwWlanConfigObjects 43 }

		--1.3.6.1.4.1.2011.6.139.11.1.43.1
		hwLocationProfileEntry OBJECT-TYPE
			SYNTAX HwLocationProfileEntry 
			MAX-ACCESS not-accessible
			STATUS current
			DESCRIPTION 
				"The index of this table is hwLocationProfileName."
			INDEX { hwLocationProfileName }
			::= { hwLocationProfileTable 1 }


		HwLocationProfileEntry ::=
			SEQUENCE {				
				hwLocationProfileName
					OCTET STRING,
				hwLocationAeroscoutTagSwitch
					INTEGER,
				hwLocationAeroscoutMuSwitch
					INTEGER,
				hwLocationAeroscoutServerPort
					Unsigned32,
				hwLocationAeroscoutViaACSwitch
					INTEGER,
				hwLocationAeroscoutViaACPort
					Unsigned32,
				hwLocationAeroscoutCompoundTime
					Unsigned32,
				hwLocationEkahauTagEnable
					INTEGER,
				hwLocationEkahauServerIPAddress
					IpAddress,
				hwLocationEkahauServerIPv6Address
					OCTET STRING,
				hwLocationEkahauServerPort
					Unsigned32,
				hwLocationEkahauViaACEnable
					INTEGER,
				hwLocationEkahauViaACPort
					Unsigned32,
				hwLocationSourceIPAddress
					IpAddress,
				hwLocationSourceIPv6Address
					OCTET STRING,
				hwLocationPrivateMuEnable
					INTEGER,
				hwLocationPrivateServerIPAddress
					IpAddress,
				hwLocationPrivateServerIPv6Address
					OCTET STRING,
				hwLocationPrivateServerPort
					Unsigned32,
				hwLocationPrivateViaACEnable
					INTEGER,
				hwLocationPrivateViaACPort
					Unsigned32,
				hwLocationPrivateReportFrequency
					Unsigned32,
				hwLocationProfileRowStatus
					RowStatus,
				hwLocationProfileAeroscoutShareKey
					OCTET STRING,
				hwLocationPaiboMuEnable
					INTEGER,
				hwLocationPaiboReportFrequency
					Unsigned32,
				hwLocationPaiboServerIPAddress
					IpAddress,
				hwLocationPaiboServerIPv6Address
					OCTET STRING,
				hwLocationPaiboServerPort
					Unsigned32,
				hwLocationPaiboViaACPort
					Unsigned32,
				hwLocationPaiboPSK
					OCTET STRING,
				hwLocationPaiboIV
					OCTET STRING,
				hwLocationPrivateMUVersion
					OCTET STRING,
				hwLocationPrivateServerAddressDomain
				    OCTET STRING,
				hwLocationPrivateProtocol
				    INTEGER,
				hwLocationPrivateSSLPolicyName
				    OCTET STRING,
				hwLocationSurFilterMuEnable
					INTEGER,
				hwLocationSurFilterReportFrequency
					Unsigned32,
				hwLocationSurFilterReportProtocol
					INTEGER,
				hwLocationSurFilterServerIPAddress
					IpAddress,
				hwLocationSurFilterServerPort
					Unsigned32,
				hwLocationSurFilterViaACPort
					Unsigned32,
				hwLocationSurFilterUserName
					OCTET STRING,
				hwLocationSurFilterPassword
					OCTET STRING,
				hwLocationSurFilterDataSourceID
					OCTET STRING,
				hwLocationSurFilterCompress
					INTEGER,
				hwLocationCollectLocationDataSwitch
					INTEGER,
				hwLocationCollectLocationDataRSSIThreshold
					Integer32
			 }

		 --1.3.6.1.4.1.2011.6.139.11.1.43.1.1
		hwLocationProfileName OBJECT-TYPE
			SYNTAX OCTET STRING (SIZE (1..35))
			MAX-ACCESS not-accessible
			STATUS current
			DESCRIPTION 
				"This object indicates the name of a location profile. It is the index of the table."
			::= { hwLocationProfileEntry 1 }

		 --1.3.6.1.4.1.2011.6.139.11.1.43.1.2
		hwLocationAeroscoutTagSwitch OBJECT-TYPE
			SYNTAX INTEGER
				{
				disable(1) ,
				enable(2)
				}
			MAX-ACCESS read-write
			STATUS current
			DESCRIPTION 
				"This object indicates the status of the AeroScout tag location function. The default value is 1."
			::= { hwLocationProfileEntry 2 }

		 --1.3.6.1.4.1.2011.6.139.11.1.43.1.3
		hwLocationAeroscoutMuSwitch OBJECT-TYPE
			SYNTAX INTEGER
				{
				disable(1) ,
				enable(2)
				}
			MAX-ACCESS read-write
			STATUS current
			DESCRIPTION 
				"This object indicates the status of the AeroScout MU location function. The default value is 1."
			::= { hwLocationProfileEntry 3 }

		 --1.3.6.1.4.1.2011.6.139.11.1.43.1.4
		hwLocationAeroscoutServerPort OBJECT-TYPE
			SYNTAX Unsigned32 (0 | 1025..65535)
			MAX-ACCESS read-write
			STATUS current
			DESCRIPTION 
				"This object indicates the port used by APs or ACs to report AeroScout location data to the AE server."
			::= { hwLocationProfileEntry 4 }

		 --1.3.6.1.4.1.2011.6.139.11.1.43.1.5
		hwLocationAeroscoutViaACSwitch OBJECT-TYPE
			SYNTAX INTEGER
				{
				disable(1) ,
				enable(2)
				}
			MAX-ACCESS read-write
			STATUS current
			DESCRIPTION 
				"This object indicates whether AeroScout tag location data is reported to the AC. This parameter has no default value."
			::= { hwLocationProfileEntry 5 }

		 --1.3.6.1.4.1.2011.6.139.11.1.43.1.6
		hwLocationAeroscoutViaACPort OBJECT-TYPE
			SYNTAX Unsigned32
			MAX-ACCESS read-write
			STATUS current
			DESCRIPTION 
				"This object indicates that AeroScout location data is reported to the AC that forwards the data to the AE. A port is configured for the AP to report location data to the AC. The value ranges from 1025 to 65535. The value 0 indicates ViaACSwitch is disable."
			::= { hwLocationProfileEntry 6 }

		 --1.3.6.1.4.1.2011.6.139.11.1.43.1.7
		hwLocationAeroscoutCompoundTime OBJECT-TYPE
			SYNTAX Unsigned32 (0..65535)
			MAX-ACCESS read-write
			STATUS current
			DESCRIPTION 
				"This object indicates the AerosScout location data compound time. The value 0 indicates that data is not compounded and the AP reports location data in real time. The default value is 65535 and the unit is 0.1s."
			::= { hwLocationProfileEntry 7 }

		 --1.3.6.1.4.1.2011.6.139.11.1.43.1.8
		hwLocationEkahauTagEnable OBJECT-TYPE
			SYNTAX INTEGER
				{
				disable(1) ,
				enable(2)
				}
			MAX-ACCESS read-write
			STATUS current
			DESCRIPTION 
				"This object indicates the status of the Ekahau tag location function. The default value is 1."
			::= { hwLocationProfileEntry 8 }

		 --1.3.6.1.4.1.2011.6.139.11.1.43.1.9
		hwLocationEkahauServerIPAddress OBJECT-TYPE
			SYNTAX IpAddress
			MAX-ACCESS read-write
			STATUS current
			DESCRIPTION 
				"This object indicates the IP address of the location server for Ekahau tag location."
			::= { hwLocationProfileEntry 9 }

		 --1.3.6.1.4.1.2011.6.139.11.1.43.1.10
		hwLocationEkahauServerIPv6Address OBJECT-TYPE
			SYNTAX OCTET STRING
			MAX-ACCESS read-write
			STATUS current
			DESCRIPTION 
				"This object indicates the IPv6 address of the location server for Ekahau tag location."
			::= { hwLocationProfileEntry 10 }

		 --1.3.6.1.4.1.2011.6.139.11.1.43.1.11
		hwLocationEkahauServerPort OBJECT-TYPE
			SYNTAX Unsigned32 (0 | 1025..65535)
			MAX-ACCESS read-write
			STATUS current
			DESCRIPTION 
				"This object indicates the port number of the location server for Ekahau tag location."
			::= { hwLocationProfileEntry 11 }

		 --1.3.6.1.4.1.2011.6.139.11.1.43.1.12
		hwLocationEkahauViaACEnable OBJECT-TYPE
			SYNTAX INTEGER
				{
				disable(1) ,
				enable(2)
				}
			MAX-ACCESS read-write
			STATUS current
			DESCRIPTION 
				"This object indicates whether Ekahau tag location data is reported to the AC."
			::= { hwLocationProfileEntry 12 }

		 --1.3.6.1.4.1.2011.6.139.11.1.43.1.13
		hwLocationEkahauViaACPort OBJECT-TYPE
			SYNTAX Unsigned32 (0 | 1025..65535)
			MAX-ACCESS read-write
			STATUS current
			DESCRIPTION 
				"This object indicates that Ekahau location data is reported to the AC that forwards the data to the AE. A port is configured for the AP to report location data to the AC."
			::= { hwLocationProfileEntry 13 }

		 --1.3.6.1.4.1.2011.6.139.11.1.43.1.14
		hwLocationSourceIPAddress OBJECT-TYPE
			SYNTAX IpAddress
			MAX-ACCESS read-write
			STATUS current
			DESCRIPTION 
				"This object indicates the source IPv4 address for reporting location data in AeroScout or Ekahau location mode. You choose an IPv4 or IPv6 address."
			::= { hwLocationProfileEntry 14 }

		 --1.3.6.1.4.1.2011.6.139.11.1.43.1.15
		hwLocationSourceIPv6Address OBJECT-TYPE
			SYNTAX OCTET STRING
			MAX-ACCESS read-write
			STATUS current
			DESCRIPTION 
				"This object indicates the source IPv6 address for reporting location data in AeroScout or Ekahau location mode. You choose an IPv4 or IPv6 address."
			::= { hwLocationProfileEntry 15 }

		 --1.3.6.1.4.1.2011.6.139.11.1.43.1.16
		hwLocationPrivateMuEnable OBJECT-TYPE
			SYNTAX INTEGER
				{
				disable(1) ,
				enable(2)
				}
			MAX-ACCESS read-write
			STATUS current
			DESCRIPTION 
				"This object indicates the status of the Huawei proprietary terminal location function. The default value is 1."
			::= { hwLocationProfileEntry 16 }

		 --1.3.6.1.4.1.2011.6.139.11.1.43.1.17
		hwLocationPrivateServerIPAddress OBJECT-TYPE
			SYNTAX IpAddress
			MAX-ACCESS read-write
			STATUS current
			DESCRIPTION 
				"This object indicates the IP address of the server for the Huawei proprietary location function."
			::= { hwLocationProfileEntry 17 }

		 --1.3.6.1.4.1.2011.6.139.11.1.43.1.18
		hwLocationPrivateServerIPv6Address OBJECT-TYPE
			SYNTAX OCTET STRING
			MAX-ACCESS read-write
			STATUS current
			DESCRIPTION 
				"This object indicates the IPv6 address of the server for the Huawei proprietary location function."
			::= { hwLocationProfileEntry 18 }

		 --1.3.6.1.4.1.2011.6.139.11.1.43.1.19
		hwLocationPrivateServerPort OBJECT-TYPE
			SYNTAX Unsigned32 (0..65535)
			MAX-ACCESS read-write
			STATUS current
			DESCRIPTION 
				"This object indicates the port number of the server for the Huawei proprietary location function."
			::= { hwLocationProfileEntry 19 }

		 --1.3.6.1.4.1.2011.6.139.11.1.43.1.20
		hwLocationPrivateViaACEnable OBJECT-TYPE
			SYNTAX INTEGER
				{
				disable(1) ,
				enable(2)
				}
			MAX-ACCESS read-write
			STATUS current
			DESCRIPTION 
				"This object indicates whether Huawei proprietary terminal location data is reported to the AC. The default value is 2.1: Enable2: Disable"
			::= { hwLocationProfileEntry 20 }

		 --1.3.6.1.4.1.2011.6.139.11.1.43.1.21
		hwLocationPrivateViaACPort OBJECT-TYPE
			SYNTAX Unsigned32 (0|5000..65535)
			MAX-ACCESS read-write
			STATUS current
			DESCRIPTION 
				"This object indicates that Huawei proprietary terminal location data is reported to the AC that forwards the data to the location server. A port is configured for the AP to report location data to the AC.
The default destination IP address and port number to which the AP reports terminal location data is the AC's IP address and 6411 respectively."
			::= { hwLocationProfileEntry 21 }

		 --1.3.6.1.4.1.2011.6.139.11.1.43.1.22
		hwLocationPrivateReportFrequency OBJECT-TYPE
			SYNTAX Unsigned32 (500..60000)
			MAX-ACCESS read-write
			STATUS current
			DESCRIPTION 
				"This object indicates the interval for the AP to report location data in Huawei proprietary terminal location mode. The default value is 20000 ms."
			::= { hwLocationProfileEntry 22 }

		 --1.3.6.1.4.1.2011.6.139.11.1.43.1.23
		hwLocationProfileRowStatus OBJECT-TYPE
			SYNTAX RowStatus
			MAX-ACCESS read-write
			STATUS current
			DESCRIPTION 
				"This object indicates the row status of this table. ROWSTATUS_CREATEANDFLOW and ROWSTATUS_DESTROY are commonly used.ROWSTATUS_UNDEFINED: undefinedROWSTATUS_ACTIVE: activeROWSTATUS_NOTINSERVICE: notInServiceROWSTATUS_NOTREADY: notReadyROWSTATUS_CREATEANDFLOW: createAndGoROWSTATUS_CREATEANDWAIT: createAndWaitROWSTATUS_DESTROY: destroy"
			::= { hwLocationProfileEntry 23 }
		-- 1.3.6.1.4.1.2011.6.139.11.1.43.1.24
		hwLocationProfileAeroscoutShareKey OBJECT-TYPE
			SYNTAX OCTET STRING (SIZE (0|6..68))
			MAX-ACCESS read-write
			STATUS current
			DESCRIPTION
				"This object indicates the sharekey of the aeroscout server."
			::= { hwLocationProfileEntry 24 }


		-- 1.3.6.1.4.1.2011.6.139.11.1.43.1.25
		hwLocationPaiboMuEnable OBJECT-TYPE
			SYNTAX INTEGER
				{
				disable(1),
				enable(2)
				}
			MAX-ACCESS read-write
			STATUS current
			DESCRIPTION
				"This object indicates whether Paibo terminal location data is reported to the AC. The default value is 1.1: Disable2: Enable"
			::= { hwLocationProfileEntry 25 }


		-- 1.3.6.1.4.1.2011.6.139.11.1.43.1.26
		hwLocationPaiboReportFrequency OBJECT-TYPE
			SYNTAX Unsigned32 (500..600000)
			MAX-ACCESS read-write
			STATUS current
			DESCRIPTION
				"This object indicates the interval for the AP to report location data in Paibo terminal location mode. The default value is 60000 ms."
			::= { hwLocationProfileEntry 26 }
		

		-- 1.3.6.1.4.1.2011.6.139.11.1.43.1.27
		hwLocationPaiboServerIPAddress OBJECT-TYPE
			SYNTAX IpAddress
			MAX-ACCESS read-write
			STATUS current
			DESCRIPTION
				"This object indicates the IP address of the server for the Paibo location function."
			::= { hwLocationProfileEntry 27 }

		-- 1.3.6.1.4.1.2011.6.139.11.1.43.1.28
		hwLocationPaiboServerIPv6Address OBJECT-TYPE
			SYNTAX OCTET STRING
			MAX-ACCESS read-write
			STATUS current
			DESCRIPTION
				"This object indicates the IPv6 address of the server for the Paibo location function."
			::= { hwLocationProfileEntry 28 }

		-- 1.3.6.1.4.1.2011.6.139.11.1.43.1.29
		hwLocationPaiboServerPort OBJECT-TYPE
			SYNTAX Unsigned32 (0..65535)
			MAX-ACCESS read-write
			STATUS current
			DESCRIPTION
				"This object indicates the port number of the server for the Paibo location function."
			::= { hwLocationProfileEntry 29 }

		-- 1.3.6.1.4.1.2011.6.139.11.1.43.1.30
		hwLocationPaiboViaACPort OBJECT-TYPE
			SYNTAX Unsigned32 (0 | 5000..65535)
			MAX-ACCESS read-write
			STATUS current
			DESCRIPTION
				"This object indicates the port number of the server for the Paibo location function."
			::= { hwLocationProfileEntry 30 }

		-- 1.3.6.1.4.1.2011.6.139.11.1.43.1.31
		hwLocationPaiboPSK OBJECT-TYPE
			SYNTAX OCTET STRING (SIZE (6..68))
			MAX-ACCESS read-write
			STATUS current
			DESCRIPTION
				"This object indicates the psk of paibo server."
			::= { hwLocationProfileEntry 31 }

		-- 1.3.6.1.4.1.2011.6.139.11.1.43.1.32
		hwLocationPaiboIV OBJECT-TYPE
			SYNTAX OCTET STRING (SIZE (6..68))
			MAX-ACCESS read-write
			STATUS current
			DESCRIPTION
				"This object indicates the iv of paibo server."
			::= { hwLocationProfileEntry 32 }
			
-- 1.3.6.1.4.1.2011.6.139.11.1.43.1.33
		hwLocationPrivateMUVersion OBJECT-TYPE
			SYNTAX OCTET STRING (SIZE (0..2))
			MAX-ACCESS read-write
			STATUS current
			DESCRIPTION
				"This object indicates the protocol version of the Huawei proprietary terminal location function. The default value is v3."
			::= { hwLocationProfileEntry 33 }
			
		-- 1.3.6.1.4.1.2011.6.139.11.1.43.1.34
		hwLocationPrivateServerAddressDomain OBJECT-TYPE
			SYNTAX OCTET STRING (SIZE (0..255))
			MAX-ACCESS read-write
			STATUS current
			DESCRIPTION
				"This object indicates the domain of the server for the Huawei proprietary location function."
			::= { hwLocationProfileEntry 34 }			
		-- 1.3.6.1.4.1.2011.6.139.11.1.43.1.35
		hwLocationPrivateProtocol OBJECT-TYPE
			SYNTAX INTEGER
				{
				udp(1),
				https(2),
				http(3)
				}
			MAX-ACCESS read-write
			STATUS current
			DESCRIPTION
		        "This object indicates the report protocol for the Huawei proprietary location function. The default value is 1. The Value of https(2) is not support since V200R019C10."
			::= { hwLocationProfileEntry 35 }
	
		-- 1.3.6.1.4.1.2011.6.139.11.1.43.1.36
		hwLocationPrivateSSLPolicyName OBJECT-TYPE
			SYNTAX OCTET STRING (SIZE (0..31))
			MAX-ACCESS read-write
			STATUS current
			DESCRIPTION
				"This object indicates the ssl policy name for the Huawei proprietary location function."
			::= { hwLocationProfileEntry 36 }
		-- 1.3.6.1.4.1.2011.6.139.11.1.43.1.37
		hwLocationSurFilterMuEnable OBJECT-TYPE
			SYNTAX INTEGER
				{
				disable(1),
				enable(2)
				}
			MAX-ACCESS read-write
			STATUS current
			DESCRIPTION
				"This object indicates whether Surfilter terminal location data is reported to the AC. The default value is 1. 1: Disable 2: Enable"
			::= { hwLocationProfileEntry 37 }
			
		-- 1.3.6.1.4.1.2011.6.139.11.1.43.1.38
		hwLocationSurFilterReportFrequency OBJECT-TYPE
			SYNTAX Unsigned32 (500..600000)
			MAX-ACCESS read-write
			STATUS current
			DESCRIPTION
				"This object indicates the protoc for the AP to report location data in Surfilter terminal location mode. The default value is 60000 ms."
			::= { hwLocationProfileEntry 38 }

		-- 1.3.6.1.4.1.2011.6.139.11.1.43.1.39
		hwLocationSurFilterReportProtocol OBJECT-TYPE
			SYNTAX INTEGER
				{
				sftp(1),
				ftp(2)
				}
			MAX-ACCESS read-write
			STATUS current
			DESCRIPTION
				"This object indicates the protocol using for the AP to report location data in Surfilter terminal location mode. The default protocol is sftp."
			::= { hwLocationProfileEntry 39 }

		-- 1.3.6.1.4.1.2011.6.139.11.1.43.1.40
		hwLocationSurFilterServerIPAddress OBJECT-TYPE
			SYNTAX IpAddress
			MAX-ACCESS read-write
			STATUS current
			DESCRIPTION
				"This object indicates the IP address of the server for the Surfilter location function."
			::= { hwLocationProfileEntry 40 }

		-- 1.3.6.1.4.1.2011.6.139.11.1.43.1.41
		hwLocationSurFilterServerPort OBJECT-TYPE
			SYNTAX Unsigned32 (1..65535)
			MAX-ACCESS read-write
			STATUS current
			DESCRIPTION
				"This object indicates the port number of the server for the Surfilter location function."
			::= { hwLocationProfileEntry 41 }

		-- 1.3.6.1.4.1.2011.6.139.11.1.43.1.42
		hwLocationSurFilterViaACPort OBJECT-TYPE
			SYNTAX Unsigned32 (0 | 5000..65535)
			MAX-ACCESS read-write
			STATUS current
			DESCRIPTION
				"This object indicates the port number of the server for the Surfilter location function."
			::= { hwLocationProfileEntry 42 }

		-- 1.3.6.1.4.1.2011.6.139.11.1.43.1.43
		hwLocationSurFilterUserName OBJECT-TYPE
			SYNTAX OCTET STRING (SIZE (0..31))
			MAX-ACCESS read-write
			STATUS current
			DESCRIPTION
				"This object indicates the user name of the server for the Surfilter location function."
			::= { hwLocationProfileEntry 43 }

		-- 1.3.6.1.4.1.2011.6.139.11.1.43.1.44
		hwLocationSurFilterPassword OBJECT-TYPE
			SYNTAX OCTET STRING (SIZE (0..188))
			MAX-ACCESS read-write
			STATUS current
			DESCRIPTION
				"This object indicates the password of the server for the Surfilter location function."
			::= { hwLocationProfileEntry 44 }

		-- 1.3.6.1.4.1.2011.6.139.11.1.43.1.45
		hwLocationSurFilterDataSourceID OBJECT-TYPE
			SYNTAX OCTET STRING (SIZE (0 | 6..6))
			MAX-ACCESS read-write
			STATUS current
			DESCRIPTION
				"This object indicates the data source ID of the server for the Surfilter location function."
			::= { hwLocationProfileEntry 45 }

		-- 1.3.6.1.4.1.2011.6.139.11.1.43.1.46
		hwLocationSurFilterCompress OBJECT-TYPE
			SYNTAX INTEGER
				{
				compress(1),
				uncompress(2)
				}
			MAX-ACCESS read-write
			STATUS current
			DESCRIPTION
				"This object indicates whether the Surfilter terminal location data reported to the AC is compressed. The default value is 1. 1: Compress 2: Uncompress"
			::= { hwLocationProfileEntry 46 }			
			
		-- 1.3.6.1.4.1.2011.6.139.11.1.43.1.47
		hwLocationCollectLocationDataSwitch OBJECT-TYPE
			SYNTAX INTEGER
				{
				disable(1),
				enable(2)
				}
			MAX-ACCESS read-write
			STATUS current
			DESCRIPTION
				"This object indicates whether collect location data enable. The default value is 1.1: Disable2: Enable"
			::= { hwLocationProfileEntry 47 }			
			
		
		-- 1.3.6.1.4.1.2011.6.139.11.1.18.1.48
		hwLocationCollectLocationDataRSSIThreshold OBJECT-TYPE
			SYNTAX Integer32 (-95..0)
			MAX-ACCESS read-write
			STATUS current
			DESCRIPTION
				"This object indicates the collect location data rssi threshold. The default value is -75"
			::= { hwLocationProfileEntry 48 }


		-- 1.3.6.1.4.1.2011.6.139.11.1.45
		hwHotspot2ProfileTable OBJECT-TYPE
			SYNTAX SEQUENCE OF HwHotspot2ProfileEntry 
			MAX-ACCESS not-accessible
			STATUS current
			DESCRIPTION 
				"This table is used to configure and query Hotspot2.0 profile parameters."
			::= { hwWlanConfigObjects 45 }

		--1.3.6.1.4.1.2011.6.139.11.1.45.1
		hwHotspot2ProfileEntry OBJECT-TYPE
			SYNTAX HwHotspot2ProfileEntry 
			MAX-ACCESS not-accessible
			STATUS current
			DESCRIPTION 
				"The index of this table is hwHotspot2ProfileName."
			INDEX { hwHotspot2ProfileName }
			::= { hwHotspot2ProfileTable 1 }


		HwHotspot2ProfileEntry ::=
			SEQUENCE {				
				hwHotspot2ProfileName
					OCTET STRING,
				hwHotspot2NetworkType
					Unsigned32,
				hwHotspot2InternetAccess
					INTEGER,
				hwHotspot2VenueGroupCode
					Unsigned32,
				hwHotspot2VenueTypeCode
					Unsigned32,
				hwHotspot2Hessid
					MacAddress,
				hwHotspot2IPv4AddressAvail
					Unsigned32,
				hwHotspot2IPv6AddressAvail
					Unsigned32,
				hwHotspot2NetworkAuthenType
					Unsigned32,
				hwHotspot2RedirectUrl
					OCTET STRING,
				hwHotspot2CarryP2PCrossConnectInfo
					INTEGER,
				hwHotspot2CellularNetworkProfile
					OCTET STRING,
				hwHotspot2ConnectionCapabilityProfile
					OCTET STRING,
				hwHotspot2OperatorNameProfile
					OCTET STRING,
				hwHotspot2OperatingClassProfile
					OCTET STRING,
				hwHotspot2OperatorDomainProfile
					OCTET STRING,
				hwHotspot2NaiRealmProfile
					OCTET STRING,
				hwHotspot2VenueNameProfile
					OCTET STRING,
				hwHotspot2RoamingConsortiumProfile
					OCTET STRING,
				hwHotspot2ProfileRowStatus
					RowStatus 
			 }

		 --1.3.6.1.4.1.2011.6.139.11.1.45.1.1
		hwHotspot2ProfileName OBJECT-TYPE
			SYNTAX OCTET STRING (SIZE (1..35))
			MAX-ACCESS not-accessible
			STATUS current
			DESCRIPTION 
				"This object indicates the name of a Hotspot2.0 profile. It is the index of the table."
			::= { hwHotspot2ProfileEntry 1 }

		 --1.3.6.1.4.1.2011.6.139.11.1.45.1.2
		hwHotspot2NetworkType OBJECT-TYPE
			SYNTAX Unsigned32 (0..1|2..3|4..5|14..15)
			MAX-ACCESS read-write
			STATUS current
			DESCRIPTION 
				"This object indicates that the network type is an interworking information element. This configuration is mandatory. The AP adds this information to Beacon and Probe Response packets, which indicates network types, to assist users in discovering and selecting networks. The default value is 15.0: Private-network1: private-guest2: public-chargeable3: public-free4: personal-device5: emergency-service14: Test15: Wildcard"
			::= { hwHotspot2ProfileEntry 2 }

		 --1.3.6.1.4.1.2011.6.139.11.1.45.1.3
		hwHotspot2InternetAccess OBJECT-TYPE
			SYNTAX INTEGER
				{
				allowAcess(1),
				unallowedAcess(2)
				}
			MAX-ACCESS read-write
			STATUS current
			DESCRIPTION 
				"This object indicates that the Internet attribute is an interworking information element. This configuration is mandatory. The AP adds this information to Beacon and Probe Response packets, which indicates whether users are allowed to access the Internet, to assist users in discovering and selecting networks. The default value is 2."
			::= { hwHotspot2ProfileEntry 3 }

		 --1.3.6.1.4.1.2011.6.139.11.1.45.1.4
		hwHotspot2VenueGroupCode OBJECT-TYPE
			SYNTAX Unsigned32 (0..255|4294967295)
			MAX-ACCESS read-write
			STATUS current
			DESCRIPTION 
				"For details, see Table 7-25m-Venue Group codes and descriptions in the 802.11u protocol.
The default value 0xFFFFFFFF indicates that no configuration is added."
			::= { hwHotspot2ProfileEntry 4 }

		 --1.3.6.1.4.1.2011.6.139.11.1.45.1.5
		hwHotspot2VenueTypeCode OBJECT-TYPE
			SYNTAX Unsigned32 (0..255|4294967295)
			MAX-ACCESS read-write
			STATUS current
			DESCRIPTION 
				"For details, see Table 7-25n-Venue Type assignments in the 802.11u protocol.
The default value 0xFFFFFFFF indicates that no configuration is added."
			::= { hwHotspot2ProfileEntry 5 }

		 --1.3.6.1.4.1.2011.6.139.11.1.45.1.6
		hwHotspot2Hessid OBJECT-TYPE
			SYNTAX MacAddress
			MAX-ACCESS read-write
			STATUS current
			DESCRIPTION 
				"This object indicates the HESSID of a hot spot network. The default value is null, indicating that no configuration is added."
			::= { hwHotspot2ProfileEntry 6 }

		 --1.3.6.1.4.1.2011.6.139.11.1.45.1.7
		hwHotspot2IPv4AddressAvail OBJECT-TYPE
			SYNTAX Unsigned32 (0..7|4294967295)
			MAX-ACCESS read-write
			STATUS current
			DESCRIPTION 
				"This object indicates available types of IPv4 addresses. 8 to 63 are reserved. The default value 0xFFFFFFFF indicates that no configuration is added.0: Address type not available.1: Public IPv4 address available,2: Port-restricted IPv4 address available,3: Single NATed private IPv4 address available,4: Double NATed private IPv4 address available,5: Port-restricted IPv4 address and single NATed IPv4 address available,6: Port-restricted IPv4 address and double NATed IPv4 address available,7: Availability of the address type is not known,8 to 63: Reserved"
			::= { hwHotspot2ProfileEntry 7 }

		 --1.3.6.1.4.1.2011.6.139.11.1.45.1.8
		hwHotspot2IPv6AddressAvail OBJECT-TYPE
			SYNTAX Unsigned32 (0..2|4294967295)
			MAX-ACCESS read-write
			STATUS current
			DESCRIPTION 
				"This object indicates available types of IPv4 addresses. 3 is reserved. The default value 0xFFFFFFFF indicates that no configuration is added.0: Address type not available1: Address type available2: Availability of the address type not known3: Reserved"
			::= { hwHotspot2ProfileEntry 8 }

		 --1.3.6.1.4.1.2011.6.139.11.1.45.1.9
		hwHotspot2NetworkAuthenType OBJECT-TYPE
			SYNTAX Unsigned32 (0..3|4294967295)
			MAX-ACCESS read-write
			STATUS current
			DESCRIPTION 
				"This object indicates the network authentication type. 4 to 255 are reserved. The default value 0xFFFFFFFF indicates that no configuration is added.0: Acceptance of terms and conditions.1: On-line enrollment supported,2: http/https redirection,3: DNS redirection,4 to 255: Reserved"
			::= { hwHotspot2ProfileEntry 9 }

		 --1.3.6.1.4.1.2011.6.139.11.1.45.1.10
		hwHotspot2RedirectUrl OBJECT-TYPE
			SYNTAX OCTET STRING (SIZE (0..255))
			MAX-ACCESS read-write
			STATUS current
			DESCRIPTION 
				"This object indicates the redirection URL.This parameter is optional when Network Authentication Type is set to acceptance.This parameter is mandatory when Network Authentication Type is set to http-https-redirection.This parameter is not configurable when Network Authentication Type is set to other values."
			::= { hwHotspot2ProfileEntry 10 }

		 --1.3.6.1.4.1.2011.6.139.11.1.45.1.11
		hwHotspot2CarryP2PCrossConnectInfo OBJECT-TYPE
			SYNTAX INTEGER
				{
				disable(1) ,
				enable(2)
				}
			MAX-ACCESS read-write
			STATUS current
			DESCRIPTION 

				"This object indicates whether hot spot networks allow P2P devices to set up cross connections. Currently, this function is supported. The default value is 2."
			::= { hwHotspot2ProfileEntry 11 }

		 --1.3.6.1.4.1.2011.6.139.11.1.45.1.12
		hwHotspot2CellularNetworkProfile OBJECT-TYPE
			SYNTAX OCTET STRING (SIZE (0..35))
			MAX-ACCESS read-write
			STATUS current
			DESCRIPTION 
				"This object indicates the bound cellular network profile. By default, no cellular network profile is bound."
			::= { hwHotspot2ProfileEntry 12 }

		 --1.3.6.1.4.1.2011.6.139.11.1.45.1.13
		hwHotspot2ConnectionCapabilityProfile OBJECT-TYPE
			SYNTAX OCTET STRING (SIZE (0..35))
			MAX-ACCESS read-write
			STATUS current
			DESCRIPTION 
				"This object indicates the bound connection capability profile. By default, no connection capability profile is bound."
			::= { hwHotspot2ProfileEntry 13 }

		 --1.3.6.1.4.1.2011.6.139.11.1.45.1.14
		hwHotspot2OperatorNameProfile OBJECT-TYPE
			SYNTAX OCTET STRING (SIZE (0..35))
			MAX-ACCESS read-write
			STATUS current
			DESCRIPTION 
				"This object indicates the bound operator name profile. By default, no operator name profile is bound."
			::= { hwHotspot2ProfileEntry 14 }

		 --1.3.6.1.4.1.2011.6.139.11.1.45.1.15
		hwHotspot2OperatingClassProfile OBJECT-TYPE
			SYNTAX OCTET STRING (SIZE (0..35))
			MAX-ACCESS read-write
			STATUS current
			DESCRIPTION 
				"This object indicates the bound operating class profile. By default, no operating class profile is bound."
			::= { hwHotspot2ProfileEntry 15 }

		 --1.3.6.1.4.1.2011.6.139.11.1.45.1.16
		hwHotspot2OperatorDomainProfile OBJECT-TYPE
			SYNTAX OCTET STRING (SIZE (0..35))
			MAX-ACCESS read-write
			STATUS current
			DESCRIPTION 
				"This object indicates the bound operator domain profile. By default, no operator domain profile is bound."
			::= { hwHotspot2ProfileEntry 16 }

		 --1.3.6.1.4.1.2011.6.139.11.1.45.1.17
		hwHotspot2NaiRealmProfile OBJECT-TYPE
			SYNTAX OCTET STRING (SIZE (0..35))
			MAX-ACCESS read-write
			STATUS current
			DESCRIPTION 
				"This object indicates the bound NAI realm profile. By default, no NAI realm profile is bound."
			::= { hwHotspot2ProfileEntry 17 }

		 --1.3.6.1.4.1.2011.6.139.11.1.45.1.18
		hwHotspot2VenueNameProfile OBJECT-TYPE
			SYNTAX OCTET STRING (SIZE (0..35))
			MAX-ACCESS read-write
			STATUS current
			DESCRIPTION 
				"This object indicates the bound venue name profile. By default, no venue name profile is bound."
			::= { hwHotspot2ProfileEntry 18 }

		 --1.3.6.1.4.1.2011.6.139.11.1.45.1.19
		hwHotspot2RoamingConsortiumProfile OBJECT-TYPE
			SYNTAX OCTET STRING (SIZE (0..35))
			MAX-ACCESS read-write
			STATUS current
			DESCRIPTION 
				"This object indicates the bound roaming consortium profile. By default, no roaming consortium profile is bound."
			::= { hwHotspot2ProfileEntry 19 }

		 --1.3.6.1.4.1.2011.6.139.11.1.45.1.20
		hwHotspot2ProfileRowStatus OBJECT-TYPE
			SYNTAX RowStatus
			MAX-ACCESS read-write
			STATUS current
			DESCRIPTION 
				"This object indicates the row status of this table. ROWSTATUS_CREATEANDFLOW and ROWSTATUS_DESTROY are commonly used.ROWSTATUS_UNDEFINED: undefinedROWSTATUS_ACTIVE: activeROWSTATUS_NOTINSERVICE: notInServiceROWSTATUS_NOTREADY: notReadyROWSTATUS_CREATEANDFLOW: createAndGoROWSTATUS_CREATEANDWAIT: createAndWaitROWSTATUS_DESTROY: destroy"
			::= { hwHotspot2ProfileEntry 20 }

		--1.3.6.1.4.1.2011.6.139.11.1.46
		hwCellularNetworkProfileTable OBJECT-TYPE
			SYNTAX SEQUENCE OF HwCellularNetworkProfileEntry 
			MAX-ACCESS not-accessible
			STATUS current
			DESCRIPTION 
				"This table is used to configure and query cellular network profile parameters."
			::= { hwWlanConfigObjects 46 }

		--1.3.6.1.4.1.2011.6.139.11.1.46.1
		hwCellularNetworkProfileEntry OBJECT-TYPE
			SYNTAX HwCellularNetworkProfileEntry 
			MAX-ACCESS not-accessible
			STATUS current
			DESCRIPTION 
				"The index of this table is hwCellularNetworkProfileName."
			INDEX { hwCellularNetworkProfileName }
			::= { hwCellularNetworkProfileTable 1 }


		HwCellularNetworkProfileEntry ::=
			SEQUENCE {				
				hwCellularNetworkProfileName
					OCTET STRING,
				hwCellularNetworkProfilePlmnIDList
					OCTET STRING,
				hwCellularNetworkProfileRowStatus
					RowStatus 
			 }

		 --1.3.6.1.4.1.2011.6.139.11.1.46.1.1
		hwCellularNetworkProfileName OBJECT-TYPE
			SYNTAX OCTET STRING (SIZE (1..35))
			MAX-ACCESS not-accessible
			STATUS current
			DESCRIPTION 
				"This object indicates the name of a cellular network profile. It is the index of the table."
			::= { hwCellularNetworkProfileEntry 1 }

		 --1.3.6.1.4.1.2011.6.139.11.1.46.1.2
		hwCellularNetworkProfilePlmnIDList OBJECT-TYPE
			SYNTAX OCTET STRING (SIZE (0..255))
			MAX-ACCESS read-write
			STATUS current
			DESCRIPTION 
				"NOTE By default, no configuration is added.PLMNs are separated by question marks (?).A maximum of 32 PLMNs can be configured.A PLMN is a 5-digit or 6-digit numeric string."
			::= { hwCellularNetworkProfileEntry 2 }

		 --1.3.6.1.4.1.2011.6.139.11.1.46.1.3
		hwCellularNetworkProfileRowStatus OBJECT-TYPE
			SYNTAX RowStatus
			MAX-ACCESS read-write
			STATUS current
			DESCRIPTION 
				"This object indicates the row status of this table. createAndGo(4) and destroy(6) are commonly used."
			::= { hwCellularNetworkProfileEntry 3 }

		--1.3.6.1.4.1.2011.6.139.11.1.47
		hwConnectionCapabilityProfileTable OBJECT-TYPE
			SYNTAX SEQUENCE OF HwConnectionCapabilityProfileEntry 
			MAX-ACCESS not-accessible
			STATUS current
			DESCRIPTION 
				"This table is used to configure and query connection capability profile parameters."
			::= { hwWlanConfigObjects 47 }

		--1.3.6.1.4.1.2011.6.139.11.1.47.1
		hwConnectionCapabilityProfileEntry OBJECT-TYPE
			SYNTAX HwConnectionCapabilityProfileEntry 
			MAX-ACCESS not-accessible
			STATUS current
			DESCRIPTION 
				"The index of this table is hwConnectionCapabilityProfileName."
			INDEX { hwConnectionCapabilityProfileName }
			::= { hwConnectionCapabilityProfileTable 1 }


		HwConnectionCapabilityProfileEntry ::=
			SEQUENCE {				
				hwConnectionCapabilityProfileName
					OCTET STRING,
				hwConnectionCapabilityEsp
					INTEGER,
				hwConnectionCapabilityIcmp
					INTEGER,
				hwConnectionCapabilityTcpFtp
					INTEGER,
				hwConnectionCapabilityTcpHttp
					INTEGER,
				hwConnectionCapabilityTcpPptpVpn
					INTEGER,
				hwConnectionCapabilityTcpSsh
					INTEGER,
				hwConnectionCapabilityTcpTlsVpn
					INTEGER,
				hwConnectionCapabilityTcpVoip
					INTEGER,
				hwConnectionCapabilityUdpIke2Port4500
					INTEGER,
				hwConnectionCapabilityUdpIke2Port500
					INTEGER,
				hwConnectionCapabilityUdpVoip
					INTEGER,
				hwConnectionCapabilityProfileRowStatus
					RowStatus 
			 }

		 --1.3.6.1.4.1.2011.6.139.11.1.47.1.1
		hwConnectionCapabilityProfileName OBJECT-TYPE
			SYNTAX OCTET STRING (SIZE (1..35))
			MAX-ACCESS not-accessible
			STATUS current
			DESCRIPTION 
				"This object indicates the name of a connection capability profile. It is the index of the table."
			::= { hwConnectionCapabilityProfileEntry 1 }

		 --1.3.6.1.4.1.2011.6.139.11.1.47.1.2
		hwConnectionCapabilityEsp OBJECT-TYPE
			SYNTAX INTEGER
				{
				unknown(1),
				on(2),
				off(3)
				}
			MAX-ACCESS read-write
			STATUS current
			DESCRIPTION 
				"This object indicates whether ESP is supported.
The default value is unknown(1)."
			::= { hwConnectionCapabilityProfileEntry 2 }

		 --1.3.6.1.4.1.2011.6.139.11.1.47.1.3
		hwConnectionCapabilityIcmp OBJECT-TYPE
			SYNTAX INTEGER
				{
				unknown(1),
				on(2),
				off(3)
				}
			MAX-ACCESS read-write
			STATUS current
			DESCRIPTION 
				"This object indicates whether ICMP is supported.
The default value is unknown(1)."
			::= { hwConnectionCapabilityProfileEntry 3 }

		 --1.3.6.1.4.1.2011.6.139.11.1.47.1.4
		hwConnectionCapabilityTcpFtp OBJECT-TYPE
			SYNTAX INTEGER
				{
				unknown(1),
				on(2),
				off(3)
				}
			MAX-ACCESS read-write
			STATUS current
			DESCRIPTION 
				"This object indicates whether FTP(TCP) is supported.
The default value is unknown(1)."
			::= { hwConnectionCapabilityProfileEntry 4 }

		 --1.3.6.1.4.1.2011.6.139.11.1.47.1.5
		hwConnectionCapabilityTcpHttp OBJECT-TYPE
			SYNTAX INTEGER
				{
				unknown(1),
				on(2),
				off(3)
				}
			MAX-ACCESS read-write
			STATUS current
			DESCRIPTION 
				"This object indicates whether HTTP (port 80) is supported.
The default value is unknown(1)."
			::= { hwConnectionCapabilityProfileEntry 5 }

		 --1.3.6.1.4.1.2011.6.139.11.1.47.1.6
		hwConnectionCapabilityTcpPptpVpn OBJECT-TYPE
			SYNTAX INTEGER
				{
				unknown(1),
				on(2),
				off(3)
				}
			MAX-ACCESS read-write
			STATUS current
			DESCRIPTION 
				"This object indicates whether PPTP for VPN services (port 1723) is supported.
The default value is unknown(1)."
			::= { hwConnectionCapabilityProfileEntry 6 }

		 --1.3.6.1.4.1.2011.6.139.11.1.47.1.7
		hwConnectionCapabilityTcpSsh OBJECT-TYPE
			SYNTAX INTEGER
				{
				unknown(1),
				on(2),
				off(3)
				}
			MAX-ACCESS read-write
			STATUS current
			DESCRIPTION 
				"This object indicates whether SSH is supported.
The default value is unknown(1)."
			::= { hwConnectionCapabilityProfileEntry 7 }

		 --1.3.6.1.4.1.2011.6.139.11.1.47.1.8
		hwConnectionCapabilityTcpTlsVpn OBJECT-TYPE
			SYNTAX INTEGER
				{
				unknown(1),
				on(2),
				off(3)
				}
			MAX-ACCESS read-write
			STATUS current
			DESCRIPTION 
				"This object indicates whether TLS VPN (port 443) is supported.
The default value is unknown(1)."
			::= { hwConnectionCapabilityProfileEntry 8 }

		 --1.3.6.1.4.1.2011.6.139.11.1.47.1.9
		hwConnectionCapabilityTcpVoip OBJECT-TYPE
			SYNTAX INTEGER
				{
				unknown(1),
				on(2),
				off(3)
				}
			MAX-ACCESS read-write
			STATUS current
			DESCRIPTION 
				"This object indicates whether VoIP (port 5060) is supported.
The default value is unknown(1)."
			::= { hwConnectionCapabilityProfileEntry 9 }

		 --1.3.6.1.4.1.2011.6.139.11.1.47.1.10
		hwConnectionCapabilityUdpIke2Port4500 OBJECT-TYPE
			SYNTAX INTEGER
				{
				unknown(1),
				on(2),
				off(3)
				}
			MAX-ACCESS read-write
			STATUS current
			DESCRIPTION 
				"This object indicates whether IKEv2 (port 4500) is supported.
The default value is unknown(1)."
			::= { hwConnectionCapabilityProfileEntry 10 }

		 --1.3.6.1.4.1.2011.6.139.11.1.47.1.11
		hwConnectionCapabilityUdpIke2Port500 OBJECT-TYPE
			SYNTAX INTEGER
				{
				unknown(1),
				on(2),
				off(3)
				}
			MAX-ACCESS read-write
			STATUS current
			DESCRIPTION 
				"This object indicates whether IKEv2 (port 500) is supported.
The default value is unknown(1)."
			::= { hwConnectionCapabilityProfileEntry 11 }

		 --1.3.6.1.4.1.2011.6.139.11.1.47.1.12
		hwConnectionCapabilityUdpVoip OBJECT-TYPE
			SYNTAX INTEGER
				{
				unknown(1),
				on(2),
				off(3)
				}
			MAX-ACCESS read-write
			STATUS current
			DESCRIPTION 
				"This object indicates whether VoIP (port 5060) is supported.
The default value is unknown(1)."
			::= { hwConnectionCapabilityProfileEntry 12 }

		 --1.3.6.1.4.1.2011.6.139.11.1.47.1.13
		hwConnectionCapabilityProfileRowStatus OBJECT-TYPE
			SYNTAX RowStatus
			MAX-ACCESS read-write
			STATUS current
			DESCRIPTION 
				"This object indicates the row status of this table. createAndGo(4) and destroy(6) are commonly used."
			::= { hwConnectionCapabilityProfileEntry 13 }

		--1.3.6.1.4.1.2011.6.139.11.1.48
		hwOperatorNameProfileTable OBJECT-TYPE
			SYNTAX SEQUENCE OF HwOperatorNameProfileEntry 
			MAX-ACCESS not-accessible
			STATUS current
			DESCRIPTION 
				"This table is used to configure and query operator name profile parameters."
			::= { hwWlanConfigObjects 48 }

		--1.3.6.1.4.1.2011.6.139.11.1.48.1
		hwOperatorNameProfileEntry OBJECT-TYPE
			SYNTAX HwOperatorNameProfileEntry 
			MAX-ACCESS not-accessible
			STATUS current
			DESCRIPTION 
				"The index of this table is hwOperatorNameProfileName."
			INDEX { hwOperatorNameProfileName }
			::= { hwOperatorNameProfileTable 1 }


		HwOperatorNameProfileEntry ::=
			SEQUENCE {				
				hwOperatorNameProfileName
					OCTET STRING,
				hwOperatorNameLanguageCodeList
					OCTET STRING,
				hwOperatorFriendlyNameList
					OCTET STRING,
				hwOperatorNameProfileRowStatus
					RowStatus 
			 }

		 --1.3.6.1.4.1.2011.6.139.11.1.48.1.1
		hwOperatorNameProfileName OBJECT-TYPE
			SYNTAX OCTET STRING (SIZE (1..35))
			MAX-ACCESS not-accessible
			STATUS current
			DESCRIPTION 
				"This object indicates the name of an operator name profile. It is the index of the table."
			::= { hwOperatorNameProfileEntry 1 }

		 --1.3.6.1.4.1.2011.6.139.11.1.48.1.2
		hwOperatorNameLanguageCodeList OBJECT-TYPE
			SYNTAX OCTET STRING (SIZE (0..256))
			MAX-ACCESS read-write
			STATUS current
			DESCRIPTION 
				"A value of LanguageCode indicates a language. It is a string of 2-3 characters.
chi/zho/zh indicates Chinese and eng/en indicates English.
NOTE By default, no configuration is added.Values of LanguageCode are separated by question marks (?).A maximum of 32 LanguageCode values can be configured.A LanguageCode value must match a FriendlyName value."
			::= { hwOperatorNameProfileEntry 2 }

		 --1.3.6.1.4.1.2011.6.139.11.1.48.1.3
		hwOperatorFriendlyNameList OBJECT-TYPE
			SYNTAX OCTET STRING (SIZE (0..2048))
			MAX-ACCESS read-write
			STATUS current
			DESCRIPTION 
				"NOTE By default, no configuration is added.A FriendlyName value is a string of 1-32 characters. FriendlyName values are separated by question marks (?).A maximum of 32 FriendlyName values can be configured.A LanguageCode value must match a FriendlyName value."
			::= { hwOperatorNameProfileEntry 3 }

		 --1.3.6.1.4.1.2011.6.139.11.1.48.1.4
		hwOperatorNameProfileRowStatus OBJECT-TYPE
			SYNTAX RowStatus
			MAX-ACCESS read-write
			STATUS current
			DESCRIPTION 
				"This object indicates the row status of this table. createAndGo(4) and destroy(6) are commonly used."
			::= { hwOperatorNameProfileEntry 4 }

		--1.3.6.1.4.1.2011.6.139.11.1.49
		hwOperatorClassProfileTable OBJECT-TYPE
			SYNTAX SEQUENCE OF HwOperatorClassProfileEntry 
			MAX-ACCESS not-accessible
			STATUS current
			DESCRIPTION 
				"This table is used to configure operating class profile parameters."
			::= { hwWlanConfigObjects 49 }

		--1.3.6.1.4.1.2011.6.139.11.1.49.1
		hwOperatorClassProfileEntry OBJECT-TYPE
			SYNTAX HwOperatorClassProfileEntry 
			MAX-ACCESS not-accessible
			STATUS current
			DESCRIPTION 
				"The index of this table is hwOperatorClassProfileName."
			INDEX { hwOperatorClassProfileName }
			::= { hwOperatorClassProfileTable 1 }


		HwOperatorClassProfileEntry ::=
			SEQUENCE {				
				hwOperatorClassProfileName
					OCTET STRING,
				hwOperatorClassIndicationList
					OCTET STRING,
				hwOperatorClassProfileRowStatus
					RowStatus 
			 }

		 --1.3.6.1.4.1.2011.6.139.11.1.49.1.1
		hwOperatorClassProfileName OBJECT-TYPE
			SYNTAX OCTET STRING (SIZE (1..35))
			MAX-ACCESS not-accessible
			STATUS current
			DESCRIPTION 
				"This object indicates the name of an operating class profile profile. It is the index of the table."
			::= { hwOperatorClassProfileEntry 1 }

		 --1.3.6.1.4.1.2011.6.139.11.1.49.1.2
		hwOperatorClassIndicationList OBJECT-TYPE
			SYNTAX OCTET STRING (SIZE (0..256))
			MAX-ACCESS read-write
			STATUS current
			DESCRIPTION 
				"NOTE By default, no configuration is added.A value of OperatorClassIndication is an integer that ranges from 1 to 255.A maximum of 32 OperatorClassIndication values can be configured."
			::= { hwOperatorClassProfileEntry 2 }

		 --1.3.6.1.4.1.2011.6.139.11.1.49.1.3
		hwOperatorClassProfileRowStatus OBJECT-TYPE
			SYNTAX RowStatus
			MAX-ACCESS read-write
			STATUS current
			DESCRIPTION 
				"This object indicates the row status of this table. createAndGo(4) and destroy(6) are commonly used."
			::= { hwOperatorClassProfileEntry 3 }

		--1.3.6.1.4.1.2011.6.139.11.1.50
		hwOperatorDomainNameProfileTable OBJECT-TYPE
			SYNTAX SEQUENCE OF HwOperatorDomainNameProfileEntry 
			MAX-ACCESS not-accessible
			STATUS current
			DESCRIPTION 
				"This table is used to configure and query operator domain profile parameters."
			::= { hwWlanConfigObjects 50 }

		--1.3.6.1.4.1.2011.6.139.11.1.50.1
		hwOperatorDomainNameProfileEntry OBJECT-TYPE
			SYNTAX HwOperatorDomainNameProfileEntry 
			MAX-ACCESS not-accessible
			STATUS current
			DESCRIPTION 
				"The index of this table is hwOperatorDomainNameProfileName."
			INDEX { hwOperatorDomainNameProfileName }
			::= { hwOperatorDomainNameProfileTable 1 }


		HwOperatorDomainNameProfileEntry ::=
			SEQUENCE {				
				hwOperatorDomainNameProfileName
					OCTET STRING,
				hwOperatorDomainNameList
					OCTET STRING,
				hwOperatorDomainNameProfileRowStatus
					RowStatus 
			 }

		 --1.3.6.1.4.1.2011.6.139.11.1.50.1.1
		hwOperatorDomainNameProfileName OBJECT-TYPE
			SYNTAX OCTET STRING (SIZE (1..35))
			MAX-ACCESS not-accessible
			STATUS current
			DESCRIPTION 
				"This object indicates the name of an operating class profile profile. It is the index of the table."
			::= { hwOperatorDomainNameProfileEntry 1 }

		 --1.3.6.1.4.1.2011.6.139.11.1.50.1.2
		hwOperatorDomainNameList OBJECT-TYPE
			SYNTAX OCTET STRING (SIZE (0..2048))
			MAX-ACCESS read-write
			STATUS current
			DESCRIPTION 
				"NOTE By default, no configuration is added.A DomainName value is a string of 1-64 characters in compliance with RFC1035.DomainName values are separated by question marks (?).A maximum of 32 DomainName values can be configured."
			::= { hwOperatorDomainNameProfileEntry 2 }

		 --1.3.6.1.4.1.2011.6.139.11.1.50.1.3
		hwOperatorDomainNameProfileRowStatus OBJECT-TYPE
			SYNTAX RowStatus
			MAX-ACCESS read-write
			STATUS current
			DESCRIPTION 
				"This object indicates the row status of this table. createAndGo(4) and destroy(6) are commonly used."
			::= { hwOperatorDomainNameProfileEntry 3 }

		--1.3.6.1.4.1.2011.6.139.11.1.51
		hwNAIRealmProfileTable OBJECT-TYPE
			SYNTAX SEQUENCE OF HwNAIRealmProfileEntry 
			MAX-ACCESS not-accessible
			STATUS current
			DESCRIPTION 
				"This table is used to configure and query NAI realm profile parameters."
			::= { hwWlanConfigObjects 51 }

		--1.3.6.1.4.1.2011.6.139.11.1.51.1
		hwNAIRealmProfileEntry OBJECT-TYPE
			SYNTAX HwNAIRealmProfileEntry 
			MAX-ACCESS not-accessible
			STATUS current
			DESCRIPTION 
				"Indexes of this table are hwNAIRealmProfileName, hwNAIRealmName, hwNAIRealmEapMethodType, and hwNAIRealmEapAuthenID."
			INDEX { hwNAIRealmProfileName,hwNAIRealmName,hwNAIRealmEapMethodType,hwNAIRealmEapAuthenID }
			::= { hwNAIRealmProfileTable 1 }


		HwNAIRealmProfileEntry ::=
			SEQUENCE {				
				hwNAIRealmProfileName
					OCTET STRING,
				hwNAIRealmName
					OCTET STRING,
				hwNAIRealmEapMethodType
					Unsigned32,
				hwNAIRealmEapAuthenID
					Unsigned32,
				hwNAIRealmEapAuthenPara
					Unsigned32,
				hwNAIRealmProfileRowStatus
					RowStatus
			 }

		 --1.3.6.1.4.1.2011.6.139.11.1.51.1.1
		hwNAIRealmProfileName OBJECT-TYPE
			SYNTAX OCTET STRING (SIZE (1..35))
			MAX-ACCESS not-accessible
			STATUS current
			DESCRIPTION 
				"This object indicates the name of a NAI realm profile. It is the index of the table."
			::= { hwNAIRealmProfileEntry 1 }

		 --1.3.6.1.4.1.2011.6.139.11.1.51.1.2
		hwNAIRealmName OBJECT-TYPE
			SYNTAX OCTET STRING (SIZE (0..63))
			MAX-ACCESS not-accessible
			STATUS current
			DESCRIPTION 
				"This object indicates a network identifier."
			::= { hwNAIRealmProfileEntry 2 }

		 --1.3.6.1.4.1.2011.6.139.11.1.51.1.3
		hwNAIRealmEapMethodType OBJECT-TYPE
			SYNTAX Unsigned32 (0..255 | 4294967295)
			MAX-ACCESS not-accessible
			STATUS current
			DESCRIPTION 
				"This object indicates the authorization type.
The default value is 0xffffffff that indicates that the following four types are supported: EAP_AKA, EAP_SIM, EAP_TLS, and EAP_TTLS."
			::= { hwNAIRealmProfileEntry 3 }

		 --1.3.6.1.4.1.2011.6.139.11.1.51.1.4
		hwNAIRealmEapAuthenID OBJECT-TYPE
			SYNTAX Unsigned32 (0..255 | 4294967295)
			MAX-ACCESS not-accessible
			STATUS current
			DESCRIPTION 
				"This object indicates the authorization ID.
The default value is 0xffffffff that indicates that all IDs within the value range are supported."
			::= { hwNAIRealmProfileEntry 4 }

		 --1.3.6.1.4.1.2011.6.139.11.1.51.1.5
		hwNAIRealmEapAuthenPara OBJECT-TYPE
			SYNTAX Unsigned32 (0..255 | 4294967295)
			MAX-ACCESS read-write
			STATUS current
			DESCRIPTION 
				"This object indicate authorization parameter.
The default value is 0xffffffff that indicates all parameters within the value range are supported."
			::= { hwNAIRealmProfileEntry 5 }

		 --1.3.6.1.4.1.2011.6.139.11.1.51.1.6
		hwNAIRealmProfileRowStatus OBJECT-TYPE
			SYNTAX RowStatus
			MAX-ACCESS read-write
			STATUS current
			DESCRIPTION 
				"This object indicates the row status of this table. createAndGo(4) and destroy(6) are commonly used."
			::= { hwNAIRealmProfileEntry 6 }

		--1.3.6.1.4.1.2011.6.139.11.1.52
		hwVenueNameProfileTable OBJECT-TYPE
			SYNTAX SEQUENCE OF HwVenueNameProfileEntry 
			MAX-ACCESS not-accessible
			STATUS current
			DESCRIPTION 
				"This table is used to configure and query venue name profile parameters."
			::= { hwWlanConfigObjects 52 }

		--1.3.6.1.4.1.2011.6.139.11.1.52.1
		hwVenueNameProfileEntry OBJECT-TYPE
			SYNTAX HwVenueNameProfileEntry 
			MAX-ACCESS not-accessible
			STATUS current
			DESCRIPTION 
				"The index of this table is hwVenueNameProfileName."
			INDEX { hwVenueNameProfileName }
			::= { hwVenueNameProfileTable 1 }


		HwVenueNameProfileEntry ::=
			SEQUENCE {				
				hwVenueNameProfileName
					OCTET STRING,
				hwVenueNameLanguageCodeList
					OCTET STRING,
				hwVenueNameList
					OCTET STRING,
				hwVenueNameProfileRowStatus
					RowStatus 
			 }

		 --1.3.6.1.4.1.2011.6.139.11.1.52.1.1
		hwVenueNameProfileName OBJECT-TYPE
			SYNTAX OCTET STRING (SIZE (1..35))
			MAX-ACCESS not-accessible
			STATUS current
			DESCRIPTION 
				"This object indicates the name of a venue name profile. It is the index of the table."
			::= { hwVenueNameProfileEntry 1 }

		 --1.3.6.1.4.1.2011.6.139.11.1.52.1.2
		hwVenueNameLanguageCodeList OBJECT-TYPE
			SYNTAX OCTET STRING (SIZE (0..256))
			MAX-ACCESS read-write
			STATUS current
			DESCRIPTION 
				"A value of LanguageCode indicates a language. It is a string of 2-3 characters.
For details about GUI value ranges, see ISO 639 on the Codes for the Representation of Names of Languages page. The path is http://www.loc.gov/standards/iso639-2/php/ code_list.php. chi/zho/zh indicates Chinese and eng/en indicates English.
NOTE By default, no configuration is added.Values of LanguageCode are separated by question marks (?).A maximum of 32 LanguageCode values can be configured.A LanguageCode value must match a VenueName value."
			::= { hwVenueNameProfileEntry 2 }

		 --1.3.6.1.4.1.2011.6.139.11.1.52.1.3
		hwVenueNameList OBJECT-TYPE
			SYNTAX OCTET STRING (SIZE (0..2048))
			MAX-ACCESS read-write
			STATUS current
			DESCRIPTION 
				"If the language-code is set to eng, the name is a string of characters. Rules are the same as those for SSIDs. When it is set to other values, the venue-name is set to a hexadecimal UTF-8 code because current WLANs support English only, for example, venue-name language-code ZHO name 025AB1472568.
NOTE By default, no configuration is added.A venue-name value cannot exceed 32 characters.venue-name values are separated by question marks (?).A LanguageCode value must match a VenueName value."
			::= { hwVenueNameProfileEntry 3 }

		 --1.3.6.1.4.1.2011.6.139.11.1.52.1.4
		hwVenueNameProfileRowStatus OBJECT-TYPE
			SYNTAX RowStatus
			MAX-ACCESS read-write
			STATUS current
			DESCRIPTION 
				"This object indicates the row status of this table. createAndGo(4) and destroy(6) are commonly used."
			::= { hwVenueNameProfileEntry 4 }

		--1.3.6.1.4.1.2011.6.139.11.1.53
		hwRoamingConsortiumProfileTable OBJECT-TYPE
			SYNTAX SEQUENCE OF HwRoamingConsortiumProfileEntry 
			MAX-ACCESS not-accessible
			STATUS current
			DESCRIPTION 
				"This table is used to configure and query roaming consortium profile parameters."
			::= { hwWlanConfigObjects 53 }

		--1.3.6.1.4.1.2011.6.139.11.1.53.1
		hwRoamingConsortiumProfileEntry OBJECT-TYPE
			SYNTAX HwRoamingConsortiumProfileEntry 
			MAX-ACCESS not-accessible
			STATUS current
			DESCRIPTION 
				"The index of this table is hwRoamingConsortiumProfileName."
			INDEX { hwRoamingConsortiumProfileName }
			::= { hwRoamingConsortiumProfileTable 1 }


		HwRoamingConsortiumProfileEntry ::=
			SEQUENCE {				
				hwRoamingConsortiumProfileName
					OCTET STRING,
				hwRoamingConsortiumOIList
					OCTET STRING,
				hwRoamingConsortiumOIInBeaconList
					OCTET STRING,
				hwRoamingConsortiumProfileRowStatus
					RowStatus 
			 }

		 --1.3.6.1.4.1.2011.6.139.11.1.53.1.1
		hwRoamingConsortiumProfileName OBJECT-TYPE
			SYNTAX OCTET STRING (SIZE (1..35))
			MAX-ACCESS not-accessible
			STATUS current
			DESCRIPTION 
				"This object indicates the name of a roaming consortium profile. It is the index of the table."
			::= { hwRoamingConsortiumProfileEntry 1 }

		 --1.3.6.1.4.1.2011.6.139.11.1.53.1.2
		hwRoamingConsortiumOIList OBJECT-TYPE
			SYNTAX OCTET STRING
			MAX-ACCESS read-write
			STATUS current
			DESCRIPTION 
				"This object indicates the roaming consortium member.
The roaming consortium OI is a hexadecimal number in the format of HH-HH-HH or HH-HH-HH-HH-HH. The length of a roaming consortium OI is three to five bytes, for example, 12-34-56?12-34-58?34-45-67.
NOTE By default, no configuration is added.RoamingConsortiumOI values are separated by question marks (?).A maximum of 32 RoamingConsortiumOI values can be configured.A RoamingConsortiumOI value must match an OIInBeacon value."
			::= { hwRoamingConsortiumProfileEntry 2 }

		 --1.3.6.1.4.1.2011.6.139.11.1.53.1.3
		hwRoamingConsortiumOIInBeaconList OBJECT-TYPE
			SYNTAX OCTET STRING
			MAX-ACCESS read-write
			STATUS current
			DESCRIPTION 
				"This object indicates whether a roaming consortium member carries the inbeacon tag, for example, YES?NO?NO.
NOTE By default, no configuration is added.A RoamingConsortiumOI value must match an OIInBeacon value.A maximum of three RoamingConsortiumOI values can be configured.in-beacon can be set to YES."
			::= { hwRoamingConsortiumProfileEntry 3 }

		 --1.3.6.1.4.1.2011.6.139.11.1.53.1.4
		hwRoamingConsortiumProfileRowStatus OBJECT-TYPE
			SYNTAX RowStatus
			MAX-ACCESS read-write
			STATUS current
			DESCRIPTION 
				"This object indicates the row status of this table. createAndGo(4) and destroy(6) are commonly used."
			::= { hwRoamingConsortiumProfileEntry 4 }
		

		-- 1.3.6.1.4.1.2011.6.139.11.1.54
		hwSACProfileTable OBJECT-TYPE
			SYNTAX SEQUENCE OF HwSACProfileEntry 
			MAX-ACCESS not-accessible
			STATUS current
			DESCRIPTION 
				"This table is used to configure and query SAC profile parameters."
			::= { hwWlanConfigObjects 54 }
		

		-- 1.3.6.1.4.1.2011.6.139.11.1.54.1
		hwSACProfileEntry OBJECT-TYPE
			SYNTAX HwSACProfileEntry 
			MAX-ACCESS not-accessible
			STATUS current
			DESCRIPTION 
				"The index of this table is hwSACProfileName."
			INDEX { hwSACProfileName }
			::= { hwSACProfileTable 1 }


		HwSACProfileEntry ::=
			SEQUENCE {				
				hwSACProfileName
					OCTET STRING,
				hwSACProfUserStat
					INTEGER,
				hwSACProfVapStat
					INTEGER,
				hwSACProfRowStatus
					RowStatus 
			 }

	
		-- 1.3.6.1.4.1.2011.6.139.11.1.54.1.1
		hwSACProfileName OBJECT-TYPE
			SYNTAX OCTET STRING (SIZE (1..35))
			MAX-ACCESS not-accessible
			STATUS current
			DESCRIPTION 
				"This object indicates the name of an SAC profile. It is the index of the table."
			::= { hwSACProfileEntry 1 }

	
		-- 1.3.6.1.4.1.2011.6.139.11.1.54.1.2
		hwSACProfUserStat OBJECT-TYPE
			SYNTAX INTEGER
				{
				disable(1),
				enable(2)
				}
			MAX-ACCESS read-write
			STATUS current
			DESCRIPTION 
				"This object indicates whether the user statistics function is enabled in the SAC profile.
The default value is disable (1)."
			::= { hwSACProfileEntry 2 }

		 
		-- 1.3.6.1.4.1.2011.6.139.11.1.54.1.3
		hwSACProfVapStat OBJECT-TYPE
			SYNTAX INTEGER
				{
				disable(1),
				enable(2)
				}
			MAX-ACCESS read-write
			STATUS current
			DESCRIPTION 
				"This object indicates whether the VAP statistics function is enabled in the SAC profile.
The default value is disable (1)."
			::= { hwSACProfileEntry 3 }


		-- 1.3.6.1.4.1.2011.6.139.11.1.54.1.4
		hwSACProfRowStatus OBJECT-TYPE
			SYNTAX RowStatus
			MAX-ACCESS read-write
			STATUS current
			DESCRIPTION 
				"This object indicates the row status."
			::= { hwSACProfileEntry 4 }

		-- 1.3.6.1.4.1.2011.6.139.11.1.55
		hwSACProfileActionTable OBJECT-TYPE
			SYNTAX SEQUENCE OF HwSACProfileActionEntry 
			MAX-ACCESS not-accessible
			STATUS current
			DESCRIPTION 
				"This table describes SAC profile action configurations.This table is used to configure actions in an SAC profile."
			::= { hwWlanConfigObjects 55 }
		
		-- 1.3.6.1.4.1.2011.6.139.11.1.55.1
		hwSACProfileActionEntry OBJECT-TYPE
			SYNTAX HwSACProfileActionEntry 
			MAX-ACCESS not-accessible
			STATUS current
			DESCRIPTION 
				"Indexes of this table are hwSACProfileName and hwSACProfileActionIndex."
			INDEX { hwSACProfileName,hwSACProfileActionIndex}
			::= { hwSACProfileActionTable 1 }


		HwSACProfileActionEntry ::=
			SEQUENCE {				
				hwSACProfileActionIndex
					Unsigned32,
				hwSACProfileActProtocolType
					INTEGER,
				hwSACProfileActProtocolName
					OCTET STRING,
				hwSACProfileActProtocolGrpName
					OCTET STRING,
				hwSACProfileActionType
					INTEGER,
				hwSACProfileActCarCir
					Unsigned32,
				hwSACProfileActRemarkDscpValue
					Unsigned32,
				hwSACProfileActRemark8021pValue
					Unsigned32,
				hwSACProfileActionRowstatus
					RowStatus 
			 }

		-- 1.3.6.1.4.1.2011.6.139.11.1.55.1.1
		hwSACProfileActionIndex OBJECT-TYPE
			SYNTAX Unsigned32
			MAX-ACCESS not-accessible
			STATUS current
			DESCRIPTION 
				"This object indicates the internal index of the action. It is the index of the table."
			::= { hwSACProfileActionEntry 1 }

		-- 1.3.6.1.4.1.2011.6.139.11.1.55.1.2
		hwSACProfileActProtocolType OBJECT-TYPE
			SYNTAX INTEGER
				{
				unknown(0) ,
				application(1) ,
				applicationGroup(2)
				}
			MAX-ACCESS read-write
			STATUS current
			DESCRIPTION 
				"This object indicates the protocol type."
			::= { hwSACProfileActionEntry 2 }

		-- 1.3.6.1.4.1.2011.6.139.11.1.55.1.3
		hwSACProfileActProtocolName OBJECT-TYPE
			SYNTAX OCTET STRING (SIZE (0..255))
			MAX-ACCESS read-write
			STATUS current
			DESCRIPTION 
				"This object indicates the protocol name."
			::= { hwSACProfileActionEntry 3 }

		-- 1.3.6.1.4.1.2011.6.139.11.1.55.1.4
		hwSACProfileActProtocolGrpName OBJECT-TYPE
			SYNTAX OCTET STRING (SIZE (0..35))
			MAX-ACCESS read-write
			STATUS current
			DESCRIPTION 
				"This object indicates the protocol group name."
			::= { hwSACProfileActionEntry 4 }
		

		-- 1.3.6.1.4.1.2011.6.139.11.1.55.1.5
		hwSACProfileActionType OBJECT-TYPE
			SYNTAX INTEGER
				{
				unknown(0) ,
				deny(1),
				car(2),
				remarkDscp(3),
				remark8021p(4)
				}
			MAX-ACCESS read-create
			STATUS current
			DESCRIPTION 
				"This object indicates the action type."
			::= { hwSACProfileActionEntry 5 }
		

		-- 1.3.6.1.4.1.2011.6.139.11.1.55.1.6
		hwSACProfileActCarCir OBJECT-TYPE
			SYNTAX Unsigned32 (64..10000000|4294967295)
			MAX-ACCESS read-write
			STATUS current
			DESCRIPTION 
				"This object indicates the CAR CIR value."
			::= { hwSACProfileActionEntry 6 }
		

		-- 1.3.6.1.4.1.2011.6.139.11.1.55.1.7
		hwSACProfileActRemarkDscpValue OBJECT-TYPE
			SYNTAX Unsigned32 (0..63)
			MAX-ACCESS read-write
			STATUS current
			DESCRIPTION 
				"This object indicates the DSCP value."
			::= { hwSACProfileActionEntry 7 }
		

		-- 1.3.6.1.4.1.2011.6.139.11.1.55.1.8
		hwSACProfileActRemark8021pValue OBJECT-TYPE
			SYNTAX Unsigned32 (0..7)
			MAX-ACCESS read-write
			STATUS current
			DESCRIPTION 
				"This object indicates the 802.1p priority."
			::= { hwSACProfileActionEntry 8 }
		

		-- 1.3.6.1.4.1.2011.6.139.11.1.55.1.9
		hwSACProfileActionRowstatus OBJECT-TYPE
			SYNTAX RowStatus
			MAX-ACCESS read-write
			STATUS current
			DESCRIPTION 
				"This object indicates the row status."
			::= { hwSACProfileActionEntry 9 }
		

		-- 1.3.6.1.4.1.2011.6.139.11.1.56
		hwWlanAPProvision OBJECT IDENTIFIER ::= { hwWlanConfigObjects 56 }

		

		 --1.3.6.1.4.1.2011.6.139.11.1.59.2
		-- 1.3.6.1.4.1.2011.6.139.11.1.56.1
		hwWlanAPProvisionAddressMode OBJECT-TYPE
			SYNTAX INTEGER
				{
				static(1),
				dhcp(2),
				slaac(3),
				invalid(-1)
				}
			MAX-ACCESS read-write
			STATUS current
			DESCRIPTION 
				"This object indicates the IPv4 address allocation mode."
			::= { hwWlanAPProvision 1 }

		 --1.3.6.1.4.1.2011.6.139.11.1.59.3
		hwWlanAPProvisionIPv4Address OBJECT-TYPE
			SYNTAX IpAddress
			MAX-ACCESS read-write
			STATUS current
			DESCRIPTION 
				"This object indicates the AP's IPv4 address.
hwWlanAPProvisionIPv4Address takes effect if hwAPIPv4Method is set to static."
			::= { hwWlanAPProvision 2 }

		 --1.3.6.1.4.1.2011.6.139.11.1.59.4
		hwWlanAPProvisionIPv4Mask OBJECT-TYPE
			SYNTAX IpAddress
			MAX-ACCESS read-write
			STATUS current
			DESCRIPTION 
				"This object indicates the AP's IPv4 mask.
hwWlanAPProvisionIPv4Mask takes effect if hwAPIPv4Method is set to static."
			::= { hwWlanAPProvision 3 }

		 --1.3.6.1.4.1.2011.6.139.11.1.59.5
		hwWlanAPProvisionIPv4Gateway OBJECT-TYPE
			SYNTAX IpAddress
			MAX-ACCESS read-write
			STATUS current
			DESCRIPTION 
				"This object indicates the AP's IPv4 gateway.
hwWlanAPProvisionIPv4Gateway takes effect if hwAPIPv4Method is set to static."
			::= { hwWlanAPProvision 4 }

		 --1.3.6.1.4.1.2011.6.139.11.1.59.6
		hwWlanAPProvisionIPv6Address OBJECT-TYPE
			SYNTAX OCTET STRING (SIZE (0..46))
			MAX-ACCESS read-write
			STATUS current
			DESCRIPTION 
				"This object indicates the AP's IPv6 address.
hwWlanAPProvisionIPv6Address takes effect if hwAPIPv6Method is set to static."
			::= { hwWlanAPProvision 5 }

		 --1.3.6.1.4.1.2011.6.139.11.1.59.7
		hwWlanAPProvisionIPv6PrefixLen OBJECT-TYPE
			SYNTAX Unsigned32 (0..128)
			MAX-ACCESS read-write
			STATUS current
			DESCRIPTION 
				"This object indicates the length of the IPv6 address prefix."
			::= { hwWlanAPProvision 6 }

		
		 --1.3.6.1.4.1.2011.6.139.11.1.59.8
		hwWlanAPProvisionIPv6Gateway OBJECT-TYPE
			SYNTAX OCTET STRING (SIZE (0..46))
			MAX-ACCESS read-write
			STATUS current
			DESCRIPTION 
				"This object indicates the AP's IPv6 gateway.
hwWlanAPProvisionIPv6Gateway takes effect if hwAPIPv6Method is set to static."
			::= { hwWlanAPProvision 7 }

		 --1.3.6.1.4.1.2011.6.139.11.1.59.9
		hwWlanAPProvisionGroupName OBJECT-TYPE
			SYNTAX OCTET STRING (SIZE (0..35))
			MAX-ACCESS read-write
			STATUS current
			DESCRIPTION 
				"This object indicates the group name."
			::= { hwWlanAPProvision 8 }

		 --1.3.6.1.4.1.2011.6.139.11.1.59.10
		hwWlanAPProvisionName OBJECT-TYPE
			SYNTAX OCTET STRING (SIZE (0..31))
			MAX-ACCESS read-write
			STATUS current
			DESCRIPTION 
				"This object indicates the name of an AP."
			::= { hwWlanAPProvision 9 }

		 --1.3.6.1.4.1.2011.6.139.11.1.59.11
		hwWlanAPProvisionIPv4ACList OBJECT-TYPE
			SYNTAX OCTET STRING
			MAX-ACCESS read-write
			STATUS current
			DESCRIPTION 
				"This object indicates the AC IPv4 address list.
NOTE ACL rules are separated by question marks (?).A maximum of four ACL rules can be configured."
			::= { hwWlanAPProvision 10 }

		 --1.3.6.1.4.1.2011.6.139.11.1.59.12
		hwWlanAPProvisionIPv6ACList OBJECT-TYPE
			SYNTAX OCTET STRING
			MAX-ACCESS read-write
			STATUS current
			DESCRIPTION 
				"This object indicates the AC IPv6 address list.
NOTE ACL rules are separated by question marks (?).A maximum of four ACL rules can be configured."
			::= { hwWlanAPProvision 11 }

		 --1.3.6.1.4.1.2011.6.139.11.1.59.13
		hwWlanAPProvisionCommitAPName OBJECT-TYPE
			SYNTAX OCTET STRING (SIZE (1..31))
			MAX-ACCESS read-write
			STATUS current
			DESCRIPTION 
				"This object indicates that the configuration is delivered based on AP names."
			::= { hwWlanAPProvision 12 }

		 --1.3.6.1.4.1.2011.6.139.11.1.59.14
		hwWlanAPProvisionCommitAPMac OBJECT-TYPE
			SYNTAX MacAddress
			MAX-ACCESS read-write
			STATUS current
			DESCRIPTION 
				"This object indicates that the configuration is delivered based on MAC addresses of APs."
			::= { hwWlanAPProvision 13 }

		 --1.3.6.1.4.1.2011.6.139.11.1.59.15
		hwWlanAPProvisionCommitAPGroup OBJECT-TYPE
			SYNTAX OCTET STRING (SIZE (1..35))
			MAX-ACCESS read-write
			STATUS current
			DESCRIPTION 
				"This object indicates that the configuration is delivered based on AP groups."
			::= { hwWlanAPProvision 14 }
			
		hwWlanAPProvisionAPMode OBJECT-TYPE
			SYNTAX INTEGER
				{
				fat(1),
				cloud(2),
				invalid(-1)
				}
			MAX-ACCESS read-write
			STATUS current
			DESCRIPTION 
				"This object indicates the AP mode."
			::= { hwWlanAPProvision 15 }
			
		hwWlanAPProvisionCommitAPId OBJECT-TYPE
			SYNTAX Unsigned32
			MAX-ACCESS read-write
			STATUS current
			DESCRIPTION
				"This object indicates that the configuration is delivered based on AP ID."
			::= { hwWlanAPProvision 16 }
			
		hwWlanAPProvisionCommitAll OBJECT-TYPE
			SYNTAX Integer32
			MAX-ACCESS read-write
			STATUS current
			DESCRIPTION 
				"This object indicates that the configuration is delivered to all APs."
			::= { hwWlanAPProvision 17 }

		hwWlanAPProvisionManagementVlan OBJECT-TYPE
			SYNTAX Unsigned32 (0..4094)
			MAX-ACCESS read-write
			STATUS current
			DESCRIPTION 
				"This object indicates that the AP management vlan."
			::= { hwWlanAPProvision 18 }
			
		--1.3.6.1.4.1.2011.6.139.11.1.60
		hwWlanRadioCalibrateManagement OBJECT IDENTIFIER ::= { hwWlanConfigObjects 57 }

	
		-- 1.3.6.1.4.1.2011.6.139.11.1.57.1
		hwWlanRadioCalibrateMode OBJECT-TYPE
			SYNTAX INTEGER
				{
				auto(1),
				manual(2),
				schedule(3)
				}
			MAX-ACCESS read-write
			STATUS current
			DESCRIPTION 
				"This object indicates the radio calibration mode.
The default value is auto(1)."
			::= { hwWlanRadioCalibrateManagement 1 }

		-- 1.3.6.1.4.1.2011.6.139.11.1.57.2
		hwWlanRadioCalibrateScheduleTime OBJECT-TYPE
			SYNTAX OCTET STRING
			MAX-ACCESS read-write
			STATUS current
			DESCRIPTION 
				"This object indicates the scheduled radio calibration time."
			::= { hwWlanRadioCalibrateManagement 2 }

	
		-- 1.3.6.1.4.1.2011.6.139.11.1.57.3
		hwWlanRadioCalibrateManualStartup OBJECT-TYPE
			SYNTAX Integer32 (1)
			MAX-ACCESS read-write
			STATUS current
			DESCRIPTION 
				"This object indicates the manually triggered radio calibration. It is valid only when the radio calibration mode is manual."
			::= { hwWlanRadioCalibrateManagement 3 }

		 
		-- 1.3.6.1.4.1.2011.6.139.11.1.57.4
		hwWlanRadioCalibrateAutoInterval OBJECT-TYPE
			SYNTAX Integer32 (30..1440)
			MAX-ACCESS read-write
			STATUS current
			DESCRIPTION 
				"This object indicates the automatic radio calibration interval.
It is expressed in minutes.
The default value is 1440."
			::= { hwWlanRadioCalibrateManagement 4 }


		-- 1.3.6.1.4.1.2011.6.139.11.1.57.5
		hwWlanRadioCalibratePolicy OBJECT-TYPE
			SYNTAX Unsigned32
			MAX-ACCESS read-write
			STATUS current
			DESCRIPTION 
				"This object indicates the radio calibration policy.bit0: rogue-ap bit2: nonWifi bit3: noise-floor bit1 is invalid.
				The default value is 0, indicating that this function is not enabled."
			::= { hwWlanRadioCalibrateManagement 5 }

		 --1.3.6.1.4.1.2011.6.139.11.1.60.6
		-- 1.3.6.1.4.1.2011.6.139.11.1.57.6
		hwWlanRadioCalibrateSensitivity OBJECT-TYPE
			SYNTAX INTEGER
				{
				medium(1),
				high(2),
				low(3),
				insensitivity(4), 
				custom(5) 
				}
			MAX-ACCESS read-write
			STATUS current
			DESCRIPTION 
				"This object indicates the radio calibration sensitivity.
The default value is medium(1)."
			::= { hwWlanRadioCalibrateManagement 6 }

		 --1.3.6.1.4.1.2011.6.139.11.1.60.7
		-- 1.3.6.1.4.1.2011.6.139.11.1.57.7
		hwWlanRadioCalibrateAutoStartTime OBJECT-TYPE
			SYNTAX OCTET STRING
			MAX-ACCESS read-write
			STATUS current
			DESCRIPTION 
				"This object indicates the start time of automatic radio calibration.
				The default value is 03:00:00."
			::= { hwWlanRadioCalibrateManagement 7 }


		-- 1.3.6.1.4.1.2011.6.139.11.1.57.8
		hwWlanRadioCalibrateManualApGroup OBJECT-TYPE
			SYNTAX OCTET STRING
			MAX-ACCESS read-write
			STATUS current
			DESCRIPTION
				"This object indicates the manually triggered radio calibration based on the AP group. 
				It is valid only when the radio calibration mode is manual."
			::= { hwWlanRadioCalibrateManagement 8 }


		-- 1.3.6.1.4.1.2011.6.139.11.1.57.9
		hwWlanRadioCalibrateManualApList OBJECT-TYPE
			SYNTAX OCTET STRING
			MAX-ACCESS read-write
			STATUS current
			DESCRIPTION
				"This object indicates the manually triggered radio calibrationbased on the AP list. 
				It is valid only when the radio calibration mode is manual."
			::= { hwWlanRadioCalibrateManagement 9 }


		-- 1.3.6.1.4.1.2011.6.139.11.1.57.10
		hwWlanRadioCalibrateManualProcess OBJECT-TYPE
			SYNTAX Integer32 (0..100)
			MAX-ACCESS read-only
			STATUS current
			DESCRIPTION
				"This object indicates the radio calibration status"
			::= { hwWlanRadioCalibrateManagement 10 }
		
		-- 1.3.6.1.4.1.2011.6.139.11.1.57.11
		hwWlanRadioCalibrateFlexibleRadio OBJECT-TYPE
			SYNTAX INTEGER
				{
				disable(1),
				autoSwitch(2),
				autoOff(3)
				}
			MAX-ACCESS read-write
			STATUS current
			DESCRIPTION
				"This object indicates the calibration radio flexible-radio status switch.
				The default value is disable(1)."
			::= { hwWlanRadioCalibrateManagement 11 }
        -- 1.3.6.1.4.1.2011.6.139.11.1.57.12
		hwWlanRadioCalibrateFlexRadioManualRecognize OBJECT-TYPE
			SYNTAX INTEGER
				{
				enable(1)
				}
			MAX-ACCESS read-write
			STATUS current
			DESCRIPTION
				"This object indicates the calibration radio flexible-radio manual recognize."
			::= { hwWlanRadioCalibrateManagement 12 }   
        -- 1.3.6.1.4.1.2011.6.139.11.1.57.13
		hwWlanRadioCalibrateFlexibleRadioProcess OBJECT-TYPE
			SYNTAX INTEGER
				{
				identifying(1),
				nonidentifying(2)
				}
			MAX-ACCESS read-only
			STATUS current
			DESCRIPTION
				"This object indicates the calibration radio flexible-radio process."
			::= { hwWlanRadioCalibrateManagement 13 }
		-- 1.3.6.1.4.1.2011.6.139.11.1.57.14
        	hwWlanRadioCalibrateFlexibleRadioRecognizeTime OBJECT-TYPE
			SYNTAX OCTET STRING
			MAX-ACCESS read-only
			STATUS current
			DESCRIPTION
				"This object indicates the start time of flxible radio recolonization."
			::= { hwWlanRadioCalibrateManagement 14 }

		-- 1.3.6.1.4.1.2011.6.139.11.1.57.15
        	hwWlanRadioCalibrateSensitivityCustomValue OBJECT-TYPE
			SYNTAX Unsigned32 (0..95)
			MAX-ACCESS read-write
			STATUS current
			DESCRIPTION
				"This object indicates the custom threshold of calibrate sensitivity. It can be set when hwWlanRadioCalibrateSensitivity is custom(5). A larger value indicates lower calibration sensitivity."
			::= { hwWlanRadioCalibrateManagement 15 }
			
		-- 1.3.6.1.4.1.2011.6.139.11.1.57.16
		hwWlanRadioCalibrateScheduleTimeRange OBJECT-TYPE
			SYNTAX OCTET STRING (SIZE (1..32))
			MAX-ACCESS read-write
			STATUS current
			DESCRIPTION
				"Description."
			::= { hwWlanRadioCalibrateManagement 16 }
		-- 1.3.6.1.4.1.2011.6.139.11.1.57.17
        	hwWlanRadioCalibrateReferenceDataAnalysis OBJECT-TYPE
			SYNTAX INTEGER
				{
				disable(1) ,
				enable(2)
				}
			MAX-ACCESS read-write
			STATUS current
			DESCRIPTION
				"This object indicates the status of the referencing data-analysis  function. The default value is 2."
			::= { hwWlanRadioCalibrateManagement 17 }

		-- 1.3.6.1.4.1.2011.6.139.11.1.57.18
        	hwWlanRadioCalibrateEnvironmentDeteriorateValue OBJECT-TYPE
			SYNTAX Unsigned32 (1..48)
			MAX-ACCESS read-write
			STATUS current
			DESCRIPTION
				"This object indicates the environment deterioration threshold function. The default value is 16."
			::= { hwWlanRadioCalibrateManagement 18 }
		                 
--    1.3.6.1.4.1.2011.6.139.11.1.61
-- 1.3.6.1.4.1.2011.6.139.11.1.58
-- 1.3.6.1.4.1.2011.6.139.11.1.58
-- 1.3.6.1.4.1.2011.6.139.11.1.58
-- 1.3.6.1.4.1.2011.6.139.11.1.58
		-- 1.3.6.1.4.1.2011.6.139.11.1.58
		hwWlanMobilityObjects OBJECT IDENTIFIER ::= { hwWlanConfigObjects 58 }
		
--  1.3.6.1.4.1.2011.6.139.11.1.61.1
-- 1.3.6.1.4.1.2011.6.139.11.1.61.1
		-- 1.3.6.1.4.1.2011.6.139.11.1.58.1
		hwWlanMobilityManagement OBJECT IDENTIFIER ::= { hwWlanMobilityObjects 1 }

		 --1.3.6.1.4.1.2011.6.139.11.1.61.1.1
		-- 1.3.6.1.4.1.2011.6.139.11.1.58.1.1
		hwWlanMasterControllerSwitch OBJECT-TYPE
			SYNTAX INTEGER
				{
				disable(1) ,
				enable(2)
				}
			MAX-ACCESS read-write
			STATUS current
			DESCRIPTION 
				"This object indicates the status of the CUC function.
The default value is disable (1)."
			::= { hwWlanMobilityManagement 1 }

		 --1.3.6.1.4.1.2011.6.139.11.1.61.1.2
		-- 1.3.6.1.4.1.2011.6.139.11.1.58.1.2
		hwWlanConnectMasterControllerSwitch OBJECT-TYPE
			SYNTAX INTEGER
				{
				disconnect(1) ,
				connect(2)
				}
			MAX-ACCESS read-write
			STATUS current
			DESCRIPTION 
				"This objection indicates the status of the connection between the AC and Master Controller. The establishment of connection between the AC and Master Controller requires the IP address of the Master Controller.
The default value is disconnect(1)."
			::= { hwWlanMobilityManagement 2 }

		 --1.3.6.1.4.1.2011.6.139.11.1.61.1.3
		-- 1.3.6.1.4.1.2011.6.139.11.1.58.1.3
		hwWlanConnectMasterControllerIPv4Addr OBJECT-TYPE
			SYNTAX IpAddress
			MAX-ACCESS read-write
			STATUS current
			DESCRIPTION 
				"This object indicates the IPv4 address of the CUC that needs to set up a link with the Master Controller."
			::= { hwWlanMobilityManagement 3 }

		 --1.3.6.1.4.1.2011.6.139.11.1.61.1.4
		-- 1.3.6.1.4.1.2011.6.139.11.1.58.1.4
		hwWlanConnectMasterControllerIPv6Addr OBJECT-TYPE
			SYNTAX OCTET STRING
			MAX-ACCESS read-write
			STATUS current
			DESCRIPTION 
				"This object indicates the IPv6 address of the CUC that needs to set up a link with the Master Controller."
			::= { hwWlanMobilityManagement 4 }
		
		-- 1.3.6.1.4.1.2011.6.139.11.1.58.1.5
		hwWlanMobilityServerIPv4 OBJECT-TYPE
			SYNTAX IpAddress
			MAX-ACCESS read-write
			STATUS current
			DESCRIPTION
				"Description."
			::= { hwWlanMobilityManagement 5 }

		
		-- 1.3.6.1.4.1.2011.6.139.11.1.58.1.6
		hwWlanMobilityServerIPv6 OBJECT-TYPE
			SYNTAX OCTET STRING
			MAX-ACCESS read-write
			STATUS current
			DESCRIPTION
				"Description."
			::= { hwWlanMobilityManagement 6 }

		
		-- 1.3.6.1.4.1.2011.6.139.11.1.58.1.7
		hwWlanMobilityServerState OBJECT-TYPE
			SYNTAX INTEGER
				{
				fault(1),
				vmiss(2),
				normal(3)
				}
			MAX-ACCESS read-only
			STATUS current
			DESCRIPTION
				"Description."
			::= { hwWlanMobilityManagement 7 }

		
		-- 1.3.6.1.4.1.2011.6.139.11.1.58.1.8
		hwWlanMobilityServerSwitch OBJECT-TYPE
			SYNTAX INTEGER
				{
				disable(1),
				enable(2)
				}
			MAX-ACCESS read-write
			STATUS current
			DESCRIPTION
				"Description."
			::= { hwWlanMobilityManagement 8 }

		-- 1.3.6.1.4.1.2011.6.139.11.1.58.1.9
		hwWlanMobilityServerLocalIPv4 OBJECT-TYPE
			SYNTAX IpAddress
			MAX-ACCESS read-write
			STATUS current
			DESCRIPTION
				"Description."
			::= { hwWlanMobilityManagement 9 }
		
--     1.3.6.1.4.1.2011.6.139.11.1.61.2

		-- 1.3.6.1.4.1.2011.6.139.11.1.58.2
		hwWlanMobilityAcTable OBJECT-TYPE
			SYNTAX SEQUENCE OF HwWlanMobilityAcEntry 
			MAX-ACCESS not-accessible
			STATUS current
			DESCRIPTION 
				"Description."
			::= { hwWlanMobilityObjects 2 }

		--1.3.6.1.4.1.2011.6.139.11.1.61.2.1
		-- 1.3.6.1.4.1.2011.6.139.11.1.58.2.1
		hwWlanMobilityAcEntry OBJECT-TYPE
			SYNTAX HwWlanMobilityAcEntry 
			MAX-ACCESS not-accessible
			STATUS current
			DESCRIPTION 
				"The index of this table is hwWlanMemAcIndex."
			INDEX { hwWlanMemAcIndex }
			::= { hwWlanMobilityAcTable 1 }


		HwWlanMobilityAcEntry ::=
			SEQUENCE {				
				hwWlanMemAcIndex
					Integer32,
				hwWlanAcIPv4Address
					IpAddress,
				hwWlanAcIPv6Address
					OCTET STRING,
				hwWlanAcState
					INTEGER,
				hwWlanAcRowStatus
					RowStatus 
			 }

		 --1.3.6.1.4.1.2011.6.139.11.1.61.2.1.1
		-- 1.3.6.1.4.1.2011.6.139.11.1.58.2.1.1
		hwWlanMemAcIndex OBJECT-TYPE
			SYNTAX Integer32
			MAX-ACCESS not-accessible
			STATUS current
			DESCRIPTION 
				"This object indicates the AP ID."
			::= { hwWlanMobilityAcEntry 1 }

		 --1.3.6.1.4.1.2011.6.139.11.1.61.2.1.2
		-- 1.3.6.1.4.1.2011.6.139.11.1.58.2.1.2
		hwWlanAcIPv4Address OBJECT-TYPE
			SYNTAX IpAddress
			MAX-ACCESS read-write
			STATUS current
			DESCRIPTION 
				"This object indicates the AC's IPv4 address."
			::= { hwWlanMobilityAcEntry 2 }

		 --1.3.6.1.4.1.2011.6.139.11.1.61.2.1.3
		-- 1.3.6.1.4.1.2011.6.139.11.1.58.2.1.3
		hwWlanAcIPv6Address OBJECT-TYPE
			SYNTAX OCTET STRING
			MAX-ACCESS read-write
			STATUS current
			DESCRIPTION 
				"This object indicates the AC's IPv6 address."
			::= { hwWlanMobilityAcEntry 3 }

		 --1.3.6.1.4.1.2011.6.139.11.1.61.2.1.4
		-- 1.3.6.1.4.1.2011.6.139.11.1.58.2.1.4
		hwWlanAcState OBJECT-TYPE
			SYNTAX INTEGER
				{
				normal(1) ,
				fault(2)
				}
			MAX-ACCESS read-only
			STATUS current
			DESCRIPTION 
				"This object indicates the state of connections to the AC."
			::= { hwWlanMobilityAcEntry 4 }

		 --1.3.6.1.4.1.2011.6.139.11.1.61.2.1.5
		-- 1.3.6.1.4.1.2011.6.139.11.1.58.2.1.5
		hwWlanAcRowStatus OBJECT-TYPE
			SYNTAX RowStatus
			MAX-ACCESS read-write
			STATUS current
			DESCRIPTION 
				"This object indicates the row status."
			::= { hwWlanMobilityAcEntry 5 }

		--1.3.6.1.4.1.2011.6.139.11.1.61.3
		-- 1.3.6.1.4.1.2011.6.139.11.1.58.3
		hwWlanMobilityGroupTable OBJECT-TYPE
			SYNTAX SEQUENCE OF HwWlanMobilityGroupEntry 
			MAX-ACCESS not-accessible
			STATUS current
			DESCRIPTION 
				"Description."
			::= { hwWlanMobilityObjects 3 }

		--1.3.6.1.4.1.2011.6.139.11.1.61.3.1
		-- 1.3.6.1.4.1.2011.6.139.11.1.58.3.1
		hwWlanMobilityGroupEntry OBJECT-TYPE
			SYNTAX HwWlanMobilityGroupEntry 
			MAX-ACCESS not-accessible
			STATUS current
			DESCRIPTION 
				"The index of this table is hwWlanMobilityGroupName."
			INDEX { hwWlanMobilityGroupName }
			::= { hwWlanMobilityGroupTable 1 }


		HwWlanMobilityGroupEntry ::=
			SEQUENCE {				
				hwWlanMobilityGroupName
					OCTET STRING,
				hwWlanMobilityGroupRowStatus
					RowStatus 
			 }

		 --1.3.6.1.4.1.2011.6.139.11.1.61.3.1.1
		-- 1.3.6.1.4.1.2011.6.139.11.1.58.3.1.1
		hwWlanMobilityGroupName OBJECT-TYPE
			SYNTAX OCTET STRING
			MAX-ACCESS not-accessible
			STATUS current
			DESCRIPTION 
				"This object indicates the mobility group name."
			::= { hwWlanMobilityGroupEntry 1 }

		 --1.3.6.1.4.1.2011.6.139.11.1.61.3.1.2
		-- 1.3.6.1.4.1.2011.6.139.11.1.58.3.1.2
		hwWlanMobilityGroupRowStatus OBJECT-TYPE
			SYNTAX RowStatus
			MAX-ACCESS read-write
			STATUS current
			DESCRIPTION 
				"This object indicates to add or delete mobility groups."
			::= { hwWlanMobilityGroupEntry 2 }

		--1.3.6.1.4.1.2011.6.139.11.1.61.4
		-- 1.3.6.1.4.1.2011.6.139.11.1.58.4
		hwWlanMobilityGroupMemberTable OBJECT-TYPE
			SYNTAX SEQUENCE OF HwWlanMobilityGroupMemberEntry 
			MAX-ACCESS not-accessible
			STATUS current
			DESCRIPTION 
				"Description."
			::= { hwWlanMobilityObjects 4 }

		--1.3.6.1.4.1.2011.6.139.11.1.61.4.1
		-- 1.3.6.1.4.1.2011.6.139.11.1.58.4.1
		hwWlanMobilityGroupMemberEntry OBJECT-TYPE
			SYNTAX HwWlanMobilityGroupMemberEntry 
			MAX-ACCESS not-accessible
			STATUS current
			DESCRIPTION 
				"Indexes of this table are hwWlanMobilityGroupName and hwWlanMobilityGroupMemberACIndex."
			INDEX { hwWlanMobilityGroupMemberACIndex,hwWlanMobilityGroupName }
			::= { hwWlanMobilityGroupMemberTable 1 }


		HwWlanMobilityGroupMemberEntry ::=
			SEQUENCE {				
				hwWlanMobilityGroupMemberACIndex
					Integer32,
				hwWlanMobilityGroupMemberRowStatus
					RowStatus 
			 }

		 --1.3.6.1.4.1.2011.6.139.11.1.61.4.1.1
		-- 1.3.6.1.4.1.2011.6.139.11.1.58.4.1.1
		hwWlanMobilityGroupMemberACIndex OBJECT-TYPE
			SYNTAX Integer32
			MAX-ACCESS not-accessible
			STATUS current
			DESCRIPTION 
				"This object indicates mobility group members (AC ID)."
			::= { hwWlanMobilityGroupMemberEntry 1 }

		 --1.3.6.1.4.1.2011.6.139.11.1.61.4.1.2
		-- 1.3.6.1.4.1.2011.6.139.11.1.58.4.1.2
		hwWlanMobilityGroupMemberRowStatus OBJECT-TYPE
			SYNTAX RowStatus
			MAX-ACCESS read-write
			STATUS current
			DESCRIPTION 
				"This object indicates to add or delete mobility group members."
			::= { hwWlanMobilityGroupMemberEntry 2 }
		
		-- 1.3.6.1.4.1.2011.6.139.11.1.58.5
		hwWlanMobilityMemberIPv4Table OBJECT-TYPE
			SYNTAX SEQUENCE OF HwWlanMobilityMemberIPv4Entry
			MAX-ACCESS not-accessible
			STATUS current
			DESCRIPTION
				"Description."
			::= { hwWlanMobilityObjects 5 }

		
		-- 1.3.6.1.4.1.2011.6.139.11.1.58.5.1
		hwWlanMobilityMemberIPv4Entry OBJECT-TYPE
			SYNTAX HwWlanMobilityMemberIPv4Entry
			MAX-ACCESS not-accessible
			STATUS current
			DESCRIPTION
				"Description."
			INDEX { hwWlanMobilityGroupName, hwWlanMobilityMemberIPv4Addr }
			::= { hwWlanMobilityMemberIPv4Table 1 }

		
		HwWlanMobilityMemberIPv4Entry ::=
			SEQUENCE { 
				hwWlanMobilityMemberIPv4Addr
					IpAddress,
				hwWlanMobilityMemberIPv4Description
					OCTET STRING,
				hwWlanMobilityMemberIPv4State
					INTEGER,
				hwWlanMobilityMemberIPv4RowStatus
					RowStatus
			 }

		-- 1.3.6.1.4.1.2011.6.139.11.1.58.5.1.1
		hwWlanMobilityMemberIPv4Addr OBJECT-TYPE
			SYNTAX IpAddress
			MAX-ACCESS read-write
			STATUS current
			DESCRIPTION
				"Description."
			::= { hwWlanMobilityMemberIPv4Entry 1 }

		
		-- 1.3.6.1.4.1.2011.6.139.11.1.58.5.1.2
		hwWlanMobilityMemberIPv4Description OBJECT-TYPE
			SYNTAX OCTET STRING
			MAX-ACCESS read-write
			STATUS current
			DESCRIPTION
				"Description."
			::= { hwWlanMobilityMemberIPv4Entry 2 }

		
		-- 1.3.6.1.4.1.2011.6.139.11.1.58.5.1.3
		hwWlanMobilityMemberIPv4State OBJECT-TYPE
			SYNTAX INTEGER
				{
				fault(1),
				normal(2),
				vmiss(3),
				invalid(4)
				}
			MAX-ACCESS read-only
			STATUS current
			DESCRIPTION
				"Description."
			::= { hwWlanMobilityMemberIPv4Entry 3 }

		
		-- 1.3.6.1.4.1.2011.6.139.11.1.58.5.1.4
		hwWlanMobilityMemberIPv4RowStatus OBJECT-TYPE
			SYNTAX RowStatus
			MAX-ACCESS read-write
			STATUS current
			DESCRIPTION
				"Description."
			::= { hwWlanMobilityMemberIPv4Entry 4 }

		
		-- 1.3.6.1.4.1.2011.6.139.11.1.58.6
		hwWlanMobilityMemberIPv6Table OBJECT-TYPE
			SYNTAX SEQUENCE OF HwWlanMobilityMemberIPv6Entry
			MAX-ACCESS not-accessible
			STATUS current
			DESCRIPTION
				"Description."
			::= { hwWlanMobilityObjects 6 }

		
		-- 1.3.6.1.4.1.2011.6.139.11.1.58.6.1
		hwWlanMobilityMemberIPv6Entry OBJECT-TYPE
			SYNTAX HwWlanMobilityMemberIPv6Entry
			MAX-ACCESS not-accessible
			STATUS current
			DESCRIPTION
				"Description."
			INDEX { hwWlanMobilityGroupName, hwWlanMobilityMemberIPv6Addr }
			::= { hwWlanMobilityMemberIPv6Table 1 }

		
		HwWlanMobilityMemberIPv6Entry ::=
			SEQUENCE { 
				hwWlanMobilityMemberIPv6Addr
					OCTET STRING,
				hwWlanMobilityMemberIPv6Description
					OCTET STRING,
				hwWlanMobilityMemberIPv6State
					INTEGER,
				hwWlanMobilityMemberIPv6RowStatus
					RowStatus
			 }

		-- 1.3.6.1.4.1.2011.6.139.11.1.58.6.1.1
		hwWlanMobilityMemberIPv6Addr OBJECT-TYPE
			SYNTAX OCTET STRING
			MAX-ACCESS read-write
			STATUS current
			DESCRIPTION
				"Description."
			::= { hwWlanMobilityMemberIPv6Entry 1 }

		
		-- 1.3.6.1.4.1.2011.6.139.11.1.58.6.1.2
		hwWlanMobilityMemberIPv6Description OBJECT-TYPE
			SYNTAX OCTET STRING
			MAX-ACCESS read-write
			STATUS current
			DESCRIPTION
				"Description."
			::= { hwWlanMobilityMemberIPv6Entry 2 }

		
		-- 1.3.6.1.4.1.2011.6.139.11.1.58.6.1.3
		hwWlanMobilityMemberIPv6State OBJECT-TYPE
			SYNTAX INTEGER
				{
				fault(1),
				normal(2),
				vmiss(3),
				invalid(4)
				}
			MAX-ACCESS read-only
			STATUS current
			DESCRIPTION
				"Description."
			::= { hwWlanMobilityMemberIPv6Entry 3 }

		
		-- 1.3.6.1.4.1.2011.6.139.11.1.58.6.1.4
		hwWlanMobilityMemberIPv6RowStatus OBJECT-TYPE
			SYNTAX RowStatus
			MAX-ACCESS read-write
			STATUS current
			DESCRIPTION
				"Description."
			::= { hwWlanMobilityMemberIPv6Entry 4 }

		
		-- 1.3.6.1.4.1.2011.6.139.11.1.58.7
		hwWlanMobilityClientIPv4Table OBJECT-TYPE
			SYNTAX SEQUENCE OF HwWlanMobilityClientIPv4Entry
			MAX-ACCESS not-accessible
			STATUS current
			DESCRIPTION
				"Description."
			::= { hwWlanMobilityObjects 7 }

		
		-- 1.3.6.1.4.1.2011.6.139.11.1.58.7.1
		hwWlanMobilityClientIPv4Entry OBJECT-TYPE
			SYNTAX HwWlanMobilityClientIPv4Entry
			MAX-ACCESS not-accessible
			STATUS current
			DESCRIPTION
				"Description."
			INDEX { hwWlanMobilityClientIPv4Addr }
			::= { hwWlanMobilityClientIPv4Table 1 }

		
		HwWlanMobilityClientIPv4Entry ::=
			SEQUENCE { 
				hwWlanMobilityClientIPv4Addr
					IpAddress,
				hwWlanMobilityClientIPv4State
					INTEGER
			 }

		-- 1.3.6.1.4.1.2011.6.139.11.1.58.7.1.1
		hwWlanMobilityClientIPv4Addr OBJECT-TYPE
			SYNTAX IpAddress
			MAX-ACCESS read-only
			STATUS current
			DESCRIPTION
				"Description."
			::= { hwWlanMobilityClientIPv4Entry 1 }

		
		-- 1.3.6.1.4.1.2011.6.139.11.1.58.7.1.2
		hwWlanMobilityClientIPv4State OBJECT-TYPE
			SYNTAX INTEGER
				{
				fault(1),
				normal(2),
				vmiss(3)
				}
			MAX-ACCESS read-only
			STATUS current
			DESCRIPTION
				"Description."
			::= { hwWlanMobilityClientIPv4Entry 2 }

		
		-- 1.3.6.1.4.1.2011.6.139.11.1.58.8
		hwWlanMobilityClientIPv6Table OBJECT-TYPE
			SYNTAX SEQUENCE OF HwWlanMobilityClientIPv6Entry
			MAX-ACCESS not-accessible
			STATUS current
			DESCRIPTION
				"Description."
			::= { hwWlanMobilityObjects 8 }

		
		-- 1.3.6.1.4.1.2011.6.139.11.1.58.8.1
		hwWlanMobilityClientIPv6Entry OBJECT-TYPE
			SYNTAX HwWlanMobilityClientIPv6Entry
			MAX-ACCESS not-accessible
			STATUS current
			DESCRIPTION
				"Description."
			INDEX { hwWlanMobilityClientIPv6Addr }
			::= { hwWlanMobilityClientIPv6Table 1 }

		
		HwWlanMobilityClientIPv6Entry ::=
			SEQUENCE { 
				hwWlanMobilityClientIPv6Addr
					OCTET STRING,
				hwWlanMobilityClientIPv6State
					INTEGER
			 }

		-- 1.3.6.1.4.1.2011.6.139.11.1.58.8.1.1
		hwWlanMobilityClientIPv6Addr OBJECT-TYPE
			SYNTAX OCTET STRING
			MAX-ACCESS read-only
			STATUS current
			DESCRIPTION
				"Description."
			::= { hwWlanMobilityClientIPv6Entry 1 }

		
		-- 1.3.6.1.4.1.2011.6.139.11.1.58.8.1.2
		hwWlanMobilityClientIPv6State OBJECT-TYPE
			SYNTAX INTEGER
				{
				fault(1),
				normal(2),
				vmiss(3)
				}
			MAX-ACCESS read-only
			STATUS current
			DESCRIPTION
				"Description."
			::= { hwWlanMobilityClientIPv6Entry 2 }

		
--     1.3.6.1.4.1.2011.6.139.11.1.62

		-- 1.3.6.1.4.1.2011.6.139.11.1.59
		hwWlanLanguageCodeTable OBJECT-TYPE
			SYNTAX SEQUENCE OF HwWlanLanguageCodeEntry 
			MAX-ACCESS not-accessible
			STATUS current
			DESCRIPTION 
				"It is the language code table. It complies with ISO 639 and is used by hotspot networks to obtain language code information."
			::= { hwWlanConfigObjects 59 }
		
--  1.3.6.1.4.1.2011.6.139.11.1.62.1
-- 1.3.6.1.4.1.2011.6.139.11.1.62.1
		-- 1.3.6.1.4.1.2011.6.139.11.1.59.1
		hwWlanLanguageCodeEntry OBJECT-TYPE
			SYNTAX HwWlanLanguageCodeEntry 
			MAX-ACCESS not-accessible
			STATUS current
			DESCRIPTION 
				"The index of this table is hwWlanLanguageCode."
			INDEX { hwWlanLanguageCode }
			::= { hwWlanLanguageCodeTable 1 }


		HwWlanLanguageCodeEntry ::=
			SEQUENCE {				
				hwWlanLanguageCode
					OCTET STRING,
				hwWlanLanguageCodeDescription
					OCTET STRING 
			 }

		 --1.3.6.1.4.1.2011.6.139.11.1.62.1.1
		-- 1.3.6.1.4.1.2011.6.139.11.1.59.1.1
		hwWlanLanguageCode OBJECT-TYPE
			SYNTAX OCTET STRING (SIZE (2..3))
			MAX-ACCESS not-accessible
			STATUS current
			DESCRIPTION 
				"This object indicates the language code."
			::= { hwWlanLanguageCodeEntry 1 }

		 --1.3.6.1.4.1.2011.6.139.11.1.62.1.2
		-- 1.3.6.1.4.1.2011.6.139.11.1.59.1.2
		hwWlanLanguageCodeDescription OBJECT-TYPE
			SYNTAX OCTET STRING
			MAX-ACCESS read-only
			STATUS current
			DESCRIPTION 
				"This object indicates the description of language codes."
			::= { hwWlanLanguageCodeEntry 2 }

		--1.3.6.1.4.1.2011.6.139.11.1.63
		-- 1.3.6.1.4.1.2011.6.139.11.1.60
		hwFatApConfigObjects OBJECT IDENTIFIER ::= { hwWlanConfigObjects 60 }
		
--  1.3.6.1.4.1.2011.6.139.11.1.63.1
-- 1.3.6.1.4.1.2011.6.139.11.1.63.1
		-- 1.3.6.1.4.1.2011.6.139.11.1.60.1
		hwFatApGlobalConfig OBJECT IDENTIFIER ::= { hwFatApConfigObjects 1 }

		 --1.3.6.1.4.1.2011.6.139.11.1.63.1.1
		-- 1.3.6.1.4.1.2011.6.139.11.1.60.1.1
		hwFatApCountryCode OBJECT-TYPE
			SYNTAX OCTET STRING (SIZE (2..8))
			MAX-ACCESS read-write
			STATUS current
			DESCRIPTION 
				"Description."
			::= { hwFatApGlobalConfig 1 }

		 --1.3.6.1.4.1.2011.6.139.11.1.63.1.2
		-- 1.3.6.1.4.1.2011.6.139.11.1.60.1.2
		hwFatApMaxStaNum OBJECT-TYPE
			SYNTAX Unsigned32 (1..256)
			MAX-ACCESS read-write
			STATUS current
			DESCRIPTION 
				"Description."
			::= { hwFatApGlobalConfig 2 }

		 --1.3.6.1.4.1.2011.6.139.11.1.63.1.3
		-- 1.3.6.1.4.1.2011.6.139.11.1.60.1.3
		hwFatApStaAccessMode OBJECT-TYPE
			SYNTAX INTEGER
				{
				disable(1),
				blacklist(2),
				whitelist(3)
				}
			MAX-ACCESS read-write
			STATUS current
			DESCRIPTION 
				"Description."
			::= { hwFatApGlobalConfig 3 }

		 --1.3.6.1.4.1.2011.6.139.11.1.63.1.4
		-- 1.3.6.1.4.1.2011.6.139.11.1.60.1.4
		hwFatApStaAccessModePorfile OBJECT-TYPE
			SYNTAX OCTET STRING (SIZE (0..35))
			MAX-ACCESS read-write
			STATUS current
			DESCRIPTION 
				"Description."
			::= { hwFatApGlobalConfig 4 }

		 --1.3.6.1.4.1.2011.6.139.11.1.63.1.5
		-- 1.3.6.1.4.1.2011.6.139.11.1.60.1.5
		hwFatApHighTempThreshold OBJECT-TYPE
			SYNTAX Unsigned32 (20..100|65535)
			MAX-ACCESS read-write
			STATUS current
			DESCRIPTION 
				"Description."
			::= { hwFatApGlobalConfig 5 }

		 --1.3.6.1.4.1.2011.6.139.11.1.63.1.6
		-- 1.3.6.1.4.1.2011.6.139.11.1.60.1.6
		hwFatApLowTempThreshold OBJECT-TYPE
			SYNTAX Integer32 (-70..10|65535)
			MAX-ACCESS read-write
			STATUS current
			DESCRIPTION 
				"Description."
			::= { hwFatApGlobalConfig 6 }

		 --1.3.6.1.4.1.2011.6.139.11.1.63.1.7
		-- 1.3.6.1.4.1.2011.6.139.11.1.60.1.7
		hwFatApDcaChannel5GBandwidth OBJECT-TYPE
			SYNTAX INTEGER
				{
				ht20(1),
				ht40(2),
				ht80(3)
				}
			MAX-ACCESS read-write
			STATUS current
			DESCRIPTION 
				"Description."
			::= { hwFatApGlobalConfig 7 }

		 --1.3.6.1.4.1.2011.6.139.11.1.63.1.8
		-- 1.3.6.1.4.1.2011.6.139.11.1.60.1.8
		hwFatApDcaChannel5GChannelSet OBJECT-TYPE
			SYNTAX OCTET STRING (SIZE (1..256))
			MAX-ACCESS read-write
			STATUS current
			DESCRIPTION 
				"Description."
			::= { hwFatApGlobalConfig 8 }

		 --1.3.6.1.4.1.2011.6.139.11.1.63.1.9
		-- 1.3.6.1.4.1.2011.6.139.11.1.60.1.9
		hwFatApDcaChannel2GChannelSet OBJECT-TYPE
			SYNTAX OCTET STRING (SIZE (1..256))
			MAX-ACCESS read-write
			STATUS current
			DESCRIPTION 
				"Description."
			::= { hwFatApGlobalConfig 9 }
 		 --1.3.6.1.4.1.2011.6.139.11.1.63.1.10
		-- 1.3.6.1.4.1.2011.6.139.11.1.60.1.10
		hwFatApDynamicBlackAgingTime OBJECT-TYPE
			SYNTAX Unsigned32 (180..3600)
			MAX-ACCESS read-write
			STATUS current
			DESCRIPTION 
				"Description."
			::= { hwFatApGlobalConfig 10 }
			
		--1.3.6.1.4.1.2011.6.139.11.1.63.1.11
		-- 1.3.6.1.4.1.2011.6.139.11.1.60.1.11
		hwFatApAntennaOutputMode OBJECT-TYPE
			SYNTAX INTEGER
				{
				combine(1),
				split(2)
				}
			MAX-ACCESS read-write
			STATUS current
			DESCRIPTION 
				"Description."
			::= { hwFatApGlobalConfig 11 }


		-- 1.3.6.1.4.1.2011.6.139.11.1.60.1.12
		hwFatApChannelLoadMode OBJECT-TYPE
			SYNTAX INTEGER
				{
				indoor(1),
				outdoor(2)
				}
			MAX-ACCESS read-write
			STATUS current
			DESCRIPTION
				"Description."
			::= { hwFatApGlobalConfig 12 }
			
		-- 1.3.6.1.4.1.2011.6.139.11.1.60.1.13
		hwFatApStaArpNDProxyBeforeAssoc OBJECT-TYPE
			SYNTAX INTEGER
				{
				no(1),
				yes(2)
				}
			MAX-ACCESS read-write
			STATUS current
			DESCRIPTION
				"Description."
			::= { hwFatApGlobalConfig 13 }

		-- 1.3.6.1.4.1.2011.6.139.11.1.60.2
		hwFatApRadioTable OBJECT-TYPE
			SYNTAX SEQUENCE OF HwFatApRadioEntry 
			MAX-ACCESS not-accessible
			STATUS current
			DESCRIPTION 
				"Description."
			::= { hwFatApConfigObjects 2 }

		--1.3.6.1.4.1.2011.6.139.11.1.63.2.1
		-- 1.3.6.1.4.1.2011.6.139.11.1.60.2.1
		hwFatApRadioEntry OBJECT-TYPE
			SYNTAX HwFatApRadioEntry 
			MAX-ACCESS not-accessible
			STATUS current
			DESCRIPTION 
				"Description."
			INDEX { hwFatApRadio }
			::= { hwFatApRadioTable 1 }


		HwFatApRadioEntry ::=
			SEQUENCE {				
				hwFatApRadio
					Unsigned32,
				hwFatApRadio0Frequency
					INTEGER,
				hwFatApRadio2gProfile
					OCTET STRING,
				hwFatApRadio5gProfile
					OCTET STRING,
				hwFatApRadioMeshProfile
					OCTET STRING,
				hwFatApLocationProfile
					OCTET STRING,
				hwFatApRadioRowStatus
					RowStatus,
				hwFatApMeshWhitelistProfile
					OCTET STRING,
				hwFatApWdsWhitelistProfile
					OCTET STRING,
				hwFatApRadioSwitch
					INTEGER,
				hwFatApRadioChannel
					Unsigned32,
				hwFatApRadioBandwidth
					INTEGER,
				hwFatApRadioEirp
					Unsigned32,
				hwFatApRadioAntennaGain
					Integer32,
				hwFatApRadioCoverageDistance
					Unsigned32,
				hwFatApRadioWorkMode
					INTEGER,
				hwFatApWidsDeviceDetectSwitch
					INTEGER,
				hwFatApWidsAttackDetectEnBmp
					Unsigned32,
				hwFatApWidsRogueContainSwitch
					INTEGER,
			    	hwFatApRadioSecondChannel
					Unsigned32,
				hwFatApAutoChannelSelectSwitch
					INTEGER,
				hwFatApAutoTxPowerSelectSwitch
					INTEGER,
			        hwFatApCalibrateFlexibleRadioSwitch   
			        INTEGER,
				hwFatApAutoBandwidthSelectSwitch
					INTEGER,
				hwFatApReferenceDataAnalysis
					INTEGER
			}

		-- 1.3.6.1.4.1.2011.6.139.11.1.60.2.1.1
		hwFatApRadio OBJECT-TYPE
			SYNTAX Unsigned32 (0..2)
			MAX-ACCESS not-accessible
			STATUS current
			DESCRIPTION 
				"Description."
			::= { hwFatApRadioEntry 1 }

		-- 1.3.6.1.4.1.2011.6.139.11.1.60.2.1.2
		hwFatApRadio0Frequency OBJECT-TYPE
			SYNTAX INTEGER
				{
				frequency5G(1),
				frequency2G(2)
				}
			MAX-ACCESS read-write
			STATUS current
			DESCRIPTION 
				"Description."
			::= { hwFatApRadioEntry 2 }

		-- 1.3.6.1.4.1.2011.6.139.11.1.60.2.1.3
		hwFatApRadio2gProfile OBJECT-TYPE
			SYNTAX OCTET STRING (SIZE (1..35))
			MAX-ACCESS read-write
			STATUS current
			DESCRIPTION 
				"Description."
			::= { hwFatApRadioEntry 3 }

		-- 1.3.6.1.4.1.2011.6.139.11.1.60.2.1.4
		hwFatApRadio5gProfile OBJECT-TYPE
			SYNTAX OCTET STRING (SIZE (1..35))
			MAX-ACCESS read-write
			STATUS current
			DESCRIPTION 
				"Description."
			::= { hwFatApRadioEntry 4 }

		-- 1.3.6.1.4.1.2011.6.139.11.1.60.2.1.5
		hwFatApRadioMeshProfile OBJECT-TYPE
			SYNTAX OCTET STRING (SIZE (0..35))
			MAX-ACCESS read-write
			STATUS current
			DESCRIPTION 
				"Description."
			::= { hwFatApRadioEntry 5 }


		-- 1.3.6.1.4.1.2011.6.139.11.1.60.2.1.7
		hwFatApLocationProfile OBJECT-TYPE
			SYNTAX OCTET STRING (SIZE (0..35))
			MAX-ACCESS read-write
			STATUS current
			DESCRIPTION 
				"Description."
			::= { hwFatApRadioEntry 7 }

		-- 1.3.6.1.4.1.2011.6.139.11.1.60.2.1.8
		hwFatApRadioRowStatus OBJECT-TYPE
			SYNTAX RowStatus
			MAX-ACCESS read-write
			STATUS current
			DESCRIPTION 
				"Description."
			::= { hwFatApRadioEntry 8 }


		-- 1.3.6.1.4.1.2011.6.139.11.1.60.2.1.9
		hwFatApMeshWhitelistProfile OBJECT-TYPE
			SYNTAX OCTET STRING (SIZE (0..35))
			MAX-ACCESS read-write
			STATUS current
			DESCRIPTION
				"This object indicates the bound whitelist profile."
			::= { hwFatApRadioEntry 9 }


		-- 1.3.6.1.4.1.2011.6.139.11.1.60.2.1.10
		hwFatApWdsWhitelistProfile OBJECT-TYPE
			SYNTAX OCTET STRING (SIZE (0..35))
			MAX-ACCESS read-write
			STATUS current
			DESCRIPTION
				"This object indicates the bound whitelist profile."
			::= { hwFatApRadioEntry 10 }

		
		-- 1.3.6.1.4.1.2011.6.139.11.1.60.2.1.11
		hwFatApRadioSwitch OBJECT-TYPE
			SYNTAX INTEGER
				{
				disable(1),
				enable(2)
				}
			MAX-ACCESS read-write
			STATUS current
			DESCRIPTION
				"This object indicates the name of a 2G radio profile. It is the index of the table."
			::= { hwFatApRadioEntry 11 }

		
		-- 1.3.6.1.4.1.2011.6.139.11.1.60.2.1.12
		hwFatApRadioChannel OBJECT-TYPE
			SYNTAX Unsigned32
			MAX-ACCESS read-write
			STATUS current
			DESCRIPTION
				"This object indicates a radio-frequency channel. For 2.4G, the value ranges from 1 to 13. For 5G, the value ranges from 36 to 165 (with a separation interval of 4)."
			::= { hwFatApRadioEntry 12 }

		
		-- 1.3.6.1.4.1.2011.6.139.11.1.60.2.1.13
		hwFatApRadioBandwidth OBJECT-TYPE
			SYNTAX INTEGER
				{
				ht20(1),
				ht40Plus(2),
				ht40Minus(3),
				ht80(4),
				ht160(5),
				invalid(255)
				}
			MAX-ACCESS read-write
			STATUS current
			DESCRIPTION
				"This object indicate a bandwidth. The default value is 1."
			::= { hwFatApRadioEntry 13 }


		-- 1.3.6.1.4.1.2011.6.139.11.1.60.2.1.14
		hwFatApRadioEirp OBJECT-TYPE
			SYNTAX Unsigned32 (1..127)
			MAX-ACCESS read-write
			STATUS current
			DESCRIPTION
				"This object indicates a power value. The default value is 127. The configuration is saved but the actual power is determined by the maximum power supported by the AP."
			::= { hwFatApRadioEntry 14 }


		-- 1.3.6.1.4.1.2011.6.139.11.1.60.2.1.15
		hwFatApRadioAntennaGain OBJECT-TYPE
			SYNTAX Integer32 (-10..30 | 255)
			MAX-ACCESS read-write
			STATUS current
			DESCRIPTION
				"This object indicates antenna gains. The default value 0xFF indicates that the default gain of an AP is used. It is expressed in dB. Default gains vary with different types of APs."
			::= { hwFatApRadioEntry 15 }


		-- 1.3.6.1.4.1.2011.6.139.11.1.60.2.1.16
		hwFatApRadioCoverageDistance OBJECT-TYPE
			SYNTAX Unsigned32 (1..400)
			MAX-ACCESS read-write
			STATUS current
			DESCRIPTION
				"This object indicates a radio coverage distance. The default value is 3. The unit is 0.1 km."
			::= { hwFatApRadioEntry 16 }


		-- 1.3.6.1.4.1.2011.6.139.11.1.60.2.1.17
		hwFatApRadioWorkMode OBJECT-TYPE
			SYNTAX INTEGER
				{
				normal(1),
				monitor(2),
				dualband(3),
				proxyScan(4)
				}
			MAX-ACCESS read-write
			STATUS current
			DESCRIPTION
				"This object indicates the radio working mode. The default value is 1."
			::= { hwFatApRadioEntry 17 }


		-- 1.3.6.1.4.1.2011.6.139.11.1.60.2.1.18
		hwFatApWidsDeviceDetectSwitch OBJECT-TYPE
			SYNTAX INTEGER
				{
				disable(1),
				enable(2)
				}
			MAX-ACCESS read-write
			STATUS current
			DESCRIPTION
				"This object indicates the status of the device detection function. The default value is 1."
			::= { hwFatApRadioEntry 18 }


		-- 1.3.6.1.4.1.2011.6.139.11.1.60.2.1.19
		hwFatApWidsAttackDetectEnBmp OBJECT-TYPE
			SYNTAX Unsigned32
			MAX-ACCESS read-write
			STATUS current
			DESCRIPTION
				"This object indicates the bit map of the brute force attack switch. bit0:weak-iv, bit1:spoof, bit2:flood, bit3:wpa-psk, bit4:wpa2-psk, bit5:wapi-psk, bit6:wep-psk."
			::= { hwFatApRadioEntry 19 }


		-- 1.3.6.1.4.1.2011.6.139.11.1.60.2.1.20
		hwFatApWidsRogueContainSwitch OBJECT-TYPE
			SYNTAX INTEGER
				{
				disable(1),
				enable(2)
				}
			MAX-ACCESS read-write
			STATUS current
			DESCRIPTION
				"This object indicates the status of the device detection function. The default value is 1."
			::= { hwFatApRadioEntry 20 }
			
		-- 1.3.6.1.4.1.2011.6.139.11.1.60.2.1.21
		hwFatApRadioSecondChannel OBJECT-TYPE
                        SYNTAX Unsigned32
                        MAX-ACCESS read-write
                        STATUS current
                        DESCRIPTION
                        "This object indicates a radio-frequency channel. The value ranges from 42,58,106,122,138,155."
                        ::= { hwFatApRadioEntry 21 }
						
		-- 1.3.6.1.4.1.2011.6.139.11.1.60.2.1.22
		hwFatApAutoChannelSelectSwitch OBJECT-TYPE
			SYNTAX INTEGER
				{
				disable(1),
				enable(2)
				}
			MAX-ACCESS read-write
			STATUS current
			DESCRIPTION
				"This object indicates the status of the automatic channel selection function. The default value is 2."
			DEFVAL { enable }
			::= { hwFatApRadioEntry 22 }
		
		-- 1.3.6.1.4.1.2011.6.139.11.1.60.2.1.23
		hwFatApAutoTxPowerSelectSwitch OBJECT-TYPE
			SYNTAX INTEGER
				{
				disable(1),
				enable(2)
				}
			MAX-ACCESS read-write
			STATUS current
			DESCRIPTION
				"This object indicates the status of the automatic power selection function. The default value is 2."
			DEFVAL { enable }
			::= { hwFatApRadioEntry 23 }
		-- 1.3.6.1.4.1.2011.6.139.11.1.60.2.1.24
		hwFatApCalibrateFlexibleRadioSwitch OBJECT-TYPE
			SYNTAX INTEGER
				{
				disable(1),	
				enable(2)
				}
			MAX-ACCESS read-write
			STATUS current
			DESCRIPTION
				"This object indicates the status of the calibrate flexible-radio switch function. The default value is 2."
			DEFVAL { enable }
			::= { hwFatApRadioEntry 24 }
                        
		-- 1.3.6.1.4.1.2011.6.139.11.1.60.2.1.25
		hwFatApAutoBandwidthSelectSwitch OBJECT-TYPE
			SYNTAX INTEGER
				{
				disable(1),
				enable(2)
				}
			MAX-ACCESS read-write
			STATUS current
			DESCRIPTION
				"This object indicates the status of the automatic bandwidth selection function. The default value is 1."
			DEFVAL { disable }
			::= { hwFatApRadioEntry 25 }

		-- 1.3.6.1.4.1.2011.6.139.11.1.60.2.1.26
		hwFatApReferenceDataAnalysis OBJECT-TYPE
			SYNTAX INTEGER
				{
				disable(1),
				enable(2)
				}
			MAX-ACCESS read-write
			STATUS current
			DESCRIPTION
				"This object indicates the status of the referencing data-analysis  function. The default value is 2."
			DEFVAL { disable }
			::= { hwFatApRadioEntry 26 }

--     1.3.6.1.4.1.2011.6.139.11.1.60.3
-- 1.3.6.1.4.1.2011.6.139.11.1.60.3
-- 1.3.6.1.4.1.2011.6.139.11.1.60.3
-- 1.3.6.1.4.1.2011.6.139.11.1.60.3
		-- 1.3.6.1.4.1.2011.6.139.11.1.60.3
		hwFatApVapTable OBJECT-TYPE
			SYNTAX SEQUENCE OF HwFatApVapEntry 
			MAX-ACCESS not-accessible
			STATUS current
			DESCRIPTION 
				"Description."
			::= { hwFatApConfigObjects 3 }


		-- 1.3.6.1.4.1.2011.6.139.11.1.60.3.1
		hwFatApVapEntry OBJECT-TYPE
			SYNTAX HwFatApVapEntry 
			MAX-ACCESS not-accessible
			STATUS current
			DESCRIPTION 
				"Description."
			INDEX { hwFatApWlanId, hwFatApRadioId }
			::= { hwFatApVapTable 1 }


		HwFatApVapEntry ::=
			SEQUENCE {				
				hwFatApWlanId
					Unsigned32,
				hwFatApRadioId
					Unsigned32,
				hwFatApVapProfile
					OCTET STRING,
				hwFatApVapProfileRowStatus
					RowStatus 
			 }

		 --1.3.6.1.4.1.2011.6.139.11.1.63.3.1.1
		-- 1.3.6.1.4.1.2011.6.139.11.1.60.3.1.1
		hwFatApWlanId OBJECT-TYPE
			SYNTAX Unsigned32 (1..16)
			MAX-ACCESS not-accessible
			STATUS current
			DESCRIPTION 
				"Description."
			::= { hwFatApVapEntry 1 }

		 --1.3.6.1.4.1.2011.6.139.11.1.63.3.1.2
		-- 1.3.6.1.4.1.2011.6.139.11.1.60.3.1.2
		hwFatApRadioId OBJECT-TYPE
			SYNTAX Unsigned32 (0..2)
			MAX-ACCESS not-accessible
			STATUS current
			DESCRIPTION			 
		        	"Description."
			::= { hwFatApVapEntry 2 }
			
	     --1.3.6.1.4.1.2011.6.139.11.1.63.3.1.3
		-- 1.3.6.1.4.1.2011.6.139.11.1.60.3.1.3
		hwFatApVapProfile OBJECT-TYPE
			SYNTAX OCTET STRING (SIZE (1..35))
			MAX-ACCESS read-write
			STATUS current
			DESCRIPTION 
				"Description."
			::= { hwFatApVapEntry 3 }

		 --1.3.6.1.4.1.2011.6.139.11.1.63.3.1.4
		-- 1.3.6.1.4.1.2011.6.139.11.1.60.3.1.4
		hwFatApVapProfileRowStatus OBJECT-TYPE
			SYNTAX RowStatus
			MAX-ACCESS read-write
			STATUS current
			DESCRIPTION 
				"Description."
			::= { hwFatApVapEntry 4 } 
			
		-- 1.3.6.1.4.1.2011.6.139.11.1.60.4
		hwFatApRadioServiceIdxTable OBJECT-TYPE
			SYNTAX SEQUENCE OF HwFatApRadioServiceIdxEntry
			MAX-ACCESS not-accessible
			STATUS current
			DESCRIPTION
				"This table stores information about the Mesh link with the index of 1 on the vehicle-mounted Fat AP and can also be used for subsequent index-based service expansion."
			::= { hwFatApConfigObjects 4 }
		
		-- 1.3.6.1.4.1.2011.6.139.11.1.60.4.1
		hwFatApRadioServiceIdxEntry OBJECT-TYPE
			SYNTAX HwFatApRadioServiceIdxEntry
			MAX-ACCESS not-accessible
			STATUS current
			DESCRIPTION
				"Indexes of this table are hwFatApRadio and hwFatApRadioServiceIdx."
			INDEX { hwFatApRadio, hwFatApRadioServiceIdx }
			::= { hwFatApRadioServiceIdxTable 1 }
		
		HwFatApRadioServiceIdxEntry ::=
			SEQUENCE {
				hwFatApRadioServiceIdx
					Unsigned32,
				hwFatApRadioServiceIdxMeshProf
					OCTET STRING,
				hwFatApRadioIdxMeshWlistProfile
					OCTET STRING,
				hwFatApRadioServiceIdxChannel
					Unsigned32,
				hwFatApRadioServiceIdxBandwidth
					INTEGER,
				hwFatApRadioIdxSecondChannel
					Unsigned32,
				hwFatApRadioServiceIdxRowStatus
					RowStatus
			 }
			 
		--1.3.6.1.4.1.2011.6.139.11.1.60.4.1.1
		hwFatApRadioServiceIdx OBJECT-TYPE
			SYNTAX Unsigned32 (1)
			MAX-ACCESS not-accessible
			STATUS current
			DESCRIPTION
				"This object indicates the service index. The current value is 1."
			::= { hwFatApRadioServiceIdxEntry 1 }
		
		-- 1.3.6.1.4.1.2011.6.139.11.1.60.4.1.2
		hwFatApRadioServiceIdxMeshProf OBJECT-TYPE
			SYNTAX OCTET STRING (SIZE (0..35))
			MAX-ACCESS read-write
			STATUS current
			DESCRIPTION
				"This object indicates the bound mesh profile."
			::= { hwFatApRadioServiceIdxEntry 2 }
		
		-- 1.3.6.1.4.1.2011.6.139.11.1.60.4.1.3
		hwFatApRadioIdxMeshWlistProfile OBJECT-TYPE
			SYNTAX OCTET STRING (SIZE (0..35))
			MAX-ACCESS read-write
			STATUS current
			DESCRIPTION
				"This object indicates the bound whitelist profile."
			::= { hwFatApRadioServiceIdxEntry 3 }
		
		-- 1.3.6.1.4.1.2011.6.139.11.1.60.4.1.4
		hwFatApRadioServiceIdxChannel OBJECT-TYPE
			SYNTAX Unsigned32
			MAX-ACCESS read-write
			STATUS current
			DESCRIPTION
				"This object indicates a radio-frequency channel. For 2.4G, the value ranges from 1 to 13. For 5G, the value ranges from 36 to 165 (with a separation interval of 4)."
			::= { hwFatApRadioServiceIdxEntry 4 }
		
		-- 1.3.6.1.4.1.2011.6.139.11.1.60.4.1.5
		hwFatApRadioServiceIdxBandwidth OBJECT-TYPE
			SYNTAX INTEGER
				{
				ht20(1),
				ht40Plus(2),
				ht40Minus(3),
				ht80(4),
				ht160(5),
				invalid(255)
				}
			MAX-ACCESS read-write
			STATUS current
			DESCRIPTION
				"This object indicate a bandwidth. The default value is 1."
			::= { hwFatApRadioServiceIdxEntry 5 }
			
		-- 1.3.6.1.4.1.2011.6.139.11.1.60.4.1.6
		hwFatApRadioIdxSecondChannel OBJECT-TYPE
			SYNTAX Unsigned32
			MAX-ACCESS read-write
			STATUS current
			DESCRIPTION
				"This object indicates a radio-frequency channel. The value ranges from 42,58,106,122,138,155."
			::= { hwFatApRadioServiceIdxEntry 6 }

		-- 1.3.6.1.4.1.2011.6.139.11.1.60.4.1.7
		hwFatApRadioServiceIdxRowStatus OBJECT-TYPE
			SYNTAX RowStatus
			MAX-ACCESS read-write
			STATUS current
			DESCRIPTION
				"This object indicates the row status of this table. ROWSTATUS_CREATEANDFLOW and ROWSTATUS_DESTROY are commonly used."
			::= { hwFatApRadioServiceIdxEntry 7 }
		

		-- 1.3.6.1.4.1.2011.6.139.11.1.61
		hwNAIRealmProfileListTable OBJECT-TYPE
			SYNTAX SEQUENCE OF HwNAIRealmProfileListEntry 
			MAX-ACCESS not-accessible
			STATUS current
			DESCRIPTION 
				"This table describes the NAI realm profile."
			::= { hwWlanConfigObjects 61 }

		--1.3.6.1.4.1.2011.6.139.11.1.61.1
		hwNAIRealmProfileListEntry OBJECT-TYPE
			SYNTAX HwNAIRealmProfileListEntry 
			MAX-ACCESS not-accessible
			STATUS current
			DESCRIPTION 
				"The index of this table is hwNAIRealmProfileListProfileName."
			INDEX { hwNAIRealmProfileListProfileName }
			::= { hwNAIRealmProfileListTable 1 }


		HwNAIRealmProfileListEntry ::=
			SEQUENCE {				
				hwNAIRealmProfileListProfileName
					OCTET STRING,
				hwNAIRealmProfileListRowStatus
					RowStatus 
			 }

		 --1.3.6.1.4.1.2011.6.139.11.1.61.1.1
		hwNAIRealmProfileListProfileName OBJECT-TYPE
			SYNTAX OCTET STRING (SIZE (1..35))
			MAX-ACCESS not-accessible
			STATUS current
			DESCRIPTION 
				"This object indicates the profile name."
			::= { hwNAIRealmProfileListEntry 1 }     
			
		 --1.3.6.1.4.1.2011.6.139.11.1.61.1.2
		hwNAIRealmProfileListRowStatus OBJECT-TYPE
			SYNTAX RowStatus
			MAX-ACCESS read-write
			STATUS current
			DESCRIPTION 
				"This object indicates the row status of this table. createAndGo(4) and destroy(6) are commonly used."
			::= { hwNAIRealmProfileListEntry 2 }     
			  
			  
		--1.3.6.1.4.1.2011.6.139.11.1.62
		hwWidsSpoofProfileListTable OBJECT-TYPE
			SYNTAX SEQUENCE OF HwWidsSpoofProfileListEntry 
			MAX-ACCESS not-accessible
			STATUS current
			DESCRIPTION 
				"This table is used to create or delete WIDS spoof SSID profiles."
			::= { hwWlanConfigObjects 62 }

		--1.3.6.1.4.1.2011.6.139.11.1.62.1
		hwWidsSpoofProfileListEntry OBJECT-TYPE
			SYNTAX HwWidsSpoofProfileListEntry 
			MAX-ACCESS not-accessible
			STATUS current
			DESCRIPTION 
				"The index of this table is hwWidsSpoofProfileListProfileName."
			INDEX { hwWidsSpoofProfileListProfileName }
			::= { hwWidsSpoofProfileListTable 1 }


		HwWidsSpoofProfileListEntry ::=
			SEQUENCE {				
				hwWidsSpoofProfileListProfileName
					OCTET STRING,
				hwWidsSpoofProfileListRowStatus
					RowStatus 
			 }

		 --1.3.6.1.4.1.2011.6.139.11.1.62.1.1
		hwWidsSpoofProfileListProfileName OBJECT-TYPE
			SYNTAX OCTET STRING (SIZE (1..35))
			MAX-ACCESS not-accessible
			STATUS current
			DESCRIPTION 
				"This object indicates the name of a WIDS spoof SSID profile."
			::= { hwWidsSpoofProfileListEntry 1 }     
			
		 --1.3.6.1.4.1.2011.6.139.11.1.62.1.2
		hwWidsSpoofProfileListRowStatus OBJECT-TYPE
			SYNTAX RowStatus
			MAX-ACCESS read-write
			STATUS current
			DESCRIPTION 
				"This object indicates the row status of this table. createAndGo(4) and destroy(6) are commonly used."
			::= { hwWidsSpoofProfileListEntry 2 }     
			
		--1.3.6.1.4.1.2011.6.139.11.1.63
		hwWidsWhitelistProfileListTable OBJECT-TYPE
			SYNTAX SEQUENCE OF HwWidsWhitelistProfileListEntry 
			MAX-ACCESS not-accessible
			STATUS current
			DESCRIPTION 
				"This table is used to create or delete WIDS confident profiles."
			::= { hwWlanConfigObjects 63 }

		--1.3.6.1.4.1.2011.6.139.11.1.63.1
		hwWidsWhitelistProfileListEntry OBJECT-TYPE
			SYNTAX HwWidsWhitelistProfileListEntry 
			MAX-ACCESS not-accessible
			STATUS current
			DESCRIPTION 
				"The index of this table is hwWidsWhitelistProfileListProfileName."
			INDEX { hwWidsWhitelistProfileListProfileName }
			::= { hwWidsWhitelistProfileListTable 1 }


		HwWidsWhitelistProfileListEntry ::=
			SEQUENCE {				
				hwWidsWhitelistProfileListProfileName
					OCTET STRING,
				hwWidsWhitelistProfileListRowStatus
					RowStatus 
			 }

		 --1.3.6.1.4.1.2011.6.139.11.1.63.1.1
		hwWidsWhitelistProfileListProfileName OBJECT-TYPE
			SYNTAX OCTET STRING (SIZE (1..35))
			MAX-ACCESS not-accessible
			STATUS current
			DESCRIPTION 
				"This object indicates the name of a WIDS confident profile."
			::= { hwWidsWhitelistProfileListEntry 1 }     
			
		 --1.3.6.1.4.1.2011.6.139.11.1.63.1.2
		hwWidsWhitelistProfileListRowStatus OBJECT-TYPE
			SYNTAX RowStatus
			MAX-ACCESS read-write
			STATUS current
			DESCRIPTION 
				"This object indicates the row status of this table. createAndGo(4) and destroy(6) are commonly used."
			::= { hwWidsWhitelistProfileListEntry 2 }

		
		-- 1.3.6.1.4.1.2011.6.139.11.1.64
		hwWlanLoadBalanceStaticGroupTable OBJECT-TYPE
			SYNTAX SEQUENCE OF HwWlanLoadBalanceStaticGroupEntry
			MAX-ACCESS not-accessible
			STATUS current
			DESCRIPTION
				"This table records information about the static load balancing group."
			::= { hwWlanConfigObjects 64 }

		
		-- 1.3.6.1.4.1.2011.6.139.11.1.64.1
		hwWlanLoadBalanceStaticGroupEntry OBJECT-TYPE
			SYNTAX HwWlanLoadBalanceStaticGroupEntry
			MAX-ACCESS not-accessible
			STATUS current
			DESCRIPTION
				"The index of this table is hwWlanLBGroupName."
			INDEX { hwWlanLBGroupName }
			::= { hwWlanLoadBalanceStaticGroupTable 1 }

		
		HwWlanLoadBalanceStaticGroupEntry ::=
			SEQUENCE { 
				hwWlanLBGroupName
					OCTET STRING,
				hwWlanLBGapThreshold
					Unsigned32,
				hwWlanLBDenyThreshold
					Unsigned32,
				hwWlanLBStartThreshold
					Unsigned32,
				hwWlanLBGroupStatus
					Unsigned32,
				hwWlanLBGroupRowStatus
					RowStatus,
				hwWlanLBMode
					INTEGER,
				hwWlanLBChUtilGapThreshold
					Unsigned32,
				hwWlanLBChUtilStartThreshold
					Unsigned32,
				hwWlanLBGapStaNumThreshold
					Integer32,
				hwWlanLBDeauthFailTime
					Unsigned32,
				hwWlanLBBtmFailTime
					Unsigned32,
				hwWlanLBSteerRestrictTime
					Unsigned32,
				hwWlanLBSteerProbeRestrictThreshold
					Unsigned32,
				hwWlanLBSteerAuthRestrictThreshold
					Unsigned32,
				hwWlanLBRssiThreshold
					Integer32,
				hwWlanLBRssiDiffGap
					Unsigned32
			 }

		-- 1.3.6.1.4.1.2011.6.139.11.1.64.1.1
		hwWlanLBGroupName OBJECT-TYPE
			SYNTAX OCTET STRING
			MAX-ACCESS not-accessible
			STATUS current
			DESCRIPTION
				"This object indicates the name of the static load balancing group."
			::= { hwWlanLoadBalanceStaticGroupEntry 1 }

		
		-- 1.3.6.1.4.1.2011.6.139.11.1.64.1.2
		hwWlanLBGapThreshold OBJECT-TYPE
			SYNTAX Unsigned32
			MAX-ACCESS read-write
			STATUS current
			DESCRIPTION
				"This object indicates the load difference threshold of a static load balancing group."
			::= { hwWlanLoadBalanceStaticGroupEntry 2 }

		
		-- 1.3.6.1.4.1.2011.6.139.11.1.64.1.3
		hwWlanLBDenyThreshold OBJECT-TYPE
			SYNTAX Unsigned32
			MAX-ACCESS read-write
			STATUS current
			DESCRIPTION
				"This object indicates the maximum number of times an AP rejects association requests of a STA in the static load balancing group."
			::= { hwWlanLoadBalanceStaticGroupEntry 3 }

		
		-- 1.3.6.1.4.1.2011.6.139.11.1.64.1.4
		hwWlanLBStartThreshold OBJECT-TYPE
			SYNTAX Unsigned32
			MAX-ACCESS read-write
			STATUS current
			DESCRIPTION
				"This object indicates the start threshold for load balancing in a static load balancing group."
			::= { hwWlanLoadBalanceStaticGroupEntry 4 }

		
		-- 1.3.6.1.4.1.2011.6.139.11.1.64.1.5
		hwWlanLBGroupStatus OBJECT-TYPE
			SYNTAX Unsigned32
			MAX-ACCESS read-only
			STATUS current
			DESCRIPTION
				"This object indicates the load balancing status in the static load balancing group.1: Load is not balanced.2: Load is balanced."
			::= { hwWlanLoadBalanceStaticGroupEntry 5 }

		
		-- 1.3.6.1.4.1.2011.6.139.11.1.64.1.6
		hwWlanLBGroupRowStatus OBJECT-TYPE
			SYNTAX RowStatus
			MAX-ACCESS read-write
			STATUS current
			DESCRIPTION
				"This object indicates the row status of this table, which can be createAndGo(4) or destroy(6)."
			::= { hwWlanLoadBalanceStaticGroupEntry 6 }
			
		-- 1.3.6.1.4.1.2011.6.139.11.1.64.1.7
		hwWlanLBMode OBJECT-TYPE
			SYNTAX INTEGER
				{
				staNumber(1),
				channelUtilization(2)
				}
			MAX-ACCESS read-write
			STATUS current
			DESCRIPTION
				"This object indicates the mode for load balancing in a static load balancing group."
			DEFVAL { staNumber }
			::= { hwWlanLoadBalanceStaticGroupEntry 7 }
		
		-- 1.3.6.1.4.1.2011.6.139.11.1.64.1.8
		hwWlanLBChUtilGapThreshold OBJECT-TYPE
			SYNTAX Unsigned32 (1..99)
			MAX-ACCESS read-write
			STATUS current
			DESCRIPTION
				"This object indicates the load difference threshold of a static load balancing group in channel-utilization mode."
			DEFVAL { 20 }
			::= { hwWlanLoadBalanceStaticGroupEntry 8 }
		
		-- 1.3.6.1.4.1.2011.6.139.11.1.64.1.9
		hwWlanLBChUtilStartThreshold OBJECT-TYPE
			SYNTAX Unsigned32 (1..99)
			MAX-ACCESS read-write
			STATUS current
			DESCRIPTION
				"This object indicates the start threshold for load balancing in a static load balancing group in channel-utilization mode."
			DEFVAL { 50 }
			::= { hwWlanLoadBalanceStaticGroupEntry 9 }
		
		-- 1.3.6.1.4.1.2011.6.139.11.1.64.1.10
		hwWlanLBGapStaNumThreshold OBJECT-TYPE
			SYNTAX Integer32 (1..20)
			MAX-ACCESS read-write
			STATUS current
			DESCRIPTION
				"This object indicates the load difference threshold for static load balancing based on the number of STAs. The value 0 indicates that load balancing is based on the percentage of STAs."
			::= { hwWlanLoadBalanceStaticGroupEntry 10 }
		

		-- 1.3.6.1.4.1.2011.6.139.11.1.64.1.11
		hwWlanLBDeauthFailTime OBJECT-TYPE
			SYNTAX Unsigned32 (0..5)
			MAX-ACCESS read-write
			STATUS current
			DESCRIPTION
				"This object indicates the number of attempts to steer STAs in Deauthentication mode. The default value is 2."
			::= { hwWlanLoadBalanceStaticGroupEntry 11 }
		

		-- 1.3.6.1.4.1.2011.6.139.11.1.64.1.12
		hwWlanLBBtmFailTime OBJECT-TYPE
			SYNTAX Unsigned32 (0..10)
			MAX-ACCESS read-write
			STATUS current
			DESCRIPTION
				"This object indicates the number of attempts to steer STAs in BTM mode. The default value is 5."
			::= { hwWlanLoadBalanceStaticGroupEntry 12 }
		

		-- 1.3.6.1.4.1.2011.6.139.11.1.64.1.13
		hwWlanLBSteerRestrictTime OBJECT-TYPE
			SYNTAX Unsigned32 (0..10)
			MAX-ACCESS read-write
			STATUS current
			DESCRIPTION
				"This object indicates the time for suppressing STA association with non-target APs during STA steering. The default value is 5, in seconds."
			::= { hwWlanLoadBalanceStaticGroupEntry 13 }
		

		-- 1.3.6.1.4.1.2011.6.139.11.1.64.1.14
		hwWlanLBSteerProbeRestrictThreshold OBJECT-TYPE
			SYNTAX Unsigned32 (0..10)
			MAX-ACCESS read-write
			STATUS current
			DESCRIPTION
				"This object indicates the number of times non-target APs suppress STA Probe frames during STA steering. The default value is 5."
			::= { hwWlanLoadBalanceStaticGroupEntry 14 }
		

		-- 1.3.6.1.4.1.2011.6.139.11.1.64.1.15
		hwWlanLBSteerAuthRestrictThreshold OBJECT-TYPE
			SYNTAX Unsigned32 (0..5)
			MAX-ACCESS read-write
			STATUS current
			DESCRIPTION
				"This object indicates the number of times non-target APs suppress STA Authentication frames during STA steering. The default value is 0."
			::= { hwWlanLoadBalanceStaticGroupEntry 15 }
		

		-- 1.3.6.1.4.1.2011.6.139.11.1.64.1.16
		hwWlanLBRssiThreshold OBJECT-TYPE
			SYNTAX Integer32 (-75..-55)
			MAX-ACCESS read-write
			STATUS current
			DESCRIPTION
				"This object indicates the lower threshold of the target radio RSSI. The default value is -65, in dBm."
			::= { hwWlanLoadBalanceStaticGroupEntry 16 }
		

		-- 1.3.6.1.4.1.2011.6.139.11.1.64.1.17
		hwWlanLBRssiDiffGap OBJECT-TYPE
			SYNTAX Unsigned32 (0..15)
			MAX-ACCESS read-write
			STATUS current
			DESCRIPTION
				"This object indicates the threshold of the RSSI gap between the associated radio and target radio. The default value is 5, in dB."
			::= { hwWlanLoadBalanceStaticGroupEntry 17 }
		-- 1.3.6.1.4.1.2011.6.139.11.1.65
		hwWlanLoadBalanceStaticGroupMemberTable OBJECT-TYPE
			SYNTAX SEQUENCE OF HwWlanLoadBalanceStaticGroupMemberEntry
			MAX-ACCESS not-accessible
			STATUS current
			DESCRIPTION
				"This table records information about members in the static load balancing group."
			::= { hwWlanConfigObjects 65 }

		
		-- 1.3.6.1.4.1.2011.6.139.11.1.65.1
		hwWlanLoadBalanceStaticGroupMemberEntry OBJECT-TYPE
			SYNTAX HwWlanLoadBalanceStaticGroupMemberEntry
			MAX-ACCESS not-accessible
			STATUS current
			DESCRIPTION
				"The indexes of this table are hwWlanLBGroupName, hwWlanApName, and hwWlanRadioID."
			INDEX { hwWlanLBGroupName, hwWlanApName, hwWlanRadioID }
			::= { hwWlanLoadBalanceStaticGroupMemberTable 1 }

		
		HwWlanLoadBalanceStaticGroupMemberEntry ::=
			SEQUENCE { 
				hwWlanLBMemberRowStatus
					RowStatus
			 }

		-- 1.3.6.1.4.1.2011.6.139.11.1.65.1.1
		hwWlanLBMemberRowStatus OBJECT-TYPE
			SYNTAX RowStatus
			MAX-ACCESS read-write
			STATUS current
			DESCRIPTION
				"This object indicates the row status of this table."
			::= { hwWlanLoadBalanceStaticGroupMemberEntry 1 }

		
		-- 1.3.6.1.4.1.2011.6.139.11.1.66
		hwWlanCountryCodeTable OBJECT-TYPE
			SYNTAX SEQUENCE OF HwWlanCountryCodeEntry
			MAX-ACCESS not-accessible
			STATUS current
			DESCRIPTION
				"Description."
			::= { hwWlanConfigObjects 66 }

		
		-- 1.3.6.1.4.1.2011.6.139.11.1.66.1
		hwWlanCountryCodeEntry OBJECT-TYPE
			SYNTAX HwWlanCountryCodeEntry
			MAX-ACCESS not-accessible
			STATUS current
			DESCRIPTION
				"Description."
			INDEX { hwWlanCountryCode }
			::= { hwWlanCountryCodeTable 1 }

		
		HwWlanCountryCodeEntry ::=
			SEQUENCE { 
				hwWlanCountryCode
					OCTET STRING,
				hwWlanCountryCodeEngDescription
					OCTET STRING,
				hwWlanCountryCodeAvailableChannelSet2gBW20
					OCTET STRING,
				hwWlanCountryCodeAvailableChannelSet2gBW40Plus
					OCTET STRING,
				hwWlanCountryCodeAvailableChannelSet2gBW40Minus
					OCTET STRING,
				hwWlanCountryCodeAvailableChannelSet5gBW20
					OCTET STRING,
				hwWlanCountryCodeAvailableChannelSet5gBW40Plus
					OCTET STRING,
				hwWlanCountryCodeAvailableChannelSet5gBW40Minus
					OCTET STRING,
				hwWlanCountryCodeAvailableChannelSet5gBW80
					OCTET STRING,
				hwWlanCountryCodeAvailableChannelSet5gBW160
					OCTET STRING
			 }

		-- 1.3.6.1.4.1.2011.6.139.11.1.66.1.1
		hwWlanCountryCode OBJECT-TYPE
			SYNTAX OCTET STRING (SIZE (0..255))
			MAX-ACCESS not-accessible
			STATUS current
			DESCRIPTION
				"Description."
			::= { hwWlanCountryCodeEntry 1 }

		
		-- 1.3.6.1.4.1.2011.6.139.11.1.66.1.2
		hwWlanCountryCodeEngDescription OBJECT-TYPE
			SYNTAX OCTET STRING (SIZE (0..255))
			MAX-ACCESS read-only
			STATUS current
			DESCRIPTION
				"Description."
			::= { hwWlanCountryCodeEntry 2 }

		
		-- 1.3.6.1.4.1.2011.6.139.11.1.66.1.3
		hwWlanCountryCodeAvailableChannelSet2gBW20 OBJECT-TYPE
			SYNTAX OCTET STRING (SIZE (0..255))
			MAX-ACCESS read-only
			STATUS current
			DESCRIPTION
				"Description."
			::= { hwWlanCountryCodeEntry 3 }

		
		-- 1.3.6.1.4.1.2011.6.139.11.1.66.1.4
		hwWlanCountryCodeAvailableChannelSet2gBW40Plus OBJECT-TYPE
			SYNTAX OCTET STRING (SIZE (0..255))
			MAX-ACCESS read-only
			STATUS current
			DESCRIPTION
				"Description."
			::= { hwWlanCountryCodeEntry 4 }

		
		-- 1.3.6.1.4.1.2011.6.139.11.1.66.1.5
		hwWlanCountryCodeAvailableChannelSet2gBW40Minus OBJECT-TYPE
			SYNTAX OCTET STRING (SIZE (0..255))
			MAX-ACCESS read-only
			STATUS current
			DESCRIPTION
				"Description."
			::= { hwWlanCountryCodeEntry 5 }

		
		-- 1.3.6.1.4.1.2011.6.139.11.1.66.1.6
		hwWlanCountryCodeAvailableChannelSet5gBW20 OBJECT-TYPE
			SYNTAX OCTET STRING (SIZE (0..255))
			MAX-ACCESS read-only
			STATUS current
			DESCRIPTION
				"Description."
			::= { hwWlanCountryCodeEntry 6 }

		
		-- 1.3.6.1.4.1.2011.6.139.11.1.66.1.7
		hwWlanCountryCodeAvailableChannelSet5gBW40Plus OBJECT-TYPE
			SYNTAX OCTET STRING (SIZE (0..255))
			MAX-ACCESS read-only
			STATUS current
			DESCRIPTION
				"Description."
			::= { hwWlanCountryCodeEntry 7 }

		
		-- 1.3.6.1.4.1.2011.6.139.11.1.66.1.8
		hwWlanCountryCodeAvailableChannelSet5gBW40Minus OBJECT-TYPE
			SYNTAX OCTET STRING (SIZE (0..255))
			MAX-ACCESS read-only
			STATUS current
			DESCRIPTION
				"Description."
			::= { hwWlanCountryCodeEntry 8 }

		
		-- 1.3.6.1.4.1.2011.6.139.11.1.66.1.9
		hwWlanCountryCodeAvailableChannelSet5gBW80 OBJECT-TYPE
			SYNTAX OCTET STRING (SIZE (0..255))
			MAX-ACCESS read-only
			STATUS current
			DESCRIPTION
				"Description."
			::= { hwWlanCountryCodeEntry 9 }
			
		-- 1.3.6.1.4.1.2011.6.139.11.1.66.1.10
		hwWlanCountryCodeAvailableChannelSet5gBW160 OBJECT-TYPE
			SYNTAX OCTET STRING (SIZE (0..255))
			MAX-ACCESS read-only
			STATUS current
			DESCRIPTION
				"Description."
			::= { hwWlanCountryCodeEntry 10 }			

		--1.3.6.1.4.1.2011.6.139.11.1.67
		hwUCCProfileTable OBJECT-TYPE
			SYNTAX SEQUENCE OF HwUCCProfileEntry 
			MAX-ACCESS not-accessible
			STATUS current
			DESCRIPTION 
				"This table is used to configure and query UCC profile parameters."
			::= { hwWlanConfigObjects 67 }

		--1.3.6.1.4.1.2011.6.139.11.1.67.1
		hwUCCProfileEntry OBJECT-TYPE
			SYNTAX HwUCCProfileEntry 
			MAX-ACCESS not-accessible
			STATUS current
			DESCRIPTION 
				"The index of this table is hwUCCProfileName."
			INDEX { hwUCCProfileName }
			::= { hwUCCProfileTable 1 }


		HwUCCProfileEntry ::=
			SEQUENCE {				
				hwUCCProfileName
					OCTET STRING,
				hwUCCProfLyncVoice8021p
					INTEGER,
				hwUCCProfLyncVoice8021pValue
					Unsigned32,
				hwUCCProfLyncVoiceDscp
					INTEGER,
				hwUCCProfLyncVoiceDscpValue
					Unsigned32,
				hwUCCProfLyncVideo8021p
					INTEGER,
				hwUCCProfLyncVideo8021pValue
					Unsigned32,
				hwUCCProfLyncVideoDscp
					INTEGER,
				hwUCCProfLyncVideoDscpValue
					Unsigned32,					
				hwUCCProfLyncShare8021p
					INTEGER,
				hwUCCProfLyncShare8021pValue
					Unsigned32,
				hwUCCProfLyncShareDscp
					INTEGER,
				hwUCCProfLyncShareDscpValue
					Unsigned32,
				hwUCCProfLyncFileTransfer8021p
					INTEGER,
				hwUCCProfLyncFileTransfer8021pValue
					Unsigned32,
				hwUCCProfLyncFileTransferDscp
					INTEGER,
				hwUCCProfLyncFileTransferDscpValue
					Unsigned32,				
			        hwUCCProfileRowStatus
					RowStatus 
			 }

		 --1.3.6.1.4.1.2011.6.139.11.1.67.1.1
		hwUCCProfileName OBJECT-TYPE
			SYNTAX OCTET STRING (SIZE (1..35))
			MAX-ACCESS not-accessible
			STATUS current
			DESCRIPTION 
				"This object indicates the name of a UCC profile. It is the index of the table."
			::= { hwUCCProfileEntry 1 }

		 --1.3.6.1.4.1.2011.6.139.11.1.67.1.2
		hwUCCProfLyncVoice8021p OBJECT-TYPE
			SYNTAX INTEGER
				{
				disable(1),
				enable(2)
				}
			MAX-ACCESS read-write
			STATUS current
			DESCRIPTION 
				"This object indicates the switch of lync-voice remark 8021p."
			::= { hwUCCProfileEntry 2 }
			
		 --1.3.6.1.4.1.2011.6.139.11.1.67.1.3
		hwUCCProfLyncVoice8021pValue OBJECT-TYPE
			SYNTAX Unsigned32 (0..7 | 255)
			MAX-ACCESS read-write
			STATUS current
			DESCRIPTION 
				"This object indicates the value of lync-voice remark 8021p."
			::= { hwUCCProfileEntry 3 }

		 --1.3.6.1.4.1.2011.6.139.11.1.67.1.4
		hwUCCProfLyncVoiceDscp OBJECT-TYPE
			SYNTAX INTEGER
				{
				disable(1),
				enable(2)
				}
			MAX-ACCESS read-write
			STATUS current
			DESCRIPTION 
				"This object indicates the switch of lync-voice remark dscp."
			::= { hwUCCProfileEntry 4 }

		 --1.3.6.1.4.1.2011.6.139.11.1.67.1.5
		hwUCCProfLyncVoiceDscpValue OBJECT-TYPE
			SYNTAX Unsigned32 (0..63 | 255)
			MAX-ACCESS read-write
			STATUS current
			DESCRIPTION 
				"This object indicates the value of lync-voice remark dscp."
			::= { hwUCCProfileEntry 5 }
			
		 --1.3.6.1.4.1.2011.6.139.11.1.67.1.6
		hwUCCProfLyncVideo8021p OBJECT-TYPE
			SYNTAX INTEGER
				{
				disable(1),
				enable(2)
				}
			MAX-ACCESS read-write
			STATUS current
			DESCRIPTION 
				"This object indicates the switch of lync-video remark 8021p."
			::= { hwUCCProfileEntry 6 }
			
		 --1.3.6.1.4.1.2011.6.139.11.1.67.1.7
		hwUCCProfLyncVideo8021pValue OBJECT-TYPE
			SYNTAX Unsigned32 (0..7 | 255)
			MAX-ACCESS read-write
			STATUS current
			DESCRIPTION 
				"This object indicates the value of lync-video remark 8021p."
			::= { hwUCCProfileEntry 7 }

		 --1.3.6.1.4.1.2011.6.139.11.1.67.1.8
		hwUCCProfLyncVideoDscp OBJECT-TYPE
			SYNTAX INTEGER
				{
				disable(1),
				enable(2)
				}
			MAX-ACCESS read-write
			STATUS current
			DESCRIPTION 
				"This object indicates the switch of lync-video remark dscp."
			::= { hwUCCProfileEntry 8 }

		 --1.3.6.1.4.1.2011.6.139.11.1.67.1.9
		hwUCCProfLyncVideoDscpValue OBJECT-TYPE
			SYNTAX Unsigned32 (0..63 | 255)
			MAX-ACCESS read-write
			STATUS current
			DESCRIPTION 
				"This object indicates the value of lync-video remark dscp."
			::= { hwUCCProfileEntry 9 }

		 --1.3.6.1.4.1.2011.6.139.11.1.67.1.10
		hwUCCProfLyncShare8021p OBJECT-TYPE
			SYNTAX INTEGER
				{
				disable(1),
				enable(2)
				}
			MAX-ACCESS read-write
			STATUS current
			DESCRIPTION 
				"This object indicates the switch of lync-destop-share remark 8021p."
			::= { hwUCCProfileEntry 10 }
			
		 --1.3.6.1.4.1.2011.6.139.11.1.67.1.11
		hwUCCProfLyncShare8021pValue OBJECT-TYPE
			SYNTAX Unsigned32 (0..7 | 255)
			MAX-ACCESS read-write
			STATUS current
			DESCRIPTION 
				"This object indicates the value of lync-destop-share remark 8021p."
			::= { hwUCCProfileEntry 11 }

		 --1.3.6.1.4.1.2011.6.139.11.1.67.1.12
		hwUCCProfLyncShareDscp OBJECT-TYPE
			SYNTAX INTEGER
				{
				disable(1),
				enable(2)
				}
			MAX-ACCESS read-write
			STATUS current
			DESCRIPTION 
				"This object indicates the switch of lync-destop-share remark dscp."
			::= { hwUCCProfileEntry 12 }

		 --1.3.6.1.4.1.2011.6.139.11.1.67.1.13
		hwUCCProfLyncShareDscpValue OBJECT-TYPE
			SYNTAX Unsigned32 (0..63 | 255)
			MAX-ACCESS read-write
			STATUS current
			DESCRIPTION 
				"This object indicates the value of lync-destop-share remark dscp."
			::= { hwUCCProfileEntry 13 }
			
		 --1.3.6.1.4.1.2011.6.139.11.1.67.1.14
		hwUCCProfLyncFileTransfer8021p OBJECT-TYPE
			SYNTAX INTEGER
				{
				disable(1),
				enable(2)
				}
			MAX-ACCESS read-write
			STATUS current
			DESCRIPTION 
				"This object indicates the switch of lync-file-transfer remark 8021p."
			::= { hwUCCProfileEntry 14 }
			
		 --1.3.6.1.4.1.2011.6.139.11.1.67.1.15
		hwUCCProfLyncFileTransfer8021pValue OBJECT-TYPE
			SYNTAX Unsigned32 (0..7 | 255)
			MAX-ACCESS read-write
			STATUS current
			DESCRIPTION 
				"This object indicates the value of lync-file-transfer remark 8021p."
			::= { hwUCCProfileEntry 15 }

		 --1.3.6.1.4.1.2011.6.139.11.1.67.1.16
		hwUCCProfLyncFileTransferDscp OBJECT-TYPE
			SYNTAX INTEGER
				{
				disable(1),
				enable(2)
				}
			MAX-ACCESS read-write
			STATUS current
			DESCRIPTION 
				"This object indicates the switch of lync-file-transfer remark dscp."
			::= { hwUCCProfileEntry 16 }

		 --1.3.6.1.4.1.2011.6.139.11.1.67.1.17
		hwUCCProfLyncFileTransferDscpValue OBJECT-TYPE
			SYNTAX Unsigned32 (0..63 | 255)
			MAX-ACCESS read-write
			STATUS current
			DESCRIPTION 
				"This object indicates the value of lync-file-transfer remark dscp."
			::= { hwUCCProfileEntry 17 }

		 --1.3.6.1.4.1.2011.6.139.11.1.67.1.18
		hwUCCProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwUCCProfileEntry 18 }
		
		-- 1.3.6.1.4.1.2011.6.139.11.1.68
		hwSoftgreProfileTable OBJECT-TYPE
			SYNTAX SEQUENCE OF HwSoftgreProfileEntry
			MAX-ACCESS not-accessible
			STATUS current
			DESCRIPTION
				"Description."
			::= { hwWlanConfigObjects 68 }

		
		-- 1.3.6.1.4.1.2011.6.139.11.1.68.1
		hwSoftgreProfileEntry OBJECT-TYPE
			SYNTAX HwSoftgreProfileEntry
			MAX-ACCESS not-accessible
			STATUS current
			DESCRIPTION
				"Description."
			INDEX { hwSoftgreProfileName }
			::= { hwSoftgreProfileTable 1 }

		
		HwSoftgreProfileEntry ::=
			SEQUENCE { 
				hwSoftgreProfileName
					OCTET STRING,
				hwSoftgreDestinationIPAddress
					IpAddress,
				hwSoftgreDestinationIPv6Address
					OCTET STRING,
				hwSoftgreKeepaliveFlag
					INTEGER,
				hwSoftgreKeepalivePeriod
					Unsigned32,
				hwSoftgreKeepaliveRetryTimes
					Unsigned32,
				hwSoftgreProfileRowStatus
					RowStatus,
				hwSoftgreUntaggedVlanId
					Unsigned32
			 }

		-- 1.3.6.1.4.1.2011.6.139.11.1.68.1.1
		hwSoftgreProfileName OBJECT-TYPE
			SYNTAX OCTET STRING (SIZE (1..35))
			MAX-ACCESS not-accessible
			STATUS current
			DESCRIPTION
				"Description."
			::= { hwSoftgreProfileEntry 1 }

		
		-- 1.3.6.1.4.1.2011.6.139.11.1.68.1.2
		hwSoftgreDestinationIPAddress OBJECT-TYPE
			SYNTAX IpAddress
			MAX-ACCESS read-write
			STATUS current
			DESCRIPTION
				"Description."
			::= { hwSoftgreProfileEntry 2 }

		
		-- 1.3.6.1.4.1.2011.6.139.11.1.68.1.3
		hwSoftgreDestinationIPv6Address OBJECT-TYPE
			SYNTAX OCTET STRING
			MAX-ACCESS read-write
			STATUS current
			DESCRIPTION
				"Description."
			::= { hwSoftgreProfileEntry 3 }

		
		-- 1.3.6.1.4.1.2011.6.139.11.1.68.1.4
		hwSoftgreKeepaliveFlag OBJECT-TYPE
			SYNTAX INTEGER
				{
				disable(1),
				enable(2)
				}
			MAX-ACCESS read-write
			STATUS current
			DESCRIPTION
				"Description."
			::= { hwSoftgreProfileEntry 4 }

		
		-- 1.3.6.1.4.1.2011.6.139.11.1.68.1.5
		hwSoftgreKeepalivePeriod OBJECT-TYPE
			SYNTAX Unsigned32 (1..32767)
			MAX-ACCESS read-write
			STATUS current
			DESCRIPTION
				"Description."
			::= { hwSoftgreProfileEntry 5 }

		
		-- 1.3.6.1.4.1.2011.6.139.11.1.68.1.6
		hwSoftgreKeepaliveRetryTimes OBJECT-TYPE
			SYNTAX Unsigned32 (1..255)
			MAX-ACCESS read-write
			STATUS current
			DESCRIPTION
				"Description."
			::= { hwSoftgreProfileEntry 6 }

		
		-- 1.3.6.1.4.1.2011.6.139.11.1.68.1.7
		hwSoftgreProfileRowStatus OBJECT-TYPE
			SYNTAX RowStatus
			MAX-ACCESS read-write
			STATUS current
			DESCRIPTION
				"Description."
			::= { hwSoftgreProfileEntry 7 }
		
		-- 1.3.6.1.4.1.2011.6.139.11.1.68.1.8
		hwSoftgreUntaggedVlanId OBJECT-TYPE
			SYNTAX Unsigned32 (0 | 1..4094)
			MAX-ACCESS read-write
			STATUS current
			DESCRIPTION
				"This object indicates the untagged vlan id of the softgre profile."
			::= { hwSoftgreProfileEntry 8 }
			
		-- 1.3.6.1.4.1.2011.6.139.11.1.69
		hwWlanIDIndexedAPSpecificTable OBJECT-TYPE
			SYNTAX SEQUENCE OF HwWlanIDIndexedAPSpecificEntry
			MAX-ACCESS not-accessible
			STATUS current
			DESCRIPTION 
				"This table is used to create or delete an AP specific profile and bind an AP system profile, 2G radio profile, or domain profile to it or unbind an AP system profile, 2G radio profile, or domain profile from it."
			::= { hwWlanConfigObjects 69 }
		--1.3.6.1.4.1.2011.6.139.11.1.69.1
		hwWlanIDIndexedAPSpecificEntry OBJECT-TYPE
			SYNTAX HwWlanIDIndexedAPSpecificEntry 
			MAX-ACCESS not-accessible
			STATUS current
			DESCRIPTION 
				"The index of this table is hwWlanIDIndexedAPSpApId."
			INDEX { hwWlanIDIndexedAPSpApId }
			::= { hwWlanIDIndexedAPSpecificTable 1 }
		HwWlanIDIndexedAPSpecificEntry ::=
			SEQUENCE { 
				hwWlanIDIndexedAPSpApId
					Unsigned32,
				hwWlanIDIndexedAPSpAPSystemProfile
					OCTET STRING,
				hwWlanIDIndexedAPSpDomainProfile
					OCTET STRING,				
				hwWlanIDIndexedAPSpApMac
					MacAddress,				
				hwWlanIDIndexedAPSpApTypeInfo
					OCTET STRING,
				hwWlanIDIndexedAPSpWidsProfile
					OCTET STRING,
				hwWlanIDIndexedAPSpRowStatus
					RowStatus,
				hwWlanIDIndexedAPSpBleProfile
					OCTET STRING,
				hwWlanIDIndexedAPSpLongitude
					OCTET STRING,
				hwWlanIDIndexedAPSpLatitude
					OCTET STRING,
				hwWlanIDIndexedSpApAddressMode
					INTEGER,
				hwWlanIDIndexedSpApIPv4Address
					IpAddress,
				hwWlanIDIndexedSpApIPv4Mask
					IpAddress,
				hwWlanIDIndexedSpApIPv4Gateway
					IpAddress,
				hwWlanIDIndexedSpApIPv6Address
					OCTET STRING,
				hwWlanIDIndexedSpApIPv6PrefixLen
					Unsigned32,
				hwWlanIDIndexedSpApIPv6Gateway
					OCTET STRING,
				hwWlanIDIndexedSpIPv4ACList
					OCTET STRING,
				hwWlanIDIndexedSpIPv6ACList
					OCTET STRING,
				hwWlanIDIndexedSpGroupName
					OCTET STRING,
				hwWlanIDIndexedSpApName
					OCTET STRING,
				hwWlanIDIndexedAPSpLocation
					OCTET STRING,
				hwWlanIDIndexedAPSpSiteCode
					OCTET STRING,
				hwWlanIDIndexedAPSpDomainName
					OCTET STRING,
				hwWlanIDIndexedSpBranchGroupName
					OCTET STRING,
				hwWlanIDIndexedSpManagementVlan
					Unsigned32
			 }
		-- 1.3.6.1.4.1.2011.6.139.11.1.69.1.1
		hwWlanIDIndexedAPSpApId OBJECT-TYPE
			SYNTAX Unsigned32
			MAX-ACCESS not-accessible
			STATUS current
			DESCRIPTION
				"This object indicates the AP ID."
			::= { hwWlanIDIndexedAPSpecificEntry 1 }
		-- 1.3.6.1.4.1.2011.6.139.11.1.69.1.2
		hwWlanIDIndexedAPSpAPSystemProfile OBJECT-TYPE
			SYNTAX OCTET STRING (SIZE (0..35))
			MAX-ACCESS read-write
			STATUS current
			DESCRIPTION 
				"This object indicates the system profile bound to the AP specific profile."
			::= { hwWlanIDIndexedAPSpecificEntry 2 }
		-- 1.3.6.1.4.1.2011.6.139.11.1.69.1.3
		hwWlanIDIndexedAPSpDomainProfile OBJECT-TYPE
			SYNTAX OCTET STRING (SIZE (0..35))
			MAX-ACCESS read-write
			STATUS current
			DESCRIPTION 
				"This object indicates the domain profile bound to the AP specific profile."
			::= { hwWlanIDIndexedAPSpecificEntry 3 }
		-- 1.3.6.1.4.1.2011.6.139.11.1.69.1.4
		hwWlanIDIndexedAPSpApMac OBJECT-TYPE
			SYNTAX MacAddress
			MAX-ACCESS read-write
			STATUS current
			DESCRIPTION
				"This object indicates the MAC address of an AP."
			::= { hwWlanIDIndexedAPSpecificEntry 4 }
		-- 1.3.6.1.4.1.2011.6.139.11.1.69.1.5
		hwWlanIDIndexedAPSpApTypeInfo OBJECT-TYPE
			SYNTAX OCTET STRING (SIZE (0..35))
			MAX-ACCESS read-write
			STATUS current
			DESCRIPTION
				"This object indicates the domain profile bound to the AP specific profile."
			::= { hwWlanIDIndexedAPSpecificEntry 5 }
		-- 1.3.6.1.4.1.2011.6.139.11.1.69.1.6
		hwWlanIDIndexedAPSpWidsProfile OBJECT-TYPE
			SYNTAX OCTET STRING (SIZE (0..35))
			MAX-ACCESS read-write
			STATUS current
			DESCRIPTION
				"This object indicates the bound WIDS profile."
			::= { hwWlanIDIndexedAPSpecificEntry 6 }
		-- 1.3.6.1.4.1.2011.6.139.11.1.69.1.7
		hwWlanIDIndexedAPSpRowStatus OBJECT-TYPE
			SYNTAX RowStatus
			MAX-ACCESS read-write
			STATUS current
			DESCRIPTION 
				"This object indicates the row status of this table. ROWSTATUS_CREATEANDFLOW and ROWSTATUS_DESTROY are commonly used?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwWlanIDIndexedAPSpecificEntry 7 }
		
		-- 1.3.6.1.4.1.2011.6.139.11.1.69.1.8
		hwWlanIDIndexedAPSpBleProfile OBJECT-TYPE
			SYNTAX OCTET STRING (SIZE (0..35))
			MAX-ACCESS read-write
			STATUS current
			DESCRIPTION
				"Description."
			::= { hwWlanIDIndexedAPSpecificEntry 8 }
			
		-- 1.3.6.1.4.1.2011.6.139.11.1.69.1.9
		hwWlanIDIndexedAPSpLongitude OBJECT-TYPE
			SYNTAX OCTET STRING (SIZE (1..15))
			MAX-ACCESS read-write
			STATUS current
			DESCRIPTION
				"This object indicates the longitude."
			::= { hwWlanIDIndexedAPSpecificEntry 9 }
			
		-- 1.3.6.1.4.1.2011.6.139.11.1.69.1.10
		hwWlanIDIndexedAPSpLatitude OBJECT-TYPE
			SYNTAX OCTET STRING (SIZE (1..14))
			MAX-ACCESS read-write
			STATUS current
			DESCRIPTION
				"This object indicates the latitude."
			::= { hwWlanIDIndexedAPSpecificEntry 10 }
		
		-- 1.3.6.1.4.1.2011.6.139.11.1.69.1.11
		hwWlanIDIndexedSpApAddressMode OBJECT-TYPE
			SYNTAX INTEGER
				{
				invalid(-1),
				static(1),
				dhcp(2),
				slaac(3)
				}
			MAX-ACCESS read-write
			STATUS current
			DESCRIPTION
				"This object indicates the IP address allocation mode."
			::= { hwWlanIDIndexedAPSpecificEntry 11 }
		
		-- 1.3.6.1.4.1.2011.6.139.11.1.69.1.12
		hwWlanIDIndexedSpApIPv4Address OBJECT-TYPE
			SYNTAX IpAddress
			MAX-ACCESS read-write
			STATUS current
			DESCRIPTION
				"This object indicates the AP's IPv4 address.
 	hwWlanIDIndexedSpApIPv4Address takes effect if hwWlanIDIndexedSpApAddressMode is set to static."
			::= { hwWlanIDIndexedAPSpecificEntry 12 }
		
		-- 1.3.6.1.4.1.2011.6.139.11.1.69.1.13
		hwWlanIDIndexedSpApIPv4Mask OBJECT-TYPE
			SYNTAX IpAddress
			MAX-ACCESS read-write
			STATUS current
			DESCRIPTION
				"This object indicates the AP's IPv4 mask.
 	hwWlanIDIndexedSpApIPv4Mask takes effect if hwWlanIDIndexedSpApAddressMode is set to static."
			::= { hwWlanIDIndexedAPSpecificEntry 13 }
		
		-- 1.3.6.1.4.1.2011.6.139.11.1.69.1.14
		hwWlanIDIndexedSpApIPv4Gateway OBJECT-TYPE
			SYNTAX IpAddress
			MAX-ACCESS read-write
			STATUS current
			DESCRIPTION
				"This object indicates the AP's IPv4 gateway.
 	hwWlanIDIndexedSpApIPv4Gateway takes effect if hwWlanIDIndexedSpApAddressMode is set to static."
			::= { hwWlanIDIndexedAPSpecificEntry 14 }
		
		-- 1.3.6.1.4.1.2011.6.139.11.1.69.1.15
		hwWlanIDIndexedSpApIPv6Address OBJECT-TYPE
			SYNTAX OCTET STRING (SIZE (0..46))
			MAX-ACCESS read-write
			STATUS current
			DESCRIPTION
				"This object indicates the AP's IPv6 address.
 	hwWlanIDIndexedSpApIPv6Address takes effect if hwWlanIDIndexedSpApAddressMode is set to static."
			::= { hwWlanIDIndexedAPSpecificEntry 15 }
		
		-- 1.3.6.1.4.1.2011.6.139.11.1.69.1.16
		hwWlanIDIndexedSpApIPv6PrefixLen OBJECT-TYPE
			SYNTAX Unsigned32 (0..128)
			MAX-ACCESS read-write
			STATUS current
			DESCRIPTION
				"This object indicates the length of the IPv6 address prefix."
			::= { hwWlanIDIndexedAPSpecificEntry 16 }
		
		-- 1.3.6.1.4.1.2011.6.139.11.1.69.1.17
		hwWlanIDIndexedSpApIPv6Gateway OBJECT-TYPE
			SYNTAX OCTET STRING (SIZE (0..46))
			MAX-ACCESS read-write
			STATUS current
			DESCRIPTION
				"This object indicates the AP's IPv6 gateway.
 	hwWlanIDIndexedSpApIPv6Gateway takes effect if hwWlanIDIndexedSpApAddressMode is set to static."
			::= { hwWlanIDIndexedAPSpecificEntry 17 }
		
		-- 1.3.6.1.4.1.2011.6.139.11.1.69.1.18
		hwWlanIDIndexedSpIPv4ACList OBJECT-TYPE
			SYNTAX OCTET STRING
			MAX-ACCESS read-write
			STATUS current
			DESCRIPTION
				"This object indicates the AC IPv4 address list.
 	NOTE AC lists are separated by question marks (?).A maximum of four AC lists can be configured."
			::= { hwWlanIDIndexedAPSpecificEntry 18 }
		
		-- 1.3.6.1.4.1.2011.6.139.11.1.69.1.19
		hwWlanIDIndexedSpIPv6ACList OBJECT-TYPE
			SYNTAX OCTET STRING
			MAX-ACCESS read-write
			STATUS current
			DESCRIPTION
				"This object indicates the AC IPv6 address list.
 	NOTE AC lists are separated by question marks (?).A maximum of four AC lists can be configured."
			::= { hwWlanIDIndexedAPSpecificEntry 19 }
		
		-- 1.3.6.1.4.1.2011.6.139.11.1.69.1.20
		hwWlanIDIndexedSpGroupName OBJECT-TYPE
			SYNTAX OCTET STRING (SIZE (0..35))
			MAX-ACCESS read-write
			STATUS current
			DESCRIPTION
				"Description."
			::= { hwWlanIDIndexedAPSpecificEntry 20 }
		
		-- 1.3.6.1.4.1.2011.6.139.11.1.69.1.21
		hwWlanIDIndexedSpApName OBJECT-TYPE
			SYNTAX OCTET STRING (SIZE (0..31))
			MAX-ACCESS read-write
			STATUS current
			DESCRIPTION
				"Description."
			::= { hwWlanIDIndexedAPSpecificEntry 21 }
			
		-- 1.3.6.1.4.1.2011.6.139.11.1.69.1.22
		hwWlanIDIndexedAPSpLocation OBJECT-TYPE
			SYNTAX OCTET STRING (SIZE (0..63))
			MAX-ACCESS read-write
			STATUS current
			DESCRIPTION
				"Description."
			::= { hwWlanIDIndexedAPSpecificEntry 22 }

		-- 1.3.6.1.4.1.2011.6.139.11.1.69.1.23
		hwWlanIDIndexedAPSpSiteCode OBJECT-TYPE
			SYNTAX OCTET STRING (SIZE (0..14))
			MAX-ACCESS read-write
			STATUS current
			DESCRIPTION
				"This object indicates the site code."
			::= { hwWlanIDIndexedAPSpecificEntry 23 }

		
		-- 1.3.6.1.4.1.2011.6.139.11.1.69.1.24
		hwWlanIDIndexedAPSpDomainName OBJECT-TYPE
			SYNTAX OCTET STRING (SIZE (0..255))
			MAX-ACCESS read-write
			STATUS current
			DESCRIPTION
				"This object indicates the domain name."
			::= { hwWlanIDIndexedAPSpecificEntry 24 }

		
		-- 1.3.6.1.4.1.2011.6.139.11.1.69.1.25
		hwWlanIDIndexedSpBranchGroupName OBJECT-TYPE
			SYNTAX OCTET STRING (SIZE (0..35))
			MAX-ACCESS read-write
			STATUS current
			DESCRIPTION
				"This object indicates the AP branch group name."
			::= { hwWlanIDIndexedAPSpecificEntry 25 }
	    		
		hwWlanIDIndexedSpManagementVlan OBJECT-TYPE
			SYNTAX Unsigned32 (0..4094)
			MAX-ACCESS read-write
			STATUS current
			DESCRIPTION
				"This object indicates the AP management vlan."
			::= { hwWlanIDIndexedAPSpecificEntry 26 }
-- 1.3.6.1.4.1.2011.6.139.11.1.70
-- 1.3.6.1.4.1.2011.6.139.11.1.70
-- 1.3.6.1.4.1.2011.6.139.11.1.70
-- 1.3.6.1.4.1.2011.6.139.11.1.70
-- 1.3.6.1.4.1.2011.6.139.11.1.70
-- 1.3.6.1.4.1.2011.6.139.11.1.70
		-- 1.3.6.1.4.1.2011.6.139.11.1.70
		hwIDIndexedAPSpecificWiredPortTable OBJECT-TYPE
			SYNTAX SEQUENCE OF HwIDIndexedAPSpecificWiredPortEntry 
			MAX-ACCESS not-accessible
			STATUS current
			DESCRIPTION 
				"This table is used to bind an AP wired port profile to an AP specific profile or unbind an AP wired port profile from an AP specific profile.."
			::= { hwWlanConfigObjects 70 }
		--1.3.6.1.4.1.2011.6.139.11.1.70.1
		hwIDIndexedAPSpecificWiredPortEntry OBJECT-TYPE
			SYNTAX HwIDIndexedAPSpecificWiredPortEntry 
			MAX-ACCESS not-accessible
			STATUS current
			DESCRIPTION 
				"Indexes of this table are  hwIDIndexedAPSpWPInterfaceType, hwIDIndexedAPSpWPInterfaceNum and hwWlanIDIndexedAPSpApId."
			INDEX { hwIDIndexedAPSpWPInterfaceType, hwIDIndexedAPSpWPInterfaceNum, hwWlanIDIndexedAPSpApId }
			::= { hwIDIndexedAPSpecificWiredPortTable 1 }
		HwIDIndexedAPSpecificWiredPortEntry ::=
			SEQUENCE {				
				hwIDIndexedAPSpWPInterfaceType
					INTEGER,
				hwIDIndexedAPSpWPInterfaceNum
					Unsigned32,
				hwIDIndexedAPSpWPProfile
					OCTET STRING,
				hwIDIndexedAPSpWPRowStatus
					RowStatus
			 }
		 --1.3.6.1.4.1.2011.6.139.11.1.70.1.1
		hwIDIndexedAPSpWPInterfaceType OBJECT-TYPE
			SYNTAX INTEGER
				{
				fe(1),
				ge(2) ,
				trunk(3),
				multige(4),
				xge(5)
				}
			MAX-ACCESS not-accessible
			STATUS current
			DESCRIPTION 
				"This object indicates the interface type."
			::= { hwIDIndexedAPSpecificWiredPortEntry 1 }
		 --1.3.6.1.4.1.2011.6.139.11.1.70.1.2
		hwIDIndexedAPSpWPInterfaceNum OBJECT-TYPE
			SYNTAX Unsigned32 (0..27)
			MAX-ACCESS not-accessible
			STATUS current
			DESCRIPTION 
				"This object indicates the interface index."
			::= { hwIDIndexedAPSpecificWiredPortEntry 2 }
		 --1.3.6.1.4.1.2011.6.139.11.1.70.1.3
		hwIDIndexedAPSpWPProfile OBJECT-TYPE
			SYNTAX OCTET STRING (SIZE (0..35))
			MAX-ACCESS read-write
			STATUS current
			DESCRIPTION 
				"This object indicates the bound wired port profile."
			::= { hwIDIndexedAPSpecificWiredPortEntry 3 }
		 --1.3.6.1.4.1.2011.6.139.11.1.70.1.4
		hwIDIndexedAPSpWPRowStatus OBJECT-TYPE
			SYNTAX RowStatus
			MAX-ACCESS read-write
			STATUS current
			DESCRIPTION 
				"This object indicates the row status of this table. ROWSTATUS_CREATEANDFLOW and ROWSTATUS_DESTROY are commonly used?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwIDIndexedAPSpecificWiredPortEntry 4 }
		--1.3.6.1.4.1.2011.6.139.11.1.71
		hwIDIndexedAPSpecificRadioTable OBJECT-TYPE
			SYNTAX SEQUENCE OF HwIDIndexedAPSpecificRadioEntry 
			MAX-ACCESS not-accessible
			STATUS current
			DESCRIPTION 
				"This table records the information about profiles bound based on radio in an AP specific profile, including 5G radio profile, Mesh profile, WDS profile, WIDS profile, location profile, and spectrum profile."
			::= { hwWlanConfigObjects 71 }
		--1.3.6.1.4.1.2011.6.139.11.1.71.1
		hwIDIndexedAPSpecificRadioEntry OBJECT-TYPE
			SYNTAX HwIDIndexedAPSpecificRadioEntry 
			MAX-ACCESS not-accessible
			STATUS current
			DESCRIPTION 
				"Indexes of this table are hwIDIndexedAPSpRadio and hwWlanIDIndexedAPSpApId."
			INDEX { hwIDIndexedAPSpRadio, hwWlanIDIndexedAPSpApId }
			::= { hwIDIndexedAPSpecificRadioTable 1 }
		HwIDIndexedAPSpecificRadioEntry ::=
			SEQUENCE {				
				hwIDIndexedAPSpRadio
					Unsigned32,
				hwIDIndexedAPSp5gRadioProfile
					OCTET STRING,
				hwIDIndexedAPSpMeshProfile
					OCTET STRING,
				hwIDIndexedAPSpWdsProfile
					OCTET STRING,
				hwIDIndexedAPSpLocationProfile
					OCTET STRING,
				hwIDIndexedAPSpRadio2gProfile
					OCTET STRING,
				hwIDIndexedAPSpMeshWhitelistProfile
					OCTET STRING,
				hwIDIndexedAPSpWdsWhitelistProfile
					OCTET STRING,
				hwIDIndexedAPSpRadioSwitch
					INTEGER,
				hwIDIndexedAPSpRadioChannel
					Unsigned32,
				hwIDIndexedAPSpRadioBandwidth
					INTEGER,
				hwIDIndexedAPSpRadioEirp
					Unsigned32,
				hwIDIndexedAPSpRadioAntennaGain
					Integer32,
				hwIDIndexedAPSpRadioCoverageDistance
					Unsigned32,
				hwIDIndexedAPSpRadioWorkMode
					INTEGER,
				hwIDIndexedAPSpRadioFrequency
					INTEGER,
				hwIDIndexedAPSpSpectrumAnalysisSwitch
					INTEGER,
				hwIDIndexedAPSpWidsDeviceDetectSwitch
					INTEGER,
				hwIDIndexedAPSpWidsAttackDetectEnBmp
					Unsigned32,
				hwIDIndexedAPSpWidsRogueContainSwitch
					INTEGER,
				hwIDIndexedAPSpRadioRowStatus
					RowStatus,
				hwIDIndexedAPSpRadioSecondChannel
					Unsigned32,
				hwIDIndexedAPSpAutoChannelSelectSwitch
					INTEGER,
				hwIDIndexedAPSpAutoTxPowerSelectSwitch
					INTEGER,
				hwIDIndexedAPSpSfnRoamCtsSwitch
					INTEGER,
				hwIDIndexedAPSpSfnRoamBeaconSwitch
					INTEGER,
				hwIDIndexedAPSpSfnRoamCtsDelay
					Unsigned32,   
				hwIDIndexedAPSpRadioCalibrateFlexibleRadio
				    INTEGER,
				hwIDIndexedAPSpAutoBandwidthSelectSwitch
				     INTEGER,
				hwIDIndexedAPSpReferenceDataAnalysis
				     INTEGER
			 }
		 --1.3.6.1.4.1.2011.6.139.11.1.71.1.1
		hwIDIndexedAPSpRadio OBJECT-TYPE
			SYNTAX Unsigned32 (0..2)
			MAX-ACCESS not-accessible
			STATUS current
			DESCRIPTION 
				"This object indicates the radio ID. It is the index of the table."
			::= { hwIDIndexedAPSpecificRadioEntry 1 }
		 --1.3.6.1.4.1.2011.6.139.11.1.71.1.2
		hwIDIndexedAPSp5gRadioProfile OBJECT-TYPE
			SYNTAX OCTET STRING (SIZE (0..35))
			MAX-ACCESS read-write
			STATUS current
			DESCRIPTION 
				"This object indicates the bound 5G radio profile."
			::= { hwIDIndexedAPSpecificRadioEntry 2 }
		 --1.3.6.1.4.1.2011.6.139.11.1.71.1.3
		hwIDIndexedAPSpMeshProfile OBJECT-TYPE
			SYNTAX OCTET STRING (SIZE (0..35))
			MAX-ACCESS read-write
			STATUS current
			DESCRIPTION 
				"This object indicates the bound Mesh profile."
			::= { hwIDIndexedAPSpecificRadioEntry 3 }
		 --1.3.6.1.4.1.2011.6.139.11.1.71.1.4
		hwIDIndexedAPSpWdsProfile OBJECT-TYPE
			SYNTAX OCTET STRING (SIZE (0..35))
			MAX-ACCESS read-write
			STATUS current
			DESCRIPTION 
				"This object indicates the bound WDS profile."
			::= { hwIDIndexedAPSpecificRadioEntry 4 }
	 --1.3.6.1.4.1.2011.6.139.11.1.71.1.5
		hwIDIndexedAPSpLocationProfile OBJECT-TYPE
			SYNTAX OCTET STRING (SIZE (0..35))
			MAX-ACCESS read-write
			STATUS current
			DESCRIPTION 
				"This object indicates the bound location profile."
			::= { hwIDIndexedAPSpecificRadioEntry 5 }
		-- 1.3.6.1.4.1.2011.6.139.11.1.71.1.6
		hwIDIndexedAPSpRadio2gProfile OBJECT-TYPE
			SYNTAX OCTET STRING (SIZE (0..35))
			MAX-ACCESS read-write
			STATUS current
			DESCRIPTION
				"This object indicates the system profile to which AP groups are bound. The default value is default."
			::= { hwIDIndexedAPSpecificRadioEntry 6 }
		-- 1.3.6.1.4.1.2011.6.139.11.1.71.1.7
		hwIDIndexedAPSpMeshWhitelistProfile OBJECT-TYPE
			SYNTAX OCTET STRING (SIZE (0..35))
			MAX-ACCESS read-write
			STATUS current
			DESCRIPTION
				"This object indicates the bound whitelist profile."
			::= { hwIDIndexedAPSpecificRadioEntry 7 }
		-- 1.3.6.1.4.1.2011.6.139.11.1.71.1.8
		hwIDIndexedAPSpWdsWhitelistProfile OBJECT-TYPE
			SYNTAX OCTET STRING (SIZE (0..35))
			MAX-ACCESS read-write
			STATUS current
			DESCRIPTION
				"This object indicates the bound whitelist profile."
			::= { hwIDIndexedAPSpecificRadioEntry 8 }
		-- 1.3.6.1.4.1.2011.6.139.11.1.71.1.9
		hwIDIndexedAPSpRadioSwitch OBJECT-TYPE
			SYNTAX INTEGER
				{
				disable(1),
				invalid(255)
				}
			MAX-ACCESS read-write
			STATUS current
			DESCRIPTION
				"This object indicates the name of a 2G radio profile. It is the index of the table."
			::= { hwIDIndexedAPSpecificRadioEntry 9 }
		-- 1.3.6.1.4.1.2011.6.139.11.1.71.1.10
		hwIDIndexedAPSpRadioChannel OBJECT-TYPE
			SYNTAX Unsigned32
			MAX-ACCESS read-write
			STATUS current
			DESCRIPTION
				"This object indicates a radio-frequency channel. For 2.4G, the value ranges from 1 to 13. For 5G, the value ranges from 36 to 196 (with a separation interval of 4)."
			::= { hwIDIndexedAPSpecificRadioEntry 10 }
		-- 1.3.6.1.4.1.2011.6.139.11.1.71.1.11
		hwIDIndexedAPSpRadioBandwidth OBJECT-TYPE
			SYNTAX INTEGER
				{
				ht20(1),
				ht40Plus(2),
				ht40Minus(3),
				ht80(4),
                                                                             ht160(5),
				invalid(255)
				}
			MAX-ACCESS read-write
			STATUS current
			DESCRIPTION
				"This object indicate a bandwidth. The default value is 1."
			::= { hwIDIndexedAPSpecificRadioEntry 11 }
		-- 1.3.6.1.4.1.2011.6.139.11.1.71.1.12
		hwIDIndexedAPSpRadioEirp OBJECT-TYPE
			SYNTAX Unsigned32 (1..127 | 255)
			MAX-ACCESS read-write
			STATUS current
			DESCRIPTION
				"This object indicates a power value. The default value is 127(from V2R8C10; The default value is 255 before V2R8C10.). The configuration is saved but the actual power is determined by the maximum power supported by the AP."
			::= { hwIDIndexedAPSpecificRadioEntry 12 }
		-- 1.3.6.1.4.1.2011.6.139.11.1.71.1.13
		hwIDIndexedAPSpRadioAntennaGain OBJECT-TYPE
			SYNTAX Integer32 (-10..30 | 255)
			MAX-ACCESS read-write
			STATUS current
			DESCRIPTION
				"This object indicates antenna gains. The default value 0xFF indicates that the default gain of an AP is used. It is expressed in dB. Default gains vary with different types of APs."
			::= { hwIDIndexedAPSpecificRadioEntry 13 }
		-- 1.3.6.1.4.1.2011.6.139.11.1.71.1.14
		hwIDIndexedAPSpRadioCoverageDistance OBJECT-TYPE
			SYNTAX Unsigned32 (1..400 | 65535)
			MAX-ACCESS read-write
			STATUS current
			DESCRIPTION
				"This object indicates a radio coverage distance. The default value is 3. The unit is 0.1 km."
			::= { hwIDIndexedAPSpecificRadioEntry 14 }
		-- 1.3.6.1.4.1.2011.6.139.11.1.71.1.15
		hwIDIndexedAPSpRadioWorkMode OBJECT-TYPE
			SYNTAX INTEGER
				{
				normal(1),
				monitor(2),
				dualband(3),
				proxyScan(4),
				invalid(255)
				}
			MAX-ACCESS read-write
			STATUS current
			DESCRIPTION
				"This object indicates the radio working mode. The default value is 1."
			::= { hwIDIndexedAPSpecificRadioEntry 15 }
		-- 1.3.6.1.4.1.2011.6.139.11.1.71.1.16
		hwIDIndexedAPSpRadioFrequency OBJECT-TYPE
			SYNTAX INTEGER
				{
				frequency2G(1),
				frequency5G(2),
				invalid(255)
				}
			MAX-ACCESS read-write
			STATUS current
			DESCRIPTION
				"This object indicates the setting of the frequency band for radio 0. The default value is invalid. 1: frequency2G, 2: frequency5G."
			::= { hwIDIndexedAPSpecificRadioEntry 16 }
		-- 1.3.6.1.4.1.2011.6.139.11.1.71.1.17
		hwIDIndexedAPSpSpectrumAnalysisSwitch OBJECT-TYPE
			SYNTAX INTEGER
				{
				enable(2),
				invalid(255)
				}
			MAX-ACCESS read-write
			STATUS current
			DESCRIPTION
				"This object indicates the status of the spectrum analysis function. The default value is 1."
			::= { hwIDIndexedAPSpecificRadioEntry 17 }
		-- 1.3.6.1.4.1.2011.6.139.11.1.71.1.18
		hwIDIndexedAPSpWidsDeviceDetectSwitch OBJECT-TYPE
			SYNTAX INTEGER
				{
				enable(2),
				invalid(255)
				}
			MAX-ACCESS read-write
			STATUS current
			DESCRIPTION
				"This object indicates the status of the device detection function. The default value is 1."
			::= { hwIDIndexedAPSpecificRadioEntry 18 }
		-- 1.3.6.1.4.1.2011.6.139.11.1.71.1.19
		hwIDIndexedAPSpWidsAttackDetectEnBmp OBJECT-TYPE
			SYNTAX Unsigned32
			MAX-ACCESS read-write
			STATUS current
			DESCRIPTION
				"This object indicates the bit map of the brute force attack switch. bit0:weak-iv, bit1:spoof, bit2:flood, bit3:wpa-psk, bit4:wpa2-psk, bit5:wapi-psk, bit6:wep-psk."
			::= { hwIDIndexedAPSpecificRadioEntry 19 }
		-- 1.3.6.1.4.1.2011.6.139.11.1.71.1.20
		hwIDIndexedAPSpWidsRogueContainSwitch OBJECT-TYPE
			SYNTAX INTEGER
				{
				enable(2),
				invalid(255)
				}
			MAX-ACCESS read-write
			STATUS current
			DESCRIPTION
				"This object indicates the status of the device detection function. The default value is 1."
			::= { hwIDIndexedAPSpecificRadioEntry 20 }
		-- 1.3.6.1.4.1.2011.6.139.11.1.71.1.21
		hwIDIndexedAPSpRadioRowStatus OBJECT-TYPE
			SYNTAX RowStatus
			MAX-ACCESS read-write
			STATUS current
			DESCRIPTION 
				"This object indicates the row status of this table. ROWSTATUS_CREATEANDFLOW and ROWSTATUS_DESTROY are commonly used."
			::= { hwIDIndexedAPSpecificRadioEntry 21 }
		-- 1.3.6.1.4.1.2011.6.139.11.1.71.1.22
		hwIDIndexedAPSpRadioSecondChannel OBJECT-TYPE
			SYNTAX Unsigned32
			MAX-ACCESS read-write
			STATUS current
			DESCRIPTION
				"This object indicates a second radio-frequency channel.The value ranges from 42,58,106,122,138,155."
			::= { hwIDIndexedAPSpecificRadioEntry 22 }
			
		-- 1.3.6.1.4.1.2011.6.139.11.1.71.1.23
		hwIDIndexedAPSpAutoChannelSelectSwitch OBJECT-TYPE
			SYNTAX INTEGER
				{
				disable(1),
 				enable(2),
				invalid(255)
				}
			MAX-ACCESS read-write
			STATUS current
			DESCRIPTION
				"This object indicates the status of the automatic channel selection function."
			::= { hwIDIndexedAPSpecificRadioEntry 23 }
		
		-- 1.3.6.1.4.1.2011.6.139.11.1.71.1.24
		hwIDIndexedAPSpAutoTxPowerSelectSwitch OBJECT-TYPE
			SYNTAX INTEGER
				{
				disable(1),
				enable(2),
				invalid(255)
				}
			MAX-ACCESS read-write
			STATUS current
			DESCRIPTION
				"This object indicates the status of the automatic power selection function."
			::= { hwIDIndexedAPSpecificRadioEntry 24 } 

		
		-- 1.3.6.1.4.1.2011.6.139.11.1.71.1.25
		hwIDIndexedAPSpSfnRoamCtsSwitch OBJECT-TYPE
			SYNTAX INTEGER
				{
				disable(1),
				invalid(255)

				}
			MAX-ACCESS read-write
			STATUS current
			DESCRIPTION
				"This object indicates the status of Cts Switch. The default value is 255."
			::= { hwIDIndexedAPSpecificRadioEntry 25 }

		
		-- 1.3.6.1.4.1.2011.6.139.11.1.71.1.26
		hwIDIndexedAPSpSfnRoamBeaconSwitch OBJECT-TYPE
			SYNTAX INTEGER
				{
				disable(1),
				invalid(255)
				}
			MAX-ACCESS read-write
			STATUS current
			DESCRIPTION
				"This object indicates the status of Beacon Switch. The default value is 255."
			::= { hwIDIndexedAPSpecificRadioEntry 26 }

		
		-- 1.3.6.1.4.1.2011.6.139.11.1.71.1.27
		hwIDIndexedAPSpSfnRoamCtsDelay OBJECT-TYPE
			SYNTAX Unsigned32 (0..255)
			MAX-ACCESS read-write
			STATUS current
			DESCRIPTION
				"This object indicates Cts Delay time. The default value is 0."
			::= { hwIDIndexedAPSpecificRadioEntry 27 }

		-- 1.3.6.1.4.1.2011.6.139.11.1.71.1.28
		hwIDIndexedAPSpRadioCalibrateFlexibleRadio OBJECT-TYPE
			SYNTAX INTEGER
				{
				disable(1),
				invalid(255)
				}
			MAX-ACCESS read-write
			STATUS current
			DESCRIPTION
				"This object indicates the status of calibrate flexible-radio. The default value is 255."
			::= { hwIDIndexedAPSpecificRadioEntry 28 }
		-- 1.3.6.1.4.1.2011.6.139.11.1.71.1.29
		hwIDIndexedAPSpAutoBandwidthSelectSwitch OBJECT-TYPE
			SYNTAX INTEGER
				{
				disable(1),
				enable(2),
				invalid(255)
				}
			MAX-ACCESS read-write
			STATUS current
			DESCRIPTION
				"This object indicates the status of the automatic bandwidth selection function. The default value is 255."
			DEFVAL { invalid }
			::= { hwIDIndexedAPSpecificRadioEntry 29 }
		-- 1.3.6.1.4.1.2011.6.139.11.1.71.1.30
		hwIDIndexedAPSpReferenceDataAnalysis OBJECT-TYPE
			SYNTAX INTEGER
				{
				disable(1),
				enable(2),
				invalid(255)
				}
			MAX-ACCESS read-write
			STATUS current
			DESCRIPTION
				"This object indicates the status of the referencing data-analysis  function. The default value is 255."
			DEFVAL { invalid }
			::= { hwIDIndexedAPSpecificRadioEntry 30 }
		-- 1.3.6.1.4.1.2011.6.139.11.1.72
		hwIDIndexedAPSpecificVapTable OBJECT-TYPE
			SYNTAX SEQUENCE OF HwIDIndexedAPSpecificVapEntry 
			MAX-ACCESS not-accessible
			STATUS current
			DESCRIPTION 
				"This table is used to create VAPs in an AP specific profile."
			::= { hwWlanConfigObjects 72 }
		--1.3.6.1.4.1.2011.6.139.11.1.72.1
		hwIDIndexedAPSpecificVapEntry OBJECT-TYPE
			SYNTAX HwIDIndexedAPSpecificVapEntry 
			MAX-ACCESS not-accessible
			STATUS current
			DESCRIPTION 
				"Indexes of this table are hwIDIndexedAPSpWlan, hwIDIndexedAPSpRadio, and hwWlanIDIndexedAPSpApId."
			INDEX { hwIDIndexedAPSpWlan, hwIDIndexedAPSpRadio, hwWlanIDIndexedAPSpApId}
			::= { hwIDIndexedAPSpecificVapTable 1 }
		HwIDIndexedAPSpecificVapEntry ::=
			SEQUENCE {				
				hwIDIndexedAPSpWlan
					Unsigned32,
				hwIDIndexedAPSpVapProfile
					OCTET STRING,
				hwIDIndexedAPSpVapRowStatus
					RowStatus,
				hwIDIndexedAPSpVapServiceVlan
					Unsigned32,
				hwIDIndexedAPSpVapVlanPool
					OCTET STRING
			 }
		 --1.3.6.1.4.1.2011.6.139.11.1.72.1.1
		hwIDIndexedAPSpWlan OBJECT-TYPE
			SYNTAX Unsigned32 (1..16)
			MAX-ACCESS not-accessible
			STATUS current
			DESCRIPTION 
				"This object indicates the WLAN ID. It is the index of the table."
			::= { hwIDIndexedAPSpecificVapEntry 1 }
		 --1.3.6.1.4.1.2011.6.139.11.1.72.1.2
		hwIDIndexedAPSpVapProfile OBJECT-TYPE
			SYNTAX OCTET STRING (SIZE (1..35))
			MAX-ACCESS read-write
			STATUS current
			DESCRIPTION 
				"This object indicates the bound VAP profile."
			::= { hwIDIndexedAPSpecificVapEntry 2 }
		 --1.3.6.1.4.1.2011.6.139.11.1.72.1.3
		hwIDIndexedAPSpVapRowStatus OBJECT-TYPE
			SYNTAX RowStatus
			MAX-ACCESS read-write
			STATUS current
			DESCRIPTION 
				"This object indicates the row status of this table. createAndGo(4) and destroy(6) are commonly used."
			::= { hwIDIndexedAPSpecificVapEntry 3 }

		--1.3.6.1.4.1.2011.6.139.11.1.72.1.4
		hwIDIndexedAPSpVapServiceVlan OBJECT-TYPE
			SYNTAX Unsigned32 (1..4094)
			MAX-ACCESS read-write
			STATUS current
			DESCRIPTION
				"This object indicates the service VLAN for the VAP. The invalid value is 0."
			::= { hwIDIndexedAPSpecificVapEntry 4 }
		

		--1.3.6.1.4.1.2011.6.139.11.1.72.1.5
		hwIDIndexedAPSpVapVlanPool OBJECT-TYPE
			SYNTAX OCTET STRING (SIZE (0..31))
			MAX-ACCESS read-write
			STATUS current
			DESCRIPTION
				"This object indicates the VLAN pool to which the VAP is bound."
			::= { hwIDIndexedAPSpecificVapEntry 5 }

		-- 1.3.6.1.4.1.2011.6.139.11.1.73
		hwBleProfileTable OBJECT-TYPE
			SYNTAX SEQUENCE OF HwBleProfileEntry
			MAX-ACCESS not-accessible
			STATUS current
			DESCRIPTION
				"Description."
			::= { hwWlanConfigObjects 73 }
			
		-- 1.3.6.1.4.1.2011.6.139.11.1.73.1
		hwBleProfileEntry OBJECT-TYPE
			SYNTAX HwBleProfileEntry
			MAX-ACCESS not-accessible
			STATUS current
			DESCRIPTION
				"Description."
			INDEX { hwWlanBLEProfileName }
			::= { hwBleProfileTable 1 }

		HwBleProfileEntry ::=
			SEQUENCE { 
				hwWlanBLEProfileName
					OCTET STRING,
				hwWlanBLEBroadcasterEnable
					INTEGER,
				hwWlanBLETxPower
					Integer32,
				hwWlanBLEBroadcastingUUID
					OCTET STRING,
				hwWlanBLEBroadcastingMajor
					OCTET STRING,
				hwWlanBLEBroadcastingMinor
					OCTET STRING,
				hwWlanBLEBroadcastingReferenceRSSI
					Integer32,
				hwWlanBLEBroadcastingInterval
					Unsigned32,
				hwWlanBLESnifferEnable
					INTEGER,
				hwWlanBLEProfileRowStatus
					RowStatus,
				hwWlanBLEBroadcastingUUIDHex
					OCTET STRING,
				hwWlanBLEBroadcastingMajorHex
					OCTET STRING,
				hwWlanBLEBroadcastingMajorDecimal
					Integer32,
				hwWlanBLEBroadcastingMinorHex
					OCTET STRING,
				hwWlanBLEBroadcastingMinorDecimal
					Integer32,
		                hwWlanBLESnifferMode
                                        INTEGER,
                                hwWlanBLEReportEnable
                                        INTEGER,
                                hwWlanBLEReportMode
                                        INTEGER,
                                hwWlanBLEReportInterval
                                        Integer32,
                                hwWlanBLEReportServerIPAddress
                                        IpAddress,
                                hwWlanBLEReportServerIPv6Address
                                        OCTET STRING,
                                hwWlanBLEReportServerPort
                                        Unsigned32,
                                hwWlanBLEReportServerViaACEnable
                                        INTEGER,
                                hwWlanBLEReportServerViaACPort
                                        Unsigned32,
                                hwWlanBLESourceIPAddress
                                         IpAddress,
                                hwWlanBLESourceIPv6Address
			                OCTET STRING,
			        hwWlanBLEServerAddressDomain
                                        OCTET STRING
			 }

		-- 1.3.6.1.4.1.2011.6.139.11.1.73.1.1
		hwWlanBLEProfileName OBJECT-TYPE
			SYNTAX OCTET STRING (SIZE (1..35))
			MAX-ACCESS not-accessible
			STATUS current
			DESCRIPTION
				"Description."
			::= { hwBleProfileEntry 1 }

		-- 1.3.6.1.4.1.2011.6.139.11.1.73.1.2
		hwWlanBLEBroadcasterEnable OBJECT-TYPE
			SYNTAX INTEGER
				{
				disable(1),
				enable(2)
				}
			MAX-ACCESS read-write
			STATUS current
			DESCRIPTION
				"Description."
			DEFVAL { disable }
			::= { hwBleProfileEntry 2 }

		-- 1.3.6.1.4.1.2011.6.139.11.1.73.1.3
		hwWlanBLETxPower OBJECT-TYPE
			SYNTAX Integer32
			UNITS "dbm"
			MAX-ACCESS read-write
			STATUS current
			DESCRIPTION
				"Description."
			DEFVAL { 0 }
			::= { hwBleProfileEntry 3 }

		-- 1.3.6.1.4.1.2011.6.139.11.1.73.1.4
		hwWlanBLEBroadcastingUUID OBJECT-TYPE
			SYNTAX OCTET STRING (SIZE (0..16))
			MAX-ACCESS read-write
			STATUS current
			DESCRIPTION
				"This object indicates the string type value of UUID field in the BLE broadcast frame."
			::= { hwBleProfileEntry 4 }

		-- 1.3.6.1.4.1.2011.6.139.11.1.73.1.5
		hwWlanBLEBroadcastingMajor OBJECT-TYPE
			SYNTAX OCTET STRING (SIZE (0..2))
			MAX-ACCESS read-write
			STATUS current
			DESCRIPTION
				"This object indicates the string type value of Major field in the BLE broadcast frame."
			::= { hwBleProfileEntry 5 }

		-- 1.3.6.1.4.1.2011.6.139.11.1.73.1.6
		hwWlanBLEBroadcastingMinor OBJECT-TYPE
			SYNTAX OCTET STRING (SIZE (0..2))
			MAX-ACCESS read-write
			STATUS current
			DESCRIPTION
				"This object indicates the string type value of Minor field in the BLE broadcast frame."
			::= { hwBleProfileEntry 6 }

		-- 1.3.6.1.4.1.2011.6.139.11.1.73.1.7
		hwWlanBLEBroadcastingReferenceRSSI OBJECT-TYPE
			SYNTAX Integer32 (-97..-50 | 0)
			UNITS "dbm"
			MAX-ACCESS read-write
			STATUS current
			DESCRIPTION
				"Description."
			DEFVAL { -65 }
			::= { hwBleProfileEntry 7 }

		-- 1.3.6.1.4.1.2011.6.139.11.1.73.1.8
		hwWlanBLEBroadcastingInterval OBJECT-TYPE
			SYNTAX Unsigned32 (100..10240)
			UNITS "ms"
			MAX-ACCESS read-write
			STATUS current
			DESCRIPTION
				"Description."
			DEFVAL { 500 }
			::= { hwBleProfileEntry 8 }

		-- 1.3.6.1.4.1.2011.6.139.11.1.73.1.9
		hwWlanBLESnifferEnable OBJECT-TYPE
			SYNTAX INTEGER
				{
				disable(1),
				enable(2)
				}
			MAX-ACCESS read-write
			STATUS current
			DESCRIPTION
				"Description."
			DEFVAL { disable }
			::= { hwBleProfileEntry 9 }

		-- 1.3.6.1.4.1.2011.6.139.11.1.73.1.10
		hwWlanBLEProfileRowStatus OBJECT-TYPE
			SYNTAX RowStatus
			MAX-ACCESS read-write
			STATUS current
			DESCRIPTION
				"This object indicates the row status of this table. createAndGo(4) and destroy(6) are commonly used."
			::= { hwBleProfileEntry 10 }
			
		-- 1.3.6.1.4.1.2011.6.139.11.1.73.1.11
		hwWlanBLEBroadcastingUUIDHex OBJECT-TYPE
			SYNTAX OCTET STRING (SIZE (0..32))
			MAX-ACCESS read-write
			STATUS current
			DESCRIPTION
				"This object indicates the hex type value of UUID field in the BLE broadcast frame."
			::= { hwBleProfileEntry 11 }
		
		-- 1.3.6.1.4.1.2011.6.139.11.1.73.1.12
		hwWlanBLEBroadcastingMajorHex OBJECT-TYPE
			SYNTAX OCTET STRING (SIZE (0..4))
			MAX-ACCESS read-write
			STATUS current
			DESCRIPTION
				"This object indicates the hex type value of Major field in the BLE broadcast frame."
			::= { hwBleProfileEntry 12 }
		
		-- 1.3.6.1.4.1.2011.6.139.11.1.73.1.13
		hwWlanBLEBroadcastingMajorDecimal OBJECT-TYPE
			SYNTAX Integer32 (-1 | 0..65535)
			MAX-ACCESS read-write
			STATUS current
			DESCRIPTION
				"This object indicates the decimal type value of Major field in the BLE broadcast frame. The default value is -1."
			::= { hwBleProfileEntry 13 }
		
		-- 1.3.6.1.4.1.2011.6.139.11.1.73.1.14
		hwWlanBLEBroadcastingMinorHex OBJECT-TYPE
			SYNTAX OCTET STRING (SIZE (0..4))
			MAX-ACCESS read-write
			STATUS current
			DESCRIPTION
				"This object indicates the hex type value of Minor field in the BLE broadcast frame."
			::= { hwBleProfileEntry 14 }
		
		-- 1.3.6.1.4.1.2011.6.139.11.1.73.1.15
		hwWlanBLEBroadcastingMinorDecimal OBJECT-TYPE
			SYNTAX Integer32 (-1 | 0..65535)
			MAX-ACCESS read-write
			STATUS current
			DESCRIPTION
				"This object indicates the decimal type value of Minor field in the BLE broadcast frame. The default value is -1."
			::= { hwBleProfileEntry 15 }
		
		-- 1.3.6.1.4.1.2011.6.139.11.1.73.1.16
		hwWlanBLESnifferMode OBJECT-TYPE
			SYNTAX INTEGER
				{
				disable(1),
				ibeacon(2),
				tag(3),
				transparent(4)
				}
			MAX-ACCESS read-write
			STATUS current
			DESCRIPTION
				"Description."
			::= { hwBleProfileEntry 16 }
		
		-- 1.3.6.1.4.1.2011.6.139.11.1.73.1.17
		hwWlanBLEReportEnable OBJECT-TYPE
			SYNTAX INTEGER
				{
				disable(1),
				enable(2)
				}
			MAX-ACCESS read-write
			STATUS current
			DESCRIPTION
				"Description."
			::= { hwBleProfileEntry 17 }
		
		-- 1.3.6.1.4.1.2011.6.139.11.1.73.1.18
		hwWlanBLEReportMode OBJECT-TYPE
			SYNTAX INTEGER
				{
				periodic(1),
				immediate(2)
				}
			MAX-ACCESS read-write
			STATUS current
			DESCRIPTION
				"Description."
			::= { hwBleProfileEntry 18 }
		
		-- 1.3.6.1.4.1.2011.6.139.11.1.73.1.19
		hwWlanBLEReportInterval OBJECT-TYPE
			SYNTAX Integer32 (1..600)
			MAX-ACCESS read-write
			STATUS current
			DESCRIPTION
				"Description."
			DEFVAL { '10'b }
			::= { hwBleProfileEntry 19 }
		
		-- 1.3.6.1.4.1.2011.6.139.11.1.73.1.20
		hwWlanBLEReportServerIPAddress OBJECT-TYPE
			SYNTAX IpAddress
			MAX-ACCESS read-write
			STATUS current
			DESCRIPTION
				"Description."
			::= { hwBleProfileEntry 20 }
		
		-- 1.3.6.1.4.1.2011.6.139.11.1.73.1.21
		hwWlanBLEReportServerIPv6Address OBJECT-TYPE
			SYNTAX OCTET STRING
			MAX-ACCESS read-write
			STATUS current
			DESCRIPTION
				"Description."
			::= { hwBleProfileEntry 21 }
		
		-- 1.3.6.1.4.1.2011.6.139.11.1.73.1.22
		hwWlanBLEReportServerPort OBJECT-TYPE
			SYNTAX Unsigned32 (0 | 1..65535)
			MAX-ACCESS read-write
			STATUS current
			DESCRIPTION
				"Description."
			::= { hwBleProfileEntry 22 }
		
		-- 1.3.6.1.4.1.2011.6.139.11.1.73.1.23
		hwWlanBLEReportServerViaACEnable OBJECT-TYPE
			SYNTAX INTEGER
				{
				disable(1),
				enable(2)
				}
			MAX-ACCESS read-write
			STATUS current
			DESCRIPTION
				"Description."
			::= { hwBleProfileEntry 23 }
		
		-- 1.3.6.1.4.1.2011.6.139.11.1.73.1.24
		hwWlanBLEReportServerViaACPort OBJECT-TYPE
			SYNTAX Unsigned32 (0 | 5000..65535)
			MAX-ACCESS read-write
			STATUS current
			DESCRIPTION
				"Description."
			::= { hwBleProfileEntry 24 }

                                   -- 1.3.6.1.4.1.2011.6.139.11.1.73.1.25
		hwWlanBLESourceIPAddress OBJECT-TYPE
			SYNTAX IpAddress
			MAX-ACCESS read-write
			STATUS current
			DESCRIPTION
				"This object indicates the source IPv4 address for reporting ble location data. You choose an IPv4 address."
			::= { hwBleProfileEntry 25 }
		
		-- 1.3.6.1.4.1.2011.6.139.11.1.73.1.26
		hwWlanBLESourceIPv6Address OBJECT-TYPE
			SYNTAX OCTET STRING
			MAX-ACCESS read-write
			STATUS current
			DESCRIPTION
				"This object indicates the source IPv6 address for reporting ble location data. You choose an IPv6 address."
			::= { hwBleProfileEntry 26 }
		-- 1.3.6.1.4.1.2011.6.139.11.1.73.1.27
		hwWlanBLEServerAddressDomain OBJECT-TYPE
			SYNTAX OCTET STRING (SIZE (0..255))
			MAX-ACCESS read-write
			STATUS current
			DESCRIPTION
				"This object indicates server's domain name."
			::= { hwBleProfileEntry 27 }
          				
		
		
		-- 1.3.6.1.4.1.2011.6.139.11.1.74
		hwAPGroupCardTable OBJECT-TYPE
			SYNTAX SEQUENCE OF HwAPGroupCardEntry
			MAX-ACCESS not-accessible
			STATUS current
			DESCRIPTION
				"Description."
			::= { hwWlanConfigObjects 74 }

		-- 1.3.6.1.4.1.2011.6.139.11.1.74.1
		hwAPGroupCardEntry OBJECT-TYPE
			SYNTAX HwAPGroupCardEntry
			MAX-ACCESS not-accessible
			STATUS current
			DESCRIPTION
				"Description."
			INDEX { hwAPGrpCardIndex, hwAPGroupName }
			::= { hwAPGroupCardTable 1 }

		
		HwAPGroupCardEntry ::=
			SEQUENCE { 
				hwAPGrpCardIndex
					Unsigned32,
				hwAPGrpCardSerialProfile
					OCTET STRING,
				hwAPGrpCardProfile
					OCTET STRING,
				hwAPGrpCardNetUDPPort
					Unsigned32,
				hwAPGrpIoTRowStatus
					RowStatus,
				hwAPGrpCardNetTCPPort
					Unsigned32,
				hwAPGroupCardWiredPortProfile
					OCTET STRING,
				hwAPGrpCardConnType
					INTEGER,
				hwAPGrpCardNetProtocolType
					INTEGER,
				hwAPGrpCardNetPort
					Unsigned32,
				hwAPGrpCardNetExtPort
					Unsigned32
			 }

		-- 1.3.6.1.4.1.2011.6.139.11.1.74.1.1
		hwAPGrpCardIndex OBJECT-TYPE
			SYNTAX Unsigned32 (0..2)
			MAX-ACCESS not-accessible
			STATUS current
			DESCRIPTION
				"Description."
			::= { hwAPGroupCardEntry 1 }

		-- 1.3.6.1.4.1.2011.6.139.11.1.74.1.2
		hwAPGrpCardSerialProfile OBJECT-TYPE
			SYNTAX OCTET STRING (SIZE (1..35))
			MAX-ACCESS read-write
			STATUS current
			DESCRIPTION
				"Description."
			::= { hwAPGroupCardEntry 2 }

		-- 1.3.6.1.4.1.2011.6.139.11.1.74.1.3
		hwAPGrpCardProfile OBJECT-TYPE
			SYNTAX OCTET STRING (SIZE (0..35))
			MAX-ACCESS read-write
			STATUS current
			DESCRIPTION
				"Description."
			::= { hwAPGroupCardEntry 3 }

		-- 1.3.6.1.4.1.2011.6.139.11.1.74.1.4
		hwAPGrpCardNetUDPPort OBJECT-TYPE
			SYNTAX Unsigned32 (1025..55535 | 4294967295)
			MAX-ACCESS read-write
			STATUS current
			DESCRIPTION
				"Description."
			::= { hwAPGroupCardEntry 4 }

		-- 1.3.6.1.4.1.2011.6.139.11.1.74.1.5
		hwAPGrpIoTRowStatus OBJECT-TYPE
			SYNTAX RowStatus
			MAX-ACCESS read-write
			STATUS current
			DESCRIPTION
				"Description."
			::= { hwAPGroupCardEntry 5 }
		
		-- 1.3.6.1.4.1.2011.6.139.11.1.74.1.6
		hwAPGrpCardNetTCPPort OBJECT-TYPE
			SYNTAX Unsigned32 (1025..55535 | 4294967295)
			MAX-ACCESS read-write
			STATUS current
			DESCRIPTION
				"Description."
			::= { hwAPGroupCardEntry 6 }
		
		-- 1.3.6.1.4.1.2011.6.139.11.1.74.1.7
		hwAPGroupCardWiredPortProfile OBJECT-TYPE
			SYNTAX OCTET STRING (SIZE (0..35))
			MAX-ACCESS read-write
			STATUS current
			DESCRIPTION
				"Description."
			::= { hwAPGroupCardEntry 7 }
		-- 1.3.6.1.4.1.2011.6.139.11.1.74.1.8
		hwAPGrpCardConnType OBJECT-TYPE
			SYNTAX INTEGER
				{
				serial(1) ,
				ethernet(2),
				unknown(3)
				}
			MAX-ACCESS read-write
			STATUS current
			DESCRIPTION
				"Description."
			::= { hwAPGroupCardEntry 8 }
		
		-- 1.3.6.1.4.1.2011.6.139.11.1.74.1.9
		hwAPGrpCardNetProtocolType OBJECT-TYPE
			SYNTAX INTEGER
				{
				udp(1),
				tcp(2),
				invalid(3)
				}
			MAX-ACCESS read-write
			STATUS current
			DESCRIPTION
				"Description."
			::= { hwAPGroupCardEntry 9 }
		
		-- 1.3.6.1.4.1.2011.6.139.11.1.74.1.10
		hwAPGrpCardNetPort OBJECT-TYPE
			SYNTAX Unsigned32 (4294967295 | 1025..55535)
			MAX-ACCESS read-write
			STATUS current
			DESCRIPTION
				"Description."
			::= { hwAPGroupCardEntry 10 }
		
		-- 1.3.6.1.4.1.2011.6.139.11.1.74.1.11
		hwAPGrpCardNetExtPort OBJECT-TYPE
			SYNTAX Unsigned32 (4294967295 | 1025..55535)
			MAX-ACCESS read-write
			STATUS current
			DESCRIPTION
				"Description."
			::= { hwAPGroupCardEntry 11 }
		
        --  1.3.6.1.4.1.2011.6.139.11.1.75
		hwAPSpecificCardTable OBJECT-TYPE
			SYNTAX SEQUENCE OF HwAPSpecificCardEntry
			MAX-ACCESS not-accessible
			STATUS current
			DESCRIPTION
				"Description."
			::= { hwWlanConfigObjects 75 }

		-- 1.3.6.1.4.1.2011.6.139.11.1.75.1
		hwAPSpecificCardEntry OBJECT-TYPE
			SYNTAX HwAPSpecificCardEntry
			MAX-ACCESS not-accessible
			STATUS current
			DESCRIPTION
				"Description."
			INDEX { hwAPSpIoTIndex, IMPLIED hwWlanIDIndexedAPSpApId }
			::= { hwAPSpecificCardTable 1 }

		
		HwAPSpecificCardEntry ::=
			SEQUENCE { 
				hwAPSpIoTIndex
					Unsigned32,
				hwAPSpIoTSerialProfile
					OCTET STRING,
				hwAPSpIoTProfile
					OCTET STRING,
				hwAPSpIoTNetUDPPort
					Unsigned32,
				hwAPSpIoTRowStatus
					RowStatus,
				hwAPSpIoTNetTCPPort
					Unsigned32,
				hwAPSpIoTWiredPortProfile
					OCTET STRING,
				hwAPSpCardConnType
					INTEGER,
				hwAPSpIoTNetProtocolType
					INTEGER,
				hwAPSpIoTNetPort
					Unsigned32,
				hwAPSpIoTNetExtPort
					Unsigned32
			 }

		-- 1.3.6.1.4.1.2011.6.139.11.1.75.1.1
		hwAPSpIoTIndex OBJECT-TYPE
			SYNTAX Unsigned32 (0..2)
			MAX-ACCESS not-accessible
			STATUS current
			DESCRIPTION
				"Description."
			::= { hwAPSpecificCardEntry 1 }

		-- 1.3.6.1.4.1.2011.6.139.11.1.75.1.2
		hwAPSpIoTSerialProfile OBJECT-TYPE
			SYNTAX OCTET STRING (SIZE (1..35))
			MAX-ACCESS read-write
			STATUS current
			DESCRIPTION
				"Description."
			::= { hwAPSpecificCardEntry 2 }

		-- 1.3.6.1.4.1.2011.6.139.11.1.75.1.3
		hwAPSpIoTProfile OBJECT-TYPE
			SYNTAX OCTET STRING (SIZE (0..35))
			MAX-ACCESS read-write
			STATUS current
			DESCRIPTION
				"Description."
			::= { hwAPSpecificCardEntry 3 }

		-- 1.3.6.1.4.1.2011.6.139.11.1.75.1.4
		hwAPSpIoTNetUDPPort OBJECT-TYPE
			SYNTAX Unsigned32 (1025..55535 | 4294967295)
			MAX-ACCESS read-write
			STATUS current
			DESCRIPTION
				"Description."
			::= { hwAPSpecificCardEntry 4 }

		-- 1.3.6.1.4.1.2011.6.139.11.1.75.1.5
		hwAPSpIoTRowStatus OBJECT-TYPE
			SYNTAX RowStatus
			MAX-ACCESS read-write
			STATUS current
			DESCRIPTION
				"Description."
			::= { hwAPSpecificCardEntry 5 }
		
		-- 1.3.6.1.4.1.2011.6.139.11.1.75.1.6
		hwAPSpIoTNetTCPPort OBJECT-TYPE
			SYNTAX Unsigned32 (1025..55535 | 4294967295)
			MAX-ACCESS read-write
			STATUS current
			DESCRIPTION
				"Description."
			::= { hwAPSpecificCardEntry 6 }
		
		-- 1.3.6.1.4.1.2011.6.139.11.1.75.1.7
		hwAPSpIoTWiredPortProfile OBJECT-TYPE
			SYNTAX OCTET STRING (SIZE (0..35))
			MAX-ACCESS read-write
			STATUS current
			DESCRIPTION
				"Description."
			::= { hwAPSpecificCardEntry 7 }
		-- 1.3.6.1.4.1.2011.6.139.11.1.74.1.8
		hwAPSpCardConnType OBJECT-TYPE
			SYNTAX INTEGER
				{
				serial(1) ,
				ethernet(2),
				unknown(3)
				}
			MAX-ACCESS read-write
			STATUS current
			DESCRIPTION
				"Description."
			::= { hwAPSpecificCardEntry 8 }
		
		-- 1.3.6.1.4.1.2011.6.139.11.1.75.1.9
		hwAPSpIoTNetProtocolType OBJECT-TYPE
			SYNTAX INTEGER
				{
				udp(1),
				tcp(2),
				invalid(3)
				}
			MAX-ACCESS read-write
			STATUS current
			DESCRIPTION
				"Description."
			::= { hwAPSpecificCardEntry 9 }
		
		-- 1.3.6.1.4.1.2011.6.139.11.1.75.1.10
		hwAPSpIoTNetPort OBJECT-TYPE
			SYNTAX Unsigned32 (4294967295 | 1025..55535)
			MAX-ACCESS read-write
			STATUS current
			DESCRIPTION
				"Description."
			::= { hwAPSpecificCardEntry 10 }
		
		-- 1.3.6.1.4.1.2011.6.139.11.1.75.1.11
		hwAPSpIoTNetExtPort OBJECT-TYPE
			SYNTAX Unsigned32 (4294967295 | 1025..55535)
			MAX-ACCESS read-write
			STATUS current
			DESCRIPTION
				"Description."
			::= { hwAPSpecificCardEntry 11 }
		
        --  1.3.6.1.4.1.2011.6.139.11.1.76
		hwIoTSerialProfileTable OBJECT-TYPE
			SYNTAX SEQUENCE OF HwIoTSerialProfileEntry
			MAX-ACCESS not-accessible
			STATUS current
			DESCRIPTION
				"Description."
			::= { hwWlanConfigObjects 76 }

		-- 1.3.6.1.4.1.2011.6.139.11.1.76.1
		hwIoTSerialProfileEntry OBJECT-TYPE
			SYNTAX HwIoTSerialProfileEntry
			MAX-ACCESS not-accessible
			STATUS current
			DESCRIPTION
				"Description."
			INDEX { hwIoTSerialProfileName }
			::= { hwIoTSerialProfileTable 1 }

		
		HwIoTSerialProfileEntry ::=
			SEQUENCE { 
				hwIoTSerialProfileName
					OCTET STRING,
				hwIoTSerialSpeed
					Unsigned32,
				hwIoTSerialParity
					INTEGER,
				hwIoTSerialStopbits
					INTEGER,
				hwIoTSerialFrameFormat
					INTEGER,
				hwIoTSerialFrameLength
					Unsigned32,
				hwIoTSerialFrameStart
					Unsigned32,
				hwIoTSerialFrameStop
					Unsigned32,
				hwIoTSerialProfileRowStatus
					RowStatus
			 }

		-- 1.3.6.1.4.1.2011.6.139.11.1.76.1.1
		hwIoTSerialProfileName OBJECT-TYPE
			SYNTAX OCTET STRING (SIZE (1..35))
			MAX-ACCESS not-accessible
			STATUS current
			DESCRIPTION
				"Description."
			::= { hwIoTSerialProfileEntry 1 }

		-- 1.3.6.1.4.1.2011.6.139.11.1.76.1.2
		hwIoTSerialSpeed OBJECT-TYPE
			SYNTAX Unsigned32 (9600..115200)
			MAX-ACCESS read-write
			STATUS current
			DESCRIPTION
				"Description."
			::= { hwIoTSerialProfileEntry 2 }

		-- 1.3.6.1.4.1.2011.6.139.11.1.76.1.3
		hwIoTSerialParity OBJECT-TYPE
			SYNTAX INTEGER
				{
				none(1),
				odd(2),
				even(3),
				space(4),
				mark(5)
				}
			MAX-ACCESS read-write
			STATUS current
			DESCRIPTION
				"Description."
			DEFVAL { none }
			::= { hwIoTSerialProfileEntry 3 }

		-- 1.3.6.1.4.1.2011.6.139.11.1.76.1.4
		hwIoTSerialStopbits OBJECT-TYPE
			SYNTAX INTEGER
				{
				one(1),
				two(2)
				}
			MAX-ACCESS read-write
			STATUS current
			DESCRIPTION
				"Description."
			DEFVAL { one }
			::= { hwIoTSerialProfileEntry 4 }

		-- 1.3.6.1.4.1.2011.6.139.11.1.76.1.5
		hwIoTSerialFrameFormat OBJECT-TYPE
			SYNTAX INTEGER
				{
				fixedLength(1),
				frameBeginEnd(2)
				}
			MAX-ACCESS read-write
			STATUS current
			DESCRIPTION
				"Description."
			DEFVAL { frameBeginEnd }
			::= { hwIoTSerialProfileEntry 5 }

		-- 1.3.6.1.4.1.2011.6.139.11.1.76.1.6
		hwIoTSerialFrameLength OBJECT-TYPE
			SYNTAX Unsigned32 (1..1400)
			MAX-ACCESS read-write
			STATUS current
			DESCRIPTION
				"Description."
			DEFVAL { 512 }
			::= { hwIoTSerialProfileEntry 6 }

		-- 1.3.6.1.4.1.2011.6.139.11.1.76.1.7
		hwIoTSerialFrameStart OBJECT-TYPE
			SYNTAX Unsigned32 (0..255)
			MAX-ACCESS read-write
			STATUS current
			DESCRIPTION
				"Description."
			DEFVAL { 'aa'h }
			::= { hwIoTSerialProfileEntry 7 }

		-- 1.3.6.1.4.1.2011.6.139.11.1.76.1.8
		hwIoTSerialFrameStop OBJECT-TYPE
			SYNTAX Unsigned32 (0..255)
			MAX-ACCESS read-write
			STATUS current
			DESCRIPTION
				"Description."
			DEFVAL { '7e'h }
			::= { hwIoTSerialProfileEntry 8 }

		-- 1.3.6.1.4.1.2011.6.139.11.1.76.1.9
		hwIoTSerialProfileRowStatus OBJECT-TYPE
			SYNTAX RowStatus
			MAX-ACCESS read-write
			STATUS current
			DESCRIPTION
				"Description."
			::= { hwIoTSerialProfileEntry 9 }

		-- 1.3.6.1.4.1.2011.6.139.11.1.77
		hwIoTProfileTable OBJECT-TYPE
			SYNTAX SEQUENCE OF HwIoTProfileEntry
			MAX-ACCESS not-accessible
			STATUS current
			DESCRIPTION
				"Description."
			::= { hwWlanConfigObjects 77 }

		-- 1.3.6.1.4.1.2011.6.139.11.1.77.1
		hwIoTProfileEntry OBJECT-TYPE
			SYNTAX HwIoTProfileEntry
			MAX-ACCESS not-accessible
			STATUS current
			DESCRIPTION
				"Description."
			INDEX { hwIoTProfileName }
			::= { hwIoTProfileTable 1 }

		
		HwIoTProfileEntry ::=
			SEQUENCE { 
				hwIoTProfileName
					OCTET STRING,
				hwIoTProfileConfigAgentPermitIp
					IpAddress,
				hwIoTProfileConfigAgentPermitMaskLen
					Unsigned32,
				hwIoTProfileShareKey
					OCTET STRING,
				hwIoTProfileRowStatus
					RowStatus,
				hwIoTProfileType
					INTEGER,
				hwIoTProfileAntennaStatus
					INTEGER
			 }

		-- 1.3.6.1.4.1.2011.6.139.11.1.77.1.1
		hwIoTProfileName OBJECT-TYPE
			SYNTAX OCTET STRING (SIZE (1..35))
			MAX-ACCESS not-accessible
			STATUS current
			DESCRIPTION
				"Description."
			::= { hwIoTProfileEntry 1 }

		-- 1.3.6.1.4.1.2011.6.139.11.1.77.1.2
		hwIoTProfileConfigAgentPermitIp OBJECT-TYPE
			SYNTAX IpAddress
			MAX-ACCESS read-write
			STATUS current
			DESCRIPTION
				"Description."
			::= { hwIoTProfileEntry 2 }

		-- 1.3.6.1.4.1.2011.6.139.11.1.77.1.3
		hwIoTProfileConfigAgentPermitMaskLen OBJECT-TYPE
			SYNTAX Unsigned32 (0..32)
			MAX-ACCESS read-write
			STATUS current
			DESCRIPTION
				"Description."
			::= { hwIoTProfileEntry 3 }

		-- 1.3.6.1.4.1.2011.6.139.11.1.77.1.4
		hwIoTProfileShareKey OBJECT-TYPE
			SYNTAX OCTET STRING (SIZE (0..68))
			MAX-ACCESS read-write
			STATUS current
			DESCRIPTION
				"Description."
			::= { hwIoTProfileEntry 4 }

		-- 1.3.6.1.4.1.2011.6.139.11.1.77.1.5
		hwIoTProfileRowStatus OBJECT-TYPE
			SYNTAX RowStatus
			MAX-ACCESS read-write
			STATUS current
			DESCRIPTION
				"Description."
			::= { hwIoTProfileEntry 5 }
		
               -- 1.3.6.1.4.1.2011.6.139.11.1.77.1.6
      	       hwIoTProfileType OBJECT-TYPE
			SYNTAX INTEGER
				{
				common(0),
				casEdu(1)
				}
			MAX-ACCESS read-write
			STATUS current
			DESCRIPTION
				"This object indicates the profile type. The default value is 0."
			::= { hwIoTProfileEntry 6 }

		-- 1.3.6.1.4.1.2011.6.139.11.1.77.1.7
		hwIoTProfileAntennaStatus OBJECT-TYPE
			SYNTAX INTEGER
				{
				external(1),
				internal(2),
				invalid(3)
				}
			MAX-ACCESS read-write
			STATUS current
			DESCRIPTION
				"This object indicates the antenna status of card."
			::= { hwIoTProfileEntry 7 }
			
--     1.3.6.1.4.1.2011.6.139.11.1.78
-- 1.3.6.1.4.1.2011.6.139.11.1.78
-- 1.3.6.1.4.1.2011.6.139.11.1.78
-- 1.3.6.1.4.1.2011.6.139.11.1.78
		-- 1.3.6.1.4.1.2011.6.139.11.1.78
		hwIoTProfileManagementServerTable OBJECT-TYPE
			SYNTAX SEQUENCE OF HwIoTProfileManagementServerEntry
			MAX-ACCESS not-accessible
			STATUS current
			DESCRIPTION
				"Description."
			::= { hwWlanConfigObjects 78 }


		-- 1.3.6.1.4.1.2011.6.139.11.1.78.1
		hwIoTProfileManagementServerEntry OBJECT-TYPE
			SYNTAX HwIoTProfileManagementServerEntry
			MAX-ACCESS not-accessible
			STATUS current
			DESCRIPTION
				"Description."
			INDEX { hwIoTProfileName, hwIoTProfileManagementServerIndex }
			::= { hwIoTProfileManagementServerTable 1 }

		
		HwIoTProfileManagementServerEntry ::=
			SEQUENCE { 
				hwIoTProfileManagementServerIndex
					Unsigned32,
				hwIoTProfileManagementServerIp
					IpAddress,
				hwIoTProfileManagementServerPort
					Unsigned32,
				hwIoTProfileManagementServerRowStatus
					RowStatus,
				hwIoTProfileManagementServerDomain
					OCTET STRING
			 }

		-- 1.3.6.1.4.1.2011.6.139.11.1.78.1.1
		hwIoTProfileManagementServerIndex OBJECT-TYPE
			SYNTAX Unsigned32 (0..4)
			MAX-ACCESS not-accessible
			STATUS current
			DESCRIPTION
				"Description."
			::= { hwIoTProfileManagementServerEntry 1 }

		-- 1.3.6.1.4.1.2011.6.139.11.1.78.1.2
		hwIoTProfileManagementServerIp OBJECT-TYPE
			SYNTAX IpAddress
			MAX-ACCESS read-write
			STATUS current
			DESCRIPTION
				"Description."
			::= { hwIoTProfileManagementServerEntry 2 }

		-- 1.3.6.1.4.1.2011.6.139.11.1.78.1.3
		hwIoTProfileManagementServerPort OBJECT-TYPE
			SYNTAX Unsigned32 (1..65535 | 4294967295)
			MAX-ACCESS read-write
			STATUS current
			DESCRIPTION
				"Description."
			::= { hwIoTProfileManagementServerEntry 3 }

		-- 1.3.6.1.4.1.2011.6.139.11.1.78.1.4
		hwIoTProfileManagementServerRowStatus OBJECT-TYPE
			SYNTAX RowStatus
			MAX-ACCESS read-write
			STATUS current
			DESCRIPTION
				"Description."
			::= { hwIoTProfileManagementServerEntry 4 }
	
		-- 1.3.6.1.4.1.2011.6.139.11.1.78.1.5
		hwIoTProfileManagementServerDomain OBJECT-TYPE
			SYNTAX OCTET STRING (SIZE (1..63))
			MAX-ACCESS read-write
			STATUS current
			DESCRIPTION
				"Description."
			::= { hwIoTProfileManagementServerEntry 5 }		

		
		-- 1.3.6.1.4.1.2011.6.139.11.1.79
		hwVapAntiAttackUserDefFloodTable OBJECT-TYPE
			SYNTAX SEQUENCE OF HwVapAntiAttackUserDefFloodEntry
			MAX-ACCESS not-accessible
			STATUS current
			DESCRIPTION
				"This table describes SAC profile action configurations.This table is used to configure actions in an SAC profile."
			::= { hwWlanConfigObjects 79 }

		-- 1.3.6.1.4.1.2011.6.139.11.1.79.1
		hwVapAntiAttackUserDefFloodEntry OBJECT-TYPE
			SYNTAX HwVapAntiAttackUserDefFloodEntry
			MAX-ACCESS not-accessible
			STATUS current
			DESCRIPTION
				"Indexes of this table are hwVapAntiAttackDefFloodIndex and hwVapProfileName."
			INDEX { hwVapAntiAttackDefFloodIndex, hwVapProfileName }
			::= { hwVapAntiAttackUserDefFloodTable 1 }

		
		HwVapAntiAttackUserDefFloodEntry ::=
			SEQUENCE { 
				hwVapAntiAttackDefFloodIndex
					Unsigned32,
				hwVapAntiAttackDefFloodProtocolType
					INTEGER,
				hwVapAntiAttackDefFloodProtocolValue
					Unsigned32,
				hwVapAntiAttackDefFloodStaRateThreshold
					Unsigned32,
				hwVapAntiAttackDefFloodBlacklistSwitch
					INTEGER,
				hwVapAntiAttackDefFloodRowStatus
					RowStatus
			 }

		-- 1.3.6.1.4.1.2011.6.139.11.1.79.1.1
		hwVapAntiAttackDefFloodIndex OBJECT-TYPE
			SYNTAX Unsigned32 (0..7)
			MAX-ACCESS not-accessible
			STATUS current
			DESCRIPTION
				"This object indicates the internal index of the action. It is the index of the table."
			::= { hwVapAntiAttackUserDefFloodEntry 1 }

		-- 1.3.6.1.4.1.2011.6.139.11.1.79.1.2
		hwVapAntiAttackDefFloodProtocolType OBJECT-TYPE
			SYNTAX INTEGER
				{
				unknown(0),
				l2(1),
				ipv4(2),
				ipv6(3),
				tcp(4),
				udp(5)
				}
			MAX-ACCESS read-write
			STATUS current
			DESCRIPTION
				"This object indicates the protocol type."
			::= { hwVapAntiAttackUserDefFloodEntry 2 }

		-- 1.3.6.1.4.1.2011.6.139.11.1.79.1.3
		hwVapAntiAttackDefFloodProtocolValue OBJECT-TYPE
			SYNTAX Unsigned32 (0..65535)
			MAX-ACCESS read-write
			STATUS current
			DESCRIPTION
				"This object indicates the protocol value."
			::= { hwVapAntiAttackUserDefFloodEntry 3 }

		-- 1.3.6.1.4.1.2011.6.139.11.1.79.1.4
		hwVapAntiAttackDefFloodStaRateThreshold OBJECT-TYPE
			SYNTAX Unsigned32 (1..500 | 4294967295)
			MAX-ACCESS read-write
			STATUS current
			DESCRIPTION
				"This object indicates the anti-attack user-defined flood sta-rate-threshold for the VAP."
			::= { hwVapAntiAttackUserDefFloodEntry 4 }

		-- 1.3.6.1.4.1.2011.6.139.11.1.79.1.5
		hwVapAntiAttackDefFloodBlacklistSwitch OBJECT-TYPE
			SYNTAX INTEGER
				{
				disable(1),
				enable(2)
				}
			MAX-ACCESS read-write
			STATUS current
			DESCRIPTION
				"This object indicates the status of the VAP anti-attack user-defined flood blacklist function."
			::= { hwVapAntiAttackUserDefFloodEntry 5 }

		-- 1.3.6.1.4.1.2011.6.139.11.1.79.1.6
		hwVapAntiAttackDefFloodRowStatus OBJECT-TYPE
			SYNTAX RowStatus
			MAX-ACCESS read-write
			STATUS current
			DESCRIPTION
				"This object indicates the row status."
			::= { hwVapAntiAttackUserDefFloodEntry 6 }
			
--  1.3.6.1.4.1.2011.6.139.11.1.80
		-- 1.3.6.1.4.1.2011.6.139.11.1.80
		hwApProfIGMPSnoopingGroupTable OBJECT-TYPE
			SYNTAX SEQUENCE OF HwApProfIGMPSnoopingGroupEntry
			MAX-ACCESS not-accessible
			STATUS current
			DESCRIPTION
				"Description."
			::= { hwWlanConfigObjects 80 }
		
--  1.3.6.1.4.1.2011.6.139.11.1.80.1
		-- 1.3.6.1.4.1.2011.6.139.11.1.80.1
		hwApProfIGMPSnoopingGroupEntry OBJECT-TYPE
			SYNTAX HwApProfIGMPSnoopingGroupEntry
			MAX-ACCESS not-accessible
			STATUS current
			DESCRIPTION
				"Description."
			INDEX { hwApSystemProfName, hwAPProfIGMPSnoopingGroupIndex }
			::= { hwApProfIGMPSnoopingGroupTable 1 }
		
		HwApProfIGMPSnoopingGroupEntry ::=
			SEQUENCE { 
				hwAPProfIGMPSnoopingGroupIndex
					Unsigned32,
				hwAPProfIGMPSnoopingGroupStartGroupAddr
					IpAddress,
				hwAPProfIGMPSnoopingGroupEndGroupAddr
					IpAddress,
				hwAPProfIGMPSnoopingGroupBandwidth
					Unsigned32,
				hwAPProfIGMPSnoopingGroupRowStatus
					RowStatus
			 }

--  1.3.6.1.4.1.2011.6.139.11.1.80.1.1
		-- 1.3.6.1.4.1.2011.6.139.11.1.80.1.1
		hwAPProfIGMPSnoopingGroupIndex OBJECT-TYPE
			SYNTAX Unsigned32 (0..31)
			MAX-ACCESS not-accessible
			STATUS current
			DESCRIPTION
				"Description."
			::= { hwApProfIGMPSnoopingGroupEntry 1 }
		
--  1.3.6.1.4.1.2011.6.139.11.1.80.1.2
		-- 1.3.6.1.4.1.2011.6.139.11.1.80.1.2
		hwAPProfIGMPSnoopingGroupStartGroupAddr OBJECT-TYPE
			SYNTAX IpAddress
			MAX-ACCESS read-write
			STATUS current
			DESCRIPTION
				"Description."
			::= { hwApProfIGMPSnoopingGroupEntry 2 }
		
--  1.3.6.1.4.1.2011.6.139.11.1.80.1.3
		-- 1.3.6.1.4.1.2011.6.139.11.1.80.1.3
		hwAPProfIGMPSnoopingGroupEndGroupAddr OBJECT-TYPE
			SYNTAX IpAddress
			MAX-ACCESS read-write
			STATUS current
			DESCRIPTION
				"Description."
			::= { hwApProfIGMPSnoopingGroupEntry 3 }
		
--  1.3.6.1.4.1.2011.6.139.11.1.80.1.4
		-- 1.3.6.1.4.1.2011.6.139.11.1.80.1.4
		hwAPProfIGMPSnoopingGroupBandwidth OBJECT-TYPE
			SYNTAX Unsigned32 (4294967295 | 1..100000)
			MAX-ACCESS read-write
			STATUS current
			DESCRIPTION
				"Description."
			::= { hwApProfIGMPSnoopingGroupEntry 4 }
		
--  1.3.6.1.4.1.2011.6.139.11.1.80.1.5
		-- 1.3.6.1.4.1.2011.6.139.11.1.80.1.5
		hwAPProfIGMPSnoopingGroupRowStatus OBJECT-TYPE
			SYNTAX RowStatus
			MAX-ACCESS read-write
			STATUS current
			DESCRIPTION
				"Description."
			::= { hwApProfIGMPSnoopingGroupEntry 5 }
		
		-- 1.3.6.1.4.1.2011.6.139.11.1.81
		hwAPWiredPortProfileTrafficRemarkTable OBJECT-TYPE
			SYNTAX SEQUENCE OF HwAPWiredPortProfileTrafficRemarkEntry
			MAX-ACCESS not-accessible
			STATUS current
			DESCRIPTION
				"Description."
			::= { hwWlanConfigObjects 81 }
		
		-- 1.3.6.1.4.1.2011.6.139.11.1.81.1
		hwAPWiredPortProfileTrafficRemarkEntry OBJECT-TYPE
			SYNTAX HwAPWiredPortProfileTrafficRemarkEntry
			MAX-ACCESS not-accessible
			STATUS current
			DESCRIPTION
				"Description."
			INDEX { hwAPWiredPortProfileName, hwAPWiredPortProfileTrafficRemarkIPType, hwAPWiredPortProfileTrafficRemarkDirection }
			::= { hwAPWiredPortProfileTrafficRemarkTable 1 }
		
		HwAPWiredPortProfileTrafficRemarkEntry ::=
			SEQUENCE { 
				hwAPWiredPortProfileTrafficRemarkDirection
					INTEGER,
				hwAPWiredPortProfileTrafficRemarkIPType
					INTEGER,
				hwAPWiredPortProfileTrafficRemarkACLID
					Unsigned32,
				hwAPWiredPortProfileTrafficRemarkType
					INTEGER,
				hwAPWiredPortProfileTrafficRemarkValue
					Unsigned32,
				hwAPWiredPortProfileTrafficRemarkRowStatus
					RowStatus
			 }

		-- 1.3.6.1.4.1.2011.6.139.11.1.81.1.1
		hwAPWiredPortProfileTrafficRemarkDirection OBJECT-TYPE
			SYNTAX INTEGER
				{
				inbond(1),
				outbond(2)
				}
			MAX-ACCESS not-accessible
			STATUS current
			DESCRIPTION
				"Description."
			::= { hwAPWiredPortProfileTrafficRemarkEntry 1 }
		
		-- 1.3.6.1.4.1.2011.6.139.11.1.81.1.2
		hwAPWiredPortProfileTrafficRemarkIPType OBJECT-TYPE
			SYNTAX INTEGER
				{
				ipv4(1),
				ipv6(2),
				l2(3)
				}
			MAX-ACCESS not-accessible
			STATUS current
			DESCRIPTION
				"Description."
			::= { hwAPWiredPortProfileTrafficRemarkEntry 2 }
		
		-- 1.3.6.1.4.1.2011.6.139.11.1.81.1.3
		hwAPWiredPortProfileTrafficRemarkACLID OBJECT-TYPE
			SYNTAX Unsigned32 (3000..3031 | 4000..4031)
			MAX-ACCESS read-write
			STATUS current
			DESCRIPTION
				"Description."
			::= { hwAPWiredPortProfileTrafficRemarkEntry 3 }
		
		-- 1.3.6.1.4.1.2011.6.139.11.1.81.1.4
		hwAPWiredPortProfileTrafficRemarkType OBJECT-TYPE
			SYNTAX INTEGER
				{
				dscp(1),
				dot1p(2)
				}
			MAX-ACCESS read-write
			STATUS current
			DESCRIPTION
				"Description."
			::= { hwAPWiredPortProfileTrafficRemarkEntry 4 }
		
		-- 1.3.6.1.4.1.2011.6.139.11.1.81.1.5
		hwAPWiredPortProfileTrafficRemarkValue OBJECT-TYPE
			SYNTAX Unsigned32 (0..63)
			MAX-ACCESS read-write
			STATUS current
			DESCRIPTION
				"Description."
			::= { hwAPWiredPortProfileTrafficRemarkEntry 5 }
		
		-- 1.3.6.1.4.1.2011.6.139.11.1.81.1.6
		hwAPWiredPortProfileTrafficRemarkRowStatus OBJECT-TYPE
			SYNTAX RowStatus
			MAX-ACCESS read-write
			STATUS current
			DESCRIPTION
				"Description."
			::= { hwAPWiredPortProfileTrafficRemarkEntry 6 }

		-- 1.3.6.1.4.1.2011.6.139.11.1.82
		hwAPTrafficProfileRemarkTable OBJECT-TYPE
			SYNTAX SEQUENCE OF HwAPTrafficProfileRemarkEntry
			MAX-ACCESS not-accessible
			STATUS current
			DESCRIPTION
				"Description."
			::= { hwWlanConfigObjects 82 }	
			
		-- 1.3.6.1.4.1.2011.6.139.11.1.82.1
		hwAPTrafficProfileRemarkEntry OBJECT-TYPE
			SYNTAX HwAPTrafficProfileRemarkEntry
			MAX-ACCESS not-accessible
			STATUS current
			DESCRIPTION
				"Description."
			INDEX { hwAPTrafficProfileName, hwAPTrafficProfileRemarkDirection, hwAPTrafficProfileRemarkIPType }
			::= { hwAPTrafficProfileRemarkTable 1 }		
		
		
		HwAPTrafficProfileRemarkEntry ::=
		SEQUENCE { 
			hwAPTrafficProfileRemarkDirection
				INTEGER,
			hwAPTrafficProfileRemarkIPType
				INTEGER,
			hwAPTrafficProfileRemarkACLID
				Integer32,
			hwAPTrafficProfileRemarkType
				INTEGER,
			hwAPTrafficProfileRemarkValue
				Integer32,
			hwAPTrafficProfileRemarkRowStatus
				RowStatus
		 }
	
		-- 1.3.6.1.4.1.2011.6.139.11.1.82.1.1
		hwAPTrafficProfileRemarkDirection OBJECT-TYPE
			SYNTAX INTEGER
				{
				inbound(1),
				outbound(2)
				}
			MAX-ACCESS not-accessible
			STATUS current
			DESCRIPTION
				"This object indicates the ACL rule direction for packet remarking in a traffic profile. This parameter has no default value."
			::= { hwAPTrafficProfileRemarkEntry 1 }

		-- 1.3.6.1.4.1.2011.6.139.11.1.82.1.2
		hwAPTrafficProfileRemarkIPType OBJECT-TYPE
			SYNTAX INTEGER
				{
				ipv4(1),
				ipv6(2),
				l2(3)
				}
			MAX-ACCESS not-accessible
			STATUS current
			DESCRIPTION
				"This object indicates the ACL rule type for packet remarking in a traffic profile. This parameter has no default value."
			::= { hwAPTrafficProfileRemarkEntry 2 }
		

		-- 1.3.6.1.4.1.2011.6.139.11.1.82.1.3
		hwAPTrafficProfileRemarkACLID OBJECT-TYPE
			SYNTAX Integer32 (3000..3031 | 4000..4031 | 6000..6031)
			MAX-ACCESS read-write
			STATUS current
			DESCRIPTION
				"This object indicates the ACL rule for packet remarking in a traffic profile."
			::= { hwAPTrafficProfileRemarkEntry 3 }
		

		-- 1.3.6.1.4.1.2011.6.139.11.1.82.1.4
		hwAPTrafficProfileRemarkType OBJECT-TYPE
			SYNTAX INTEGER
				{
				dscp(1),
				dot11e(3)
				}
			MAX-ACCESS read-write
			STATUS current
			DESCRIPTION
				"This object indicates the ACL rule type for packet remarking in a traffic profile. This parameter has no default value."
			::= { hwAPTrafficProfileRemarkEntry 4 }
		

		-- 1.3.6.1.4.1.2011.6.139.11.1.80.1.5
		hwAPTrafficProfileRemarkValue OBJECT-TYPE
			SYNTAX Integer32 (0..63)
			MAX-ACCESS read-write
			STATUS current
			DESCRIPTION
				"This object indicates the ACL rule value for packet remarking in a traffic profile. This parameter has no default value."
			::= { hwAPTrafficProfileRemarkEntry 5 }
		

		-- 1.3.6.1.4.1.2011.6.139.11.1.82.1.6
		hwAPTrafficProfileRemarkRowStatus OBJECT-TYPE
			SYNTAX RowStatus
			MAX-ACCESS read-write
			STATUS current
			DESCRIPTION
				"This object indicates the row status of this table. ROWSTATUS_CREATEANDFLOW and ROWSTATUS_DESTROY are commonly used."
			::= { hwAPTrafficProfileRemarkEntry 6 }
			
		-- 1.3.6.1.4.1.2011.6.139.11.1.83
		hwWlanClusterConfig OBJECT IDENTIFIER ::= { hwWlanConfigObjects 83 }
		
		-- 1.3.6.1.4.1.2011.6.139.11.1.83.1
		hwWlanClusterMasterConfig OBJECT IDENTIFIER ::= { hwWlanClusterConfig 1 }
		
		-- 1.3.6.1.4.1.2011.6.139.11.1.83.1.1
		hwWlanClusterMasterIPv4Address OBJECT-TYPE
			SYNTAX IpAddress
			MAX-ACCESS read-write
			STATUS current
			DESCRIPTION
				"This object indicates the IPv4 address of the master controller."
			::= { hwWlanClusterMasterConfig 1 }
			
		-- 1.3.6.1.4.1.2011.6.139.11.1.83.1.2
		hwWlanClusterMasterIPv6Address OBJECT-TYPE
			SYNTAX OCTET STRING
			MAX-ACCESS read-write
			STATUS current
			DESCRIPTION
				"This object indicates the IPv6 address of the master controller."
			::= { hwWlanClusterMasterConfig 2 }
			
		-- 1.3.6.1.4.1.2011.6.139.11.1.83.1.3
		hwWlanClusterPsk OBJECT-TYPE
			SYNTAX OCTET STRING
			MAX-ACCESS read-write
			STATUS current
			DESCRIPTION
				"This object indicates the psk of the master controller."
			::= { hwWlanClusterMasterConfig 3 }

                                          -- 1.3.6.1.4.1.2011.6.139.11.1.83.2
		hwWlanClusterRedundancyConfig OBJECT IDENTIFIER ::= { hwWlanClusterConfig 2 }
		
		-- 1.3.6.1.4.1.2011.6.139.11.1.83.2.1
		hwWlanClusterRedundancyLocalIPv4Address OBJECT-TYPE
			SYNTAX IpAddress
			MAX-ACCESS read-write
			STATUS current
			DESCRIPTION
				"This object indicates the IPv4 address of the local ac."
			::= { hwWlanClusterRedundancyConfig 1 }
			
		-- 1.3.6.1.4.1.2011.6.139.11.1.83.2.2
		hwWlanClusterRedundancyLocalIPv6Address OBJECT-TYPE
			SYNTAX OCTET STRING
			MAX-ACCESS read-write
			STATUS current
			DESCRIPTION
				"This object indicates the IPv6 address of the local ac."
			::= { hwWlanClusterRedundancyConfig 2 }	
			
		-- 1.3.6.1.4.1.2011.6.139.11.1.83.2.3
		hwWlanClusterRedundancyPeerIPv4Address OBJECT-TYPE
			SYNTAX IpAddress
			MAX-ACCESS read-write
			STATUS current
			DESCRIPTION
				"This object indicates the IPv4 address of the peer ac."
			::= { hwWlanClusterRedundancyConfig 3 }

                                           -- 1.3.6.1.4.1.2011.6.139.11.1.83.2.4
		hwWlanClusterRedundancyPeerIPv6Address OBJECT-TYPE
			SYNTAX OCTET STRING
			MAX-ACCESS read-write
			STATUS current
			DESCRIPTION
				"This object indicates the IPv6 address of the peer ac."
			::= { hwWlanClusterRedundancyConfig 4 }
			
		-- 1.3.6.1.4.1.2011.6.139.11.1.83.2.5
		hwWlanClusterRedundancyTrackVRRPID OBJECT-TYPE
			SYNTAX Integer32
			MAX-ACCESS read-write
			STATUS current
			DESCRIPTION
				"This object indicates the vrrp id."
			::= { hwWlanClusterRedundancyConfig 5 }
		
		-- 1.3.6.1.4.1.2011.6.139.11.1.83.2.6
		hwWlanClusterRedundancyTrackInterface OBJECT-TYPE
			SYNTAX Integer32
			MAX-ACCESS read-write
			STATUS current
			DESCRIPTION
				"This object indicates the interface index."
			::= { hwWlanClusterRedundancyConfig 6 }
			
		-- 1.3.6.1.4.1.2011.6.139.11.1.83.2.7
		hwWlanClusterRedundancyPsk OBJECT-TYPE
			SYNTAX OCTET STRING
			MAX-ACCESS read-write
			STATUS current
			DESCRIPTION
				"This object indicates the psk of the redundancy ac."
			::= { hwWlanClusterRedundancyConfig 7 }	
			
		-- 1.3.6.1.4.1.2011.6.139.11.1.83.2.8
		hwWlanClusterRedundancyTrackVRRPType OBJECT-TYPE
			SYNTAX INTEGER
				{
				vrrpv4(1),
				vrrpv6(2),
				invalid(3)
				}
			MAX-ACCESS read-write
			STATUS current
			DESCRIPTION
				"This object indicates the information about the track VRRP type."
			::= { hwWlanClusterRedundancyConfig 8 }
		
		-- 1.3.6.1.4.1.2011.6.139.11.1.83.3
		hwWlanClusterLocalIPv4Table OBJECT-TYPE
			SYNTAX SEQUENCE OF HwWlanClusterLocalIPv4Entry
			MAX-ACCESS not-accessible
			STATUS current
			DESCRIPTION
				"This table describes the configuration of the local controller."
			::= { hwWlanClusterConfig 3 }
			
		-- 1.3.6.1.4.1.2011.6.139.11.1.83.3.1
		hwWlanClusterLocalIPv4Entry OBJECT-TYPE
			SYNTAX HwWlanClusterLocalIPv4Entry
			MAX-ACCESS not-accessible
			STATUS current
			DESCRIPTION
				"This table has no index."
			INDEX { hwWlanClusterLocalIPv4Address }
			::= { hwWlanClusterLocalIPv4Table 1 }
			
		HwWlanClusterLocalIPv4Entry ::=
			SEQUENCE { 
				hwWlanClusterLocalIPv4Address
					IpAddress,
				hwWlanClusterLocalIPv4Psk
					OCTET STRING,
				hwWlanClusterLocalIPv4RowStatus
					RowStatus
			 }
			 
		-- 1.3.6.1.4.1.2011.6.139.11.1.83.3.1.1
		hwWlanClusterLocalIPv4Address OBJECT-TYPE
			SYNTAX IpAddress
			MAX-ACCESS not-accessible
			STATUS current
			DESCRIPTION
				"This object indicates the IPv4 address of the local controller."
			::= { hwWlanClusterLocalIPv4Entry 1 }
		
		-- 1.3.6.1.4.1.2011.6.139.11.1.83.3.1.2
		hwWlanClusterLocalIPv4Psk OBJECT-TYPE
			SYNTAX OCTET STRING
			MAX-ACCESS read-write
			STATUS current
			DESCRIPTION
				"This object indicates the psk of the local controller."
			::= { hwWlanClusterLocalIPv4Entry 2 }
			
		-- 1.3.6.1.4.1.2011.6.139.11.1.83.3.1.3
		hwWlanClusterLocalIPv4RowStatus OBJECT-TYPE
			SYNTAX RowStatus
			MAX-ACCESS read-write
			STATUS current
			DESCRIPTION
				"This object indicates the row status."
			::= { hwWlanClusterLocalIPv4Entry 3 }
			
		-- 1.3.6.1.4.1.2011.6.139.11.1.83.4
		hwWlanClusterLocalIPv6Table OBJECT-TYPE
			SYNTAX SEQUENCE OF HwWlanClusterLocalIPv6Entry
			MAX-ACCESS not-accessible
			STATUS current
			DESCRIPTION
				"This table describes the configuration of the local controller."
			::= { hwWlanClusterConfig 4 }
				
		-- 1.3.6.1.4.1.2011.6.139.11.1.83.4.1
		hwWlanClusterLocalIPv6Entry OBJECT-TYPE
			SYNTAX HwWlanClusterLocalIPv6Entry
			MAX-ACCESS not-accessible
			STATUS current
			DESCRIPTION
				"This table has no index."
			INDEX { hwWlanClusterLocalIPv6Address }
			::= { hwWlanClusterLocalIPv6Table 1 }
			
		HwWlanClusterLocalIPv6Entry ::=
			SEQUENCE { 
				hwWlanClusterLocalIPv6Address
					OCTET STRING,
				hwWlanClusterLocalIPv6Psk
					OCTET STRING,
				hwWlanClusterLocalIPv6RowStatus
					RowStatus
			 }
			 
		-- 1.3.6.1.4.1.2011.6.139.11.1.83.4.1.1
		hwWlanClusterLocalIPv6Address OBJECT-TYPE
			SYNTAX OCTET STRING
			MAX-ACCESS not-accessible
			STATUS current
			DESCRIPTION
				"This object indicates the IPv6 address of the local controller."
			::= { hwWlanClusterLocalIPv6Entry 1 }
		
		-- 1.3.6.1.4.1.2011.6.139.11.1.83.4.1.2
		hwWlanClusterLocalIPv6Psk OBJECT-TYPE
			SYNTAX OCTET STRING
			MAX-ACCESS read-write
			STATUS current
			DESCRIPTION
				"This object indicates the psk of the local controller."
			::= { hwWlanClusterLocalIPv6Entry 2 }
		
		-- 1.3.6.1.4.1.2011.6.139.11.1.83.4.1.3
		hwWlanClusterLocalIPv6RowStatus OBJECT-TYPE
			SYNTAX RowStatus
			MAX-ACCESS read-write
			STATUS current
			DESCRIPTION
				"This object indicates the row status."
			::= { hwWlanClusterLocalIPv6Entry 3 }
			
		-- 1.3.6.1.4.1.2011.6.139.11.1.83.5
		hwWlanClusterSynConfig OBJECT IDENTIFIER ::= { hwWlanClusterConfig 5 }
		
		-- 1.3.6.1.4.1.2011.6.139.11.1.83.5.1
		hwWlanClusterSynIPv4Address OBJECT-TYPE
			SYNTAX IpAddress
			MAX-ACCESS read-write
			STATUS current
			DESCRIPTION
				"This object indicates the Ipv4 address of the synchronize-configuration."
			::= { hwWlanClusterSynConfig 1 }
			
		-- 1.3.6.1.4.1.2011.6.139.11.1.83.5.2
		hwWlanClusterSynIPv6Address OBJECT-TYPE
			SYNTAX OCTET STRING
			MAX-ACCESS read-write
			STATUS current
			DESCRIPTION
				"This object indicates the Ipv6 address of the synchronize-configuration."
			::= { hwWlanClusterSynConfig 2 }
		
		-- 1.3.6.1.4.1.2011.6.139.11.1.83.5.3
		hwWlanClusterSynConfigurationOper OBJECT-TYPE
			SYNTAX INTEGER
				{
		                synConfig(1)
		                }
			MAX-ACCESS read-write
			STATUS current
			DESCRIPTION
				"This object indicates to synchronize configuration. It is write only."
			::= { hwWlanClusterSynConfig 3 }

		-- 1.3.6.1.4.1.2011.6.139.11.1.83.5.4
		hwWlanClusterSynConfigScheduleEnable OBJECT-TYPE
			SYNTAX INTEGER
				{
		                 disable(1),
                                                       enable(2)
		                }
			MAX-ACCESS read-write
			STATUS current
			DESCRIPTION
				"This object indicates to the switch of scheduled synchronize configuration."
			::= { hwWlanClusterSynConfig 4 }

		-- 1.3.6.1.4.1.2011.6.139.11.1.83.5.5
		hwWlanClusterSynConfigScheduleTime OBJECT-TYPE
			SYNTAX OCTET STRING
			MAX-ACCESS read-write
			STATUS current
			DESCRIPTION
				"This object indicates the scheduled synchronize configuration time."
			::= { hwWlanClusterSynConfig 5 }

		-- 1.3.6.1.4.1.2011.6.139.11.1.83.5.6
		hwWlanClusterSynConfigScheduleInterval OBJECT-TYPE
			SYNTAX Integer32 (720..7200)
			MAX-ACCESS read-write
			STATUS current
			DESCRIPTION
				"This object indicates the interval of scheduled synchronize configuration.
				It is expressed in minutes.
				The default value is 1440."
			::= { hwWlanClusterSynConfig 6 }

		--1.3.6.1.4.1.2011.6.139.11.1.83.6
        	hwWlanClusterACListInfoTable OBJECT-TYPE
            		SYNTAX SEQUENCE OF HwWlanClusterACListInfoEntry
            		MAX-ACCESS not-accessible
            		STATUS current
        		DESCRIPTION
				"This table describes the ac information."
			::= { hwWlanClusterConfig 6 }

       		--1.3.6.1.4.1.2011.6.139.11.1.83.6.1
        	hwWlanClusterACListInfoEntry OBJECT-TYPE
            		SYNTAX HwWlanClusterACListInfoEntry
			MAX-ACCESS not-accessible
			STATUS current
			DESCRIPTION
				"This table has no index."
			INDEX { hwWlanClusterACIndex}
			::= { hwWlanClusterACListInfoTable 1 }

		HwWlanClusterACListInfoEntry ::=
			SEQUENCE { 
				hwWlanClusterACIndex
					Unsigned32,
				hwWlanClusterACIPv4
					IpAddress,
				hwWlanClusterACIPv6
					OCTET STRING,
                                hwWlanClusterACRole
                                        INTEGER,
                                hwWlanClusterACType
                                        OCTET STRING,
                                hwWlanClusterACVersion
                                        OCTET STRING,
                                hwWlanClusterACStatus
                                        INTEGER,
                                hwWlanClusterACLastSynTime
                                        OCTET STRING
			 }

		-- 1.3.6.1.4.1.2011.6.139.11.1.83.6.1.1
		hwWlanClusterACIndex OBJECT-TYPE
			SYNTAX Unsigned32 (0..63)
			MAX-ACCESS not-accessible
			STATUS current
			DESCRIPTION
				"This object indicates the index of hwWlanClusterACListInfo."
			::= { hwWlanClusterACListInfoEntry 1}
		
		-- 1.3.6.1.4.1.2011.6.139.11.1.83.6.1.2
		hwWlanClusterACIPv4 OBJECT-TYPE
			SYNTAX IpAddress
			MAX-ACCESS read-only
			STATUS current
			DESCRIPTION
				"This object indicates the ipv4 address of the ac."
			::= { hwWlanClusterACListInfoEntry 2 }
			
		-- 1.3.6.1.4.1.2011.6.139.11.1.83.6.1.3
		hwWlanClusterACIPv6 OBJECT-TYPE
			SYNTAX OCTET STRING
			MAX-ACCESS read-only
			STATUS current
			DESCRIPTION
				"This object indicates the ipv6 address of the ac."
			::= { hwWlanClusterACListInfoEntry 3 }
			
		-- 1.3.6.1.4.1.2011.6.139.11.1.83.6.1.4
		hwWlanClusterACRole OBJECT-TYPE
			SYNTAX INTEGER
                         {
                             master (1),
                             slave (2),
                             backup (3)
                         }
			MAX-ACCESS read-only
			STATUS current
			DESCRIPTION
				"This object indicates the role of the ac."
			::= { hwWlanClusterACListInfoEntry 4}

                                           -- 1.3.6.1.4.1.2011.6.139.11.1.83.6.1.5
		hwWlanClusterACType OBJECT-TYPE
			SYNTAX OCTET STRING
			MAX-ACCESS read-only
			STATUS current
			DESCRIPTION
				"This object indicates the type of the ac."
			::= { hwWlanClusterACListInfoEntry 5 }
			
		-- 1.3.6.1.4.1.2011.6.139.11.1.83.6.1.6
		hwWlanClusterACVersion OBJECT-TYPE
			SYNTAX OCTET STRING
			MAX-ACCESS read-only
			STATUS current
			DESCRIPTION
				"This object indicates the version of the ac."
			::= { hwWlanClusterACListInfoEntry 6 }

		
		-- 1.3.6.1.4.1.2011.6.139.11.1.83.6.1.7
		hwWlanClusterACStatus OBJECT-TYPE
			SYNTAX INTEGER
	                {
                           down(1),
                           up(2),
                           pskmismatch(3),
                           vermismatch(4),
                           cfgmismatch(5),
                           devmismatch(6),
                           initial(7)
            }
            MAX-ACCESS read-only
			STATUS current
			DESCRIPTION
				"This object indicates the status of the ac."
			::= { hwWlanClusterACListInfoEntry 7 }
			
		-- 1.3.6.1.4.1.2011.6.139.11.1.83.6.1.8
		hwWlanClusterACLastSynTime OBJECT-TYPE
			SYNTAX OCTET STRING
			MAX-ACCESS read-only
			STATUS current
			DESCRIPTION
				"This object indicates the last synchronize time of the ac."
			::= { hwWlanClusterACListInfoEntry 8 }
			
		-- 1.3.6.1.4.1.2011.6.139.11.1.84
		hwWiredPortProfileTrafficFilterTable OBJECT-TYPE
			SYNTAX SEQUENCE OF HwWiredPortProfileTrafficFilterEntry
			MAX-ACCESS not-accessible
			STATUS current
			DESCRIPTION
				"This table is used to configure QoS filter information."
			::= { hwWlanConfigObjects 84 }
		
		-- 1.3.6.1.4.1.2011.6.139.11.1.84.1
		hwWiredPortProfileTrafficFilterEntry OBJECT-TYPE
			SYNTAX HwWiredPortProfileTrafficFilterEntry
			MAX-ACCESS not-accessible
			STATUS current
			DESCRIPTION
				"The indexes of this table are hwAPWiredPortProfileName, hwWiredPortProfileTrafficFilterID and hwWiredPortProfileTrafficFilterDirection.
				"
			INDEX { hwAPWiredPortProfileName, hwWiredPortProfileTrafficFilterDirection, hwWiredPortProfileTrafficFilterID }
			::= { hwWiredPortProfileTrafficFilterTable 1 }
		
		HwWiredPortProfileTrafficFilterEntry ::=
			SEQUENCE { 
				hwWiredPortProfileTrafficFilterDirection
					INTEGER,
				hwWiredPortProfileTrafficFilterID
					Unsigned32,
				hwWiredPortProfileTrafficFilterType
					INTEGER,
				hwWiredPortProfileTrafficFilterACLNum1
					Integer32,
				hwWiredPortProfileTrafficFilterACLNum2
					Integer32,
				hwWiredPortProfileTrafficFilterRowStatus
					RowStatus
			 }

		-- 1.3.6.1.4.1.2011.6.139.11.1.84.1.1
		hwWiredPortProfileTrafficFilterDirection OBJECT-TYPE
			SYNTAX INTEGER
				{
				inbound(1),
				outbound(2)
				}
			MAX-ACCESS not-accessible
			STATUS current
			DESCRIPTION
				"This object indicates the ACL rule direction for packet filtering in a wired port profile. This parameter has no default value."
			::= { hwWiredPortProfileTrafficFilterEntry 1 }
		
		-- 1.3.6.1.4.1.2011.6.139.11.1.84.1.2
		hwWiredPortProfileTrafficFilterID OBJECT-TYPE
			SYNTAX Unsigned32
			MAX-ACCESS not-accessible
			STATUS current
			DESCRIPTION
				"This object indicates the ACL rule ID for packet filtering in a wired port profile. This parameter has no default value."
			::= { hwWiredPortProfileTrafficFilterEntry 2 }
		
		-- 1.3.6.1.4.1.2011.6.139.11.1.84.1.3
		hwWiredPortProfileTrafficFilterType OBJECT-TYPE
			SYNTAX INTEGER
				{
				ipv4(1),
				ipv6(2),
				l2(3),
				ipv4L2(4)
				}
			MAX-ACCESS read-write
			STATUS current
			DESCRIPTION
				"This object indicates the ACL rule type for packet filtering in a wired port profile. This parameter has no default value."
			::= { hwWiredPortProfileTrafficFilterEntry 3 }
		
		-- 1.3.6.1.4.1.2011.6.139.11.1.84.1.4
		hwWiredPortProfileTrafficFilterACLNum1 OBJECT-TYPE
			SYNTAX Integer32 (3000..3031 | 4000..4031)
			MAX-ACCESS read-write
			STATUS current
			DESCRIPTION
				"This object indicates the ACL rule for packet filtering in a wired port profile.
				"
			::= { hwWiredPortProfileTrafficFilterEntry 4 }
		
		-- 1.3.6.1.4.1.2011.6.139.11.1.84.1.5
		hwWiredPortProfileTrafficFilterACLNum2 OBJECT-TYPE
			SYNTAX Integer32 (4000..4031)
			MAX-ACCESS read-write
			STATUS current
			DESCRIPTION
				"This object indicates the ACL rule for packet filtering in a wired port profile.
				"
			::= { hwWiredPortProfileTrafficFilterEntry 5 }
		
		-- 1.3.6.1.4.1.2011.6.139.11.1.84.1.6
		hwWiredPortProfileTrafficFilterRowStatus OBJECT-TYPE
			SYNTAX RowStatus
			MAX-ACCESS read-write
			STATUS current
			DESCRIPTION
				"This object indicates the row status of this table. ROWSTATUS_CREATEANDFLOW and ROWSTATUS_DESTROY are commonly used.
				"
			::= { hwWiredPortProfileTrafficFilterEntry 6 }
		
		-- 1.3.6.1.4.1.2011.6.139.11.1.85
		hwWiredPortProfileTrafficRemarkTable OBJECT-TYPE
			SYNTAX SEQUENCE OF HwWiredPortProfileTrafficRemarkEntry
			MAX-ACCESS not-accessible
			STATUS current
			DESCRIPTION
				"This table is used to configure QoS remark information.
				"
			::= { hwWlanConfigObjects 85 }
		
		-- 1.3.6.1.4.1.2011.6.139.11.1.85.1
		hwWiredPortProfileTrafficRemarkEntry OBJECT-TYPE
			SYNTAX HwWiredPortProfileTrafficRemarkEntry
			MAX-ACCESS not-accessible
			STATUS current
			DESCRIPTION
				"The indexes of this table are hwAPWiredPortProfileName, hwWiredPortProfileTrafficRemarkDirection and hwWiredPortProfileTrafficRemarkID."
			INDEX { hwAPWiredPortProfileName, hwWiredPortProfileTrafficRemarkDirection, hwWiredPortProfileTrafficRemarkID }
			::= { hwWiredPortProfileTrafficRemarkTable 1 }
		
		HwWiredPortProfileTrafficRemarkEntry ::=
			SEQUENCE { 
				hwWiredPortProfileTrafficRemarkDirection
					INTEGER,
				hwWiredPortProfileTrafficRemarkID
					Unsigned32,
				hwWiredPortProfileTrafficRemarkIPType
					INTEGER,
				hwWiredPortProfileTrafficRemarkACLNum1
					Integer32,
				hwWiredPortProfileTrafficRemarkACLNum2
					Integer32,
				hwWiredPortProfileTrafficRemarkType
					INTEGER,
				hwWiredPortProfileTrafficRemarkValue
					Integer32,
				hwWiredPortProfileTrafficRemarkRowStatus
					RowStatus
			 }

		-- 1.3.6.1.4.1.2011.6.139.11.1.85.1.1
		hwWiredPortProfileTrafficRemarkDirection OBJECT-TYPE
			SYNTAX INTEGER
				{
				inbound(1),
				outbound(2)
				}
			MAX-ACCESS not-accessible
			STATUS current
			DESCRIPTION
				"This object indicates the ACL rule direction for packet remarking in a wired port profile. This parameter has no default value."
			::= { hwWiredPortProfileTrafficRemarkEntry 1 }
		
		-- 1.3.6.1.4.1.2011.6.139.11.1.85.1.2
		hwWiredPortProfileTrafficRemarkID OBJECT-TYPE
			SYNTAX Unsigned32
			MAX-ACCESS not-accessible
			STATUS current
			DESCRIPTION
				"This object indicates the ACL rule ID for packet remarking in a wired port profile. This parameter has no default value."
			::= { hwWiredPortProfileTrafficRemarkEntry 2 }
		
		-- 1.3.6.1.4.1.2011.6.139.11.1.85.1.3
		hwWiredPortProfileTrafficRemarkIPType OBJECT-TYPE
			SYNTAX INTEGER
				{
				ipv4(1),
				ipv6(2),
				l2(3),
				ipv4L2(4)
				}
			MAX-ACCESS read-write
			STATUS current
			DESCRIPTION
				"This object indicates the ACL rule IP type for packet remarking in a wired port profile. This parameter has no default value."
			::= { hwWiredPortProfileTrafficRemarkEntry 3 }
		
		-- 1.3.6.1.4.1.2011.6.139.11.1.85.1.4
		hwWiredPortProfileTrafficRemarkACLNum1 OBJECT-TYPE
			SYNTAX Integer32 (3000..3031 | 4000..4031)
			MAX-ACCESS read-write
			STATUS current
			DESCRIPTION
				"This object indicates the ACL rule for packet remarking in a wired port profile."
			::= { hwWiredPortProfileTrafficRemarkEntry 4 }
		
		-- 1.3.6.1.4.1.2011.6.139.11.1.85.1.5
		hwWiredPortProfileTrafficRemarkACLNum2 OBJECT-TYPE
			SYNTAX Integer32 (4000..4031)
			MAX-ACCESS read-write
			STATUS current
			DESCRIPTION
				"This object indicates the ACL rule for packet remarking in a wired port profile."
			::= { hwWiredPortProfileTrafficRemarkEntry 5 }
		
		-- 1.3.6.1.4.1.2011.6.139.11.1.85.1.6
		hwWiredPortProfileTrafficRemarkType OBJECT-TYPE
			SYNTAX INTEGER
				{
				dscp(1),
				dot1p(2)
				}
			MAX-ACCESS read-write
			STATUS current
			DESCRIPTION
				"This object indicates the ACL rule mask type for packet remarking in a wired port profile. This parameter has no default value.
				"
			::= { hwWiredPortProfileTrafficRemarkEntry 6 }
		
		-- 1.3.6.1.4.1.2011.6.139.11.1.85.1.7
		hwWiredPortProfileTrafficRemarkValue OBJECT-TYPE
			SYNTAX Integer32 (0..63)
			MAX-ACCESS read-write
			STATUS current
			DESCRIPTION
				"This object indicates the ACL rule mask value for packet remarking in a wired port profile. This parameter has no default value."
			::= { hwWiredPortProfileTrafficRemarkEntry 7 }
		
		-- 1.3.6.1.4.1.2011.6.139.11.1.85.1.8
		hwWiredPortProfileTrafficRemarkRowStatus OBJECT-TYPE
			SYNTAX RowStatus
			MAX-ACCESS read-write
			STATUS current
			DESCRIPTION
				"This object indicates the row status of this table. ROWSTATUS_CREATEANDFLOW and ROWSTATUS_DESTROY are commonly used."
			::= { hwWiredPortProfileTrafficRemarkEntry 8 }
			
		-- 1.3.6.1.4.1.2011.6.139.11.1.86
		hwTrafficProfileTrafficFilterTable OBJECT-TYPE
			SYNTAX SEQUENCE OF HwTrafficProfileTrafficFilterEntry
			MAX-ACCESS not-accessible
			STATUS current
			DESCRIPTION
				"This table is used to configure QoS filter information."
			::= { hwWlanConfigObjects 86 }
		
		-- 1.3.6.1.4.1.2011.6.139.11.1.86.1
		hwTrafficProfileTrafficFilterEntry OBJECT-TYPE
			SYNTAX HwTrafficProfileTrafficFilterEntry
			MAX-ACCESS not-accessible
			STATUS current
			DESCRIPTION
				"The indexes of this table are hwAPTrafficProfileName, hwTrafficProfileTrafficFilterID and hwTrafficProfileTrafficFilterDirection.
				"
			INDEX { hwAPTrafficProfileName, hwTrafficProfileTrafficFilterDirection, hwTrafficProfileTrafficFilterID }
			::= { hwTrafficProfileTrafficFilterTable 1 }
		
		HwTrafficProfileTrafficFilterEntry ::=
			SEQUENCE { 
				hwTrafficProfileTrafficFilterDirection
					INTEGER,
				hwTrafficProfileTrafficFilterID
					Unsigned32,
				hwTrafficProfileTrafficFilterTpye
					INTEGER,
				hwTrafficProfileTrafficFilterACLNum1
					Integer32,
				hwTrafficProfileTrafficFilterACLNum2
					Integer32,
				hwTrafficProfileTrafficFilterRowStatus
					RowStatus
			 }

		-- 1.3.6.1.4.1.2011.6.139.11.1.86.1.1
		hwTrafficProfileTrafficFilterDirection OBJECT-TYPE
			SYNTAX INTEGER
				{
				inbound(1),
				outbound(2)
				}
			MAX-ACCESS not-accessible
			STATUS current
			DESCRIPTION
				"This object indicates the ACL rule direction for packet filtering in a traffic profile. This parameter has no default value."
			::= { hwTrafficProfileTrafficFilterEntry 1 }
		
		-- 1.3.6.1.4.1.2011.6.139.11.1.86.1.2
		hwTrafficProfileTrafficFilterID OBJECT-TYPE
			SYNTAX Unsigned32
			MAX-ACCESS not-accessible
			STATUS current
			DESCRIPTION
				"This object indicates the ACL rule ID for packet filtering in a traffic profile. This parameter has no default value."
			::= { hwTrafficProfileTrafficFilterEntry 2 }
		
		-- 1.3.6.1.4.1.2011.6.139.11.1.86.1.3
		hwTrafficProfileTrafficFilterTpye OBJECT-TYPE
			SYNTAX INTEGER
				{
				ipv4(1),
				ipv6(2),
				l2(3),
				ipv4L2(4)
				}
			MAX-ACCESS read-write
			STATUS current
			DESCRIPTION
				"This object indicates the ACL rule type for packet filtering in a traffic profile. This parameter has no default value."
			::= { hwTrafficProfileTrafficFilterEntry 3 }
		
		-- 1.3.6.1.4.1.2011.6.139.11.1.86.1.4
		hwTrafficProfileTrafficFilterACLNum1 OBJECT-TYPE
			SYNTAX Integer32 (3000..3031 | 4000..4031 | 6000..6031)
			MAX-ACCESS read-write
			STATUS current
			DESCRIPTION
				"This object indicates the ACL rule for packet filtering in a traffic profile.
				"
			::= { hwTrafficProfileTrafficFilterEntry 4 }
		
		-- 1.3.6.1.4.1.2011.6.139.11.1.86.1.5
		hwTrafficProfileTrafficFilterACLNum2 OBJECT-TYPE
			SYNTAX Integer32 (4000..4031)
			MAX-ACCESS read-write
			STATUS current
			DESCRIPTION
				"This object indicates the ACL rule for packet filtering in a traffic profile.
				"
			::= { hwTrafficProfileTrafficFilterEntry 5 }
		
		-- 1.3.6.1.4.1.2011.6.139.11.1.86.1.6
		hwTrafficProfileTrafficFilterRowStatus OBJECT-TYPE
			SYNTAX RowStatus
			MAX-ACCESS read-write
			STATUS current
			DESCRIPTION
				"This object indicates the row status of this table. ROWSTATUS_CREATEANDFLOW and ROWSTATUS_DESTROY are commonly used.
				"
			::= { hwTrafficProfileTrafficFilterEntry 6 }
		
		-- 1.3.6.1.4.1.2011.6.139.11.1.87
		hwTrafficProfileTrafficRemarkTable OBJECT-TYPE
			SYNTAX SEQUENCE OF HwTrafficProfileTrafficRemarkEntry
			MAX-ACCESS not-accessible
			STATUS current
			DESCRIPTION
				"This table is used to configure QoS remark information.
				"
			::= { hwWlanConfigObjects 87 }
		
		-- 1.3.6.1.4.1.2011.6.139.11.1.87.1
		hwTrafficProfileTrafficRemarkEntry OBJECT-TYPE
			SYNTAX HwTrafficProfileTrafficRemarkEntry
			MAX-ACCESS not-accessible
			STATUS current
			DESCRIPTION
				"The indexes of this table are hwAPTrafficProfileName, hwTrafficProfileTrafficRemarkDirection and hwTrafficProfileTrafficRemarkID."
			INDEX { hwAPTrafficProfileName, hwTrafficProfileTrafficRemarkDirection, hwTrafficProfileTrafficRemarkID }
			::= { hwTrafficProfileTrafficRemarkTable 1 }
		
		HwTrafficProfileTrafficRemarkEntry ::=
			SEQUENCE { 
				hwTrafficProfileTrafficRemarkDirection
					INTEGER,
				hwTrafficProfileTrafficRemarkID
					Unsigned32,
				hwTrafficProfileTrafficRemarkIPType
					INTEGER,
				hwTrafficProfileTrafficRemarkACLNum1
					Integer32,
				hwTrafficProfileTrafficRemarkACLNum2
					Integer32,
				hwTrafficProfileTrafficRemarkType
					INTEGER,
				hwTrafficProfileTrafficRemarkValue
					Integer32,
				hwTrafficProfileTrafficRemarkRowStatus
					RowStatus
			 }

		-- 1.3.6.1.4.1.2011.6.139.11.1.87.1.1
		hwTrafficProfileTrafficRemarkDirection OBJECT-TYPE
			SYNTAX INTEGER
				{
				inbound(1),
				outbound(2)
				}
			MAX-ACCESS not-accessible
			STATUS current
			DESCRIPTION
				"This object indicates the ACL rule direction for packet remarking in a traffic profile. This parameter has no default value."
			::= { hwTrafficProfileTrafficRemarkEntry 1 }
		
		-- 1.3.6.1.4.1.2011.6.139.11.1.87.1.2
		hwTrafficProfileTrafficRemarkID OBJECT-TYPE
			SYNTAX Unsigned32 
			MAX-ACCESS not-accessible
			STATUS current
			DESCRIPTION
				"This object indicates the ACL rule ID for packet remarking in a traffic profile. This parameter has no default value."
			::= { hwTrafficProfileTrafficRemarkEntry 2 }
		
		-- 1.3.6.1.4.1.2011.6.139.11.1.87.1.3
		hwTrafficProfileTrafficRemarkIPType OBJECT-TYPE
			SYNTAX INTEGER
				{
				ipv4(1),
				ipv6(2),
				l2(3),
				ipv4L2(4)
				}
			MAX-ACCESS read-write
			STATUS current
			DESCRIPTION
				"This object indicates the ACL rule IP type for packet remarking in a traffic profile. This parameter has no default value."
			::= { hwTrafficProfileTrafficRemarkEntry 3 }
		
		-- 1.3.6.1.4.1.2011.6.139.11.1.87.1.4
		hwTrafficProfileTrafficRemarkACLNum1 OBJECT-TYPE
			SYNTAX Integer32 (3000..3031 | 4000..4031 | 6000..6031)
			MAX-ACCESS read-write
			STATUS current
			DESCRIPTION
				"This object indicates the ACL rule for packet remarking in a traffic profile."
			::= { hwTrafficProfileTrafficRemarkEntry 4 }
		
		-- 1.3.6.1.4.1.2011.6.139.11.1.87.1.5
		hwTrafficProfileTrafficRemarkACLNum2 OBJECT-TYPE
			SYNTAX Integer32 (4000..4031)
			MAX-ACCESS read-write
			STATUS current
			DESCRIPTION
				"This object indicates the ACL rule for packet remarking in a traffic profile."
			::= { hwTrafficProfileTrafficRemarkEntry 5 }
		
		-- 1.3.6.1.4.1.2011.6.139.11.1.87.1.6
		hwTrafficProfileTrafficRemarkType OBJECT-TYPE
			SYNTAX INTEGER
				{
				dscp(1),
				dot11e(3)
				}
			MAX-ACCESS read-write
			STATUS current
			DESCRIPTION
				"This object indicates the ACL rule mask type for packet remarking in a traffic profile. This parameter has no default value.
				"
			::= { hwTrafficProfileTrafficRemarkEntry 6 }
		
		-- 1.3.6.1.4.1.2011.6.139.11.1.87.1.7
		hwTrafficProfileTrafficRemarkValue OBJECT-TYPE
			SYNTAX Integer32 (0..63)
			MAX-ACCESS read-write
			STATUS current
			DESCRIPTION
				"This object indicates the ACL rule mask value for packet remarking in a traffic profile. This parameter has no default value."
			::= { hwTrafficProfileTrafficRemarkEntry 7 }
		
		-- 1.3.6.1.4.1.2011.6.139.11.1.87.1.8
		hwTrafficProfileTrafficRemarkRowStatus OBJECT-TYPE
			SYNTAX RowStatus
			MAX-ACCESS read-write
			STATUS current
			DESCRIPTION
				"This object indicates the row status of this table. ROWSTATUS_CREATEANDFLOW and ROWSTATUS_DESTROY are commonly used."
			::= { hwTrafficProfileTrafficRemarkEntry 8 }		
		-- 1.3.6.1.4.1.2011.6.139.11.1.88
		hwWlanBranchGroupConfig OBJECT IDENTIFIER ::= { hwWlanConfigObjects 88 }	
		-- 1.3.6.1.4.1.2011.6.139.11.1.88.1
		hwBranchGroupTable OBJECT-TYPE
			SYNTAX SEQUENCE OF HwBranchGroupEntry
			MAX-ACCESS not-accessible
			STATUS current
			DESCRIPTION
				"This table is used to configure branch group information.
				"
			::= { hwWlanBranchGroupConfig 1 }		
		-- 1.3.6.1.4.1.2011.6.139.11.1.88.1.1
		hwBranchGroupEntry OBJECT-TYPE
			SYNTAX HwBranchGroupEntry
			MAX-ACCESS not-accessible
			STATUS current
			DESCRIPTION
				"The indexes of this table are hwBranchGroupName."
			INDEX { hwBranchGroupName }
			::= { hwBranchGroupTable 1 }
		
		HwBranchGroupEntry ::=
			SEQUENCE { 
				hwBranchGroupName
					OCTET STRING,
				hwBranchGroupUserAccountNumber
					Integer32,
				hwBranchGroupAPNumber
					Integer32,
				hwBranchGroupFileStatus
					INTEGER,
				hwBranchGroupServerCertFileType
					INTEGER,
				hwBranchGroupServerCertFileName
					OCTET STRING,
				hwBranchGroupServerCAFileName
					OCTET STRING,				
				hwBranchGroupServerPSKType
					INTEGER,
				hwBranchGroupServerPSKFileName
					OCTET STRING,
				hwBranchGroupServerPSKPassword
					OCTET STRING,
				hwBranchGroupFileLoadOper
					INTEGER,
				hwBranchGroupFileLoadPercent
					Integer32,
				hwBranchGroupFileLoadFailedAP
					Integer32,	
				hwBranchGroupRowStatus
					RowStatus
			 }
		-- 1.3.6.1.4.1.2011.6.139.11.1.88.1.1.1
		hwBranchGroupName OBJECT-TYPE
			SYNTAX OCTET STRING (SIZE (1..35))
			MAX-ACCESS not-accessible
			STATUS current
			DESCRIPTION
				"This object indicates the AP branch group name. It is the index of the table."
			::= { hwBranchGroupEntry 1 }
		
		-- 1.3.6.1.4.1.2011.6.139.11.1.88.1.1.2
		hwBranchGroupUserAccountNumber OBJECT-TYPE
			SYNTAX Integer32 
			MAX-ACCESS read-only
			STATUS current
			DESCRIPTION
				"This object indicates the AP branch group name user accout number."
			::= { hwBranchGroupEntry 2 }
		
		-- 1.3.6.1.4.1.2011.6.139.11.1.88.1.1.3
		hwBranchGroupAPNumber OBJECT-TYPE
			SYNTAX Integer32 
			MAX-ACCESS read-only
			STATUS current
			DESCRIPTION
				"This object indicates the AP branch group name AP number."
			::= { hwBranchGroupEntry 3 }
		-- 1.3.6.1.4.1.2011.6.139.11.1.88.1.1.4
		hwBranchGroupFileStatus OBJECT-TYPE
			SYNTAX INTEGER
				{
				success(1),
				exception(2),
				none(3),
				loading(4),
				unload(5)
				}
			MAX-ACCESS read-only
			STATUS current
			DESCRIPTION
				"This object indicates the AP branch group file status."
			::= { hwBranchGroupEntry 4 }
		-- 1.3.6.1.4.1.2011.6.139.11.1.88.1.1.5
		hwBranchGroupServerCertFileType OBJECT-TYPE
			SYNTAX INTEGER
				{
				der(1),
				pem(3),
				na(4)
				}
			MAX-ACCESS read-write
			STATUS current
			DESCRIPTION
				"This object indicates the AP branch group Cert file type."
			::= { hwBranchGroupEntry 5 }
		-- 1.3.6.1.4.1.2011.6.139.11.1.88.1.1.6
		hwBranchGroupServerCertFileName OBJECT-TYPE
			SYNTAX OCTET STRING (SIZE (0..63))
			MAX-ACCESS read-write
			STATUS current
			DESCRIPTION
				"This object indicates the AP branch group Cert file name."
			::= { hwBranchGroupEntry 6 }
		-- 1.3.6.1.4.1.2011.6.139.11.1.88.1.1.7
		hwBranchGroupServerCAFileName OBJECT-TYPE
			SYNTAX OCTET STRING (SIZE (0..63))
			MAX-ACCESS read-write
			STATUS current
			DESCRIPTION
				"This object indicates the AP branch group CA file name."
			::= { hwBranchGroupEntry 7 }
		-- 1.3.6.1.4.1.2011.6.139.11.1.88.1.1.8
		hwBranchGroupServerPSKType OBJECT-TYPE
			SYNTAX INTEGER
				{
				pem(1),
				pkcs12(2),
				der(3),
				na(4)
				}
			MAX-ACCESS read-write
			STATUS current
			DESCRIPTION
				"This object indicates the AP branch group PSK type."
			::= { hwBranchGroupEntry 8 }
		-- 1.3.6.1.4.1.2011.6.139.11.1.88.1.1.9
		hwBranchGroupServerPSKFileName OBJECT-TYPE
			SYNTAX OCTET STRING (SIZE (0..63))
			MAX-ACCESS read-write
			STATUS current
			DESCRIPTION
				"This object indicates the AP branch group PSK file name."
			::= { hwBranchGroupEntry 9 }	
		-- 1.3.6.1.4.1.2011.6.139.11.1.88.1.1.10
		hwBranchGroupServerPSKPassword OBJECT-TYPE
			SYNTAX OCTET STRING (SIZE (1..63))
			MAX-ACCESS read-write
			STATUS current
			DESCRIPTION
				"This object indicates the AP branch group PSK file password."
			::= { hwBranchGroupEntry 10 }		
		-- 1.3.6.1.4.1.2011.6.139.11.1.88.1.1.11
		hwBranchGroupFileLoadOper OBJECT-TYPE
			SYNTAX INTEGER
				{
				start(1),
				cancel(2)
				}
			MAX-ACCESS read-write
			STATUS current
			DESCRIPTION
				"This object indicates the AP branch group file load oper."
			::= { hwBranchGroupEntry 11 }
		-- 1.3.6.1.4.1.2011.6.139.11.1.88.1.1.12
		hwBranchGroupFileLoadPercent OBJECT-TYPE
			SYNTAX Integer32
			MAX-ACCESS read-only
			STATUS current
			DESCRIPTION
				"This object indicates the AP branch group file load percent."
			::= { hwBranchGroupEntry 12 }
		-- 1.3.6.1.4.1.2011.6.139.11.1.88.1.1.13
		hwBranchGroupFileLoadFailedAP OBJECT-TYPE
			SYNTAX Integer32
			MAX-ACCESS read-only
			STATUS current
			DESCRIPTION
				"This object indicates the AP branch group file failed AP."
			::= { hwBranchGroupEntry 13 }			
		-- 1.3.6.1.4.1.2011.6.139.11.1.88.1.1.14
		hwBranchGroupRowStatus OBJECT-TYPE
			SYNTAX RowStatus
			MAX-ACCESS read-write
			STATUS current
			DESCRIPTION
				"This object indicates the row status of this table. ROWSTATUS_CREATEANDFLOW and ROWSTATUS_DESTROY are commonly used."
			::= { hwBranchGroupEntry 14 }	
		-- 1.3.6.1.4.1.2011.6.139.11.1.88.2
		hwAPBranchGroupFileTable OBJECT-TYPE
			SYNTAX SEQUENCE OF HwAPBranchGroupFileEntry
			MAX-ACCESS not-accessible
			STATUS current
			DESCRIPTION
				"This table is used to get branh group file load status."
			::= { hwWlanBranchGroupConfig 2 }
		-- 1.3.6.1.4.1.2011.6.139.11.1.88.2.1
		hwAPBranchGroupFileEntry OBJECT-TYPE
			SYNTAX HwAPBranchGroupFileEntry
			MAX-ACCESS not-accessible
			STATUS current
			DESCRIPTION
				"The indexes of this table are hwBranchGroupName and hwWlanApMac."
			INDEX { hwBranchGroupName, hwWlanApMac }
			::= { hwAPBranchGroupFileTable 1 }
		HwAPBranchGroupFileEntry ::=
			SEQUENCE { 
				hwAPBranchGroupFileStatus
					INTEGER
			 }
		-- 1.3.6.1.4.1.2011.6.139.11.1.88.2.1.1
		hwAPBranchGroupFileStatus OBJECT-TYPE
			SYNTAX INTEGER
				{
				normal(1),
				unload(2),
				loading(3),
				loadfailcancel(4),
				loadfailwriteflashfail(5),
				loadfailfilenotexist(6),
				loadfailtimeout(7),
				loadfailexception(8),
				loadfileabnormalfile(9),
				na(10)
				}
			MAX-ACCESS read-only
			STATUS current
			DESCRIPTION
				"This object indicates the branch group file load status."
			::= { hwAPBranchGroupFileEntry 1 }

		-- 1.3.6.1.4.1.2011.6.139.11.1.89
		hwWlanNaviACManagement OBJECT IDENTIFIER ::= { hwWlanConfigObjects 89 }
		
		-- 1.3.6.1.4.1.2011.6.139.11.1.89.1
		hwWlanNaviACLocalTable OBJECT-TYPE
			SYNTAX SEQUENCE OF HwWlanNaviACLocalEntry
			MAX-ACCESS not-accessible
			STATUS current
			DESCRIPTION
				"Description."
			::= { hwWlanNaviACManagement 1 }
		
		-- 1.3.6.1.4.1.2011.6.139.11.1.89.1.1
		hwWlanNaviACLocalEntry OBJECT-TYPE
			SYNTAX HwWlanNaviACLocalEntry
			MAX-ACCESS not-accessible
			STATUS current
			DESCRIPTION
				"Description."
			INDEX { hwWlanNaviRemoteACID }
			::= { hwWlanNaviACLocalTable 1 }
		
		HwWlanNaviACLocalEntry ::=
			SEQUENCE { 
				hwWlanNaviRemoteACID
					Integer32,
				hwWlanNaviRemoteACIPv4
					IpAddress,
				hwWlanNaviRemoteACIPv6
					OCTET STRING,
				hwWlanNaviRemoteACDescription
					OCTET STRING,
				hwWlanNaviRemoteACState
					INTEGER,
				hwWlanNaviRemoteACMac
					MacAddress,
				hwWlanNaviRemoteACStaNumber
					Integer32,
				hwWlanNaviRemoteACRowStatus
					RowStatus
			 }

		-- 1.3.6.1.4.1.2011.6.139.11.1.89.1.1.1
		hwWlanNaviRemoteACID OBJECT-TYPE
			SYNTAX Integer32
			MAX-ACCESS not-accessible
			STATUS current
			DESCRIPTION
				"Description."
			::= { hwWlanNaviACLocalEntry 1 }
		
		-- 1.3.6.1.4.1.2011.6.139.11.1.89.1.1.2
		hwWlanNaviRemoteACIPv4 OBJECT-TYPE
			SYNTAX IpAddress
			MAX-ACCESS read-write
			STATUS current
			DESCRIPTION
				"Description."
			::= { hwWlanNaviACLocalEntry 2 }
		
		-- 1.3.6.1.4.1.2011.6.139.11.1.89.1.1.3
		hwWlanNaviRemoteACIPv6 OBJECT-TYPE
			SYNTAX OCTET STRING
			MAX-ACCESS read-write
			STATUS current
			DESCRIPTION
				"Description."
			::= { hwWlanNaviACLocalEntry 3 }
		
		-- 1.3.6.1.4.1.2011.6.139.11.1.89.1.1.4
		hwWlanNaviRemoteACDescription OBJECT-TYPE
			SYNTAX OCTET STRING (SIZE (0..31))
			MAX-ACCESS read-write
			STATUS current
			DESCRIPTION
				"Description."
			::= { hwWlanNaviACLocalEntry 4 }
		
		-- 1.3.6.1.4.1.2011.6.139.11.1.89.1.1.5
		hwWlanNaviRemoteACState OBJECT-TYPE
			SYNTAX INTEGER
				{
				fault(1),
				vmiss(2),
				normal(3)
				}
			MAX-ACCESS read-only
			STATUS current
			DESCRIPTION
				"Description."
			::= { hwWlanNaviACLocalEntry 5 }
		
		-- 1.3.6.1.4.1.2011.6.139.11.1.89.1.1.6
		hwWlanNaviRemoteACMac OBJECT-TYPE
			SYNTAX MacAddress
			MAX-ACCESS read-only
			STATUS current
			DESCRIPTION
				"Description."
			::= { hwWlanNaviACLocalEntry 6 }
		
		-- 1.3.6.1.4.1.2011.6.139.11.1.89.1.1.7
		hwWlanNaviRemoteACStaNumber OBJECT-TYPE
			SYNTAX Integer32
			MAX-ACCESS read-only
			STATUS current
			DESCRIPTION
				"Description."
			::= { hwWlanNaviACLocalEntry 7 }
		
		-- 1.3.6.1.4.1.2011.6.139.11.1.89.1.1.8
		hwWlanNaviRemoteACRowStatus OBJECT-TYPE
			SYNTAX RowStatus
			MAX-ACCESS read-write
			STATUS current
			DESCRIPTION
				"Description."
			::= { hwWlanNaviACLocalEntry 8 }
		-- 1.3.6.1.4.1.2011.6.139.11.1.89.2
		hwWlanNaviACRemoteManagement OBJECT IDENTIFIER ::= { hwWlanNaviACManagement 2 }
		
		-- 1.3.6.1.4.1.2011.6.139.11.1.89.2.1
		hwWlanNaviACRemoteEnable OBJECT-TYPE
			SYNTAX INTEGER
				{
				disable(1),
				enable(2)
				}
			MAX-ACCESS read-write
			STATUS current
			DESCRIPTION
				"Description."
			::= { hwWlanNaviACRemoteManagement 1 }
		
		-- 1.3.6.1.4.1.2011.6.139.11.1.89.3
		hwWlanNaviACRemoteTable OBJECT-TYPE
			SYNTAX SEQUENCE OF HwWlanNaviACRemoteEntry
			MAX-ACCESS not-accessible
			STATUS current
			DESCRIPTION
				"Description."
			::= { hwWlanNaviACManagement 3 }
		
		-- 1.3.6.1.4.1.2011.6.139.11.1.89.3.1
		hwWlanNaviACRemoteEntry OBJECT-TYPE
			SYNTAX HwWlanNaviACRemoteEntry
			MAX-ACCESS not-accessible
			STATUS current
			DESCRIPTION
				"Description."
			INDEX { hwWlanNaviLocalACID }
			::= { hwWlanNaviACRemoteTable 1 }
		
		HwWlanNaviACRemoteEntry ::=
			SEQUENCE { 
				hwWlanNaviLocalACID
					Integer32,
				hwWlanNaviLocalACIPv4
					IpAddress,
				hwWlanNaviLocalACIPv6
					OCTET STRING,
				hwWlanNaviLocalACDescription
					OCTET STRING,
				hwWlanNaviLocalACState
					INTEGER,
				hwWlanNaviLocalACMac
					MacAddress,
				hwWlanNaviLocalACStaNumber
					Integer32,
				hwWlanNaviLocalACRowStatus
					RowStatus
			 }

		-- 1.3.6.1.4.1.2011.6.139.11.1.89.3.1.1
		hwWlanNaviLocalACID OBJECT-TYPE
			SYNTAX Integer32
			MAX-ACCESS not-accessible
			STATUS current
			DESCRIPTION
				"Description."
			::= { hwWlanNaviACRemoteEntry 1 }
		
		-- 1.3.6.1.4.1.2011.6.139.11.1.89.3.1.2
		hwWlanNaviLocalACIPv4 OBJECT-TYPE
			SYNTAX IpAddress
			MAX-ACCESS read-write
			STATUS current
			DESCRIPTION
				"Description."
			::= { hwWlanNaviACRemoteEntry 2 }
		
		-- 1.3.6.1.4.1.2011.6.139.11.1.89.3.1.3
		hwWlanNaviLocalACIPv6 OBJECT-TYPE
			SYNTAX OCTET STRING
			MAX-ACCESS read-write
			STATUS current
			DESCRIPTION
				"Description."
			::= { hwWlanNaviACRemoteEntry 3 }
		
		-- 1.3.6.1.4.1.2011.6.139.11.1.89.3.1.4
		hwWlanNaviLocalACDescription OBJECT-TYPE
			SYNTAX OCTET STRING (SIZE (0..31))
			MAX-ACCESS read-write
			STATUS current
			DESCRIPTION
				"Description."
			::= { hwWlanNaviACRemoteEntry 4 }
		
		-- 1.3.6.1.4.1.2011.6.139.11.1.89.3.1.5
		hwWlanNaviLocalACState OBJECT-TYPE
			SYNTAX INTEGER
				{
				fault(1),
				vmiss(2),
				normal(3)
				}
			MAX-ACCESS read-only
			STATUS current
			DESCRIPTION
				"Description."
			::= { hwWlanNaviACRemoteEntry 5 }
		
		-- 1.3.6.1.4.1.2011.6.139.11.1.89.3.1.6
		hwWlanNaviLocalACMac OBJECT-TYPE
			SYNTAX MacAddress
			MAX-ACCESS read-only
			STATUS current
			DESCRIPTION
				"Description."
			::= { hwWlanNaviACRemoteEntry 6 }
		
		-- 1.3.6.1.4.1.2011.6.139.11.1.89.3.1.7
		hwWlanNaviLocalACStaNumber OBJECT-TYPE
			SYNTAX Integer32
			MAX-ACCESS read-only
			STATUS current
			DESCRIPTION
				"Description."
			::= { hwWlanNaviACRemoteEntry 7 }
		
		-- 1.3.6.1.4.1.2011.6.139.11.1.89.3.1.8
		hwWlanNaviLocalACRowStatus OBJECT-TYPE
			SYNTAX RowStatus
			MAX-ACCESS read-write
			STATUS current
			DESCRIPTION
				"Description."
			::= { hwWlanNaviACRemoteEntry 8 }
		-- 1.3.6.1.4.1.2011.6.139.11.1.89.4
		hwWlanNaviACVapTable OBJECT-TYPE
			SYNTAX SEQUENCE OF HwWlanNaviACVapEntry
			MAX-ACCESS not-accessible
			STATUS current
			DESCRIPTION
				"Description."
			::= { hwWlanNaviACManagement 4 }

		
		-- 1.3.6.1.4.1.2011.6.139.11.1.89.4.1
		hwWlanNaviACVapEntry OBJECT-TYPE
			SYNTAX HwWlanNaviACVapEntry
			MAX-ACCESS not-accessible
			STATUS current
			DESCRIPTION
				"Description."
			INDEX { hwWlanNaviLocalACID, hwWlanNaviVapACWlanId }
			::= { hwWlanNaviACVapTable 1 }

		
		HwWlanNaviACVapEntry ::=
			SEQUENCE { 
				hwWlanNaviVapACWlanId
					Unsigned32,
				hwWlanNaviVapProfileName
					OCTET STRING,
				hwWlanNaviVapRowStatus
					RowStatus
			 }

		-- 1.3.6.1.4.1.2011.6.139.11.1.89.4.1.1
		hwWlanNaviVapACWlanId OBJECT-TYPE
			SYNTAX Unsigned32 (1..16)
			MAX-ACCESS not-accessible
			STATUS current
			DESCRIPTION
				"Description."
			::= { hwWlanNaviACVapEntry 1 }

		
		-- 1.3.6.1.4.1.2011.6.139.11.1.89.4.1.2
		hwWlanNaviVapProfileName OBJECT-TYPE
			SYNTAX OCTET STRING (SIZE (1..35))
			MAX-ACCESS read-write
			STATUS current
			DESCRIPTION
				"Description."
			::= { hwWlanNaviACVapEntry 2 }

		
		-- 1.3.6.1.4.1.2011.6.139.11.1.89.4.1.3
		hwWlanNaviVapRowStatus OBJECT-TYPE
			SYNTAX RowStatus
			MAX-ACCESS read-write
			STATUS current
			DESCRIPTION
				"Description."
			::= { hwWlanNaviACVapEntry 3 }

                -- 1.3.6.1.4.1.2011.6.139.11.1.90
		hwHighwayObjects OBJECT IDENTIFIER ::= { hwWlanConfigObjects 90 }	
				
		-- 1.3.6.1.4.1.2011.6.139.11.1.90.1
		hwHighwayProfileTable OBJECT-TYPE
			SYNTAX SEQUENCE OF HwHighwayProfileEntry
			MAX-ACCESS not-accessible
			STATUS current
			DESCRIPTION
				"This table is used to configure highway profile information."
			::= { hwHighwayObjects 1 }		
	
		-- 1.3.6.1.4.1.2011.6.139.11.1.90.1.1
		hwHighwayProfileEntry OBJECT-TYPE
			SYNTAX HwHighwayProfileEntry
			MAX-ACCESS not-accessible
			STATUS current
			DESCRIPTION
				"The indexes of this table are hwHighwayProfileName."
			INDEX { hwHighwayProfileName }
			::= { hwHighwayProfileTable 1 }
		
		HwHighwayProfileEntry ::=
			SEQUENCE { 
				hwHighwayProfileName
					OCTET STRING,
				hwHighwayStationMinSpeed
				    Integer32,   	
				hwHighwayProfileRowStatus
					RowStatus
			}

		-- 1.3.6.1.4.1.2011.6.139.11.1.90.1.1.1
		hwHighwayProfileName OBJECT-TYPE  
			SYNTAX OCTET STRING (SIZE (1..35))
			MAX-ACCESS read-write
			STATUS current
			DESCRIPTION
				"This object indicates the Highway Profile name. It is the index of the table."
			::= { hwHighwayProfileEntry 1 }	
		
			-- 1.3.6.1.4.1.2011.6.139.11.1.90.1.1.2
		hwHighwayStationMinSpeed OBJECT-TYPE  
			SYNTAX Integer32 (4..216)
			MAX-ACCESS read-write
			STATUS current
			DESCRIPTION
				"This object indicates the minimum movement speed of a STA, in km/h. The default value is 36."
			::= { hwHighwayProfileEntry 2 }					
	
		-- 1.3.6.1.4.1.2011.6.139.11.1.90.1.1.10
		hwHighwayProfileRowStatus OBJECT-TYPE
			SYNTAX RowStatus
			MAX-ACCESS read-write
			STATUS current
			DESCRIPTION
				"This object indicates the row status of this table. ROWSTATUS_CREATEANDFLOW and ROWSTATUS_DESTROY are commonly used."
			::= { hwHighwayProfileEntry 10 }	
           
           
        -- 1.3.6.1.4.1.2011.6.139.11.1.90.2
		hwHighwayApMemberTable OBJECT-TYPE
			SYNTAX SEQUENCE OF HwHighwayApMemberEntry
			MAX-ACCESS not-accessible
			STATUS current
			DESCRIPTION
				"This table is used to set highway member."
			::= { hwHighwayObjects 2 }


		-- 1.3.6.1.4.1.2011.6.139.11.1.90.2.1   
		hwHighwayApMemberEntry OBJECT-TYPE
			SYNTAX HwHighwayApMemberEntry
			MAX-ACCESS not-accessible
			STATUS current
			DESCRIPTION
				"The indexes of this table are hwHighwayApMemberTable ."
			INDEX { hwHighwayProfileName , hwHighwayRadioType , hwHighwayDirection , hwHighwayMemberName }
			::= { hwHighwayApMemberTable 1 }
		
		HwHighwayApMemberEntry ::=
			SEQUENCE { 
				hwHighwayRadioType
					INTEGER,
				hwHighwayDirection
				    INTEGER,
                hwHighwayMemberType
                    INTEGER,
                hwHighwayMemberName
                    OCTET STRING,
                hwHighwayDeloyType
                    INTEGER,  
                hwHighwayNextMemberName
                    OCTET STRING,
                hwHighwayMinRoamDistance
                    Integer32,
                hwHighwayMaxRoamDistance
                    Integer32,
                hwHighwayMemberStatus
                    INTEGER,
                hwHighwayMemberRowStatus
                    RowStatus
			 }    
	    
	    -- 1.3.6.1.4.1.2011.6.139.11.1.90.2.1.1
		hwHighwayRadioType OBJECT-TYPE
			SYNTAX INTEGER
				{
				radio2G(1),
				radio5G(2)
                }
			MAX-ACCESS read-write
			STATUS current
			DESCRIPTION
				"This object indicates radiotype."
			::= { hwHighwayApMemberEntry 1 }

       	-- 1.3.6.1.4.1.2011.6.139.11.1.90.2.1.2
		hwHighwayDirection OBJECT-TYPE
			SYNTAX INTEGER
				{
				positive(1),
				reverse(2)
                }
			MAX-ACCESS read-write
			STATUS current
			DESCRIPTION
				"This object indicates direction."
			::= { hwHighwayApMemberEntry 2 }

        -- 1.3.6.1.4.1.2011.6.139.11.1.90.2.1.3
		hwHighwayMemberType OBJECT-TYPE
			SYNTAX INTEGER
				{
				start(1),
				middle(2),
				end(3)
                }
			MAX-ACCESS read-write
			STATUS current
			DESCRIPTION
				"This object indicates member type."
			::= { hwHighwayApMemberEntry 3 }
       
        -- 1.3.6.1.4.1.2011.6.139.11.1.90.2.1.4
		hwHighwayMemberName OBJECT-TYPE
			SYNTAX OCTET STRING (SIZE (1..63))
			MAX-ACCESS read-write
			STATUS current
			DESCRIPTION
				"This object indicates member name."
			::= { hwHighwayApMemberEntry 4 }


               
        -- 1.3.6.1.4.1.2011.6.139.11.1.90.2.1.5
		hwHighwayDeloyType OBJECT-TYPE
			SYNTAX INTEGER
                {
				b2b(1),
				f2f(2)
				}
			MAX-ACCESS read-write
			STATUS current
			DESCRIPTION
				"This object indicates member deloy type."
			::= { hwHighwayApMemberEntry 5 }
         
          -- 1.3.6.1.4.1.2011.6.139.11.1.90.2.1.6
		hwHighwayNextMemberName OBJECT-TYPE
			SYNTAX OCTET STRING (SIZE (0..63))
			MAX-ACCESS read-write
			STATUS current
			DESCRIPTION
				"This object indicates member name."
			::= { hwHighwayApMemberEntry 6 }


         -- 1.3.6.1.4.1.2011.6.139.11.1.90.2.1.7
		hwHighwayMinRoamDistance OBJECT-TYPE
			SYNTAX Integer32 (0..2000)
			MAX-ACCESS read-write
			STATUS current
			DESCRIPTION
				"This object indicates member min roam distance."
			::= { hwHighwayApMemberEntry 7 }

          -- 1.3.6.1.4.1.2011.6.139.11.1.90.2.1.8
       		hwHighwayMaxRoamDistance OBJECT-TYPE
			SYNTAX Integer32 (0..2000)
			MAX-ACCESS read-write
			STATUS current
			DESCRIPTION
				"This object indicates member max roam distance."
			::= { hwHighwayApMemberEntry 8 }

        -- 1.3.6.1.4.1.2011.6.139.11.1.90.2.1.9
		hwHighwayMemberStatus OBJECT-TYPE
			SYNTAX INTEGER
                {
				notExist(1),
				abnormal(2),
				normal(3),
				notConfig(4),
				other(5)
				}
			MAX-ACCESS read-only
			STATUS current
			DESCRIPTION
				"This object indicates member status."
			::= { hwHighwayApMemberEntry 9 }


		-- 1.3.6.1.4.1.2011.6.139.11.1.90.2.1.15
		hwHighwayMemberRowStatus OBJECT-TYPE
			SYNTAX RowStatus
			MAX-ACCESS read-write
			STATUS current
			DESCRIPTION
				"This object indicates the highway member status."
			::= { hwHighwayApMemberEntry 15 }
		
		-- 1.3.6.1.4.1.2011.6.139.11.1.91
		hwWmiProfileTable OBJECT-TYPE
			SYNTAX SEQUENCE OF HwWmiProfileEntry
			MAX-ACCESS not-accessible
			STATUS current
			DESCRIPTION
				"This table is used to get and set the wmi server profile attributes."
			::= { hwWlanConfigObjects 91 }
		
		-- 1.3.6.1.4.1.2011.6.139.11.1.91.1
		hwWmiProfileEntry OBJECT-TYPE
			SYNTAX HwWmiProfileEntry
			MAX-ACCESS not-accessible
			STATUS current
			DESCRIPTION
				"The indexes of this table is hwWmiServerProfileName."
			INDEX { hwWmiServerProfileName }
			::= { hwWmiProfileTable 1 }
		
		HwWmiProfileEntry ::=
			SEQUENCE { 
				hwWmiServerProfileName
					OCTET STRING,
				hwWmiServerIPv4
					IpAddress,
				hwWmiServerPort
					Unsigned32,
				hwWmiReportInterval
					Unsigned32,
				hwWmiKeepAliveInterval
					Unsigned32,
				hwWmiRetryConnectionInterval
					Unsigned32,
				hwWmiRetryConnectionCnt
					Unsigned32,
				hwWmiMaxPacketSize
					Unsigned32,
				hwWmiDeviceDataInterval
					Unsigned32,
				hwWmiSsidDataInterval
					Unsigned32,
				hwWmiRadioDataInterval
					Unsigned32,
				hwWmiInterfaceDataInterval
					Unsigned32,
				hwWmiTerminalDataInterval
					Unsigned32,
				hwWmiLogDataInterval
					Unsigned32,
				hwWmiLocationDataInterval
					Unsigned32,
				hwWmiSecurityDataInterval
					Unsigned32,
				hwWmiRowStatus
					RowStatus,
				hwWmiNeighborDataInterval
					Unsigned32,
				hwWmiCpcarDataInterval
					Unsigned32,
				hwWmiEmdiDataInterval
					Unsigned32,
				hwWmiApplicationStatisticsDataInterval
					Unsigned32,
				hwWmiLogModuleist
					OCTET STRING,
				hwWmiTerminalDhcpOptionDataInterval
					Unsigned32,
				hwWmiTerminalHttpUaDataInterval
					Unsigned32,
				hwWmiTerminalMdnsDataInterval
					Unsigned32
			 }

		-- 1.3.6.1.4.1.2011.6.139.11.1.91.1.1
		hwWmiServerProfileName OBJECT-TYPE
			SYNTAX OCTET STRING
			MAX-ACCESS not-accessible
			STATUS current
			DESCRIPTION
				"This object indicates the wmi server profile name."
			::= { hwWmiProfileEntry 1 }
		
		-- 1.3.6.1.4.1.2011.6.139.11.1.91.1.2
		hwWmiServerIPv4 OBJECT-TYPE
			SYNTAX IpAddress
			MAX-ACCESS read-write
			STATUS current
			DESCRIPTION
				"This object indicates the server IPv4 address attribute of this wmi server profile."
			::= { hwWmiProfileEntry 2 }
		
		-- 1.3.6.1.4.1.2011.6.139.11.1.91.1.3
		hwWmiServerPort OBJECT-TYPE
			SYNTAX Unsigned32 (0 | 1..65535)
			MAX-ACCESS read-write
			STATUS current
			DESCRIPTION
				"This object indicates the server port number attribute of this wmi server profile."
			::= { hwWmiProfileEntry 3 }
		
		-- 1.3.6.1.4.1.2011.6.139.11.1.91.1.4
		hwWmiReportInterval OBJECT-TYPE
			SYNTAX Unsigned32 (10..300)
			UNITS "s"
			MAX-ACCESS read-write
			STATUS current
			DESCRIPTION
				"This object indicates the report interval attribute of this wmi server profile. The default report interval is 60s."
			DEFVAL { 60 }
			::= { hwWmiProfileEntry 4 }
		
		-- 1.3.6.1.4.1.2011.6.139.11.1.91.1.5
		hwWmiKeepAliveInterval OBJECT-TYPE
			SYNTAX Unsigned32 (1..60)
			UNITS "min"
			MAX-ACCESS read-write
			STATUS current
			DESCRIPTION
				"This object indicates the keep alive interval attribute of this wmi server profile. The default report interval is 3min."
			DEFVAL { 3 }
			::= { hwWmiProfileEntry 5 }
		
		-- 1.3.6.1.4.1.2011.6.139.11.1.91.1.6
		hwWmiRetryConnectionInterval OBJECT-TYPE
			SYNTAX Unsigned32 (5..60)
			UNITS "min"
			MAX-ACCESS read-write
			STATUS current
			DESCRIPTION
				"This object indicates the retry connection interval attribute of this wmi server profile. The default report interval is 5min."
			DEFVAL { 5 }
			::= { hwWmiProfileEntry 6 }
		
		-- 1.3.6.1.4.1.2011.6.139.11.1.91.1.7
		hwWmiRetryConnectionCnt OBJECT-TYPE
			SYNTAX Unsigned32
			MAX-ACCESS read-write
			STATUS current
			DESCRIPTION
				"This object indicates the retry connection times attribute of this wmi server profile. The default retry times is 0, which means it will alway trys to reconnect."
			DEFVAL { 0 }
			::= { hwWmiProfileEntry 7 }
		
		-- 1.3.6.1.4.1.2011.6.139.11.1.91.1.8
		hwWmiMaxPacketSize OBJECT-TYPE
			SYNTAX Unsigned32 (4..256)
			UNITS "KB"
			MAX-ACCESS read-write
			STATUS current
			DESCRIPTION
				"This object indicates the max report packet size attribute of this wmi server profile. The default max report packet size is 5KB."
			DEFVAL { 5 }
			::= { hwWmiProfileEntry 8 }
		
		-- 1.3.6.1.4.1.2011.6.139.11.1.91.1.9
		hwWmiDeviceDataInterval OBJECT-TYPE
			SYNTAX Unsigned32 (0 | 5..1800)
			UNITS "s"
			MAX-ACCESS read-write
			STATUS current
			DESCRIPTION
				"This object indicates the device date collecting interval attribute of this wmi server profile. The default collecting interval is 10s."
			DEFVAL { 10 }
			::= { hwWmiProfileEntry 9 }
		
		-- 1.3.6.1.4.1.2011.6.139.11.1.91.1.10
		hwWmiSsidDataInterval OBJECT-TYPE
			SYNTAX Unsigned32 (0 | 5..1800)
			UNITS "s"
			MAX-ACCESS read-write
			STATUS current
			DESCRIPTION
				"This object indicates the ssid date collecting interval attribute of this wmi server profile. The default collecting interval is 60s."
			DEFVAL { 60 }
			::= { hwWmiProfileEntry 10 }
		
		-- 1.3.6.1.4.1.2011.6.139.11.1.91.1.11
		hwWmiRadioDataInterval OBJECT-TYPE
			SYNTAX Unsigned32 (0 | 5..1800)
			UNITS "s"
			MAX-ACCESS read-write
			STATUS current
			DESCRIPTION
				"This object indicates the radio date collecting interval attribute of this wmi server profile. The default collecting interval is 10s."
			DEFVAL { 10 }
			::= { hwWmiProfileEntry 11 }
		
		-- 1.3.6.1.4.1.2011.6.139.11.1.91.1.12
		hwWmiInterfaceDataInterval OBJECT-TYPE
			SYNTAX Unsigned32 (0 | 5..1800)
			UNITS "s"
			MAX-ACCESS read-write
			STATUS current
			DESCRIPTION
				"This object indicates the interface date collecting interval attribute of this wmi server profile. The default collecting interval is 60s."
			DEFVAL { 60 }
			::= { hwWmiProfileEntry 12 }
		
		-- 1.3.6.1.4.1.2011.6.139.11.1.91.1.13
		hwWmiTerminalDataInterval OBJECT-TYPE
			SYNTAX Unsigned32 (0 | 5..1800)
			UNITS "s"
			MAX-ACCESS read-write
			STATUS current
			DESCRIPTION
				"This object indicates the terminal date collecting interval attribute of this wmi server profile. The default collecting interval is 10s."
			DEFVAL { 10 }
			::= { hwWmiProfileEntry 13 }
		
		-- 1.3.6.1.4.1.2011.6.139.11.1.91.1.14
		hwWmiLogDataInterval OBJECT-TYPE
			SYNTAX Unsigned32 (0 | 5..1800)
			UNITS "s"
			MAX-ACCESS read-write
			STATUS current
			DESCRIPTION
				"This object indicates the log date collecting interval attribute of this wmi server profile. The default collecting interval is 300s."
			DEFVAL { 300 }
			::= { hwWmiProfileEntry 14 }
		
		-- 1.3.6.1.4.1.2011.6.139.11.1.91.1.15
		hwWmiLocationDataInterval OBJECT-TYPE
			SYNTAX Unsigned32 (0 | 5..1800)
			UNITS "s"
			MAX-ACCESS read-write
			STATUS current
			DESCRIPTION
				"This object indicates the location date collecting interval attribute of this wmi server profile. The default collecting interval is 60s."
			DEFVAL { 60 }
			::= { hwWmiProfileEntry 15 }
		
		-- 1.3.6.1.4.1.2011.6.139.11.1.91.1.16
		hwWmiSecurityDataInterval OBJECT-TYPE
			SYNTAX Unsigned32 (0 | 5..1800)
			UNITS "s"
			MAX-ACCESS read-write
			STATUS current
			DESCRIPTION
				"This object indicates the wids date collecting interval attribute of this wmi server profile. The default collecting interval is 300s."
			DEFVAL { 300 }
			::= { hwWmiProfileEntry 16 }
		
		-- 1.3.6.1.4.1.2011.6.139.11.1.91.1.17
		hwWmiRowStatus OBJECT-TYPE
			SYNTAX RowStatus
			MAX-ACCESS read-write
			STATUS current
			DESCRIPTION
				"This object indicates the row status of this table. ROWSTATUS_CREATEANDFLOW and ROWSTATUS_DESTROY are commonly used."
			::= { hwWmiProfileEntry 17 }
		
		-- 1.3.6.1.4.1.2011.6.139.11.1.91.1.18
		hwWmiNeighborDataInterval OBJECT-TYPE
			SYNTAX Unsigned32 (0 | 5..1800)
			UNITS "s"
			MAX-ACCESS read-write
			STATUS current
			DESCRIPTION
				"This object indicates the neighbor date collecting interval attribute of this wmi server profile. The default collecting interval is 60s."
			DEFVAL { 60 }
			::= { hwWmiProfileEntry 18 }
		-- 1.3.6.1.4.1.2011.6.139.11.1.91.1.19
		hwWmiCpcarDataInterval OBJECT-TYPE
			SYNTAX Unsigned32 (0 | 5..1800)
			UNITS "s"
			MAX-ACCESS read-write
			STATUS current
			DESCRIPTION
				"This object indicates the CP-CAR date collecting interval attribute of this wmi server profile. The default collecting interval is 300s."
			DEFVAL { 300 }
			::= { hwWmiProfileEntry 19 }
		-- 1.3.6.1.4.1.2011.6.139.11.1.91.1.20
		hwWmiEmdiDataInterval OBJECT-TYPE
			SYNTAX Unsigned32 (0 | 5..1800)
			UNITS "s"
			MAX-ACCESS read-write
			STATUS current
			DESCRIPTION
				"This object indicates the enhanced media delivery index date collecting interval attribute of this wmi server profile. The default collecting interval is 10s."
			DEFVAL { 10 }
			::= { hwWmiProfileEntry 20 }
		
		-- 1.3.6.1.4.1.2011.6.139.11.1.91.1.21
		hwWmiApplicationStatisticsDataInterval OBJECT-TYPE
			SYNTAX Unsigned32 (0 | 5..1800)
			UNITS "s"
			MAX-ACCESS read-write
			STATUS current
			DESCRIPTION
				"Configure the WMI application statistics data report interval, the default collecting interval is 300s"
			DEFVAL { 300 }
			::= { hwWmiProfileEntry 21 }
		-- 1.3.6.1.4.1.2011.6.139.11.1.91.1.22
		hwWmiLogModuleist OBJECT-TYPE
			SYNTAX OCTET STRING
			MAX-ACCESS read-write
			STATUS current
			DESCRIPTION
				"This object indicates the log module list. For example, ff5a0000,ff630000,ffd10000. Setting this object to 0 indicates the deletion operation."
			::= { hwWmiProfileEntry 22 }
			
				-- 1.3.6.1.4.1.2011.6.139.11.1.91.1.23
		hwWmiTerminalDhcpOptionDataInterval OBJECT-TYPE
			SYNTAX Unsigned32 (0 | 5..1800)
			UNITS "s"
			MAX-ACCESS read-write
			STATUS current
			DESCRIPTION
				"This object indicates the terminal Dhcp Option date collecting interval attribute of this wmi server profile. The default collecting interval is 300s."
			DEFVAL { 300 }	
			::= { hwWmiProfileEntry 23 }
		
		-- 1.3.6.1.4.1.2011.6.139.11.1.91.1.24
		hwWmiTerminalHttpUaDataInterval OBJECT-TYPE
			SYNTAX Unsigned32 (0 | 5..1800)
			UNITS "s"
			MAX-ACCESS read-write
			STATUS current
			DESCRIPTION
				"This object indicates the terminal Http Ua date collecting interval attribute of this wmi server profile. The default collecting interval is 300s."
			DEFVAL { 300 }	
			::= { hwWmiProfileEntry 24 }
		
		-- 1.3.6.1.4.1.2011.6.139.11.1.91.1.25
		hwWmiTerminalMdnsDataInterval OBJECT-TYPE
			SYNTAX Unsigned32 (0 | 5..1800)
			UNITS "s"
			MAX-ACCESS read-write
			STATUS current
			DESCRIPTION
				"This object indicates the terminal Mdns date collecting interval attribute of this wmi server profile. The default collecting interval is 300s."
			DEFVAL { 300 }	
			::= { hwWmiProfileEntry 25 }

		-- 1.3.6.1.4.1.2011.6.139.11.1.92
		hwApSystemWmiProfileTable OBJECT-TYPE
			SYNTAX SEQUENCE OF HwApSystemWmiProfileEntry
			MAX-ACCESS not-accessible
			STATUS current
			DESCRIPTION
				"This table is used to bind the wmi server to the ap system profile by indexed and get binding status."
			::= { hwWlanConfigObjects 92 }
		
		-- 1.3.6.1.4.1.2011.6.139.11.1.92.1
		hwApSystemWmiProfileEntry OBJECT-TYPE
			SYNTAX HwApSystemWmiProfileEntry
			MAX-ACCESS not-accessible
			STATUS current
			DESCRIPTION
				"The indexes of this table is hwAPSystemProfName and hwApSystemWmiIndex."
			INDEX { hwApSystemProfName, hwApSystemWmiIndex }
			::= { hwApSystemWmiProfileTable 1 }
		
		HwApSystemWmiProfileEntry ::=
			SEQUENCE { 
				hwApSystemWmiIndex
					Unsigned32,
				hwApSystemWmiProfile
					OCTET STRING,
				hwApSystemWmiRowStatus
					RowStatus
			 }

		-- 1.3.6.1.4.1.2011.6.139.11.1.92.1.1
		hwApSystemWmiIndex OBJECT-TYPE
			SYNTAX Unsigned32
			MAX-ACCESS not-accessible
			STATUS current
			DESCRIPTION
				"This object indicates the channel index which the wmi server will bind to."
			::= { hwApSystemWmiProfileEntry 1 }
		
		-- 1.3.6.1.4.1.2011.6.139.11.1.92.1.2
		hwApSystemWmiProfile OBJECT-TYPE
			SYNTAX OCTET STRING (SIZE (0..35))
			MAX-ACCESS read-write
			STATUS current
			DESCRIPTION
				"This object indicates the wmi server which will bind to the ap system profile."
			::= { hwApSystemWmiProfileEntry 2 }
		
		-- 1.3.6.1.4.1.2011.6.139.11.1.92.1.3
		hwApSystemWmiRowStatus OBJECT-TYPE
			SYNTAX RowStatus
			MAX-ACCESS read-write
			STATUS current
			DESCRIPTION
				"This object indicates the row status of this table. ROWSTATUS_CREATEANDFLOW and ROWSTATUS_DESTROY are commonly used."
			::= { hwApSystemWmiProfileEntry 3 }
		
		-- 1.3.6.1.4.1.2011.6.139.11.1.93
		hwSysWmiConfigTable OBJECT-TYPE
			SYNTAX SEQUENCE OF HwSysWmiConfigEntry
			MAX-ACCESS not-accessible
			STATUS current
			DESCRIPTION
				"Description."
			::= { hwWlanConfigObjects 93 }
		
		-- 1.3.6.1.4.1.2011.6.139.11.1.93.1
		hwSysWmiConfigEntry OBJECT-TYPE
			SYNTAX HwSysWmiConfigEntry
			MAX-ACCESS not-accessible
			STATUS current
			DESCRIPTION
				"Description."
			INDEX { hwSysWmiIndex }
			::= { hwSysWmiConfigTable 1 }
		
		HwSysWmiConfigEntry ::=
			SEQUENCE { 
				hwSysWmiIndex
					Unsigned32,
				hwSysWmiServerIPv4
					IpAddress,
				hwSysWmiServerPort
					Unsigned32,
				hwSysWmiReportInterval
					Unsigned32,
				hwSysWmiKeepAliveInterval
					Unsigned32,
				hwSysWmiRetryConnectionInterval
					Unsigned32,
				hwSysWmiRetryConnectionCnt
					Unsigned32,
				hwSysWmiMaxPacketSize
					Unsigned32,
				hwSysWmiDeviceDataInterval
					Unsigned32,
				hwSysWmiSsidDataInterval
					Unsigned32,
				hwSysWmiRadioDataInterval
					Unsigned32,
				hwSysWmiInterfaceDataInterval
					Unsigned32,
				hwSysWmiTerminalDataInterval
					Unsigned32,
				hwSysWmiLogDataInterval
					Unsigned32,
				hwSysWmiLocationDataInterval
					Unsigned32,
				hwSysWmiSecurityDataInterval
					Unsigned32,
				hwSysWmiRoamDataInterval
					Unsigned32,
				hwSysWmiApplicationStatisticsDataInterval
					Unsigned32,
				hwSysWmiEmdiDataInterval
					Unsigned32,
				hwSysWmiCpcarDataInterval
					Unsigned32,
				hwSysWmiNeighborDataInterval
					Unsigned32,
				hwSysWmiLogMIDList
					OCTET STRING,
				hwSysWmiTerminalDhcpOptionDataInterval
					Unsigned32,
				hwSysWmiTerminalHttpUaDataInterval
					Unsigned32,
				hwSysWmiTerminalMdnsDataInterval
					Unsigned32,
				hwSysWmiMeshDataInterval
					Unsigned32
			 }

		-- 1.3.6.1.4.1.2011.6.139.11.1.93.1.1
		hwSysWmiIndex OBJECT-TYPE
			SYNTAX Unsigned32
			MAX-ACCESS not-accessible
			STATUS current
			DESCRIPTION
				"Description."
			::= { hwSysWmiConfigEntry 1 }
		
		-- 1.3.6.1.4.1.2011.6.139.11.1.93.1.2
		hwSysWmiServerIPv4 OBJECT-TYPE
			SYNTAX IpAddress
			MAX-ACCESS read-write
			STATUS current
			DESCRIPTION
				"Description."
			::= { hwSysWmiConfigEntry 2 }
		
		-- 1.3.6.1.4.1.2011.6.139.11.1.93.1.3
		hwSysWmiServerPort OBJECT-TYPE
			SYNTAX Unsigned32 (0 | 1..65535)
			MAX-ACCESS read-write
			STATUS current
			DESCRIPTION
				"Description."
			::= { hwSysWmiConfigEntry 3 }
		
		-- 1.3.6.1.4.1.2011.6.139.11.1.93.1.4
		hwSysWmiReportInterval OBJECT-TYPE
			SYNTAX Unsigned32 (10..300)
			UNITS "s"
			MAX-ACCESS read-write
			STATUS current
			DESCRIPTION
				"Description."
			DEFVAL { 60 }
			::= { hwSysWmiConfigEntry 4 }
		
		-- 1.3.6.1.4.1.2011.6.139.11.1.93.1.5
		hwSysWmiKeepAliveInterval OBJECT-TYPE
			SYNTAX Unsigned32 (1..60)
			UNITS "min"
			MAX-ACCESS read-write
			STATUS current
			DESCRIPTION
				"Description."
			DEFVAL { 3 }
			::= { hwSysWmiConfigEntry 5 }
		
		-- 1.3.6.1.4.1.2011.6.139.11.1.93.1.6
		hwSysWmiRetryConnectionInterval OBJECT-TYPE
			SYNTAX Unsigned32 (5..60)
			UNITS "min"
			MAX-ACCESS read-write
			STATUS current
			DESCRIPTION
				"Description."
			DEFVAL { 5 }
			::= { hwSysWmiConfigEntry 6 }
		
		-- 1.3.6.1.4.1.2011.6.139.11.1.93.1.7
		hwSysWmiRetryConnectionCnt OBJECT-TYPE
			SYNTAX Unsigned32
			MAX-ACCESS read-write
			STATUS current
			DESCRIPTION
				"Description."
			DEFVAL { 0 }
			::= { hwSysWmiConfigEntry 7 }
		
		-- 1.3.6.1.4.1.2011.6.139.11.1.93.1.8
		hwSysWmiMaxPacketSize OBJECT-TYPE
			SYNTAX Unsigned32 (4..256)
			UNITS "KB"
			MAX-ACCESS read-write
			STATUS current
			DESCRIPTION
				"Description."
			DEFVAL { 5 }
			::= { hwSysWmiConfigEntry 8 }
		
		-- 1.3.6.1.4.1.2011.6.139.11.1.93.1.9
		hwSysWmiDeviceDataInterval OBJECT-TYPE
			SYNTAX Unsigned32 (0 | 5..1800)
			UNITS "s"
			MAX-ACCESS read-write
			STATUS current
			DESCRIPTION
				"Description."
			DEFVAL { 10 }
			::= { hwSysWmiConfigEntry 9 }
		
		-- 1.3.6.1.4.1.2011.6.139.11.1.93.1.10
		hwSysWmiSsidDataInterval OBJECT-TYPE
			SYNTAX Unsigned32 (0 | 5..1800)
			UNITS "s"
			MAX-ACCESS read-write
			STATUS current
			DESCRIPTION
				"Description."
			DEFVAL { 60 }
			::= { hwSysWmiConfigEntry 10 }
		
		-- 1.3.6.1.4.1.2011.6.139.11.1.93.1.11
		hwSysWmiRadioDataInterval OBJECT-TYPE
			SYNTAX Unsigned32 (0 | 5..1800)
			UNITS "s"
			MAX-ACCESS read-write
			STATUS current
			DESCRIPTION
				"Description."
			DEFVAL { 10 }
			::= { hwSysWmiConfigEntry 11 }
		
		-- 1.3.6.1.4.1.2011.6.139.11.1.93.1.12
		hwSysWmiInterfaceDataInterval OBJECT-TYPE
			SYNTAX Unsigned32 (0 | 5..1800)
			UNITS "s"
			MAX-ACCESS read-write
			STATUS current
			DESCRIPTION
				"Description."
			DEFVAL { 60 }
			::= { hwSysWmiConfigEntry 12 }
		
		-- 1.3.6.1.4.1.2011.6.139.11.1.93.1.13
		hwSysWmiTerminalDataInterval OBJECT-TYPE
			SYNTAX Unsigned32 (0 | 5..1800)
			UNITS "s"
			MAX-ACCESS read-write
			STATUS current
			DESCRIPTION
				"Description."
			DEFVAL { 10 }
			::= { hwSysWmiConfigEntry 13 }
		
		-- 1.3.6.1.4.1.2011.6.139.11.1.93.1.14
		hwSysWmiLogDataInterval OBJECT-TYPE
			SYNTAX Unsigned32 (0 | 5..1800)
			UNITS "s"
			MAX-ACCESS read-write
			STATUS current
			DESCRIPTION
				"Description."
			DEFVAL { 300 }
			::= { hwSysWmiConfigEntry 14 }
		
		-- 1.3.6.1.4.1.2011.6.139.11.1.93.1.15
		hwSysWmiLocationDataInterval OBJECT-TYPE
			SYNTAX Unsigned32 (0 | 5..1800)
			UNITS "s"
			MAX-ACCESS read-write
			STATUS current
			DESCRIPTION
				"Description."
			DEFVAL { 60 }
			::= { hwSysWmiConfigEntry 15 }
		
		-- 1.3.6.1.4.1.2011.6.139.11.1.93.1.16
		hwSysWmiSecurityDataInterval OBJECT-TYPE
			SYNTAX Unsigned32 (0 | 5..1800)
			UNITS "s"
			MAX-ACCESS read-write
			STATUS current
			DESCRIPTION
				"Description."
			DEFVAL { 300 }
			::= { hwSysWmiConfigEntry 16 }
		
		-- 1.3.6.1.4.1.2011.6.139.11.1.93.1.17
		hwSysWmiRoamDataInterval OBJECT-TYPE
			SYNTAX Unsigned32 (0 | 5..1800)
			UNITS "s"
			MAX-ACCESS read-write
			STATUS current
			DESCRIPTION
				"Description."
			DEFVAL { 300 }
			::= { hwSysWmiConfigEntry 17 }
		
		-- 1.3.6.1.4.1.2011.6.139.11.1.93.1.18
		hwSysWmiApplicationStatisticsDataInterval OBJECT-TYPE
			SYNTAX Unsigned32 (0 | 5..1800)
			UNITS "s"
			MAX-ACCESS read-write
			STATUS current
			DESCRIPTION
				"Description."
			DEFVAL { 300 }
			::= { hwSysWmiConfigEntry 18 }
		
		-- 1.3.6.1.4.1.2011.6.139.11.1.93.1.19
		hwSysWmiEmdiDataInterval OBJECT-TYPE
			SYNTAX Unsigned32 (0 | 5..1800)
			UNITS "s"
			MAX-ACCESS read-write
			STATUS current
			DESCRIPTION
				"Description."
			DEFVAL { 10 }
			::= { hwSysWmiConfigEntry 19 }
		
		-- 1.3.6.1.4.1.2011.6.139.11.1.93.1.20
		hwSysWmiCpcarDataInterval OBJECT-TYPE
			SYNTAX Unsigned32 (0 | 5..1800)
			UNITS "s"
			MAX-ACCESS read-write
			STATUS current
			DESCRIPTION
				"Description."
			DEFVAL { 300 }
			::= { hwSysWmiConfigEntry 20 }
		
		-- 1.3.6.1.4.1.2011.6.139.11.1.93.1.21
		hwSysWmiNeighborDataInterval OBJECT-TYPE
			SYNTAX Unsigned32 (0 | 5..1800)
			UNITS "s"
			MAX-ACCESS read-write
			STATUS current
			DESCRIPTION
				"Description."
			DEFVAL { 60 }
			::= { hwSysWmiConfigEntry 21 }
		
		-- 1.3.6.1.4.1.2011.6.139.11.1.93.1.22
		hwSysWmiLogMIDList OBJECT-TYPE
			SYNTAX OCTET STRING
			MAX-ACCESS read-write
			STATUS current
			DESCRIPTION
				"Description."
			::= { hwSysWmiConfigEntry 22 }
		
		-- 1.3.6.1.4.1.2011.6.139.11.1.93.1.23
		hwSysWmiTerminalDhcpOptionDataInterval OBJECT-TYPE
			SYNTAX Unsigned32 (0 | 5..1800)
			UNITS "s"
			MAX-ACCESS read-write
			STATUS current
			DESCRIPTION
				"Description."
			DEFVAL { 300 }
			::= { hwSysWmiConfigEntry 23 }
		
		-- 1.3.6.1.4.1.2011.6.139.11.1.93.1.24
		hwSysWmiTerminalHttpUaDataInterval OBJECT-TYPE
			SYNTAX Unsigned32 (0 | 5..1800)
			UNITS "s"
			MAX-ACCESS read-write
			STATUS current
			DESCRIPTION
				"Description."
			DEFVAL { 300 }
			::= { hwSysWmiConfigEntry 24 }
		
		-- 1.3.6.1.4.1.2011.6.139.11.1.93.1.25
		hwSysWmiTerminalMdnsDataInterval OBJECT-TYPE
			SYNTAX Unsigned32 (0 | 5..1800)
			UNITS "s"
			MAX-ACCESS read-write
			STATUS current
			DESCRIPTION
				"Description."
			DEFVAL { 300 }
			::= { hwSysWmiConfigEntry 25 }
			
		 -- 1.3.6.1.4.1.2011.6.139.11.1.93.1.26
                hwSysWmiMeshDataInterval OBJECT-TYPE
                        SYNTAX Unsigned32 (0 | 5..1800)
                        UNITS "s"
                        MAX-ACCESS read-write
                        STATUS current
                        DESCRIPTION
                                "Description."
                        DEFVAL { 300 }
                        ::= { hwSysWmiConfigEntry 26 }
			
		-- 1.3.6.1.4.1.2011.6.139.11.1.94
		hwWlanLicenseCentralizedTable OBJECT-TYPE
			SYNTAX SEQUENCE OF HwWlanLicenseCentralizedEntry
			MAX-ACCESS not-accessible
			STATUS current
			DESCRIPTION
				"This table is used to get the information of license pool."
			::= { hwWlanConfigObjects 94 }
		
		-- 1.3.6.1.4.1.2011.6.139.11.1.94.1
		hwWlanLicenseCentralizedEntry OBJECT-TYPE
			SYNTAX HwWlanLicenseCentralizedEntry
			MAX-ACCESS not-accessible
			STATUS current
			DESCRIPTION
				"The indexes of this table is hwWlanLicenseClientMac."
			INDEX { hwWlanLicenseClientMac }
			::= { hwWlanLicenseCentralizedTable 1 }
		
		HwWlanLicenseCentralizedEntry ::=
			SEQUENCE { 
				hwWlanLicenseClientMac
					MacAddress,
				hwWlanLicenseClientIPv4Addr
					IpAddress,
				hwWlanLicenseClientIPv6Addr
					OCTET STRING,
				hwWlanLicenseClientRole
					INTEGER,
				hwWlanLicenseClientState
					INTEGER,
				hwWlanLicenseClientLocalLicense
					Unsigned32,
				hwWlanLicenseClientLicenseRemain
					Unsigned32,
				hwWlanLicenseClientAllocedLicense
					Unsigned32
			 }

		-- 1.3.6.1.4.1.2011.6.139.11.1.94.1.1
		hwWlanLicenseClientMac OBJECT-TYPE
			SYNTAX MacAddress
			MAX-ACCESS not-accessible
			STATUS current
			DESCRIPTION
				"This object indicates the mac-address of license centralized client."
			::= { hwWlanLicenseCentralizedEntry 1 }
		
		-- 1.3.6.1.4.1.2011.6.139.11.1.94.1.2
		hwWlanLicenseClientIPv4Addr OBJECT-TYPE
			SYNTAX IpAddress
			MAX-ACCESS read-only
			STATUS current
			DESCRIPTION
				"This object indicates the ipv4 address of license client."
			::= { hwWlanLicenseCentralizedEntry 2 }
		
		-- 1.3.6.1.4.1.2011.6.139.11.1.94.1.3
		hwWlanLicenseClientIPv6Addr OBJECT-TYPE
			SYNTAX OCTET STRING
			MAX-ACCESS read-only
			STATUS current
			DESCRIPTION
				"This object indicates the ipv6 address of license client."
			::= { hwWlanLicenseCentralizedEntry 3 }
		
		-- 1.3.6.1.4.1.2011.6.139.11.1.94.1.4
		hwWlanLicenseClientRole OBJECT-TYPE
			SYNTAX INTEGER
				{
				server(1),
				serverBackup(2),
				client(3)
				}
			MAX-ACCESS read-only
			STATUS current
			DESCRIPTION
				"This object indicates the current role of license client."
			::= { hwWlanLicenseCentralizedEntry 4 }
		
		-- 1.3.6.1.4.1.2011.6.139.11.1.94.1.5
		hwWlanLicenseClientState OBJECT-TYPE
			SYNTAX INTEGER
				{
				fault(1),
				normal(2)
				}
			MAX-ACCESS read-only
			STATUS current
			DESCRIPTION
				"This object indicates the state of license client."
			::= { hwWlanLicenseCentralizedEntry 5 }
		
		-- 1.3.6.1.4.1.2011.6.139.11.1.94.1.6
		hwWlanLicenseClientLocalLicense OBJECT-TYPE
			SYNTAX Unsigned32
			MAX-ACCESS read-only
			STATUS current
			DESCRIPTION
				"This object indicates the number of local license in license client."
			::= { hwWlanLicenseCentralizedEntry 6 }
		
		-- 1.3.6.1.4.1.2011.6.139.11.1.94.1.7
		hwWlanLicenseClientLicenseRemain OBJECT-TYPE
			SYNTAX Unsigned32
			MAX-ACCESS read-only
			STATUS current
			DESCRIPTION
				"This object indicates the remain days of license client."
			::= { hwWlanLicenseCentralizedEntry 7 }
		
		-- 1.3.6.1.4.1.2011.6.139.11.1.94.1.8
		hwWlanLicenseClientAllocedLicense OBJECT-TYPE
			SYNTAX Unsigned32
			MAX-ACCESS read-only
			STATUS current
			DESCRIPTION
				"This object indicates the alloced license of license client."
			::= { hwWlanLicenseCentralizedEntry 8 }
		
		-- 1.3.6.1.4.1.2011.6.139.11.1.95
		hwApSysBCMCSuppressionTable OBJECT-TYPE
			SYNTAX SEQUENCE OF HwApSysBCMCSuppressionEntry
			MAX-ACCESS not-accessible
			STATUS current
			DESCRIPTION
				"This table is used to configure ap broadcast and multicast suppression information."
			::= { hwWlanConfigObjects 95 }
		
		-- 1.3.6.1.4.1.2011.6.139.11.1.95.1
		hwApSysBCMCSuppressionEntry OBJECT-TYPE
			SYNTAX HwApSysBCMCSuppressionEntry
			MAX-ACCESS not-accessible
			STATUS current
			DESCRIPTION
				"The indexes of this table are hwApSystemProfName, hwApSysBCMCSuppressionPktType."
			INDEX { hwApSystemProfName, hwApSysBCMCSuppressionPktType }
			::= { hwApSysBCMCSuppressionTable 1 }
		
		HwApSysBCMCSuppressionEntry ::=
			SEQUENCE { 
				hwApSysBCMCSuppressionPktType
					INTEGER,
				hwApSysBCMCSuppressionSwitch
					INTEGER,
				hwApSysBCMCSuppressionThreshold
					Unsigned32,
				hwApSysBCMCSuppressionRowStatus
					RowStatus
			 }

		-- 1.3.6.1.4.1.2011.6.139.11.1.95.1.1
		hwApSysBCMCSuppressionPktType OBJECT-TYPE
			SYNTAX INTEGER
				{
                		otherBroadcast(1),
				arp(2),
                		igmp(3),
				nd(4),
				dhcp(5),
				dhcpv6(6),
				mdns(7),
				otherMulticast(8)
				}
			MAX-ACCESS not-accessible
			STATUS current
			DESCRIPTION
				"This object indicates the packet type of the ap broadcast and multicast suppression function. This parameter has no default value."
			::= { hwApSysBCMCSuppressionEntry 1 }
		
		-- 1.3.6.1.4.1.2011.6.139.11.1.95.1.2
		hwApSysBCMCSuppressionSwitch OBJECT-TYPE
			SYNTAX INTEGER
				{
				disable(1),
				enable(2)
				}
			MAX-ACCESS read-write
			STATUS current
			DESCRIPTION
				"This object indicates the status of the ap broadcast and multicast suppression function. The default value is 2."
			::= { hwApSysBCMCSuppressionEntry 2 }
		
		-- 1.3.6.1.4.1.2011.6.139.11.1.95.1.3
		hwApSysBCMCSuppressionThreshold OBJECT-TYPE
			SYNTAX Unsigned32 (0..1024)
			MAX-ACCESS read-write
			STATUS current
			DESCRIPTION
				"This object indicates the broadcast and multicast suppression threshold for the AP. The default value is 256 pps, otherBroadcast and otherMulticast is 16pps."
			::= { hwApSysBCMCSuppressionEntry 3 }
		
		-- 1.3.6.1.4.1.2011.6.139.11.1.95.1.4
		hwApSysBCMCSuppressionRowStatus OBJECT-TYPE
			SYNTAX RowStatus
			MAX-ACCESS read-create
			STATUS current
			DESCRIPTION
				"This object indicates the row status of this table. ROWSTATUS_CREATEANDFLOW and ROWSTATUS_DESTROY are commonly used."
			::= { hwApSysBCMCSuppressionEntry 4 }
			
		-- 1.3.6.1.4.1.2011.6.139.11.1.96
		hwVAPProfileAntiAttackTable OBJECT-TYPE
			SYNTAX SEQUENCE OF HwVAPProfileAntiAttackEntry
			MAX-ACCESS not-accessible
			STATUS current
			DESCRIPTION
				"This table is used to configure vap anti-attack information."
			::= { hwWlanConfigObjects 96 }
		
		-- 1.3.6.1.4.1.2011.6.139.11.1.96.1
		hwVAPProfileAntiAttackEntry OBJECT-TYPE
			SYNTAX HwVAPProfileAntiAttackEntry
			MAX-ACCESS not-accessible
			STATUS current
			DESCRIPTION
				"The indexes of this table are hwVapProfileName, hwVAPProfileAntiAttackPacketType"
			INDEX { hwVapProfileName, hwVAPProfileAntiAttackPacketType }
			::= { hwVAPProfileAntiAttackTable 1 }
		
		HwVAPProfileAntiAttackEntry ::=
			SEQUENCE { 
				hwVAPProfileAntiAttackPacketType
					INTEGER,
				hwVAPProfileAntiAttackSwitch
					INTEGER,
				hwVAPProfileAntiAttackStaRateThreshold
					Unsigned32,
				hwVAPProfileAntiAttackBlacklistSwitch
					INTEGER,
				hwVAPProfileAntiAttackRowStatus
					RowStatus
			 }

		-- 1.3.6.1.4.1.2011.6.139.11.1.96.1.1
		hwVAPProfileAntiAttackPacketType OBJECT-TYPE
			SYNTAX INTEGER
				{
				otherBroadcast(1),
				arp(2),
				igmp(3),
				nd(4),
				dhcp(5),
				dhcpv6(6),
				mdns(7),
				otherMulticast(8)
				}
			MAX-ACCESS not-accessible
			STATUS current
			DESCRIPTION
				"This object indicates the packet type of the VAP anti-attack flood function.This parameter has no default value."
			::= { hwVAPProfileAntiAttackEntry 1 }
		
		-- 1.3.6.1.4.1.2011.6.139.11.1.96.1.2
		hwVAPProfileAntiAttackSwitch OBJECT-TYPE
			SYNTAX INTEGER
				{
				disable(1),
				enable(2)
				}
			MAX-ACCESS read-write
			STATUS current
			DESCRIPTION
				"This object indicates the status of the VAP anti-attack flood function. The default value is 2."
			::= { hwVAPProfileAntiAttackEntry 2 }
		
		-- 1.3.6.1.4.1.2011.6.139.11.1.96.1.3
		hwVAPProfileAntiAttackStaRateThreshold OBJECT-TYPE
			SYNTAX Unsigned32 (1..5000)
			MAX-ACCESS read-write
			STATUS current
			DESCRIPTION
				"This object indicates the anti-attack flood sta-rate-threshold for the VAP. The default value is related to the protocol type. arp:4(pps), nd:8(pps), igmp:4(pps), dhcp:4(pps), dhcpv6:4(pps), mdns:4(pps), other multicast:10(pps), other boradcast:10(pps)."
			::= { hwVAPProfileAntiAttackEntry 3 }
		
		-- 1.3.6.1.4.1.2011.6.139.11.1.96.1.4
		hwVAPProfileAntiAttackBlacklistSwitch OBJECT-TYPE
			SYNTAX INTEGER
				{
				disable(1),
				enable(2)
				}
			MAX-ACCESS read-write
			STATUS current
			DESCRIPTION
				"This object indicates the status of the VAP anti-attack ARP flood blacklist function. The default value is 1."
			::= { hwVAPProfileAntiAttackEntry 4 }
		
		-- 1.3.6.1.4.1.2011.6.139.11.1.96.1.5
		hwVAPProfileAntiAttackRowStatus OBJECT-TYPE
			SYNTAX RowStatus
			MAX-ACCESS read-create
			STATUS current
			DESCRIPTION
				"This object indicates the row status of this table. ROWSTATUS_CREATEANDFLOW and ROWSTATUS_DESTROY are commonly used."
			::= { hwVAPProfileAntiAttackEntry 5 }

		-- 1.3.6.1.4.1.2011.6.139.11.1.97
		hwApProfStationConnectivityDetectStaMacTable OBJECT-TYPE
			SYNTAX SEQUENCE OF HwApProfStationConnectivityDetectStaMacEntry
			MAX-ACCESS not-accessible
			STATUS current
			DESCRIPTION
				"This table is used to configure Station Connectivity Detect Mac."
			::= { hwWlanConfigObjects 97 }
		
		-- 1.3.6.1.4.1.2011.6.139.11.1.97.1
		hwApProfStationConnectivityDetectStaMacEntry OBJECT-TYPE
			SYNTAX HwApProfStationConnectivityDetectStaMacEntry
			MAX-ACCESS not-accessible
			STATUS current
			DESCRIPTION
				"The indexes of this table are hwApSystemProfName and hwApProfStationConnectivityDetectStaMac."
			INDEX { hwApProfStationConnectivityDetectStaMac, hwApSystemProfName }
			::= { hwApProfStationConnectivityDetectStaMacTable 1 }
		
		HwApProfStationConnectivityDetectStaMacEntry ::=
			SEQUENCE { 
				hwApProfStationConnectivityDetectStaMac
					MacAddress,
				hwApProfStationConnectivityDetectStaMacRowStatus
					RowStatus
			 }

		-- 1.3.6.1.4.1.2011.6.139.11.1.97.1.1
		hwApProfStationConnectivityDetectStaMac OBJECT-TYPE
			SYNTAX MacAddress
			MAX-ACCESS not-accessible
			STATUS current
			DESCRIPTION
				"This object indicates the connectivity detect station mac, MAX number is 8"
			::= { hwApProfStationConnectivityDetectStaMacEntry 1 }
		
		-- 1.3.6.1.4.1.2011.6.139.11.1.97.1.2
		hwApProfStationConnectivityDetectStaMacRowStatus OBJECT-TYPE
			SYNTAX RowStatus
			MAX-ACCESS read-write
			STATUS current
			DESCRIPTION
				"This object indicates the row status of this table. ROWSTATUS_CREATEANDGO and ROWSTATUS_DESTROY are commonly used."
			::= { hwApProfStationConnectivityDetectStaMacEntry 2 }
			
		-- 1.3.6.1.4.1.2011.6.139.11.2
		hwWlanConfigConformance OBJECT IDENTIFIER ::= { hwWlanConfig 2 }

		--1.3.6.1.4.1.2011.6.139.11.2.1
		hwWlanConfigCompliances OBJECT IDENTIFIER ::= { hwWlanConfigConformance 1 }

		--1.3.6.1.4.1.2011.6.139.11.2.1.1
		hwWlanConfigCompliance MODULE-COMPLIANCE
			STATUS current
			DESCRIPTION 
				"Description."
			MODULE -- this module
				MANDATORY-GROUPS { hwWlanGlobalConfigGroups, hwApAuthObjectsGroups, hwAPGroupGroups, hwAPGroupWiredPortGroups, hwAPGroupRadioGroups, 
					hwAPGroupVapGroups, hwAPSpecificGroups, hwAPSpecificWiredPortGroups, hwAPSpecificRadioGroups, hwAPSpecificVapGroups, 
					hwRegulatoryDomainProfileGroups, hwApSystemProfileGroups, hwAPWiredPortProfileGroups, hwAPPortLinkProfileGroups, hw2gRadioProfileGroups, 
					hw5gRadioProfileGroups, hwRrmProfileGroups, hwAirScanProfileGroups, hwVapProfileGroups, hwSsidProfileGroups, 
					hwSecurityProfileGroups, hwAPTrafficProfileGroups, hwWlanVlanPoolGroups, hwStaWhitelistProfileGroups, hwStaBlacklistProfileGroups, 
					hwWidsProfileGroups, hwWidsSpoofProfileGroups, hwWidsWhitelistProfileGroups, hwMeshProfileGroups, hwMeshWhitelistProfileGroups, 
					hwMeshHandoverProfileGroups, hwWdsProfileGroups, hwWdsWhitelistProfileGroups, hwHotspot2ProfileGroups, hwCellularNetworkProfileGroups, 
					hwConnectionCapabilityProfileGroups, hwOperatorNameProfileGroups, hwOperatorClassProfileGroups, hwOperatorDomainNameProfileGroups, hwNAIRealmProfileGroups, 
					hwVenueNameProfileGroups, hwRoamingConsortiumProfileGroups, hwSACProfileGroups, hwSACProfActionGroups, hwAPProvisionGroups, 
					hwWlanRadioCalibrateManagementGroups, hwWlanMobilityGroups, hwWlanLanguageGroups, hwFatApConfigGroups, hwWidsSpoofProfileListGroups, 
					hwWidsWhitelistProfileListGroups, hwWlanLoadBalanceStaticGroupGroups, hwWlanLoadBalanceStaticGroupMemberGroups, hwWlanCountryCodeGroups, hwUccProfileGroups, 
					hwSoftgreProfileGroups }
			::= { hwWlanConfigCompliances 1 }

		--1.3.6.1.4.1.2011.6.139.11.2.2
		hwWlanConfigObjectGroups OBJECT IDENTIFIER ::= { hwWlanConfigConformance 2 }

		
		-- 1.3.6.1.4.1.2011.6.139.11.2.2.1
		hwWlanGlobalConfigGroups OBJECT-GROUP
			OBJECTS { hwWlanGlobalApUsername, hwWlanGlobalApPassword, hwWlanUsernamePasswordApMac, hwWlanGlobalApLldpSwitch, hwWlanGlobalIpv6Enable, 
				hwWlanStationIpv6Enable, hwWlanApDataCollectionInterval, hwTestRtCollectOnoff, hwTestApNormalCollectCycle, hwTestApRtCollectCycle, 
				hwWlanConfigCommitAll, hwWlanProtectIpAddress, hwWlanProtectIPv6Address, hwWlanProtectPriority, hwWlanProtectSwitch, 
				hwWlanProtectRestoreSwitch, hwUndoWlanProtectIpAddress, hwUndoWlanProtectPriority, hwWlanCfgHsbServiceType, hwWlanCfgHsbGroupId, 
				hwWlanCfgHsbTunnelId, hwWlanConfigCommit, hwWlanReportStaInfo, hwWlanBLELowPowerWarningThreshold, hwWlanReportStaAssocInfo,hwWlanGlobalRogueDeviceLogSwitch,
				hwWlanGlobalAntiInterferenceSwitch, hwWlanGlobalAntiInterferencePerPacketTpcSwitch, hwWlanGlobalAeroscoutLocalIPv4, hwWlanGlobalAeroscoutLocalIPv6 }
			STATUS current
			DESCRIPTION 
				"Description."
			::= { hwWlanConfigObjectGroups 1 }

		
		-- 1.3.6.1.4.1.2011.6.139.11.2.2.2
		hwApAuthObjectsGroups OBJECT-GROUP
			OBJECTS { hwWlanApAuthMode, hwWlanApMacWhitelistRowStatus, hwWlanApSnWhitelistRowStatus, hwWlanApMacBlacklistRowStatus }
			STATUS current
			DESCRIPTION 
				"Description."
			::= { hwWlanConfigObjectGroups 2 }


		-- 1.3.6.1.4.1.2011.6.139.11.2.2.3
		hwAPGroupGroups OBJECT-GROUP
			OBJECTS { hwAPGrpAPSystemProfile, hwAPGrpDomainProfile, hwAPGrpRowStatus, hwAPGrpWidsProfile, hwAPGrpBleProfile}
			STATUS current
			DESCRIPTION 
				"Description."
			::= { hwWlanConfigObjectGroups 3 }


		-- 1.3.6.1.4.1.2011.6.139.11.2.2.4
		hwAPGroupWiredPortGroups OBJECT-GROUP
			OBJECTS {hwAPGrpWPProfile, hwAPGrpWPRowStatus }
			STATUS current
			DESCRIPTION 
				"Description."
			::= { hwWlanConfigObjectGroups 4 }


		-- 1.3.6.1.4.1.2011.6.139.11.2.2.5
		hwAPGroupRadioGroups OBJECT-GROUP
			OBJECTS { hwAPGrpRadio5gProfile, hwAPGrpMeshProfile, hwAPGrpWdsProfile, hwAPGrpLocationProfile, hwAPGrpRadioRowStatus, 
				hwAPGrpRadio2gProfile, hwAPGrpMeshWhitelistProfile, hwAPGrpWdsWhitelistProfile, hwAPGrpRadioSwitch, hwAPGrpRadioChannel, 
				hwAPGrpRadioBandwidth, hwAPGrpRadioEirp, hwAPGrpRadioAntennaGain, hwAPGrpRadioCoverageDistance, hwAPGrpRadioWorkMode, 
				hwAPGrpRadioFrequency, hwAPGrpSpectrumAnalysisSwitch, hwAPGrpWidsDeviceDetectSwitch, hwAPGrpWidsAttackDetectEnBmp, hwAPGrpWidsRogueContainSwitch, 
				hwAPGrpRadioSecondChannel, hwAPGrpAutoChannelSelectSwitch, hwAPGrpAutoTxPowerSelectSwitch, hwAPGroupRadioCalibrateFlexibleRadio, hwAPGrpReferenceDataAnalysis }
			STATUS current
			DESCRIPTION 
				"Description."
			::= { hwWlanConfigObjectGroups 5 }


		-- 1.3.6.1.4.1.2011.6.139.11.2.2.6
		hwAPGroupVapGroups OBJECT-GROUP
			OBJECTS {hwAPGrpVapProfile, hwAPGrpVapRowStatus, hwAPGrpVapServiceVlan, hwAPGrpVapVlanPool }
			STATUS current
			DESCRIPTION 
				"Description."
			::= { hwWlanConfigObjectGroups 6 }


		-- 1.3.6.1.4.1.2011.6.139.11.2.2.7
		hwAPSpecificGroups OBJECT-GROUP
			OBJECTS { hwAPSpAPSystemProfile, hwAPSpDomainProfile, hwAPSpRowStatus, hwAPSpApId, hwAPSpApTypeInfo, hwAPSpWidsProfile, hwAPSpBleProfile, hwAPSpLongitude, hwAPSpLatitude,
				 hwAPSpApAddressMode,hwAPSpApIPv4Address,hwAPSpApIPv4Mask,hwAPSpApIPv4Gateway,hwAPSpApIPv6Address,hwAPSpApIPv6PrefixLen,hwAPSpApIPv6Gateway,hwAPSpIPv4ACList,hwAPSpIPv6ACList}
			STATUS current
			DESCRIPTION 
				"Description."
			::= { hwWlanConfigObjectGroups 7 }

			
		-- 1.3.6.1.4.1.2011.6.139.11.2.2.8
		hwAPSpecificWiredPortGroups OBJECT-GROUP
			OBJECTS { hwAPSpWPProfile, hwAPSpWPRowStatus, hwAPSpWPApId }
			STATUS current
			DESCRIPTION 
				"Description."
			::= { hwWlanConfigObjectGroups 8 }


		-- 1.3.6.1.4.1.2011.6.139.11.2.2.9
		hwAPSpecificRadioGroups OBJECT-GROUP
			OBJECTS { hwAPSp5gRadioProfile, hwAPSpMeshProfile, hwAPSpWdsProfile, hwAPSpLocationProfile, hwAPSpRadioRowStatus, 
				hwAPSpRadio2gProfile, hwAPSpMeshWhitelistProfile, hwAPSpWdsWhitelistProfile, hwAPSpRadioSwitch, hwAPSpRadioChannel, 
				hwAPSpRadioBandwidth, hwAPSpRadioEirp, hwAPSpRadioAntennaGain, hwAPSpRadioCoverageDistance, hwAPSpRadioWorkMode, 
				hwAPSpRadioFrequency, hwAPSpSpectrumAnalysisSwitch, hwAPSpWidsDeviceDetectSwitch, hwAPSpWidsAttackDetectEnBmp, hwAPSpWidsRogueContainSwitch, 
				hwAPSpRadioApId, hwAPSpRadioSecondChannel, hwAPSpAutoChannelSelectSwitch, hwAPSpAutoTxPowerSelectSwitch, hwAPSpRadioCalibrateFlexibleRadio, hwAPSpReferenceDataAnalysis }
			STATUS current
			DESCRIPTION 
				"Description."
			::= { hwWlanConfigObjectGroups 9 }


		-- 1.3.6.1.4.1.2011.6.139.11.2.2.10
		hwAPSpecificVapGroups OBJECT-GROUP
			OBJECTS { hwAPSpVapProfile, hwAPSpVapRowStatus, hwAPSpVapApId, hwAPSpVapServiceVlan, hwAPSpVapVlanPool }
			STATUS current
			DESCRIPTION 
				"Description."
			::= { hwWlanConfigObjectGroups 10 }


		-- 1.3.6.1.4.1.2011.6.139.11.2.2.11
		hwRegulatoryDomainProfileGroups OBJECT-GROUP
			OBJECTS { hwCountryCode, hwDcaChannel5GBandwidth, hwDcaChannel5GChannelSet, hwDcaChannel2GChannelSet, hwRegulatoryDomainProfilRowStatus
				 }
			STATUS current
			DESCRIPTION 
				"Description."
			::= { hwWlanConfigObjectGroups 11 }


		-- 1.3.6.1.4.1.2011.6.139.11.2.2.12
		hwApSystemProfileGroups OBJECT-GROUP
			OBJECTS { hwApProfStatInterval, hwApProfSampleTime, hwApProfLedSwitch, hwApProfMaxStaNum, hwApProfMtu, 
				hwApProfMeshRole, hwApProfTemporaryManagement, hwApProfManagementVlan, hwApProfHighTempThreshold, hwApProfLowTempThreshold, 
				hwApProfOpHRxPowerThreshold, hwApProfOpLRxPowerThreshold, hwApProfOpHTempThreshold, hwApProfOpLTempThreshold, hwApProfMemoryUsageThreshold, 
				hwApProfCpuUsageThreshold, hwApProfTelnetSwitch, hwApProfSTelnetSwitch, hwApProfConsoleSwitch, hwApProfLogRecordLevel, 
				hwApProfLogServerIp, hwApProfLogServerIpv6, hwApProfAlarmRestrictionSwitch, hwApProfAlarmRestrictionPeriod, hwApProfKeepServiceSwitch, 
				hwApProfProtectPriority, hwApProfProtectACIp, hwApProfProtectACIpv6, hwApProfEapStartMode, hwApProfEapStartTransform, 
				hwApProfEapStartUnicastMac, hwApProfEapResponseMode, hwApProfEapResponseTransform, hwApProfEapResponseUnicastMac, hwApProfLldpRestartDelay, 
				hwApProfLldpAdminStatus, hwApProfLldpRetransDelay, hwApProfLldpRetransHoldMultiplier, hwApProfLldpInterval, hwApProfLldpReportInterval, 
				hwApProfStaAccessMode, hwApProfStaAccessModeProfile, hwApProfRowStatus, hwApProfSFTPSwitch, hwApProfDynamicBlackListAgingTime, 
				hwApProfAntennaOutputMode, hwApProfMppActiveReselectionSwitch, hwApProfSpectrumServerIPAddress, hwApProfSpectrumServerIPv6Address, hwApProfSpectrumServerPort, 
				hwApProfSpectrumViaACSwitch, hwApProfSpectrumViaACPort, hwApProfSpectrumNonWifiDeviceAgingTime, hwApProfPoeMaxPower, hwApProfPoePowerReserved,
				hwApProfPoePowerThreshold, hwApProfPoeAfInrushSwitch, hwApProfPoeHighInrushSwitch, hwApProfPrimaryLinkIPv4, hwApProfPrimaryLinkIPv6, hwApProfBackupLinkIPv4,
				hwApProfBackupLinkIPv6, hwApProfLedOffTimeRange, hwApProfUsbSwitch, hwApProfBroadcastSuppressionArpEnable, hwApProfBroadcastSuppressionArpThreshold,
                hwApProfBroadcastSuppressionIgmpEnable, hwApProfBroadcastSuppressionIgmpThreshold,hwApProfBroadcastSuppressionNdEnable, hwApProfBroadcastSuppressionNdThreshold,
				hwApProfBroadcastSuppressionOtherEnable, hwApProfBroadcastSuppressionOtherThreshold,hwApProfBroadcastSuppressionAllEnable, hwApProfCapwapDtlsDataSwitch, hwApProfTemporaryManagementPsk, 
				hwApProfProtectLinkSwitchMode, hwApProfProtectLinkSwitchEchoProbeTime, hwApProfProtectLinkSwitchStartThreshold, hwApProfProtectLinkSwitchGapThreshold, hwApProfCardConnectType, hwApProfLldpReportEnable,hwApProfDhcpv4Option12,hwApProfBcSuppresionAutoDetectThreshold,hwApProfMcSuppresionAutoDetectThreshold,hwApProfUcSuppresionAutoDetectThreshold,hwApProfConsoleBLEMode,hwApProfDiskUsageThreshold,hwApProfStationConnectivityDetectSwitch,hwApProfStaArpNDProxyBeforeAssoc,
				hwApProfPkiCertFileType,hwApProfPkiCertFileName,hwApProfPkiCertFilePassword}			
			STATUS current
			DESCRIPTION 
				"Description."
			::= { hwWlanConfigObjectGroups 12 }


		-- 1.3.6.1.4.1.2011.6.139.11.2.2.13
		hwAPWiredPortProfileGroups OBJECT-GROUP
			OBJECTS { hwAPWiredPortPortLinkProfileName, hwAPWiredPortProfilePortDesc, hwAPWiredPortProfilePortEthTrunkID, hwAPWiredPortProfilePortSTPSwitch, hwAPWiredPortProfilePortMode, 
				hwAPWiredPortProfilePortVlanPvid, hwAPWiredPortProfilePortVlanTagged, hwAPWiredPortProfilePortVlanUntagged, hwAPWiredPortProfileUserIsolate, hwAPWiredPortProfileDhcpTrust, 
				hwAPWiredPortProfileNdTrust, hwAPWiredPortProfileRowStatus, hwAPWiredPortProfileLearnAddress, hwAPWiredPortProfileIpBindCheck, hwAPWiredPortProfileArpBindCheck, 
				hwAPWiredPortProfileSTPAutoShutdown, hwAPWiredPortProfileSTPAutoShutdownRecoveryTime, hwAPWiredPortProfileTrafficOptimizeSuppressionBc, hwAPWiredPortProfileTrafficOptimizeSuppressionUc, hwAPWiredPortProfileTrafficOptimizeSuppressionMc, 
				hwAPWiredPortProfileLearnIpv6Address, hwAPWiredPortProfileTrafficFilterAclID, hwAPWiredPortProfileTrafficFilterRowStatus, hwAPWiredPortProfileMLDSnooping, hwAPWiredPortProfileTrafficOptimizeTcpAdjustMss,hwAPWiredPortProfilePortForwardMode,hwAPWiredPortDot1xClientProfileName}
			STATUS current
			DESCRIPTION 
				"Description."
			::= { hwWlanConfigObjectGroups 13 }


		-- 1.3.6.1.4.1.2011.6.139.11.2.2.14
		hwAPPortLinkProfileGroups OBJECT-GROUP
			OBJECTS { hwAPPortLinkProfileLldpEnable, hwAPPortLinkProfileLldpTlvType, hwAPPortLinkProfileCrcAlarmEnable, hwAPPortLinkProfileCrcAlarmThreshold, hwAPPortLinkProfileCrcAlarmResumeThreshold, 
				hwAPPortLinkProfileRowStatus, hwAPPortLinkProfilePoeSwitch, hwAPPortLinkProfilePoePriority, hwAPPortLinkProfilePoeForcePowerSwitch, hwAPPortLinkProfilePoeLegacySwitch, 
				hwAPPortLinkProfilePoeOffTimeRange, hwAPPortLinkProfileAdminStatus, hwAPPortLinkProfileLldpdot3TlvType, hwAPPortLinkProfileLldpdot3PowerFormat, hwAPPortLinkProfileLldpLegacyTlvType,hwAPPortLinkProfileLldpLegacyPowerCapability,hwAPPortLinkProfileSpeed }
			STATUS current
			DESCRIPTION 
				"Description."
			::= { hwWlanConfigObjectGroups 14 }


		-- 1.3.6.1.4.1.2011.6.139.11.2.2.15
		hw2gRadioProfileGroups OBJECT-GROUP
			OBJECTS { hw2gRadioBeaconInterval, hw2gRadioGuardIntervalMode, hw2gRadioShortPreamble, hw2gRadioFragmentationThreshold, hw2gRadioHtAmpduSwitch, 
				hw2gRadioHtAmpduMaxLengthExponent, hw2gRadioDot11bgBasicRate, hw2gRadioDot11bgSupportRate, hw2gRadioMulticastRate, hw2gRadioWmmMandatorySwitch, 
				hw2gRadioApEDCAVoiceECWmax, hw2gRadioApEDCAVoiceECWmin, hw2gRadioApEDCAVoiceAIFSN, hw2gRadioApEDCAVoiceTXOPLimit, hw2gRadioApEDCAVoiceAckPolicy, 
				hw2gRadioApEDCAVideoECWmax, hw2gRadioApEDCAVideoECWmin, hw2gRadioApEDCAVideoAIFSN, hw2gRadioApEDCAVideoTXOPLimit, hw2gRadioApEDCAVideoAckPolicy, 
				hw2gRadioApEDCABEECWmax, hw2gRadioApEDCABEECWmin, hw2gRadioApEDCABEAIFSN, hw2gRadioApEDCABETXOPLimit, hw2gRadioApEDCABEAckPolicy, 
				hw2gRadioApEDCABKECWmax, hw2gRadioApEDCABKECWmin, hw2gRadioApEDCABKAIFSN, hw2gRadioApEDCABKTXOPLimit, hw2gRadioApEDCABKAckPolicy, 
				hw2gRadioWmmSwitch, hw2gRadioRtsCtsThreshold, hw2gRadioRtsCtsMode, hw2gRadioPowerAutoAdjustSwitch, hw2gRadioBeamformingSwitch, 
				hw2gRadioWifiLight, hw2gRadioChannelSwitchAnnouncementSwitch, hw2gRadioChannelSwitchMode, hw2gRadioAutoOffServiceSwitch, hw2gRadioAutoOffServiceStartTime, 
				hw2gRadioAutoOffServiceEndTime, hw2gRadioInterferenceDetectSwitch, hw2gRadioInterferenceIntraFrequencyThreshold, hw2gRadioInterferenceAdjacentFrequencyThreshold, hw2gRadioInterferenceStationThreshold, 
				hw2gRadioRrmProfile, hw2gRadioAirScanProfile, hw2gRadioProfileRowStatus, hw2gRadioProfileUtmostPowerSwitch, hw2gRadioProfileRadioType,
				hw2gRadioProfileSmartAntennaEnable, hw2gRadioProfileTxChainNum, hw2gRadioProfileRxChainNum,hw2gRadioProfileAutoOffTimeRange }
			STATUS current
			DESCRIPTION 
				"Description."
			::= { hwWlanConfigObjectGroups 15 }


		-- 1.3.6.1.4.1.2011.6.139.11.2.2.16
		hw5gRadioProfileGroups OBJECT-GROUP
			OBJECTS { hw5gRadioBeaconInterval, hw5gRadioGuardIntervalMode, hw5gRadioShortPreamble, hw5gRadioFragmentationThreshold, hw5gRadioHtAmpduSwitch, 
				hw5gRadioHtAmpduMaxLengthExponent, hw5gRadioVhtAmpduMaxLengthExponent, hw5gRadioVhtAmsduSwitch, hw5gRadioVhtAmsduMaxFrameNum, hw5gRadioDot11aBasicRate, 
				hw5gRadioDot11aSupportRate, hw5gRadioMulticastRate, hw5gRadioVhtNssMapMaxMcs, hw5gRadioWmmMandatorySwitch, hw5gRadioApEDCAVoiceECWmax, 
				hw5gRadioApEDCAVoiceECWmin, hw5gRadioApEDCAVoiceAIFSN, hw5gRadioApEDCAVoiceTXOPLimit, hw5gRadioApEDCAVoiceAckPolicy, hw5gRadioApEDCAVideoECWmax, 
				hw5gRadioApEDCAVideoECWmin, hw5gRadioApEDCAVideoAIFSN, hw5gRadioApEDCAVideoTXOPLimit, hw5gRadioApEDCAVideoAckPolicy, hw5gRadioApEDCABEECWmax, 
				hw5gRadioApEDCABEECWmin, hw5gRadioApEDCABEAIFSN, hw5gRadioApEDCABETXOPLimit, hw5gRadioApEDCABEAckPolicy, hw5gRadioApEDCABKECWmax, 
				hw5gRadioApEDCABKECWmin, hw5gRadioApEDCABKAIFSN, hw5gRadioApEDCABKTXOPLimit, hw5gRadioApEDCABKAckPolicy, hw5gRadioWmmSwitch, 
				hw5gRadioRtsCtsThreshold, hw5gRadioRtsCtsMode, hw5gRadioPowerAutoAdjustSwitch, hw5gRadioBeamformingSwitch, hw5gRadioWifiLight, 
				hw5gRadioChannelSwitchAnnouncementSwitch, hw5gRadioChannelSwitchMode, hw5gRadioAutoOffServiceSwitch, hw5gRadioAutoOffServiceStartTime, hw5gRadioAutoOffServiceEndTime, 
				hw5gRadioInterferenceDetectSwitch, hw5gRadioInterferenceIntraFrequencyThreshold, hw5gRadioInterferenceAdjacentFrequencyThreshold, hw5gRadioInterferenceStationThreshold, hw5gRadioRrmProfile, 
				hw5gRadioAirScanProfile, hw5gRadioProfileRowStatus, hw5gRadioProfileUtmostPowerSwitch, hw5gRadioProfileRadioType, hw5gRadioProfileSmartAntennaEnable, 
				hw5gRadioProfileMuMIMOEnable, hw5gRadioProfileTxChainNum, hw5gRadioProfileRxChainNum, hw5gRadioProfileAutoOffTimeRange }
			STATUS current
			DESCRIPTION 
				"Description."
			::= { hwWlanConfigObjectGroups 16 }


		-- 1.3.6.1.4.1.2011.6.139.11.2.2.17
		hwRrmProfileGroups OBJECT-GROUP
			OBJECTS { hwRrmAutoChannelSelectSwitch, hwRrmAutoTxPowerSelectSwitch, hwRrmErrRateThreshold, hwRrmAirtimeFairSchduleSwitch, hwRrmDynamicEdcaSwitch, 
				hwRrmUacLimitClientSnrSwitch, hwRrmUacClientSnrThreshold, hwRrmUacPolicySwitch, hwRrmUacPolicyType, hwRrmUacReachThresholdHideSsidSwitch, 
				hwRrmBandSteerDenyThreshold, hwRrmBandSteerLbClientThreshold, hwRrmBandSteerLbGapThreshold, hwRrmBandSteerClientBandsExpire, hwRrmLoadBalanceSwitch, 
				hwRrmLoadBalanceClientThreshold, hwRrmLoadBalanceGapThreshold, hwRrmLoadBalanceDenyThreshold, hwRrmSmartRoamCheckType, hwRrmSmartRoamSwitch, 
				hwRrmSmartRoamSnrThreshold, hwRrmSmartRoamRateThreshold, hwRrmSmartRoamSnrHighLevelMargin, hwRrmSmartRoamSnrLowLevelMargin, hwRrmSmartRoamSnrCheckInterval, 
				hwRrmSmartRoamUnableRoamExpireTime, hwRrmProfileRowStatus,hwRrmSmartRoamQuickKickoffSNRCheckInterval,hwRrmSmartRoamQuickKickoffSNRPNObserveTime,
				hwRrmSmartRoamQuickKickoffSNRPNQualifyTime,hwRrmErrRateCheckInterval,hwRrmErrRateCheckTrafficThreshold, hwRrmMultimediaAirOptimize, hwRrmHighDensityAmcOptimizeSwitch,
				hwRrmMultimediaOptimizedThresholdVoice, hwRrmMultimediaOptimizedThresholdVideo, hwRrmLbProbeReportInterval, hwRrmLbDeauthFailTime,hwRrmLbBtmFailTime,
				hwRrmLbSteerRestrictTime, hwRrmLbSteerProbeRestrictThreshold, hwRrmLbSteerAuthRestrictThreshold, hwRrmLbRssiDiffGap,
				hwRrmSmartRoamAdvancedScan, hwRrmSmartRoamQuickKickoffBackOffTime, hwRrmDynamicEdcaThresholdBE, hwRrmCalibrate5gMaxTxPwr, hwRrmCalibrate5gMinTxPwr,
				hwRrmTpcRequestSwitch, hwRrmInterferenceImmuneSwitch, hwRrmBssColorSwitch, hwRrmSpatialReuseSwitch }
			STATUS current
			DESCRIPTION 
				"Description."
			::= { hwWlanConfigObjectGroups 17 }


		-- 1.3.6.1.4.1.2011.6.139.11.2.2.18
		hwAirScanProfileGroups OBJECT-GROUP
			OBJECTS { hwAirScanPeriod, hwAirScanInterval, hwAirScanChannelSet, hwAirScanProfilRowStatus, hwAirScanVoiceAware, 
				hwAirScanVideoAware }
			STATUS current
			DESCRIPTION 
				"Description."
			::= { hwWlanConfigObjectGroups 18 }


		-- 1.3.6.1.4.1.2011.6.139.11.2.2.19
		hwVapProfileGroups OBJECT-GROUP
			OBJECTS { hwVapForwardMode, hwVapTunnelForwardProtocol, hwVapServiceSwitch, hwVapAutoOffStartTime, hwVapAutoOffEndTime, 
				hwVapTemporaryManagementSwitch, hwVapServiceVlan, hwVapVlanPool, hwVapType, hwVapStaAccessMode, 
				hwVapStaAccessModePorfile, hwVapRoamHomeAgent, hwVapRoamVlanMobilityGroup, hwVapRoamLayer3Switch, hwVapBandSteerSwitch, 
				hwVapLearnIpv4Address, hwVapLearnIpv6Address, hwVapLearnIpv4AddressStrict, hwVapIpBindCheck, hwVapArpBindCheck, 
				hwVapOptinon82InsertSwitch, hwVapOptinon82InsertRidFormat, hwVapDhcpTrustPort, hwVapNdTrustPort, hwVapSecurityProfile, 
				hwVapTrafficProfile, hwVapSsidProfile, hwVapAuthenticationProfile, hwVapSacProfile, hwVapProfileRowStatus, 
				hwVapUserProfile, hwVapHotspot2Profile, hwSoftgreProfile, hwVapOptinon82RidUserDefined, hwVapOptinon82RidMacFormat, 
				hwVapOptinon82InsertCidFormat, hwVapOptinon82CidUserDefined, hwVapOptinon82CidMacFormat, hwVapUccProfile, hwVapAntiAttackBroadcastFloodSwitch, 
				hwVapAntiAttackBroadcastFloodStaRateThreshold, hwVapAntiAttackBroadcastFloodBlacklistSwitch, hwVapLearnIpv6AddressStrict,
				hwVapAntiAttackARPFloodSwitch, hwVapAntiAttackARPFloodStaRateThreshold, hwVapAntiAttackBroadcastFloodBlacklistSwitch,
				hwVapAntiAttackNDFloodSwitch, hwVapAntiAttackNDFloodStaRateThreshold, hwVapAntiAttackNDFloodBlacklistSwitch,
				hwVapAntiAttackIGMPFloodSwitch, hwVapAntiAttackIGMPFloodStaRateThreshold, hwVapAntiAttackIGMPFloodBlacklistSwitch, hwVapDefenceProfile , 
				hwVapTimeRange, hwVapPermitVlanList, hwVapSfnRoamSwitch, hwVapStaNetworkDetectSwitch, hwVapLearnIpv4AddressIpconflictuncheck, 
				hwVapLearnIpv6AddressIpconflictuncheck, hwVapRadiusTemplate, hwVapBackUpState, hwVapBackUpMode, hwVapRadiusState, hwVapKeepServiceSwitch,
				hwVapNaviACID, hwVapNaviACWlanId, hwVapMdnsPolicyLocalACSwitch,hwVapProfileMdnsSnooping, hwVapSplitTunnelAcl, hwVapSplitTunnelAclIPv6 }
			STATUS current
			DESCRIPTION 
				"Description."
			::= { hwWlanConfigObjectGroups 19 }


		-- 1.3.6.1.4.1.2011.6.139.11.2.2.20
		hwSsidProfileGroups OBJECT-GROUP
			OBJECTS { hwSsidText, hwSsidHide, hwSsidAssocTimeout, hwSsidMaxStaNum, hwSsidLegacyStaSwitch, 
				hwSsidDtimInterval, hwSsidClientEdcaVoiceECWmax, hwSsidClientEdcaVoiceECWmin, hwSsidClientEdcaVoiceAIFSN, hwSsidClientEdcaVoiceTXOPLimit, 
				hwSsidClientEdcaVideoECWmax, hwSsidClientEdcaVideoECWmin, hwSsidClientEdcaVideoAIFSN, hwSsidClientEdcaVideoTXOPLimit, hwSsidClientEdcaBeECWmax, 
				hwSsidClientEdcaBeECWmin, hwSsidClientEdcaBeAIFSN, hwSsidClientEdcaBeTXOPLimit, hwSsidClientEdcaBkECWmax, hwSsidClientEdcaBkECWmin, 
				hwSsidClientEdcaBkAIFSN, hwSsidClientEdcaBkTXOPLimit, hwSsidInboundCarCir, hwSsidInboundCarPir, hwSsidInboundCarCbs, 
				hwSsidInboundCarPbs, hwSsidOutboundCarCir, hwSsidOutboundCarPir, hwSsidOutboundCarCbs, hwSsidOutboundCarPbs, 
				hwSsidProfileRowStatus, hwSsidHideWhileReachMaxSta, hwSsidBeacon2gRate, hwSsidBeacon5gRate, hwSsidDenyBroadcastProbe, 
				hwSsidProbeResponseRetry, hwSsidUapsd, hwSsidActiveDullClient, hwSsidMuMIMOSwitch, hwSsidProfile80211rEnable, hwSsidProfile80211rMode, 
				hwSsidProfile80211rReassociateTimeout, hwSsidQbssLoadSwitch, hwSsidMuMIMOOptimizeSwitch }
			STATUS current
			DESCRIPTION 
				"Description."
			::= { hwWlanConfigObjectGroups 20 }


		-- 1.3.6.1.4.1.2011.6.139.11.2.2.21
		hwSecurityProfileGroups OBJECT-GROUP
			OBJECTS { hwSecurityPolicy, hwSecurityWepEncrypt, hwSecurityWepPskMode, hwSecurityWepPsk1, hwSecurityWepPsk2, 
				hwSecurityWepPsk3, hwSecurityWepPsk4, hwSecurityWepDefaultKeyId, hwSecurityWpaEncrypt, hwSecurityWpaPskMode, 
				hwSecurityWpaPsk, hwSecurityWpaPtkUpdateSwitch, hwSecurityWpaPtkUpdateInterval, hwSecurityWapiPskMode, hwSecurityWapiPsk, 
				hwSecurityWapiAsuIpAddress, hwSecurityWapiIssuerCertFileName, hwSecurityWapiAsuCertFileName, hwSecurityWapiAcCertFileName, hwSecurityWapiAcPrvKeyFileName, 
				hwSecurityWapiIssuerPfxPassword, hwSecurityWapiAsuPfxPassword, hwSecurityWapiAcPfxPassword, hwSecurityWapiAcPrvKeyPassword, hwSecurityWapiCertRetransCount, 
				hwSecurityWapiBkThreshold, hwSecurityWapiBkLifetime, hwSecurityWapiUskUpdateMethod, hwSecurityWapiMskUpdateMethod, hwSecurityWapiUskUpdateInterval, 
				hwSecurityWapiUskUpdatePackets, hwSecurityWapiUskRetansCount, hwSecurityWapiMskUpdateInterval, hwSecurityWapiMskUpdatePackets, hwSecurityWapiMskRetansCount, 
				hwSecurityWapiSATimeout, hwSecurityProfileRowStatus, hwSecurityWepDot1xMode }
			STATUS current
			DESCRIPTION 
				"Description."
			::= { hwWlanConfigObjectGroups 21 }


		-- 1.3.6.1.4.1.2011.6.139.11.2.2.22
		hwAPTrafficProfileGroups OBJECT-GROUP
			OBJECTS { hwAPTrafficProfilePriorityMapDnTrustMode, hwAPTrafficProfilePriorityDscpDnMap80211e, hwAPTrafficProfilePriority80211eUpMapDscp, hwAPTrafficProfileUserIsolate, hwAPTrafficProfileRateLimitClientUp, 
				hwAPTrafficProfileRateLimitClientDn, hwAPTrafficProfileRateLimitVapUp, hwAPTrafficProfileRateLimitVapDn, hwAPTrafficProfileMldSnooping, hwAPTrafficProfileIGMPSnooping, 
				hwAPTrafficProfileIGMPSnoopingReportSuppress, hwAPTrafficProfileMcToUc, hwAPTrafficProfileOptimizeSuppressionBc, hwAPTrafficProfileOptimizeSuppressionUc, hwAPTrafficProfileOptimizeSuppressionMc, 
				hwAPTrafficProfileOptimizeTCPAdjustMSS, hwAPTrafficProfileOptimizeProxyARP, hwAPTrafficProfileOptimizeProxyND, hwAPTrafficProfileOptimizeUcSendARP, hwAPTrafficProfileOptimizeUcSendND, 
				hwAPTrafficProfileOptimizeUcSendDHCP, hwAPTrafficProfileOptimizeBcMcDenyAll, hwAPTrafficProfileOptimizeStaBridgeForward, hwAPTrafficProfileRowStatus, hwAPTrafficProfilePriorityMapUpTrustMode, 
				hwAPTrafficProfilePriorityDscpUpMapDscp, hwAPTrafficProfileFilterACLID, hwAPTrafficProfileFilterRowStatus, hwAPTrafficProfileOptimizeBcMcMismatchAct, hwAPTrafficProfileMcToUcDynamicAdatptive,
				hwAPTrafficProfileIGMPSnoopingMaxBandwidth, hwAPTrafficProfileIGMPSnoopingMaxUser, hwAPTrafficProfileRateLimitClientDynamic, hwAPTrafficProfileRateLimitClientDynamicThr }
			STATUS current
			DESCRIPTION 
				"Description."
			::= { hwWlanConfigObjectGroups 22 }


		-- 1.3.6.1.4.1.2011.6.139.11.2.2.23
		hwWlanVlanPoolGroups OBJECT-GROUP
			OBJECTS { hwVlanPoolVlanlist, hwVlanPoolAssignMethod, hwVlanPoolRowStatus }
			STATUS current
			DESCRIPTION 
				"Description."
			::= { hwWlanConfigObjectGroups 23 }


		-- 1.3.6.1.4.1.2011.6.139.11.2.2.24
		hwStaWhitelistProfileGroups OBJECT-GROUP
			OBJECTS {hwWlanStaWhitelistProfileRowStatus }
			STATUS current
			DESCRIPTION 
				"Description."
			::= { hwWlanConfigObjectGroups 24 }


		-- 1.3.6.1.4.1.2011.6.139.11.2.2.25
		hwStaBlacklistProfileGroups OBJECT-GROUP
			OBJECTS { hwWlanStaBlacklistProfileRowStatus }
			STATUS current
			DESCRIPTION 
				"Description."
			::= { hwWlanConfigObjectGroups 25 }


		-- 1.3.6.1.4.1.2011.6.139.11.2.2.26
		hwWidsProfileGroups OBJECT-GROUP
			OBJECTS { hwWidsProfileRowStatus, hwWidsDeviceReportInterval, hwWidsDeviceSyncInterval, hwWidsSpoofProfile, hwWidsWhitelistProfile, 
				hwWidsBruteForceDetectInterval, hwWidsBruteForceDetectThreshold, hwWidsBruteForceQuietTime, hwWidsFloodDetectInterval, hwWidsFloodDetectThreshold, 
				hwWidsFloodQuietTime, hwWidsWeakIvQuietTime, hwWidsSpoofQuietTime, hwWidsDynamicBlackListSwitch, hwWidsRogueContainModeBmp,
 				hwWidsContainMinRssi, hwWidsContainMinStaNum
				 }
			STATUS current
			DESCRIPTION 
				"Description."
			::= { hwWlanConfigObjectGroups 26 }

		
		-- 1.3.6.1.4.1.2011.6.139.11.2.2.30
		hwWidsSpoofProfileGroups OBJECT-GROUP
			OBJECTS { hwWidsSpoofProfileRowStatus }
			STATUS current
			DESCRIPTION 
				"Description."
			::= { hwWlanConfigObjectGroups 30 }

			
		-- 1.3.6.1.4.1.2011.6.139.11.2.2.31
		hwWidsWhitelistProfileGroups OBJECT-GROUP
			OBJECTS { hwWidsWhitelistProfileMacRowStatus, hwWidsWhitelistProfileOuiRowStatus, hwWidsWhitelistProfileSsidRowStatus }
			STATUS current
			DESCRIPTION 
				"Description."
			::= { hwWlanConfigObjectGroups 31 }


		-- 1.3.6.1.4.1.2011.6.139.11.2.2.32
		hwMeshProfileGroups OBJECT-GROUP
			OBJECTS { hwWlanMeshID, hwWlanMeshDhcpTrustPort, hwWlanMeshLinkReportInterval, hwWlanMeshMaxLinkNum, hwWlanMeshRssiThreshold, 
				hwWlanMeshSecurityProfileName, hwWlanMeshProfileHandoverProfileName, hwWlanMeshFwaSwitch, hwWlanMeshFwaEdcaMode, hwWlanMeshProfileRowStatus, 
				hwWlanMeshClientEdcaVoiceECWmax, hwWlanMeshClientEdcaVoiceECWmin, hwWlanMeshClientEdcaVoiceAIFSN, hwWlanMeshClientEdcaVoiceTXOPLimit, hwWlanMeshClientEdcaVideoECWmax, 
				hwWlanMeshClientEdcaVideoECWmin, hwWlanMeshClientEdcaVideoAIFSN, hwWlanMeshClientEdcaVideoTXOPLimit, hwWlanMeshClientEdcaBeECWmax, hwWlanMeshClientEdcaBeECWmin, 
				hwWlanMeshClientEdcaBeAIFSN, hwWlanMeshClientEdcaBeTXOPLimit, hwWlanMeshClientEdcaBkECWmax, hwWlanMeshClientEdcaBkECWmin, hwWlanMeshClientEdcaBkAIFSN, 
				hwWlanMeshClientEdcaBkTXOPLimit, hwWlanMeshNdTrustPort, hwWlanMeshLinkAgingTime, hwWlanMeshProfilePriorityMapTrustMode, hwWlanMeshProfilePriorityDscpMap80211e,
				hwWlanMeshProfileClientModeSwitch, hwWlanMeshProfileBeacon2gRate, hwWlanMeshProfileBeacon5gRate, hwWlanMeshProfileSwitchProbeInterval}
			STATUS current
			DESCRIPTION 
				"Description."
			::= { hwWlanConfigObjectGroups 32 }


		-- 1.3.6.1.4.1.2011.6.139.11.2.2.33
		hwMeshWhitelistProfileGroups OBJECT-GROUP
			OBJECTS {hwWlanMeshWhitelistProfileRowStatus, hwWlanMeshWhitelistRowStatus }
			STATUS current
			DESCRIPTION 
				"Description."
			::= { hwWlanConfigObjectGroups 33 }


		-- 1.3.6.1.4.1.2011.6.139.11.2.2.34
		hwMeshHandoverProfileGroups OBJECT-GROUP
			OBJECTS { hwWlanMeshHOLinkProbeInterval, hwWlanMeshHOMinRssiThreshold, hwWlanMeshHOMaxRssiThreshold, hwWlanMeshHOLinkHoldPeriod, hwWlanMeshHORssiMargin, 
				hwWlanMeshHOLocationBasedAlgorithmEnable, hwWlanMeshHOMovingDirection, hwWlanMeshHOPNCriteriaObserveTime, hwWlanMeshHOPNCriteriaQualifyTime, hwWlanMeshUrgentHandoverLowRateThreshold, 
				hwWlanMeshUrgentHandoverLowRatePeriod, hwWlanMeshUrgentHandoverPunishmentPeriod, hwWlanMeshUrgentHandoverPunishmentRssi, hwWlanMeshHandoverProfileRowStatus }
			STATUS current
			DESCRIPTION 
				"Description."
			::= { hwWlanConfigObjectGroups 34 }


		-- 1.3.6.1.4.1.2011.6.139.11.2.2.35
		hwWdsProfileGroups OBJECT-GROUP
			OBJECTS { hwWdsName, hwWdsMode, hwWdsDhcpTrustPort, hwWdsVlanTagged, hwWdsSecurityProfileName, 
				hwWdsProfileRowStatus, hwWdsNdTrustPort, hwWdsProfilePriorityMapTrustMode, hwWdsProfilePriorityDscpMap80211e, hwWdsMuMIMOSwitch,
				hwWdsProfileBeacon2gRate, hwWdsProfileBeacon5gRate }
			STATUS current
			DESCRIPTION 
				"Description."
			::= { hwWlanConfigObjectGroups 35 }


		-- 1.3.6.1.4.1.2011.6.139.11.2.2.36
		hwWdsWhitelistProfileGroups OBJECT-GROUP
			OBJECTS { hwWdsWhitelistProfileRowStatus,hwWdsWhitelistRowStatus }
			STATUS current
			DESCRIPTION 
				"Description."
			::= { hwWlanConfigObjectGroups 36 }

		
		-- 1.3.6.1.4.1.2011.6.139.11.2.2.37
		hwLocationProfileGroups OBJECT-GROUP
			OBJECTS { hwLocationAeroscoutTagSwitch, hwLocationAeroscoutMuSwitch, hwLocationAeroscoutServerPort, hwLocationAeroscoutViaACSwitch, hwLocationAeroscoutViaACPort, 
				hwLocationAeroscoutCompoundTime, hwLocationEkahauTagEnable, hwLocationEkahauServerIPAddress, hwLocationEkahauServerIPv6Address, hwLocationEkahauServerPort, 
				hwLocationEkahauViaACEnable, hwLocationEkahauViaACPort, hwLocationSourceIPAddress, hwLocationSourceIPv6Address, hwLocationPrivateMuEnable, 
				hwLocationPrivateServerIPAddress, hwLocationPrivateServerIPv6Address, hwLocationPrivateServerPort, hwLocationPrivateViaACEnable, hwLocationPrivateViaACPort, 
				hwLocationPrivateReportFrequency, hwLocationProfileRowStatus ,hwLocationProfileAeroscoutShareKey ,hwLocationPaiboMuEnable ,hwLocationPaiboReportFrequency
 ,hwLocationPaiboServerIPAddress, hwLocationPaiboServerIPv6Address,hwLocationPaiboServerPort, hwLocationPaiboViaACPort,  hwLocationPaiboPSK, hwLocationPaiboIV, hwLocationPrivateServerAddressDomain,
 hwLocationPrivateProtocol, hwLocationPrivateSSLPolicyName,
				hwLocationPrivateReportFrequency, hwLocationProfileRowStatus ,hwLocationProfileAeroscoutShareKey ,hwLocationPaiboMuEnable ,hwLocationPaiboReportFrequency,
				hwLocationPaiboServerIPAddress, hwLocationPaiboServerIPv6Address,hwLocationPaiboServerPort, hwLocationPaiboViaACPort,  hwLocationPaiboPSK, hwLocationPaiboIV,
				hwLocationPrivateMUVersion, hwLocationSurFilterMuEnable, hwLocationSurFilterReportFrequency, hwLocationSurFilterReportProtocol, hwLocationSurFilterServerIPAddress,
				hwLocationSurFilterServerPort, hwLocationSurFilterViaACPort, hwLocationSurFilterUserName, hwLocationSurFilterPassword, hwLocationSurFilterDataSourceID,
				hwLocationSurFilterCompress,hwLocationCollectLocationDataSwitch,hwLocationCollectLocationDataRSSIThreshold}
			STATUS current
			DESCRIPTION 
				"Description."
			::= { hwWlanConfigObjectGroups 37 }
			
			
		-- 1.3.6.1.4.1.2011.6.139.11.2.2.39
		hwHotspot2ProfileGroups OBJECT-GROUP
			OBJECTS { hwHotspot2NetworkType, hwHotspot2InternetAccess, hwHotspot2VenueGroupCode, hwHotspot2VenueTypeCode, hwHotspot2Hessid, 
				hwHotspot2IPv4AddressAvail, hwHotspot2IPv6AddressAvail, hwHotspot2NetworkAuthenType, hwHotspot2RedirectUrl, hwHotspot2CarryP2PCrossConnectInfo, 
				hwHotspot2CellularNetworkProfile, hwHotspot2ConnectionCapabilityProfile, hwHotspot2OperatorNameProfile, hwHotspot2OperatingClassProfile, hwHotspot2OperatorDomainProfile, 
				hwHotspot2NaiRealmProfile, hwHotspot2VenueNameProfile, hwHotspot2RoamingConsortiumProfile, hwHotspot2ProfileRowStatus }
			STATUS current
			DESCRIPTION 
				"Description."
			::= { hwWlanConfigObjectGroups 39 }


		-- 1.3.6.1.4.1.2011.6.139.11.2.2.40
		hwCellularNetworkProfileGroups OBJECT-GROUP
			OBJECTS { hwCellularNetworkProfilePlmnIDList, hwCellularNetworkProfileRowStatus }
			STATUS current
			DESCRIPTION 
				"Description."
			::= { hwWlanConfigObjectGroups 40 }


		-- 1.3.6.1.4.1.2011.6.139.11.2.2.41
		hwConnectionCapabilityProfileGroups OBJECT-GROUP
			OBJECTS { hwConnectionCapabilityEsp, hwConnectionCapabilityIcmp, hwConnectionCapabilityTcpFtp, hwConnectionCapabilityTcpHttp, hwConnectionCapabilityTcpPptpVpn, 
				hwConnectionCapabilityTcpSsh, hwConnectionCapabilityTcpTlsVpn, hwConnectionCapabilityTcpVoip, hwConnectionCapabilityUdpIke2Port4500, hwConnectionCapabilityUdpIke2Port500, 
				hwConnectionCapabilityUdpVoip, hwConnectionCapabilityProfileRowStatus }
			STATUS current
			DESCRIPTION 
				"Description."
			::= { hwWlanConfigObjectGroups 41 }


		-- 1.3.6.1.4.1.2011.6.139.11.2.2.42
		hwOperatorNameProfileGroups OBJECT-GROUP
			OBJECTS { hwOperatorNameLanguageCodeList, hwOperatorFriendlyNameList, hwOperatorNameProfileRowStatus }
			STATUS current
			DESCRIPTION 
				"Description."
			::= { hwWlanConfigObjectGroups 42 }


		-- 1.3.6.1.4.1.2011.6.139.11.2.2.43
		hwOperatorClassProfileGroups OBJECT-GROUP
			OBJECTS { hwOperatorClassIndicationList, hwOperatorClassProfileRowStatus }
			STATUS current
			DESCRIPTION 
				"Description."
			::= { hwWlanConfigObjectGroups 43 }


		-- 1.3.6.1.4.1.2011.6.139.11.2.2.44
		hwOperatorDomainNameProfileGroups OBJECT-GROUP
			OBJECTS { hwOperatorDomainNameList, hwOperatorDomainNameProfileRowStatus }
			STATUS current
			DESCRIPTION 
				"Description."
			::= { hwWlanConfigObjectGroups 44 }

			
		-- 1.3.6.1.4.1.2011.6.139.11.2.2.45
		hwNAIRealmProfileGroups OBJECT-GROUP
			OBJECTS {hwNAIRealmEapAuthenPara, 
				hwNAIRealmProfileRowStatus,hwNAIRealmProfileListRowStatus }
			STATUS current
			DESCRIPTION 
				"Description."
			::= { hwWlanConfigObjectGroups 45 }


		-- 1.3.6.1.4.1.2011.6.139.11.2.2.46
		hwVenueNameProfileGroups OBJECT-GROUP
			OBJECTS { hwVenueNameLanguageCodeList, hwVenueNameList, hwVenueNameProfileRowStatus }
			STATUS current
			DESCRIPTION 
				"Description."
			::= { hwWlanConfigObjectGroups 46 }


		-- 1.3.6.1.4.1.2011.6.139.11.2.2.47
		hwRoamingConsortiumProfileGroups OBJECT-GROUP
			OBJECTS {hwRoamingConsortiumOIList, hwRoamingConsortiumOIInBeaconList, hwRoamingConsortiumProfileRowStatus }
			STATUS current
			DESCRIPTION 
				"Description."
			::= { hwWlanConfigObjectGroups 47 }


		-- 1.3.6.1.4.1.2011.6.139.11.2.2.48
		hwSACProfileGroups OBJECT-GROUP
			OBJECTS {hwSACProfUserStat, hwSACProfVapStat, hwSACProfRowStatus }
			STATUS current
			DESCRIPTION 
				"Description."
			::= { hwWlanConfigObjectGroups 48 }


		-- 1.3.6.1.4.1.2011.6.139.11.2.2.49
		hwSACProfActionGroups OBJECT-GROUP
			OBJECTS { hwSACProfileActProtocolType, hwSACProfileActProtocolName, hwSACProfileActProtocolGrpName, hwSACProfileActionType, hwSACProfileActCarCir, 
				hwSACProfileActRemarkDscpValue, hwSACProfileActRemark8021pValue, hwSACProfileActionRowstatus }
			STATUS current
			DESCRIPTION 
				"Description."
			::= { hwWlanConfigObjectGroups 49 }

		
		-- 1.3.6.1.4.1.2011.6.139.11.2.2.50
		hwAPProvisionGroups OBJECT-GROUP
			OBJECTS { hwWlanAPProvisionAddressMode, hwWlanAPProvisionIPv4Address, hwWlanAPProvisionIPv4Mask, hwWlanAPProvisionIPv4Gateway, hwWlanAPProvisionIPv6Address, 
				hwWlanAPProvisionIPv6PrefixLen, hwWlanAPProvisionIPv6Gateway, hwWlanAPProvisionGroupName, hwWlanAPProvisionName, hwWlanAPProvisionIPv4ACList, 
				hwWlanAPProvisionIPv6ACList, hwWlanAPProvisionCommitAPName, hwWlanAPProvisionCommitAPMac, hwWlanAPProvisionCommitAPGroup }
			STATUS current
			DESCRIPTION 
				"Description."
			::= { hwWlanConfigObjectGroups 50 }


		-- 1.3.6.1.4.1.2011.6.139.11.2.2.51
		hwWlanRadioCalibrateManagementGroups OBJECT-GROUP
			OBJECTS { hwWlanRadioCalibrateMode, hwWlanRadioCalibrateScheduleTime, hwWlanRadioCalibrateManualStartup, hwWlanRadioCalibrateAutoInterval, hwWlanRadioCalibratePolicy, 
				hwWlanRadioCalibrateSensitivity, hwWlanRadioCalibrateAutoStartTime, hwWlanRadioCalibrateManualApGroup, hwWlanRadioCalibrateManualApList, hwWlanRadioCalibrateManualProcess, 
				hwWlanRadioCalibrateFlexibleRadio, hwWlanRadioCalibrateFlexRadioManualRecognize, hwWlanRadioCalibrateFlexibleRadioProcess, hwWlanRadioCalibrateFlexibleRadioRecognizeTime,
				hwWlanRadioCalibrateSensitivityCustomValue, hwWlanRadioCalibrateScheduleTimeRange, hwWlanRadioCalibrateReferenceDataAnalysis, hwWlanRadioCalibrateEnvironmentDeteriorateValue}
			STATUS current
			DESCRIPTION 
				"Description."
			::= { hwWlanConfigObjectGroups 51 }


		-- 1.3.6.1.4.1.2011.6.139.11.2.2.52
		hwWlanMobilityGroups OBJECT-GROUP
			OBJECTS { hwWlanMasterControllerSwitch, hwWlanConnectMasterControllerSwitch, hwWlanConnectMasterControllerIPv4Addr, hwWlanConnectMasterControllerIPv6Addr, 
			          hwWlanMobilityServerIPv4,hwWlanMobilityServerIPv6,hwWlanMobilityServerState,hwWlanMobilityServerSwitch, 
			          hwWlanAcIPv4Address, hwWlanAcIPv6Address, hwWlanAcState, hwWlanAcRowStatus, 
			          hwWlanMobilityGroupRowStatus, hwWlanMobilityGroupMemberRowStatus, 
			          hwWlanMobilityMemberIPv4Addr,hwWlanMobilityMemberIPv4Description,hwWlanMobilityMemberIPv4State,hwWlanMobilityMemberIPv4RowStatus,hwWlanMobilityMemberIPv6Addr,
			          hwWlanMobilityMemberIPv6Description,hwWlanMobilityMemberIPv6State,hwWlanMobilityMemberIPv6RowStatus,hwWlanMobilityClientIPv4Addr,hwWlanMobilityClientIPv4State,hwWlanMobilityClientIPv6Addr,
			          hwWlanMobilityClientIPv6State
				 }
			STATUS current
			DESCRIPTION 
				"Description."
			::= { hwWlanConfigObjectGroups 52 }


		-- 1.3.6.1.4.1.2011.6.139.11.2.2.53
		hwWlanLanguageGroups OBJECT-GROUP
			OBJECTS { hwWlanLanguageCodeDescription }
			STATUS current
			DESCRIPTION 
				"Description."
			::= { hwWlanConfigObjectGroups 53 }


		-- 1.3.6.1.4.1.2011.6.139.11.2.2.54
		hwFatApConfigGroups OBJECT-GROUP
			OBJECTS { hwFatApCountryCode, hwFatApMaxStaNum, hwFatApStaAccessMode, hwFatApStaAccessModePorfile, hwFatApHighTempThreshold, 
				hwFatApLowTempThreshold, hwFatApDcaChannel5GBandwidth, hwFatApDcaChannel5GChannelSet, hwFatApDcaChannel2GChannelSet, hwFatApDynamicBlackAgingTime, 
				hwFatApAntennaOutputMode, hwFatApChannelLoadMode, hwFatApStaArpNDProxyBeforeAssoc, hwFatApRadio0Frequency, hwFatApRadio2gProfile, hwFatApRadio5gProfile, hwFatApRadioMeshProfile, 
				hwFatApLocationProfile, hwFatApRadioRowStatus, hwFatApMeshWhitelistProfile, hwFatApWdsWhitelistProfile, hwFatApRadioSwitch, 
				hwFatApRadioChannel, hwFatApRadioBandwidth, hwFatApRadioEirp, hwFatApRadioAntennaGain, hwFatApRadioCoverageDistance, 
				hwFatApRadioWorkMode, hwFatApWidsDeviceDetectSwitch, hwFatApWidsAttackDetectEnBmp, hwFatApWidsRogueContainSwitch, hwFatApVapProfile, 
				hwFatApVapProfileRowStatus,hwFatApRadioSecondChannel, hwFatApAutoChannelSelectSwitch, hwFatApAutoTxPowerSelectSwitch, hwFatApCalibrateFlexibleRadioSwitch,
				hwFatApRadioServiceIdxMeshProf,hwFatApRadioIdxMeshWlistProfile, hwFatApRadioServiceIdxChannel, hwFatApRadioServiceIdxBandwidth, hwFatApRadioIdxSecondChannel,
				hwFatApRadioServiceIdxRowStatus,hwFatApAutoBandwidthSelectSwitch,hwFatApReferenceDataAnalysis}
			STATUS current
			DESCRIPTION 
				"Description."
			::= { hwWlanConfigObjectGroups 54 }

		

		-- 1.3.6.1.4.1.2011.6.139.11.2.2.55
		hwWidsSpoofProfileListGroups OBJECT-GROUP
			OBJECTS { hwWidsSpoofProfileListRowStatus }
			STATUS current
			DESCRIPTION 
				"Description."
			::= { hwWlanConfigObjectGroups 55 }

		
		-- 1.3.6.1.4.1.2011.6.139.11.2.2.56
		hwWidsWhitelistProfileListGroups OBJECT-GROUP
			OBJECTS {hwWidsWhitelistProfileListRowStatus }
			STATUS current
			DESCRIPTION 
				"Description."
			::= { hwWlanConfigObjectGroups 56 }

		
		-- 1.3.6.1.4.1.2011.6.139.11.2.2.57
		hwWlanLoadBalanceStaticGroupGroups OBJECT-GROUP
			OBJECTS { hwWlanLBGapThreshold, hwWlanLBDenyThreshold, hwWlanLBStartThreshold, hwWlanLBGroupStatus, hwWlanLBGroupRowStatus, 
				 hwWlanLBMode, hwWlanLBChUtilGapThreshold, hwWlanLBChUtilStartThreshold, hwWlanLBGapStaNumThreshold }
			STATUS current
			DESCRIPTION 
				"Description."
			::= { hwWlanConfigObjectGroups 57 }

		
		-- 1.3.6.1.4.1.2011.6.139.11.2.2.58
		hwWlanLoadBalanceStaticGroupMemberGroups OBJECT-GROUP
			OBJECTS { hwWlanLBMemberRowStatus }
			STATUS current
			DESCRIPTION 
				"Description."
			::= { hwWlanConfigObjectGroups 58 }


		-- 1.3.6.1.4.1.2011.6.139.11.2.2.59
		hwWlanCountryCodeGroups OBJECT-GROUP
			OBJECTS { hwWlanCountryCodeEngDescription, hwWlanCountryCodeAvailableChannelSet2gBW20, hwWlanCountryCodeAvailableChannelSet2gBW40Plus, hwWlanCountryCodeAvailableChannelSet2gBW40Minus, hwWlanCountryCodeAvailableChannelSet5gBW20,
				hwWlanCountryCodeAvailableChannelSet5gBW40Plus, hwWlanCountryCodeAvailableChannelSet5gBW40Minus, hwWlanCountryCodeAvailableChannelSet5gBW80,
				hwWlanCountryCodeAvailableChannelSet5gBW160 }
			STATUS current
			DESCRIPTION 
				"Description."
			::= { hwWlanConfigObjectGroups 59 }
		
		-- 1.3.6.1.4.1.2011.6.139.11.2.2.60
		hwUccProfileGroups OBJECT-GROUP
			OBJECTS { hwUCCProfLyncVoice8021p, hwUCCProfLyncVoice8021pValue, hwUCCProfLyncVoiceDscp, hwUCCProfLyncVoiceDscpValue, hwUCCProfLyncVideo8021p, 
				hwUCCProfLyncVideo8021pValue, hwUCCProfLyncVideoDscp, hwUCCProfLyncVideoDscpValue, hwUCCProfLyncShare8021p, hwUCCProfLyncShare8021pValue, 
				hwUCCProfLyncShareDscp, hwUCCProfLyncShareDscpValue, hwUCCProfLyncFileTransfer8021p, hwUCCProfLyncFileTransfer8021pValue, hwUCCProfLyncFileTransferDscp, 
				hwUCCProfLyncFileTransferDscpValue, hwUCCProfileRowStatus }
			STATUS current
			DESCRIPTION 
				"Description."
			::= { hwWlanConfigObjectGroups 60 }
		
		-- 1.3.6.1.4.1.2011.6.139.11.2.2.61
		hwSoftgreProfileGroups OBJECT-GROUP
			OBJECTS { hwSoftgreDestinationIPAddress, hwSoftgreDestinationIPv6Address, hwSoftgreKeepaliveFlag, hwSoftgreKeepalivePeriod, 
				hwSoftgreKeepaliveRetryTimes, hwSoftgreProfileRowStatus }
			STATUS current
			DESCRIPTION 
				"Description."
			::= { hwWlanConfigObjectGroups 61 }
	
		-- 1.3.6.1.4.1.2011.6.139.11.2.2.66
		hwBleProfileGroups OBJECT-GROUP
			OBJECTS { hwWlanBLEBroadcasterEnable, hwWlanBLETxPower, hwWlanBLEBroadcastingUUID, hwWlanBLEBroadcastingMajor, hwWlanBLEBroadcastingMinor, 
				hwWlanBLEBroadcastingReferenceRSSI, hwWlanBLEBroadcastingInterval, hwWlanBLESnifferEnable, hwWlanBLEProfileRowStatus, hwWlanBLEBroadcastingUUIDHex, 
				hwWlanBLEBroadcastingMajorHex, hwWlanBLEBroadcastingMajorDecimal, hwWlanBLEBroadcastingMinorHex, hwWlanBLEBroadcastingMinorDecimal,hwWlanBLESnifferMode,hwWlanBLEReportEnable,hwWlanBLEReportMode,hwWlanBLEReportInterval,hwWlanBLEReportServerIPAddress,hwWlanBLEReportServerIPv6Address,hwWlanBLEReportServerPort,
				hwWlanBLEReportServerViaACEnable,hwWlanBLEReportServerViaACPort,hwWlanBLESourceIPAddress,hwWlanBLESourceIPv6Address,hwWlanBLEServerAddressDomain }
			STATUS current
			DESCRIPTION 
				"Description."
			::= { hwWlanConfigObjectGroups 66 }

		-- 1.3.6.1.4.1.2011.6.139.11.2.2.67
		hwAPGroupCardGroups OBJECT-GROUP
			OBJECTS { hwAPGrpCardSerialProfile, hwAPGrpCardProfile, hwAPGrpCardNetUDPPort, hwAPGrpIoTRowStatus, hwAPGrpCardNetTCPPort, hwAPGroupCardWiredPortProfile,hwAPGrpCardConnType }
			STATUS current
			DESCRIPTION 
				"Description."
			::= { hwWlanConfigObjectGroups 67 }

		-- 1.3.6.1.4.1.2011.6.139.11.2.2.68
		hwAPSpecificCardGroups OBJECT-GROUP
			OBJECTS { hwAPSpIoTSerialProfile, hwAPSpIoTProfile, hwAPSpIoTNetUDPPort, hwAPSpIoTRowStatus, hwAPSpIoTNetTCPPort, hwAPSpIoTWiredPortProfile,hwAPSpCardConnType }
			STATUS current
			DESCRIPTION 
				"Description."
			::= { hwWlanConfigObjectGroups 68 }

		-- 1.3.6.1.4.1.2011.6.139.11.2.2.69
		hwIoTSerialProfileGroups OBJECT-GROUP
			OBJECTS { hwIoTSerialSpeed, hwIoTSerialParity, hwIoTSerialStopbits, hwIoTSerialFrameFormat, hwIoTSerialFrameLength, 
			  hwIoTSerialFrameStart, hwIoTSerialFrameStop, hwIoTSerialProfileRowStatus }
			STATUS current
			DESCRIPTION 
				"Description."
			::= { hwWlanConfigObjectGroups 69 }

		-- 1.3.6.1.4.1.2011.6.139.11.2.2.70
		hwIoTProfileGroups OBJECT-GROUP
			OBJECTS { hwIoTProfileConfigAgentPermitIp, hwIoTProfileConfigAgentPermitMaskLen, hwIoTProfileShareKey, hwIoTProfileRowStatus, hwIoTProfileType }
			STATUS current
			DESCRIPTION 
				"Description."
			::= { hwWlanConfigObjectGroups 70 }
			
		-- 1.3.6.1.4.1.2011.6.139.11.2.2.71
		hwIoTProfileManagementServerGroups OBJECT-GROUP
			OBJECTS { hwIoTProfileManagementServerIp, hwIoTProfileManagementServerPort, hwIoTProfileManagementServerRowStatus, hwIoTProfileManagementServerDomain }
			STATUS current
			DESCRIPTION 
				"Description."
			::= { hwWlanConfigObjectGroups 71 }
												
		-- 1.3.6.1.4.1.2011.6.139.11.2.2.79
		hwVapAntiAttackUserDefFloodGroups OBJECT-GROUP
			OBJECTS { hwVapAntiAttackDefFloodProtocolType, hwVapAntiAttackDefFloodProtocolValue, hwVapAntiAttackDefFloodStaRateThreshold,
			hwVapAntiAttackDefFloodBlacklistSwitch, hwVapAntiAttackDefFloodRowStatus }
			STATUS current
			DESCRIPTION 
				"Description."
			::= { hwWlanConfigObjectGroups 79 }
			
		-- 1.3.6.1.4.1.2011.6.139.11.2.2.88
		hwBranchGroupGroups OBJECT-GROUP
			OBJECTS { hwBranchGroupUserAccountNumber, hwBranchGroupAPNumber, hwBranchGroupFileStatus,
			hwBranchGroupServerCertFileType, hwBranchGroupServerCertFileName, hwBranchGroupServerCAFileName, hwBranchGroupServerPSKType, hwBranchGroupServerPSKFileName,
			hwBranchGroupServerPSKPassword, hwBranchGroupFileLoadOper, hwBranchGroupFileLoadPercent, hwBranchGroupFileLoadFailedAP, hwBranchGroupRowStatus }
			STATUS current
			DESCRIPTION 
				"Description."
			::= { hwWlanConfigObjectGroups 88 }
			
		-- 1.3.6.1.4.1.2011.6.139.11.2.2.95
		hwApSysBCMCSuppressionGroups OBJECT-GROUP
			OBJECTS { hwApSysBCMCSuppressionSwitch, hwApSysBCMCSuppressionThreshold, hwApSysBCMCSuppressionRowStatus }
			STATUS current
			DESCRIPTION 
				"Description."
			::= { hwWlanConfigObjectGroups 95 }

		-- 1.3.6.1.4.1.2011.6.139.11.2.2.96
		
		hwVAPProfileAntiAttackGroups OBJECT-GROUP
			OBJECTS { hwVAPProfileAntiAttackSwitch, hwVAPProfileAntiAttackStaRateThreshold, hwVAPProfileAntiAttackBlacklistSwitch, hwVAPProfileAntiAttackRowStatus }
			STATUS current
			DESCRIPTION 
				"Description."
			::= { hwWlanConfigObjectGroups 96 }
			
        	END
--
-- HUAWEI-WLAN-CONFIGURATION-MIB.mib
--
