--
-- HUAWEI-SECURITY-UPDATE-MIB.mib
-- MIB generated by MG-SOFT Visual MIB Builder Version 6.0  Build 88
-- Wednesday, September 16, 2015 at 10:30:24
--
--  =============================================================================
-- Copyright (C) 2015 by HUAWEI TECHNOLOGIES. All rights reserved.
--    
-- Description: The MIB is designed to get uapdating database information. 
-- Reference: Huawei Enterprise MIB
-- Version: V1.00
-- History: 
--          Version: V1.00 The initial version created by tengji 90006570. 
-- =============================================================================

	HUAWEI-SECURITY-UPDATE-MIB DEFINITIONS ::= BEGIN
 
		IMPORTS
			enterprises			
				FROM RFC1155-SMI			
			OBJECT-GROUP, NOTIFICATION-GROUP			
				FROM SNMPv2-CONF			
			Integer32, OBJECT-TYPE, MODULE-IDENTITY, NOTIFICATION-TYPE			
				FROM SNMPv2-SMI;				
	 
	  	-- 1.3.6.1.4.1.2011.6.122.76
		hwDatabaseUpdate MODULE-IDENTITY 
		LAST-UPDATED "201509121517Z"		-- September 12, 2015 at 14:55 GMT
		ORGANIZATION 
			"Huawei Technologies Co.,Ltd."
		CONTACT-INFO 
			"Huawei Industrial Base
				Bantian, Longgang
				Shenzhen 518129
				People's Republic of China
				Website: http://www.huawei.com
				Email: support@huawei.com"
		DESCRIPTION 
			"The HUAWEI-SECURITY-UPDATE-MIB contains objects to manage the firewall function of updating database."
		REVISION "201509121517Z"		-- September 12, 2015 at 15:17 GMT
		DESCRIPTION 
			"V1.00, completed the first draft."
		::= { hwSecurity 76 }

--
-- Node definitions
--
	    -- 1.3.6.1.4.1.2011
		huawei OBJECT IDENTIFIER ::= { enterprises 2011 }

		
		-- 1.3.6.1.4.1.2011.6
		huaweiUtility OBJECT IDENTIFIER ::= { huawei 6 }

		
		-- 1.3.6.1.4.1.2011.6.122
		hwSecurity OBJECT IDENTIFIER ::= { huaweiUtility 122 }

	    
		-- 1.3.6.1.4.1.2011.6.122.76.1
		hwDatabaseUpdateNotification OBJECT IDENTIFIER ::= { hwDatabaseUpdate 1 }

		
		-- 1.3.6.1.4.1.2011.6.122.76.1.1
		hwDatabaseUpdateTrapObjects OBJECT IDENTIFIER ::= { hwDatabaseUpdateNotification 1 }

		
		-- 1.3.6.1.4.1.2011.6.122.76.1.1.1
		hwUpdateModuleName OBJECT-TYPE
			SYNTAX OCTET STRING (SIZE (1..64))
			MAX-ACCESS accessible-for-notify
			STATUS current
			DESCRIPTION
				"The module name of updating."
			::= { hwDatabaseUpdateTrapObjects 1 }

		
		-- 1.3.6.1.4.1.2011.6.122.76.1.1.2
		hwPreUpdateVersion OBJECT-TYPE
			SYNTAX OCTET STRING
			MAX-ACCESS accessible-for-notify
			STATUS current
			DESCRIPTION
				"The pre-version of updating."
			::= { hwDatabaseUpdateTrapObjects 2 }

		
		-- 1.3.6.1.4.1.2011.6.122.76.1.1.3
		hwUpdateVersion OBJECT-TYPE
			SYNTAX OCTET STRING
			MAX-ACCESS accessible-for-notify
			STATUS current
			DESCRIPTION
				"The version of updating."
			::= { hwDatabaseUpdateTrapObjects 3 }

		
		-- 1.3.6.1.4.1.2011.6.122.76.1.1.4
		hwUpdateErrCode OBJECT-TYPE
			SYNTAX Integer32
			MAX-ACCESS accessible-for-notify
			STATUS current
			DESCRIPTION
				"Description."
			::= { hwDatabaseUpdateTrapObjects 4 }

		
		-- 1.3.6.1.4.1.2011.6.122.76.2
		hwDatabaseUpdateTraps OBJECT IDENTIFIER ::= { hwDatabaseUpdate 2 }

		
		-- 1.3.6.1.4.1.2011.6.122.76.2.1
		hwDatabaseUpdateSucc NOTIFICATION-TYPE
			OBJECTS { hwUpdateModuleName, hwPreUpdateVersion, hwUpdateVersion }
			STATUS current
			DESCRIPTION 
				"Succeed in updating database."
			::= { hwDatabaseUpdateTraps 1 }

		
		-- 1.3.6.1.4.1.2011.6.122.76.2.2
		hwDatabaseUpdateFail NOTIFICATION-TYPE
			OBJECTS { hwUpdateModuleName, hwPreUpdateVersion, hwUpdateVersion, hwUpdateErrCode }
			STATUS current
			DESCRIPTION 
				"Failed to update database."
			::= { hwDatabaseUpdateTraps 2 }

		
		-- 1.3.6.1.4.1.2011.6.122.76.3
		hwDatabaseUpdateConformance OBJECT IDENTIFIER ::= { hwDatabaseUpdate 3 }

		
		-- 1.3.6.1.4.1.2011.6.122.76.3.1
		hwDatabaseUpdateObjectGroup OBJECT-GROUP
			OBJECTS { hwUpdateModuleName, hwPreUpdateVersion, hwUpdateVersion, hwUpdateErrCode }
			STATUS current
			DESCRIPTION 
				"Description."
			::= { hwDatabaseUpdateConformance 1 }

		
		-- 1.3.6.1.4.1.2011.6.122.76.3.2
		hwDatabaseUpdateTrapGroup NOTIFICATION-GROUP
			NOTIFICATIONS { hwDatabaseUpdateSucc, hwDatabaseUpdateFail }
			STATUS current
			DESCRIPTION 
				"Description."
			::= { hwDatabaseUpdateConformance 2 }

		
	
	END

--
-- HUAWEI-SECURITY-UPDATE-MIB.mib
--
