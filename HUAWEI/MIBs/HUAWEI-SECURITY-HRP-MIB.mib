--
-- HUAWEI-SECURITY-HRP-MIB.mib
-- MIB generated by MG-SOFT Visual MIB Builder Version 4.0 Build 341
-- Thursday, January 15, 2015 at 17:19:35
--

--  =============================================================================
-- Copyright (C) 2012 by HUAWEI TECHNOLOGIES. All rights reserved.
--    
-- Description: The MIB is designed to get HRP information. 
-- Reference: Huawei Enterprise MIB
-- Version: V1.03
-- History: 
--          V1.00 The initial version created by Cao Jiancang 00005275. 
-- =============================================================================

	HUAWEI-SECURITY-HRP-MIB DEFINITIONS ::= BEGIN
 
		IMPORTS
			enterprises			
				FROM RFC1155-SMI			
			SnmpAdminString			
				FROM SNMP-FRAMEWORK-MIB			
			Integer32, Counter32, OBJECT-TYPE, MODULE-IDENTITY, NOTIFICATION-TYPE			
				FROM SNMPv2-SMI			
			MacAddress			
				FROM SNMPv2-TC;
	
	
		-- 1.3.6.1.4.1.2011.6.122.51
		hwHrp MODULE-IDENTITY 
			LAST-UPDATED "201212141000Z"		-- December 14, 2012 at 10:00 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"V1.00
				The HRP mib is for Eudemon and USG product series."
			REVISION "201212141000Z"		-- December 14, 2012 at 10:00 GMT
			DESCRIPTION 
				"V1.00, completed the first draft."
			REVISION "201501161000Z"		-- January 16, 2015 at 10:00 GMT
			DESCRIPTION 
				"V1.01, add the node hwHrpSwitchOverTimes."
			REVISION "201511121000Z"		-- November 12, 2015 at 10:00 GMT
			DESCRIPTION 
				"V1.02, add the node hwHrpSwitchOverTimes."
			REVISION "201511141000Z"		-- November 14, 2015 at 10:00 GMT
			DESCRIPTION 
				"V1.03, add the trap object hwHrpTrapLinkState."
			::= { hwSecurity 51 }

		
	
	
--
-- Node definitions
--
	
--  December 14, 2012 at 10:00 GMT
-- Revision history
-- ===============================================
-- Node definitions
-- ===============================================
-- 1.3.6.1.4.1.2011
		-- 1.3.6.1.4.1.2011
		huawei OBJECT IDENTIFIER ::= { enterprises 2011 }

		
--  1.3.6.1.4.1.2011.6
		-- 1.3.6.1.4.1.2011.6
		huaweiUtility OBJECT IDENTIFIER ::= { huawei 6 }

		
--  1.3.6.1.4.1.2011.6.122
		-- 1.3.6.1.4.1.2011.6.122
		hwSecurity OBJECT IDENTIFIER ::= { huaweiUtility 122 }

		
		-- 1.3.6.1.4.1.2011.6.122.51.1
		hwHrpObjects OBJECT IDENTIFIER ::= { hwHrp 1 }

		
--  ===============================================
-- HrpObject.
-- ===============================================
-- 1.3.6.1.4.1.2011.6.122.51.1.1
		-- 1.3.6.1.4.1.2011.6.122.51.1.1
		hwHrpLocalID OBJECT-TYPE
			SYNTAX MacAddress
			MAX-ACCESS read-only
			STATUS current
			DESCRIPTION
				"The local device ID(The mac address of ethernet interface)."
			::= { hwHrpObjects 1 }

		
--  1.3.6.1.4.1.2011.6.122.51.1.2
		-- 1.3.6.1.4.1.2011.6.122.51.1.2
		hwHrpPeerID OBJECT-TYPE
			SYNTAX MacAddress
			MAX-ACCESS read-only
			STATUS current
			DESCRIPTION
				"The peer device ID(The mac address of ethernet interface)."
			::= { hwHrpObjects 2 }

		
--  1.3.6.1.4.1.2011.6.122.51.1.3
		-- 1.3.6.1.4.1.2011.6.122.51.1.3
		hwHrpState OBJECT-TYPE
			SYNTAX SnmpAdminString
			MAX-ACCESS read-only
			STATUS current
			DESCRIPTION
				"The current state of device."
			::= { hwHrpObjects 3 }

		
--  1.3.6.1.4.1.2011.6.122.51.1.3
		-- 1.3.6.1.4.1.2011.6.122.51.1.4
		hwHrpSwitchOverTimes OBJECT-TYPE
			SYNTAX Counter32
			MAX-ACCESS read-only
			STATUS current
			DESCRIPTION
				"The current number of switchovers (Indication of instabilities)."
			::= { hwHrpObjects 4 }

		
		-- 1.3.6.1.4.1.2011.6.122.51.2
		hwHrpNotification OBJECT IDENTIFIER ::= { hwHrp 2 }

		
		-- 1.3.6.1.4.1.2011.6.122.51.2.1
		hwHrpTrapObjects OBJECT IDENTIFIER ::= { hwHrpNotification 1 }

		
--  ===============================================
-- TrapObject.
-- ===============================================
-- 1.3.6.1.4.1.2011.6.122.51.2.1.1
		-- 1.3.6.1.4.1.2011.6.122.51.2.1.1
		hwHrpTrapOldState OBJECT-TYPE
			SYNTAX SnmpAdminString
			MAX-ACCESS accessible-for-notify
			STATUS current
			DESCRIPTION
				"The old state of hrp."
			::= { hwHrpTrapObjects 1 }

		
--  1.3.6.1.4.1.2011.6.122.51.2.1.2
		-- 1.3.6.1.4.1.2011.6.122.51.2.1.2
		hwHrpTrapNewState OBJECT-TYPE
			SYNTAX SnmpAdminString
			MAX-ACCESS accessible-for-notify
			STATUS current
			DESCRIPTION
				"The new state of hrp."
			::= { hwHrpTrapObjects 2 }

		
--  1.3.6.1.4.1.2011.6.122.51.2.1.3
		-- 1.3.6.1.4.1.2011.6.122.51.2.1.3
		hwHrpTrapLocalPriority OBJECT-TYPE
			SYNTAX Integer32
			MAX-ACCESS accessible-for-notify
			STATUS current
			DESCRIPTION
				"The local priority of hrp."
			::= { hwHrpTrapObjects 3 }

		
--  1.3.6.1.4.1.2011.6.122.51.2.1.4
		-- 1.3.6.1.4.1.2011.6.122.51.2.1.4
		hwHrpTrapPeerPriority OBJECT-TYPE
			SYNTAX SnmpAdminString
			MAX-ACCESS accessible-for-notify
			STATUS current
			DESCRIPTION
				"The peer priority of hrp."
			::= { hwHrpTrapObjects 4 }

		
--  1.3.6.1.4.1.2011.6.122.51.2.1.5
		-- 1.3.6.1.4.1.2011.6.122.51.2.1.5
		hwHrpTrapLocalID OBJECT-TYPE
			SYNTAX MacAddress
			MAX-ACCESS accessible-for-notify
			STATUS current
			DESCRIPTION
				"The local device ID(The mac address of ethernet interface)."
			::= { hwHrpTrapObjects 5 }

		
--  1.3.6.1.4.1.2011.6.122.51.2.1.6
		-- 1.3.6.1.4.1.2011.6.122.51.2.1.6
		hwHrpTrapPeerID OBJECT-TYPE
			SYNTAX MacAddress
			MAX-ACCESS accessible-for-notify
			STATUS current
			DESCRIPTION
				"The peer device ID(The mac address of ethernet interface)."
			::= { hwHrpTrapObjects 6 }

--  1.3.6.1.4.1.2011.6.122.51.2.1.9
		-- 1.3.6.1.4.1.2011.6.122.51.2.1.9
		hwAutocheckTrapString OBJECT-TYPE
			SYNTAX SnmpAdminString
			MAX-ACCESS accessible-for-notify
			STATUS current
			DESCRIPTION
				"The result of comparing configuration of local device and peer device."
			::= { hwHrpTrapObjects 9 }

--  1.3.6.1.4.1.2011.6.122.51.2.1.10
		-- 1.3.6.1.4.1.2011.6.122.51.2.1.10
		hwHrpTrapLinkState OBJECT-TYPE
			SYNTAX SnmpAdminString
			MAX-ACCESS accessible-for-notify
			STATUS current
			DESCRIPTION
				"The link state of HRP."
			::= { hwHrpTrapObjects 10 }

		-- 1.3.6.1.4.1.2011.6.122.51.2.2
		hwHrpTraps OBJECT IDENTIFIER ::= { hwHrpNotification 2 }

		
--  ===============================================
-- definition of traps.      
-- ===============================================                        
		-- 1.3.6.1.4.1.2011.6.122.51.2.2.1
		hwHrpStateChange NOTIFICATION-TYPE
			OBJECTS { hwHrpTrapOldState, hwHrpTrapNewState, hwHrpTrapLocalPriority, hwHrpTrapPeerPriority }
			STATUS current
			DESCRIPTION 
				"HRP state changed."
			::= { hwHrpTraps 1 }

		
		-- 1.3.6.1.4.1.2011.6.122.51.2.2.2
		hwHrpDeviceID NOTIFICATION-TYPE
			OBJECTS { hwHrpTrapLinkState, hwHrpTrapLocalID, hwHrpTrapPeerID }
			STATUS current
			DESCRIPTION 
				"Heartbeat status changed in dual-system hot backup."
			::= { hwHrpTraps 2 }


		-- 1.3.6.1.4.1.2011.6.122.51.2.2.4
		hwHrpAutocheckResult NOTIFICATION-TYPE
			OBJECTS { hwAutocheckTrapString }
			STATUS current
			DESCRIPTION 
				"The result of comparing configuration of local device and peer device."
			::= { hwHrpTraps 4 }

		
	
	END

--
-- HUAWEI-SECURITY-HRP-MIB.mib
--
