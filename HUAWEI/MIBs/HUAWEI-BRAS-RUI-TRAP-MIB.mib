-- ===================================================================
-- Copyright (C) 2019 by HUAWEI TECHNOLOGIES. All rights reserved.
-- Description: The HUAWEI-BRAS-RUI-TRAP-MIB provides information about DataComm TRAPS 
-- Reference:
-- Version: V1.00
-- ===================================================================


    HUAWEI-BRAS-RUI-TRAP-MIB DEFINITIONS ::= BEGIN
 
        IMPORTS                                            
            OBJECT-GROUP, MODULE-COMPLIANCE, NOTIFICATION-GROUP            
                FROM SNMPv2-CONF            
            DisplayString, RowStatus                        
                FROM SNMPv2-TC
            TimeTicks, Integer32, Unsigned32, IpAddress, Counter32, OBJECT-TYPE, 
            MODULE-IDENTITY, NOTIFICATION-TYPE            
                FROM SNMPv2-SMI
            hwDatacomm            
                FROM HUAWEI-MIB;
    
    
        hwBrasRuiTrap MODULE-IDENTITY 
            LAST-UPDATED "201906240000Z"        
            ORGANIZATION 
                  "Huawei Technologies Co.,Ltd."
            CONTACT-INFO 
                  "Huawei Industrial Base Bantian, Longgang Shenzhen 518129 People's Republic of China Website: http://www.huawei.com Email: support@huawei.com "
            DESCRIPTION 
                "This is the BRAS RUI TRAP mib definition for DataCom."
            REVISION    "201906240000Z"   
            DESCRIPTION "V1.00, initial version."
    
            ::= { hwDatacomm 361 }

    
        hwBRASRUITRAPObjects OBJECT IDENTIFIER ::= { hwBrasRuiTrap 1 }
        -- 1.3.6.1.4.1.2011.5.25.361.1.1
        hwBrasRbsSynTime OBJECT-TYPE
            SYNTAX Unsigned32
            MAX-ACCESS accessible-for-notify
            STATUS current
            DESCRIPTION
                "Batch backup duration."
            ::= { hwBRASRUITRAPObjects 1 }  
        
        -- 1.3.6.1.4.1.2011.5.25.361.1.2
        hwBrasRbsSynState OBJECT-TYPE
            SYNTAX Unsigned32
            MAX-ACCESS accessible-for-notify
            STATUS current
            DESCRIPTION
                "Current synchronization status."   
            ::= { hwBRASRUITRAPObjects 2 }

        -- 1.3.6.1.4.1.2011.5.25.361.1.3
        hwBrasRbsName OBJECT-TYPE
                 SYNTAX DisplayString
                 MAX-ACCESS accessible-for-notify
                 STATUS current
                 DESCRIPTION
                   "RBS."
                 ::= { hwBRASRUITRAPObjects 3 }
        
        hwBRASRUITRAPTrap OBJECT IDENTIFIER ::= { hwBrasRuiTrap 2 }
            -- 1.3.6.1.4.1.2011.5.25.361.2.1
            hwBrasRbsConnectErr NOTIFICATION-TYPE
            OBJECTS {hwBrasRbsName}
            STATUS current
            DESCRIPTION
                "RBS heartbeat signals were abnormal. "
            ::= { hwBRASRUITRAPTrap 1 }
            
            -- 1.3.6.1.4.1.2011.5.25.361.2.2
            hwBrasRbsConnectErrResume NOTIFICATION-TYPE
            OBJECTS {hwBrasRbsName}
            STATUS current
            DESCRIPTION
                "RBS heartbeat recovers."
            ::= { hwBRASRUITRAPTrap 2 }    

            -- 1.3.6.1.4.1.2011.5.25.361.2.3
            hwBrasRbsSyncErr NOTIFICATION-TYPE
            OBJECTS {hwBrasRbsName, hwBrasRbsSynTime, hwBrasRbsSynState}
            STATUS current
            DESCRIPTION
                "Batch backup between the master and backup devices persisted for a long time. "
            ::= { hwBRASRUITRAPTrap 3 }
            
            -- 1.3.6.1.4.1.2011.5.25.361.2.4
            hwBrasRbsSyncErrResume NOTIFICATION-TYPE
            OBJECTS {hwBrasRbsName, hwBrasRbsSynTime, hwBrasRbsSynState}
            STATUS current
            DESCRIPTION
                "RBS batch backup ended. "
            ::= { hwBRASRUITRAPTrap 4 }

            -- 1.3.6.1.4.1.2011.5.25.361.2.5
            hwBrasRbsTcpStateErr NOTIFICATION-TYPE
            OBJECTS {hwBrasRbsName}
            STATUS current
            DESCRIPTION
                "The TCP connection of the BRAS RBS component on the slave main control board was in the connected state."
            ::= { hwBRASRUITRAPTrap 5 }
            
            -- 1.3.6.1.4.1.2011.5.25.361.2.6
            hwBrasRbsTcpStateErrResume NOTIFICATION-TYPE
            OBJECTS {hwBrasRbsName}
            STATUS current
            DESCRIPTION
                "The TCP connection of the BRAS RBS component on the slave main control board was not in the connected state."
            ::= { hwBRASRUITRAPTrap 6 }

            -- 1.3.6.1.4.1.2011.5.25.361.2.7
            hwBrasRuiTriggerErr NOTIFICATION-TYPE
            STATUS current
            DESCRIPTION
                "User services on the RUI backup device failed to be recovered for a long period of time."
            ::= { hwBRASRUITRAPTrap 7 }
            
            -- 1.3.6.1.4.1.2011.5.25.361.2.8
            hwBrasRuiTriggerErrResume NOTIFICATION-TYPE
            STATUS current
            DESCRIPTION
                "User services on the RUI backup device recovered."
           ::= { hwBRASRUITRAPTrap 8 }
        
        hwBRASRUITRAPConformance OBJECT IDENTIFIER ::= { hwBrasRuiTrap 3 }

        -- 1.3.6.1.4.1.2011.5.25.361.3.1
        hwBRASRUITRAPCompliances OBJECT IDENTIFIER ::= { hwBRASRUITRAPConformance 1 }

       -- 1.3.6.1.4.1.2011.5.25.361.3.1.1
       hwBRASRUITRAPCompliance MODULE-COMPLIANCE
       STATUS current
       DESCRIPTION 
              "Compliance statement for agents that provide full support for hwBRASRUITRAPMIB."
       MODULE -- this module
              MANDATORY-GROUPS { hwBRASRUIObjectGroup }
       ::= { hwBRASRUITRAPCompliances 1 }

       -- 1.3.6.1.4.1.2011.5.25.361.3.2
       hwBRASRUITrapGroups OBJECT IDENTIFIER ::= { hwBRASRUITRAPConformance 2 }

       -- 1.3.6.1.4.1.2011.5.25.361.3.2.1
       hwBRASRUIObjectGroup OBJECT-GROUP
              OBJECTS { hwBrasRbsSynTime, hwBrasRbsSynState, hwBrasRbsName}
              STATUS current
              DESCRIPTION 
                     "Group for BRAS RUI mib objects."
              ::= { hwBRASRUITrapGroups 1 }

       -- 1.3.6.1.4.1.2011.5.25.361.3.2.2
       hwBRASRUITrapGroup NOTIFICATION-GROUP
              NOTIFICATIONS {hwBrasRbsConnectErr, hwBrasRbsConnectErrResume, hwBrasRbsSyncErr, hwBrasRbsSyncErrResume, hwBrasRbsTcpStateErr, hwBrasRbsTcpStateErrResume, hwBrasRuiTriggerErr, hwBrasRuiTriggerErrResume}
              STATUS current
              DESCRIPTION 
                     "Group for all BRAS RUI mibs."
              ::= { hwBRASRUITrapGroups 2 }


    END
