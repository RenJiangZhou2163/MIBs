-- =================================================================
-- Description: IPV6-TC mib
-- Reference:   This mib was extracted from RFC2465
-- =================================================================
IPV6-TC DEFINITIONS ::= BEGIN

    IMPORTS
        Integer32                FROM SNMPv2-SMI
        TEXTUAL-CONVENTION       FROM SNMPv2-TC;


    -- definition of textual conventions
    Ipv6Address ::= TEXTUAL-CONVENTION
        DISPLAY-HINT "2x:"
        STATUS       current
        DESCRIPTION
            "This data type is used to model IPv6 addresses.
             This is a binary string of 16 octets in network
             byte-order."
        SYNTAX       OCTET STRING (SIZE (16))

    Ipv6AddressPrefix ::= TEXTUAL-CONVENTION
        DISPLAY-HINT "2x:"
        STATUS       current
        DESCRIPTION
            "This data type is used to model IPv6 address
            prefixes. This is a binary string of up to 16
            octets in network byte-order."
        SYNTAX       OCTET STRING (SIZE (0..16))

    Ipv6AddressIfIdentifier ::= TEXTUAL-CONVENTION
        DISPLAY-HINT "2x:"
        STATUS       current
        DESCRIPTION
            "This data type is used to model IPv6 address
            interface identifiers. This is a binary string
            of up to 8 octets in network byte-order."
        SYNTAX      OCTET STRING (SIZE (0..8))

    Ipv6IfIndex ::= TEXTUAL-CONVENTION
        DISPLAY-HINT "d"
        STATUS       current
        DESCRIPTION
            "A unique value, greater than zero for each
            internetwork-layer interface in the managed
            system. It is recommended that values are assigned
            contiguously starting from 1. The value for each
            internetwork-layer interface must remain constant
            at least from one re-initialization of the entity's
            network management system to the next
            re-initialization."
        SYNTAX       Integer32 (1..2147483647)

    Ipv6IfIndexOrZero ::= TEXTUAL-CONVENTION
        DISPLAY-HINT "d"
        STATUS       current
        DESCRIPTION
            "This textual convention is an extension of the
            Ipv6IfIndex convention.  The latter defines
            a greater than zero value used to identify an IPv6
            interface in the managed system.  This extension
            permits the additional value of zero.  The value
            zero is object-specific and must therefore be
            defined as part of the description of any object
            which uses this syntax.  Examples of the usage of
            zero might include situations where interface was
            unknown, or when none or all interfaces need to be
            referenced."
        SYNTAX       Integer32 (0..2147483647)

END
-- 
--    Copyright (C) The Internet Society (1997).  All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE."
