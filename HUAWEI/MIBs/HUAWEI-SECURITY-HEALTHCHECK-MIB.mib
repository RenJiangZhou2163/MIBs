--
-- HUAWEI-SECURITY-HEALTHCHECK-MIB.mib
-- MIB generated by MG-SOFT Visual MIB Builder Version 4.0 Build 341
-- Tuesday, August 19, 2014 at 18:21:11
--
-- 
--  =============================================================================
-- Copyright (C) 2014 by HUAWEI TECHNOLOGIES. All rights reserved.
--    
-- Description: The MIB is designed to get HRP information. 
-- Reference: Huawei Enterprise MIB
-- Version: V1.00
-- History: 
--          V1.00 The initial version created by Xuyanping 00105200. 
-- =============================================================================

	HUAWEI-SECURITY-HEALTHCHECK-MIB DEFINITIONS ::= BEGIN
 
		IMPORTS
			enterprises			
				FROM RFC1155-SMI			
			OBJECT-GROUP, MODULE-COMPLIANCE, NOTIFICATION-GROUP			
				FROM SNMPv2-CONF			
			OBJECT-TYPE, MODULE-IDENTITY, NOTIFICATION-TYPE			
				FROM SNMPv2-SMI;
	
	
		-- 1.3.6.1.4.1.2011.6.122.68
		hwHealthCheck MODULE-IDENTITY 
			LAST-UPDATED "201401071609Z"		-- January 07, 2014 at 16:09 GMT
			ORGANIZATION 
				"Huawei Technologies Co.,Ltd."
			CONTACT-INFO 
				"Huawei Industrial Base
                                 Bantian, Longgang
                                 Shenzhen 518129
                                 People's Republic of China
                                 Website: http://www.huawei.com
                                 Email: support@huawei.com"
			DESCRIPTION 
				"
				V1.00
				The HUAWEI-SECURITY-HEALTHCHECK-MIB contains objects to manage the firewall HEALTHCHECK module.
				"
			--  Revision history
				 REVISION    "201401071609Z"
                                 DESCRIPTION "V1.00, completed the first draft."
			::= { hwSecurity 68 }

		
	

	
-- 
-- Node definitions
-- 
-- 1.3.6.1.4.1.2011
-- 1.3.6.1.4.1.2011
-- 1.3.6.1.4.1.2011
		-- 1.3.6.1.4.1.2011
		huawei OBJECT IDENTIFIER ::= { enterprises 2011 }

		
--    1.3.6.1.4.1.2011.6
-- 1.3.6.1.4.1.2011.6
-- 1.3.6.1.4.1.2011.6
		-- 1.3.6.1.4.1.2011.6
		huaweiUtility OBJECT IDENTIFIER ::= { huawei 6 }

		
--    1.3.6.1.4.1.2011.6.122
-- 1.3.6.1.4.1.2011.6.122
-- 1.3.6.1.4.1.2011.6.122
		-- 1.3.6.1.4.1.2011.6.122
		hwSecurity OBJECT IDENTIFIER ::= { huaweiUtility 122 }

		
--   1.3.6.1.4.1.2011.6.122.68.1
-- 1.3.6.1.4.1.2011.6.122.68.1
		-- 1.3.6.1.4.1.2011.6.122.68.1
		hwHealthCheckNotification OBJECT IDENTIFIER ::= { hwHealthCheck 1 }

		
--   1.3.6.1.4.1.2011.6.122.68.1.1
-- 1.3.6.1.4.1.2011.6.122.68.1.1
		-- 1.3.6.1.4.1.2011.6.122.68.1.1
		hwHealthCheckTrapObjects OBJECT IDENTIFIER ::= { hwHealthCheckNotification 1 }

		
--    1.3.6.1.4.1.2011.6.122.45.1.1.1
-- 1.3.6.1.4.1.2011.6.122.45.1.1.2	
-- 1.3.6.1.4.1.2011.6.122.68.1.1.2
-- 1.3.6.1.4.1.2011.6.122.68.1.1.2
		-- 1.3.6.1.4.1.2011.6.122.68.1.1.1
		hwHealthCheckName OBJECT-TYPE
			SYNTAX OCTET STRING
			MAX-ACCESS accessible-for-notify
			STATUS current
			DESCRIPTION
				"The status of the Health check."
			::= { hwHealthCheckTrapObjects 1 }

		
--   1.3.6.1.4.1.2011.6.122.68.1.1.4
-- 1.3.6.1.4.1.2011.6.122.68.1.1.4
		-- 1.3.6.1.4.1.2011.6.122.68.1.1.2
		hwHealthCheckStatus OBJECT-TYPE
			SYNTAX OCTET STRING
			MAX-ACCESS accessible-for-notify
			STATUS current
			DESCRIPTION
				"Description."
			::= { hwHealthCheckTrapObjects 2 }

		
--   1.3.6.1.4.1.2011.6.122.68.2
-- 1.3.6.1.4.1.2011.6.122.68.2
		-- 1.3.6.1.4.1.2011.6.122.68.2
		hwHealthCheckTraps OBJECT IDENTIFIER ::= { hwHealthCheck 2 }

		
--    ===============================================
-- definition of traps.      
-- ===============================================                                
-- 1.3.6.1.4.1.2011.6.122.68.2.1
-- 1.3.6.1.4.1.2011.6.122.68.2.1
		-- 1.3.6.1.4.1.2011.6.122.68.2.1
		hwHealthCheckUp NOTIFICATION-TYPE
			OBJECTS { hwHealthCheckName, hwHealthCheckStatus }
			STATUS current
			DESCRIPTION 
				"The Health check changes to up"
			::= { hwHealthCheckTraps 1 }

		
--   1.3.6.1.4.1.2011.6.122.68.2.2
-- 1.3.6.1.4.1.2011.6.122.68.2.2
		-- 1.3.6.1.4.1.2011.6.122.68.2.2
		hwHealthCheckDown NOTIFICATION-TYPE
			OBJECTS { hwHealthCheckName, hwHealthCheckStatus }
			STATUS current
			DESCRIPTION 
				"The Health check changes to down"
			::= { hwHealthCheckTraps 2 }

		
--   1.3.6.1.4.1.2011.6.122.68.3
-- 1.3.6.1.4.1.2011.6.122.68.3
		-- 1.3.6.1.4.1.2011.6.122.68.3
		hwHealthCheckConformance OBJECT IDENTIFIER ::= { hwHealthCheck 3 }

		
--   1.3.6.1.4.1.2011.6.122.68.3.1
-- 1.3.6.1.4.1.2011.6.122.68.3.1
		-- 1.3.6.1.4.1.2011.6.122.68.3.1
		hwHealthCheckCompliances OBJECT IDENTIFIER ::= { hwHealthCheckConformance 1 }

		
--   1.3.6.1.4.1.2011.6.122.68.3.1.1
-- this module
-- 1.3.6.1.4.1.2011.6.122.68.3.1.1
-- this module
		-- 1.3.6.1.4.1.2011.6.122.68.3.1.1
		hwHealthCheckCompliance MODULE-COMPLIANCE
			STATUS current
			DESCRIPTION 
				"Description."
			MODULE -- this module
				MANDATORY-GROUPS { hwHealthCheckObjectGroup, hwHealthCheckTrapGroup }
			::= { hwHealthCheckCompliances 1 }

		
--   1.3.6.1.4.1.2011.6.122.68.3.2
-- 1.3.6.1.4.1.2011.6.122.68.3.2
		-- 1.3.6.1.4.1.2011.6.122.68.3.2
		hwHealthCheckMibGroups OBJECT IDENTIFIER ::= { hwHealthCheckConformance 2 }

		
--   1.3.6.1.4.1.2011.6.122.68.3.2.1
-- 1.3.6.1.4.1.2011.6.122.68.3.2.1
		-- 1.3.6.1.4.1.2011.6.122.68.3.2.1
		hwHealthCheckObjectGroup OBJECT-GROUP
			OBJECTS { hwHealthCheckName, hwHealthCheckStatus }
			STATUS current
			DESCRIPTION 
				"Description."
			::= { hwHealthCheckMibGroups 1 }

		
--   1.3.6.1.4.1.2011.6.122.68.3.2.2
-- 1.3.6.1.4.1.2011.6.122.68.3.2.2
		-- 1.3.6.1.4.1.2011.6.122.68.3.2.2
		hwHealthCheckTrapGroup NOTIFICATION-GROUP
			NOTIFICATIONS { hwHealthCheckUp, hwHealthCheckDown }
			STATUS current
			DESCRIPTION 
				"Description."
			::= { hwHealthCheckMibGroups 2 }

		
	
	END

--
-- HUAWEI-SECURITY-HEALTHCHECK-MIB.mib
--
