-- =================================================================
-- Copyright (C) 2021 by  HUAWEI TECHNOLOGIES. All rights reserved.
--
-- DESCRIPTION:  HUAWEI-AAA-MIB
-- Reference:  
-- Version: V5.00
-- History:
--         v3.04
--         modified by huangjun 2009-12-08
--         modified by z57927   2010-10-18 
--         modified by w00127306   2010-10-18 
--         modified by n00183914  2011-11-10
--         modified by g00141720  2012-12-18
--         modified by l00207906  2013-4-17
--         modified by w00221551  2013-7-19
--         modified by c67804  2013-10-15
--         modified by h00250972 2013-11-28
--         modified by l00163539 2013-12-17    
--         modified by l00181184 2014-03-06
--         modified by h00250972 2014-03-18
--         modified by w00193520 2014-03-24
--         modified by m00181544 2014-04-17
--         modified by z00253751 2014-06-17
--         modified by n00249897 2014-07-08
--         modified by j00221821 2014-08-06
--         modified by j00139153 2014-08-12
--         modified by m00181544 2014-08-20
--         modified by q00282961 2014-08-29
--         modified by yWX222555 2014-09-03
--         modified by w00102097 2014-09-06
--         modified by h63155    2014-09-21
--         modified by g00304944  2014-12-26
--         modified by w00213468  2014-12-27
--         modified by w00280908 2015-1-17
--         modified by w00289258 2015-01-23
--         modified by q00278806 2015-03-20
--         modified by d00284225 2015-04-23
--         modified by l00199557 2015-07-07
--         modified by z00242837 2015-07-16
--         modified by z00242837 2015-07-28
--         modified by d00289266 2015-07-28
--         modified by z00297089 2015-07-29
--         modified by w00215195 2015-07-29
--         modified by l00347324 2015-07-31
--         modified by s00292246 2015-08-08
--         modified by z00242837 2015-08-26
--         modified by t00305052 2015-09-11
--         modified by w00196787 2015-12-01
--         modified by w00280908 2015-12-31
--         modified by j00333366 2016-01-26
--         modified by d00309882 2016-02-16
--         modified by g00324876 2016-03-14
--         modified by l00347324  2016-03-15
--         modified by l00347174  2016-03-21
--         modified by c00350813 2016-03-28
--         modified by  l00351244 2016-04-05
--         modified by  l00347324 2016-04-08
--         modified by  d00289266 2016-04-19
--         modified by  h00357305 2016-05-14
--         modified by  h00350813 2016-05-18
--         modified by  t00298981 2016-06-17
--         modified by  l00368985 2016-06-22
--         modified by  z00356298 2016-08-04
--         modified by  z00347321 2016-08-12
--         modified by  zwx349005 2016-08-26
--         modified by  l00368985 2016-09-19
--         modified by  zwx349005 2016-09-27
--         modified by  d00289266 2016-09-27
--         modified by  x00342537 2017-01-12
--         modified by  y00377742 2017-01-16
--         modified by  h00317426 2017-02-13
--         modified by  zwx356683 2017-03-23
--         modified by  j00308710 2017-04-27
--         modified by  z00299087 2017-05-03
--         modified by  l00347324 2017-05-23
--         modified by  z00370669 2017-05-31
--         modified by  y00356406 2017-06-21
--         modified by  d00289266 2017-06-29
--         modified by  s00292246 2017-07-17
--         modified by  l00368985 2017-07-20
--         modified by  l00368985 2017-08-08
--         modified by  z00370669 2017-08-26
--         modified by  l00413857 2017-08-31
--         modified by  l00347324 2017-09-01
--         modified by  f00268918 2017-09-26
--         modified by  c00396233 2017-09-28
--         modified by  l00347324 2017-12-05
--         modified by  w00196787 2017-12-13
--         modified by  w00347324 2017-12-25
--         modified by  lwx382209 2018-01-22
--         modified by  x00403698 2018-01-26
--         modified by  lwx382209 2018-01-29
--         modified by  l00430165 2018-03-02
--         modified by  z00234140 2018-04-12
--         modified by  l00316515 2018-05-15
--         modified by  l00369723 2018-05-21
--         modified by  s00292246 2018-05-25
--         modified by  z00348688 2018-05-30
--         modified by  h00421701 2018-06-11
--         modified by  l00316515 2018-07-12
--         modified by  l00316515 2018-07-20
--         modified by  wx307392 2018-07-25
--         modified by  q00380115 2018-08-09
--         modified by  h00421701 2018-09-05
--         modified by  d00390143 2018-11-02
--         modified by  h00421701 2018-11-22
--         modified by  s00451222 2018-12-29
--         modified by  w00416141 2019-01-04
--         modified by  zwx386338 2019-01-30
--         modified by  w00421824 2019-02-20
--         modified by  h00421701 2019-02-22
--         modified by  w00416141 2019-03-25
--         modified by  z00450253 2019-03-28
--         modified by  w00416141 2019-04-13
--         modified by  z00346464 2019-04-29
--         modified by  s00475914 2019-05-08
--         modified by  d00390143 2019-06-04
--         modified by  w00416141 2019-06-13
--         modified by s00504273 2019-06-20 
--         modified by l00316515 2019-08-06    
--         modified by s00292246 2019-09-11
--         modified by l00430195 2019-09-21
--         modified by h00494426 2019-10-11
--         modified by p00455820 2019-10-29
--         modified by s00292246 2019-10-29
--         modified by s00504273 2019-11-05
--         modified by h00494426 2019-11-15
--         modified by l00430195 2019-12-04
--         modified by h00494426 2019-12-09
--         modified by h00494426 2019-12-30
--         modified by s00504273 2020-01-15
--         modified by w00466301 2020-01-17
--         modified by z00385571 2020-03-06
--         modified by w00539529 2020-03-13
--         modified by w00539529 2020-04-30
--         modified by cwx777841 2020-08-08
--         modified by w00416141 2020-09-29
--         modified by l00566851 2020-11-26
--         modified by xwx926043 2021-01-04
--         modified by w00416141 2021-02-04
--         modified by w00416141 2021-03-03
--         modified by z00586255 2021-04-14
--         modified by xwx926043 2021-04-16
--         modified by z00586255 2021-04-19
--         modified by z30004099 2021-07-22
--         modified by z00346464 2021-09-03
-- =================================================================

    HUAWEI-AAA-MIB DEFINITIONS ::= BEGIN

        IMPORTS 
            huaweiMgmt            
                FROM HUAWEI-MIB            
            IpAddress, Unsigned32, Counter64, OBJECT-TYPE, MODULE-IDENTITY, NOTIFICATION-TYPE,
            Integer32,Counter32            
                FROM SNMPv2-SMI   
		MODULE-COMPLIANCE,OBJECT-GROUP,NOTIFICATION-GROUP
		 FROM SNMPv2-CONF	
            DisplayString, RowStatus, TruthValue, MacAddress, DateAndTime            
                FROM SNMPv2-TC
            Ipv6Address, Ipv6AddressIfIdentifier, Ipv6AddressPrefix
                FROM IPV6-TC;

        hwAaa MODULE-IDENTITY 
            LAST-UPDATED "202109031700Z"
            ORGANIZATION "Huawei Technologies Co.,Ltd."
            CONTACT-INFO 
                "Huawei Industrial Base
                 Bantian, Longgang
                 Shenzhen 518129
                 People's Republic of China
                 Website: http://www.huawei.com
                 Email: support@huawei.com"

             DESCRIPTION
             "Modify hwDomainAcctRspFailuresNum,hwDomainAcctRequestsRcvNum,hwDomainAcctRspSuccessNum,hwDomainAuthenAcceptsNum,hwDomainAuthenRejectsNum,hwDomainAuthenRequestsRcvNum."
             REVISION    "202109031700Z"

             DESCRIPTION
             "Add hwPassChangeOfflineEnable"
             REVISION    "202107111700Z"

             DESCRIPTION
             "Modify the datatype of hwAccessIdleCutTime, hwAccessTimeLimit and hwAAAAccessIdleCutTime."
             REVISION    "202106241521Z"

             DESCRIPTION
             "Rollback the modification of enum node."
             REVISION    "202104192006Z"

             DESCRIPTION
             "Modify the description of hwAuthorCmdLevel, hwAuthorCmdMode and hwAuthorCmdRowStatus."
             REVISION    "202104161015Z"

             DESCRIPTION
             "Modify the value of enum type"
             REVISION    "202104141143Z"

             DESCRIPTION
             "Modify the description of hwPevlanStatTable"
             REVISION    "202103031222Z"

             DESCRIPTION
             "Add mib table hwPevlanStatTable"
             REVISION    "202102042012Z"

             DESCRIPTION
             "Change the unit of hwAccessEntry and hwAAAAccessEntry from kbps to kbit/s."
             REVISION    "202101040935Z"

            DESCRIPTION
             "Modify the description of hwSlotConnectNumMaxOnlineNum"
             REVISION    "202011261700Z"

            DESCRIPTION
             "Modify hwCachetoFTPFail, hwHDtoFTPFail"
             REVISION    "202011131700Z"

             DESCRIPTION
             "Modify the max value of hwSlotConnectNumSlot, hwSlotCardConnectNumSlot and hwSlotAccessUserStatSlot from 199999 to 2147483647"
             REVISION    "202009291725Z"

             DESCRIPTION
             "Add hwAcctIpSeparate"
             REVISION    "202009111700Z"

             DESCRIPTION
             "Modify hwAAADomainIPV6PoolPosition, hwAAADomainIPPoolPosition"
             REVISION    "202008221700Z"

             DESCRIPTION
             "Modify hwIPv6PoolLowerLimitWarningThreshold,hwPoolLowerLimitWarningThreshold"
             REVISION    "202008080930Z"

             DESCRIPTION
             "Modify hwAAADomainIPV6PoolPosition"
             REVISION    "202007161100Z"

             DESCRIPTION
             "Modify hwAAAAccessTimeLimit"
             REVISION    "202007101700Z"
            
             DESCRIPTION
             "Modify hwAAADomainIPV6PoolTable, hwAAADomainIPV6PoolEntry, hwAAADomainIPV6PoolName, hwAAADomainIPV6PoolIndex, hwAAADomainIPV6PoolPosition"
             REVISION    "202007031200Z"

             DESCRIPTION
             "Modify hwServiceSchemeIdleCutTime, hwServiceSchemeIdleCutFlow"
             REVISION    "202003131616Z"

             DESCRIPTION
             "add hwServerNoRespAcct, hwServerNoRespAuthor"
             REVISION    "202003131616Z"

             DESCRIPTION  
             "Modify hwDomainAccessLimitNum range."
             REVISION    "202003061958Z"  

             DESCRIPTION
             "add hwAAACuDomainTotalOnlineNum, hwAAACuDomainIPv4OnlineNum, hwAAACuDomainIPv6OnlineNum, hwAAACuDomainDualOnlineNum, hwAAACuUserType, hwAAACuUserTypeTotalOnlineNum, hwAAACuUserTypeIPv4OnlineNum, hwAAACuUserTypeIPv6OnlineNum, hwAAACuUserTypeDualOnlineNum"
             REVISION    "202001171956Z"

             DESCRIPTION
             "modify hwQuieterUserClearAlarm, hwQuieterUserMaxAlarm, hwQuieterPortClearAlarm, hwQuieterPortMaxAlarm, hwQuieterUserType, hwQuieterUserCurrentThreshold, hwQuieterUserLowerLimitThreshold, hwQuieterUserUpperLimitThreshold, hwQuieterPortIfName, hwQuieterPortCurrentThreshold, hwQuieterPortUserNum, hwQuieterPortLowerLimitThreshold, hwQuieterPortUpperLimitThreshold"
             REVISION    "202001152204Z"

             DESCRIPTION
             "add hwQuieterUserClearAlarm, hwQuieterUserMaxAlarm, hwQuieterPortClearAlarm, hwQuieterPortMaxAlarm, hwQuieterUserType, hwQuieterUserCurrentThreshold, hwQuieterUserLowerLimitThreshold, hwQuieterUserUpperLimitThreshold, hwQuieterPortIfName, hwQuieterPortCurrentThreshold, hwQuieterPortUserNum, hwQuieterPortLowerLimitThreshold,    hwQuieterPortUpperLimitThreshold"
             REVISION    "201912300730Z"   

             DESCRIPTION
             "add hwMaxUclGroupIpNumAlarm, hwMaxUclGroupIpNumClearAlarm, hwGroupNum, hwMaxUclGroupIpNumAlarmRate, hwIPGroupChannelUp, hwIPGroupChannelDown, hwIPGroupServiceIPAddress, hwIPGroupServicePortName, hwPkiDomain,add hwHacaChannelUp, hwHacaChannelDown, hwHacaStateChangeServerIp, hwHacaStateChangeServerPortNum"
             REVISION    "201912091509Z"   

             DESCRIPTION
             "add hwServiceSchemeRedirectIPv6ACL"
             REVISION    "201912041142Z"

              DESCRIPTION
             "add hwPPPMaxUserSlot, hwPPPMaxUserNum, hwPPPMaxPercentage, hwMacQuietUserSpec, hwMacUserPercentage, hwLowerMacUserPercentage, hwUpperMacUserPercentage, hwPPPMaxUserAlarm, hwPPPMaxUserClearAlarm, hwMacQuietMaxUserAlarm, hwMacQuietUserClearAlarm"
             REVISION    "201911150930Z"              

             DESCRIPTION
             "add hwRemoteAccessRetryInterval, hwRemoteAccessRetryTime, hwRemoteAccessBlockTime, hwRemoteAdminRetryInterval, hwRemoteAdminRetryTime, hwRemoteAdminBlockTime,
             modify hwBlockDisable,hwRemoteRetryInterval, hwRemoteRetryTime, hwRemoteBlockTime " 
             REVISION    "201911051652Z"              

             DESCRIPTION
             "modify hwAAADomainIPPoolConstantIndex"
             REVISION    "201910291517Z"
           
             DESCRIPTION
             "modify userAuthenticationFreeRuleExtRowStatus"
             REVISION    "201910291516Z"

             DESCRIPTION
             "add userAuthenProfileMacFirstForce"
             REVISION    "201910111746Z"

             DESCRIPTION
             "add hwLamPswComplexityCheckMethod" 
             REVISION    "201909211134Z"

             DESCRIPTION
             "modify hwUserAuthorState in hwAAAOnlineFailRecordTable" 
             REVISION    "201909111604Z" 
             
             DESCRIPTION
             "modify hwAccessIPv6WaitDelay,hwAAAAccessIPv6WaitDelay" 
             REVISION    "201908131604Z"  
             
             DESCRIPTION
             "add hwAdminDefaultPasswordAlarm" 
             REVISION    "201908131604Z"  

            DESCRIPTION
             "modify hwOnlineUserNumLowerLimitCpInstanceId, hwOnlineUserNumUpperLimitCpInstanceId" 
             REVISION    "201908061755Z"  

             DESCRIPTION
             "Add hwDomainAcctCopyRdsServerName, userAuthenProfileAcctRdsServerName" 
             REVISION    "201906261506Z"  
            
             DESCRIPTION
             "add hwChgPswVertifyFlag" 
             REVISION    "201906201431Z"
        
              DESCRIPTION
             "modify the minimum of hwAAAAccessCARUpCIR,
                                                   hwAAAAccessCARUpPIR,
                                                   hwAAAAccessCARUpCBS,
                                                   hwAAAAccessCARDnCIR,
                                                   hwAAAAccessCARDnPIR,
                                                   hwAAAAccessCARDnCBS,
                                                   hwAccessCARUpCIR,
                                                   hwAccessCARUpPIR,
                                                   hwAccessCARUpCBS,
                                                   hwAccessCARUpPBS,
                                                   hwAccessCARDnCIR,
                                                   hwAccessCARDnPIR,
                                                  hwAccessCARDnCBS to 0." 
             REVISION    "201906131501Z"  
 
            DESCRIPTION
             "extend the scope of hwDomainIdleCutTime" 
             REVISION    "201906041202Z"  

             DESCRIPTION
             "Add hwOperatorName, Add hwAAAUserName, Add hwChangePasswordAlarm" 
             REVISION    "201905080918Z"  

             DESCRIPTION  
             "Add hwAAACUDomainNatStateAlarm and hwAAACUDomainNatStateResume"
             REVISION    "201904291121Z"            

            DESCRIPTION
             "Modify the datatype of hwAAAOfflineIndex to Unsigned32" 
             REVISION    "201904131619Z"  

            DESCRIPTION
            "extend the scope of hwAuthenMethod and hwAuthorMethod" 

             REVISION    "201903281100Z"  
             DESCRIPTION  
             "Add userAuthenProfileHacaServerName"

             REVISION    "201903251712Z"  
             DESCRIPTION  
            "Modify range of hwIdleTimeLength" 
             
             REVISION    "201902221637Z"  
             DESCRIPTION  
            "Add hwDot1xAccessProfileDot1xNoResponse"     

             REVISION    "201902201508Z"  
             DESCRIPTION  
            "Add hwAuthenTypeAdminChap"     

             REVISION    "201901301659Z"  
             DESCRIPTION  
            "Modify hwIPv6CPWaitDHCPv6Delay,Modify range of hwSlotCardConnectNumSlot ,hwSlotAccessUserStatSlot ,hwAAAPwifAccessIPv6ManagedAddressFlag ,hwAAAPwifAccessIPv6OtherFlag."   
     
             REVISION    "201901241659Z"  
             DESCRIPTION  
            "Modify hwAccessTable"      
    
             REVISION    "201901141549Z"  
             DESCRIPTION  
            "Modify hwAccessIndex,hwAAAAccessIndex,hwVpnAccessUserStatUserStat,hwInterfaceAccessUserStatUserStat,hwDomainAccessUserStatUserStat,
                         hwSlotAccessUserStatUserStat,hwAAAInboundVPNAccessUserStat,hwAAAPwifSlotAccessUserStatUserStat,
                         hwAAAPwifAccessIndex,hwOfflineRecordUserAuthorState"     
			
            REVISION    "201812292144Z"  
            DESCRIPTION  
            "Add hwPortalAccessProfileLocalServerAccessCode"

            REVISION    "201811221026Z"  
            DESCRIPTION  
            "Add hwServiceSchemePriority"  

            REVISION    "201811021659Z"  
            DESCRIPTION  
            "Add hwAAALnsUserOnlineNum, add hwAAALnsUserMaxNum, add hwAAALnsUserNumOverLimitAlarm,  add hwAAALnsUserNumOverLimitResume"

            REVISION    "201809051145Z"  
            DESCRIPTION  
            "Add hwUserGroupPriority"  

            REVISION    "201808091145Z"  
            DESCRIPTION  
            "Add hwNACMaxUserSlot, add hwNACMaxUserNum, add hwNACMaxPercentage, add hwNacUserClearAlarm,  add hwNacMaxUserAlarm"  

            REVISION    "201808071145Z"  
            DESCRIPTION  
            "Modify hwMaxMulticastListNum"  

           REVISION    "201807261044Z"  
            DESCRIPTION  
            "Add hwLocalEapServerTable, add hwLocalEapServerSetting" 

           REVISION    "201807251508Z"  
            DESCRIPTION  
            "Modify hwDomainAccessLimitNum"  

           REVISION    "201807201508Z"  
            DESCRIPTION  
            "Modify hwAAAAccessTable"  
			
            REVISION    "201807121508Z"  
            DESCRIPTION  
            "Modify hwAccessTable,add hwAAAAccessTable"  
			
            REVISION    "201806211508Z"  
            DESCRIPTION  
            "Add hwAuthenMethodNew hwAuthorMethodNew"    
			
            REVISION    "201806111508Z"  
            DESCRIPTION  
            "Modify hwDot1xAccessProfileReauthenticationTimeout,hwMACAuthenAccessProfileReauthenticationTimeout"    

            REVISION    "201806081508Z"  
            DESCRIPTION  
            "Add hwUserNameIndexUsage,hwAAAInstanceId,hwUserNameIndexAllocAlarm,hwUserNameIndexAllocAlarmResume,hwCUUserNameIndexAllocAlarm,hwCUUserNameIndexAllocAlarmResume"    

            REVISION    "201805301508Z"  
            DESCRIPTION  
            "Add hwTotalPPPFailNum"    
        
            REVISION    "201805251508Z"  
            DESCRIPTION  
            "Add hwCUUserOnlineFailAlarm"
			
            REVISION    "201805211508Z"  
            DESCRIPTION  
            "Add hwUserAccessInterface,hwUserAccessIndex,hwUserAccessMAC,hwAAASlaveTrafficUserAlarm"   
			
            REVISION    "201805151600Z"  
            DESCRIPTION  
            "Modify hwOnlineUserNumLowerLimitCpThreshold,hwOnlineUserNumLowerLimitCpInstanceId,hwOnlineUserNumUpperLimitCpThreshold,hwOnlineUserNumUpperLimitCpInstanceId"
			
            REVISION    "201804271600Z"  
            DESCRIPTION  
            "Modify userAuthenProfileRoamAccountingMode"


             REVISION    "201804271200Z"  
            DESCRIPTION  
            "Del userAuthenProfileRoamAccountingEnable,userAuthenProfileUpdateIpAccountingEnable"
			
			REVISION    "201804221200Z"  
            DESCRIPTION  
            "Add userAuthenProfileRoamAccountingEnable,userAuthenProfileUpdateIpAccountingEnable,userAuthenProfileRoamAccountingMode"
			
            REVISION    "201804140200Z"  
            DESCRIPTION  
            "Add hwInterfaceIfIndex hwInterfaceIfName hwIpStaticUserMixedInsertAlarm"

            REVISION    "201804120200Z"  
            DESCRIPTION  
            "Add hwCUIPLowerlimitAlarm,
                            hwCUIPLowerlimitWarningResume,hwCUIPv6AddressLowerlimitAlarm,hwCUIPv6AddressLowerlimitResume,hwCUIPv6NDRAPrefixLowerlimitAlarm,
                            hwCUIPv6NDRAPrefixLowerlimitResume,hwCUIPv6PDPrefixLowerlimitAlarm,hwCUIPv6PDPrefixLowerlimitResume,hwCUUserDelegationPrefixAllocAlarm,
                            hwCUUserDelegationPrefixAllocAlarmResume,hwCUUserIPAllocAlarm,hwCUUserIPAllocAlarmResume,hwCUUserIPv6AddressAllocAlarm,
                            hwCUUserIPv6AddressAllocAlarmResume,hwCUUserNDRAPrefixAllocAlarm,hwCUUserNDRAPrefixAllocAlarmResume"

            REVISION    "201804010200Z"  
            DESCRIPTION  
            "Modify hwLocalUserBlockTimestamp"

            
			REVISION    "201803071200Z"  
            DESCRIPTION  
            "Modify hwAAANoBackupInterfaceAlarm Description"
			
			REVISION    "201803051200Z"  
            DESCRIPTION  
            "Add userAuthenProfileLdapServerName,userAuthenProfileAdServerName"
	
            		
            REVISION    "201803021200Z"  
            DESCRIPTION  
            "Add hwMACAuthenProfileAuthMethod"

            REVISION    "201802091224Z"  
            DESCRIPTION  
            "Add hwInterfaceName,hwInterfaceUserNum,hwInterfaceUserNumThreshold,hwBackupProtectionType,hwBackupProtectionAlarmLevel,hwAAANoBackupInterfaceAlarm"   
			
  
            REVISION    "201802062058Z"
            DESCRIPTION
            "Modified userAuthenProfileForcePushUrlTemplate,userAuthenProfileForcePushUrl"


            REVISION    "201802061858Z"
            DESCRIPTION
            "Modified  hwAAAOnlineSessoinUpperLimitCpAlarm,hwAAAOnlineSessoinUpperLimitCpResume,,hwAAAOnlineSessoinLowerLimitCpAlarm,hwAAAOnlineSessoinLowerLimitCpResume,hwOnlineUserNumLowerLimitCpAlarm,hwOnlineUserNumLowerLimitCpResume,hwOnlineUserNumUpperLimitCpAlarm,
             hwOnlineUserNumUpperLimitCpResume, hwRemoteDownloadAclThresholdCpAlarm,hwRemoteDownloadAclThresholdCpResume"
           
            REVISION    "201802021636Z"
            DESCRIPTION
            "Add  hwAAAOnlineSessoinUpperLimitCpAlarm,hwAAAOnlineSessoinUpperLimitCpResume,,hwAAAOnlineSessoinLowerLimitCpAlarm,hwAAAOnlineSessoinLowerLimitCpResume,hwOnlineUserNumLowerLimitCpAlarm,hwOnlineUserNumLowerLimitCpResume,hwOnlineUserNumUpperLimitCpAlarm,
             hwOnlineUserNumUpperLimitCpResume, hwRemoteDownloadAclThresholdCpAlarm,hwRemoteDownloadAclThresholdCpResume"
      
            REVISION    "201801291111Z"
            DESCRIPTION
            "Modified  hwDomainStatEntry,hwAAAStatEntry and added hwCUAAAStatTable,hwBRASLicense" 
     
            REVISION    "201801261111Z"
            DESCRIPTION
            "Modified  translation information." 

            REVISION    "201801251111Z"
            DESCRIPTION
            "Modify hwAccessCARDnPBS, hwAccessCARUpPBS, hwAccessSessionTimeout" 

            REVISION    "201801221111Z"
            DESCRIPTION
            "Modify HwSlotConnectNumEntry" 

            REVISION    "201712251111Z"
            DESCRIPTION
            "Modify hwServiceSchemeRedirectACL" 

            REVISION    "201712131111Z"
            DESCRIPTION
            "Add userAuthenProfileForcePushUrl,userAuthenProfileForcePushUrlTemplate,userAuthenProfileAccountingOfRoam,userAuthenProfileAccountingOfUpdateIP,userAuthenProfileAccountingOfUpdateInfo,userAuthenProfileNoIPCheck" 

            REVISION    "201712121111Z"
            DESCRIPTION
            "Add hwAcl6Id,hwAccessDeviceType,hwOfflineRecordAPID,hwOfflineRecordAPMAC,hwOfflineRecordSSID,hwOfflineRecordASID,hwOfflineRecordASMAC,hwOfflineRecordASIfname,hwLocalUserBlockTimestamp"

            REVISION    "201712071730Z"
            DESCRIPTION
            "Add hwCUAAAAccessUserResourceOrCpuAlarm, hwCUAAAAccessUserResourceOrCpuResume, hwCUAAASlotIPv6AddressThresholdAlarm, hwCUAAASlotIPv6AddressThresholdResume" 

            REVISION    "201712051705Z"
            DESCRIPTION
            "extend the scope of hwAuthenMethod and hwAuthorMethod"                         
   
           REVISION    "201709281351Z"
           DESCRIPTION
           "ModifyhwMACAuthenAccessProfileMACAddressFormat"

           REVISION    "201709261045Z"
           DESCRIPTION
           "ModifyhwCUUserMaxNum,hwCUUserSlotMaxNum,hwCUUserMaxNumResume,hwCUUserSlotMaxNumResume"

           REVISION    "201709011705Z"
           DESCRIPTION
           "Add hwLocalUserRole"

           REVISION    "201708311707Z"
           DESCRIPTION
           "Modify the of hwAAAAccessUserResourceOrCpuAlarm,hwAAAAccessUserResourceOrCpuResume"

           REVISION    "201708261745Z"
           DESCRIPTION
           "ModifyhwCUUserMaxNum,hwCUUserSlotMaxNum,hwCUUserMaxNumResume,hwCUUserSlotMaxNumResume"

           REVISION    "201708081100Z"
           DESCRIPTION
           "Modify hwDomainIdleCutFlow's Size list ,from 768000 to 76800000"

           REVISION    "201707201100Z"
           DESCRIPTION
           "Add hwAAAUserGroupUserStatTable, hwAAAUserGroupName,hwAAAUserGroupTotalUsersNum; Modify hwDomainIdleCutFlow's Size list ,from 768000 to 76800000"

           REVISION    "201707171706Z"
           DESCRIPTION
           "Modify hwAuthenSchemeTable, hwAcctSchemeTable, hwDomainStatTable, hwAccessTable, hwAccessExtTable, hwIPAccessTable, hwMACAccessTable, hwSlotConnectNumTable, hwSlotCardConnectNumTable, hwOfflineReasonStatTable, hwVpnAccessUserStatTable, hwInterfaceAccessUserStatTable, hwDomainAccessUserStatTable, hwSlotAccessUserStatTable, hwAAAOnlineFailRecordTable, hwDhcpOpt121RouteTable, hwAAAPwifSlotConnectNumTable, hwAAAPwifSlotCardConnectNumTable, hwAAAPwifSlotAccessUserStatTable, hwAAAPwifAccessTable"

           REVISION    "201706291416Z"
           DESCRIPTION
           "Add userAuthenProfileWebuserAuthenProfileIpTrigger"

           REVISION    "201705311505Z"
           DESCRIPTION
           "Add hwCUUserSlot,hwCUUserMaxNum,hwCUUserSlotMaxNum,hwCUUserMaxNumResume,hwCUUserSlotMaxNumResume"

           REVISION    "201705231705Z"
           DESCRIPTION
           "Add hwLocalUserExpireHour"

           REVISION    "201705031047Z"
           DESCRIPTION
           "Add userAuthenProfileAccoutingStartAckPermitArp"

           REVISION    "201704271157Z"
           DESCRIPTION
           "Modify hwSlotConnectNumSlot, hwSlotCardConnectNumSlot"

           REVISION    "201703231047Z"
           DESCRIPTION
           "Add userAuthenProfileIpAddrInAcctStart"

           REVISION    "201702131843Z"
           DESCRIPTION
           "Modify the size of hwOfflineReason"

           REVISION    "201701161705Z"
           DESCRIPTION
           "Add hwPortalAccessProfileWebProxyEnable, hwPortalAccessProfileWebProxyPort"

           REVISION    "201701121705Z"
           DESCRIPTION
           "Add hwOnlineFailNum,hwOnlineSuccessPercentage,hwUserOnlineFailAlarm"

           REVISION    "201609271140Z"
           DESCRIPTION
           "Add hwhttpdirectory"

           REVISION    "201609270940Z"
           DESCRIPTION
           "Add hwLocalUserIsExpired"

           REVISION    "201609191716Z"
           DESCRIPTION
           "hwOfflineRecordIPv6PDPrefixLength"

           REVISION    "201608261030Z"
           DESCRIPTION
           "Add hwAccessQinQVLANID,hwAccessOption82CircuitID,hwAccessOption82RemoteID,hwAccessSessionTimeout,hwAccessISPVLAN,hwAccessISPInterface,hwAccessUserNumberTable,hwAccessUserNumberEntry,hwAccessUserNumberDot1x,hwAccessUserNumberMAC,hwAccessUserNumberPortal,hwAccessUserNumberPPP,hwAccessUserNumberNone,hwAccessUserNumberStatic,hwAccessUserNumberAdmin"

           REVISION    "201608121705Z"
           DESCRIPTION
           "Add hwServiceSchemeRedirectACL"

           REVISION    "201607141152Z"
           DESCRIPTION
           "hwAAAAdminUserAuthenWithoutDomainName"

           REVISION    "201607141152Z"
           DESCRIPTION
           "Add hwTotalAuthReqNumPortal, hwTotalAuthReqNumMac, hwTotalAuthReqNumDot1x"

           REVISION    "201607061741Z"
           DESCRIPTION
           "hwAAAAdminUserAuthenWithoutDomainName"

           REVISION    "201606221704Z"
           DESCRIPTION
           "Add hwTotalFamilyUserByUsernameOnlineNum hwOfflineRecordStackTypeFlag hwOfflineRecordAccessPVC hwOfflineRecordIPv6NDRAPrefix hwOfflineRecordIPv6Address hwOfflineRecordIPv6PDPrefix hwOfflineRecordUserAuthenState hwOfflineRecordUserAcctState hwOfflineRecordUserAuthorState"

           REVISION    "201606171051Z"
           DESCRIPTION
           "Add hwUserMaxNumResume, hwUserSlotMaxNumResume"

           REVISION    "201605181050Z"
           DESCRIPTION
           "Add hwPortalAccessProfileLocalServerAnonymousUrl"

           REVISION    "201605142145Z"
           DESCRIPTION
           "Add hwAAAUserPwdWillExpirehwAAAUserPwdExpired"

           REVISION    "201604192145Z"
           DESCRIPTION
           "Add hwAccessBakeState"

           REVISION    "201604081442Z"
           DESCRIPTION
           "Add hwAccessAuthorizetype"

           REVISION    "201604051650Z"
           DESCRIPTION
           "Modify hwAccessIndex"

           REVISION    "201603280950Z"
           DESCRIPTION
           "Modify hwMACAuthenAccessProfileMACAddressFormat"

           REVISION    "201603211539Z"
           DESCRIPTION
           "Add hwReAuthenUserTable"

           REVISION    "201603170259Z"
           DESCRIPTION
           "Modify hwAccessAuthtype"

           REVISION    "201603151018Z"
           DESCRIPTION
           "Modify hwAccessIndex"

           REVISION    "201603141018Z"
           DESCRIPTION
           "Modify hwAccessIPv6OtherFlag hwAccessIPv6ManagedAddressFlag "

           REVISION    "201602161018Z"
           DESCRIPTION
           "Modify hwSlotConnectNumSlot hwSlotCardConnectNumSlot hwSlotAccessUserStatSlot to be compatible with device X1X2"

           REVISION    "201601261630Z"
           DESCRIPTION
           "Add hwAAAPwifSlotConnectNumTable,hwAAAPwifSlotCardConnectNumTable,hwAAAPwifSlotAccessUserStatTable,hwAAAPwifAccessTable"

           REVISION    "201512310950Z"
           DESCRIPTION
           "Add hwAAAAdminUserAuthenWithoutDomainName"

           REVISION    "201512011418Z"
           DESCRIPTION
           "ModifyServiceSchemeName,UserGroupName,PortalServerName,PortalBackupServerName in hwPortalAccessProfileTable"

           REVISION    "201509111138Z"
           DESCRIPTION
           "Add hwAAASessionGroupUpperLimitThreshold, hwAAASessionGroupUpperLimitResume, hwAAASessionGroupLowerLimitThreshold, hwAAASessionGroupLowerLimitAlarm, hwAAASessionGroupLowerLimitResume, hwAAASessionUpperLimitThreshold, hwAAAOnlineSessoinUpperLimitAlarm, hwAAAOnlineSessoinUpperLimitResume, hwAAASessionLowerLimitThreshold, hwAAAOnlineSessoinLowerLimitAlarm, hwAAAOnlineSessoinLowerLimitResume, hwAAASlotOnlineUserNumAlarm,hwAAASlotOnlineUserNumResume"

           REVISION    "201508261605Z"
           DESCRIPTION
           "Add userAuthenProfileAuthenFailAuthorResponseSuccess in userAuthenProfileEntry; Modify userAuthenProfilePreAuthenUserGroupName,userAuthenProfileAuthenFailAuthorUserGroupName,userAuthenProfileAuthenServerDownUserGroupName in userAuthenProfileEntry"

           REVISION    "201508080935Z"
           DESCRIPTION
           "Add hwAAAChasisIPv6AddressThreshold,hwAAASlotIPv6AddressThreshold,hwAAAChasisIPv6AddressThresholdAlarm,hwAAAChasisIPv6AddressThresholdResume,hwAAASlotIPv6AddressThresholdAlarm and hwAAASlotIPv6AddressThresholdResume"

           REVISION    "201507310917Z"
           DESCRIPTION
           "ModifyhwAccessSSID,hwAccessDomain,hwAccessUserName"

           REVISION    "201507282100Z"
           DESCRIPTION
           "Modify hwDot1xAccessProfileEthTrunkHandShakePeriod,userAuthenProfileAuthenFailAgingTime,userAuthenProfilePreAuthenAgingTime,userAuthenProfileAuthenFailReAuthenTimer"

           REVISION    "201507282055Z"
           DESCRIPTION
           "Modify hwUserGroupCarCir,hwUserGroupCarPir,hwUserGroupCarCbs,hwUserGroupCarPbs,hwUserGroupCarInBoundCir,hwUserGroupCarInBoundPir,hwUserGroupCarInBoundCbs,hwUserGroupCarInBoundPbs in hwUserGroupEntry"

           REVISION    "201507281641Z"
           DESCRIPTION
           "Modify hwMACAuthenAccessProfileTriggerPktType in HwMACAuthenAccessProfileEntry"

           REVISION    "201507161711Z"
           DESCRIPTION
           "Modify hwLocalUserAccessLimitNum in hwLocalUserEntry"

           REVISION    "201507072036Z"
           DESCRIPTION
           "Add hwMacMovedQuietUserSpec, hwMacMovedUserPercentage, hwLowerMacMovedUserPercentage, hwUpperMacMovedUserPercentage, hwMacMovedQuietMaxUserAlarm and hwMacMovedQuietUserClearAlarm "

           REVISION    "201506101250Z"
           DESCRIPTION
           "ModifyhwAccessSSID hwAccessDomain hwAccessUserName hwPortalAccessProfileDetectPeriod"

           REVISION    "201504231655Z"
           DESCRIPTION
           "AdduserAuthenticationFreeRuleExtTable , modify userAuthenticationFreeRuleTable"

           REVISION    "201504171250Z"
           DESCRIPTION
           "AddhwAAAInboundVPNAccessUserStatTable hwAAAInboundVPNAccessUserStatTable"

           REVISION    "201503260935Z"
           DESCRIPTION
           "Add userAuthenProfileDefaultDomain, userAuthenProfileForceDomain, userAuthenProfileDomainNameDelimiter, userAuthenProfileDomainNameLocation, userAuthenProfileDomainNameParseDirection and userAuthenProfilePermitDomain in userAuthenProfileEntry"

           REVISION    "201503201314Z"
           DESCRIPTION
           "Modify hwLocalUserPasswordLifetimeMin and hwLocalUserPasswordLifetimeMax in hwLocalUserEntry"

           REVISION    "201503101250Z"
           DESCRIPTION
           "AddhwAAADomainInboundQoSProfile hwAAADomainOutboundQoSProfile"

           REVISION    "201501231025Z"
           DESCRIPTION
           "Add userAuthenProfile, userAuthenticationFreeRule, hwDot1xAccessProfile, hwMACAuthenAccessProfile and hwPortalAccessProfile"

           REVISION    "201412311544Z"
           DESCRIPTION
           "Add hwAAACpuUsage and hwAAAUserResourceUsage"

           REVISION    "201412271544Z"
           DESCRIPTION
           "Add hwAAAAccessUserResourceOrCpuAlarm and hwAAAAccessUserResourceOrCpuResume"

           REVISION    "201412261617Z"
           DESCRIPTION
           "AddhwDhcpUserOnlineFailCount"

           REVISION    "201412261617Z"
           DESCRIPTION
           "AddhwDhcpUserOnlineV6FailCount"

           REVISION    "201412261617Z"
           DESCRIPTION
           "Add hwAAATimerExpireMajorLevelThreshold, hwAAATimerExpireMajorLevelResumeThreshold, hwAAATimerExpireCriticalLevelThreshold and hwAAATimerExpireCriticalLevelResumeThreshold"

           REVISION    "201409211544Z"
           DESCRIPTION
           "Add hwAAADomainIPPoolTable"

           REVISION    "201409061617Z"
           DESCRIPTION
           "Modify hwLocalUserAccessType Syntax Type . [Integer32 -> Unsigned32] "

           REVISION    "201409031050Z"
           DESCRIPTION
           "Modify hwDomainAccessLimitNum OBJECT-TYPE and hwftpdirction OBJECT-TYPE"

           REVISION    "201408271544Z"
           DESCRIPTION
           "Add hwLocalUserPwPolicyAdmin"

           REVISION    "201408271544Z"
           DESCRIPTION
           "Add hwLocalUserPwPolicyAcc"

           REVISION    "201408201050Z"
           DESCRIPTION
           "Add hwEDSGLicenseExpireAlarm and hwEDSGLicenseExpireResume"

           REVISION    "201408121725Z"
           DESCRIPTION
           "Add hwAccessDeviceName and hwAccessDeviceMACAddress"

           REVISION    "201408061050Z"
           DESCRIPTION
           "Modify node hwOfflineReason"

           REVISION    "201407141050Z"
           DESCRIPTION
           "Add hwLocalAuthorize and hwRemoteAuthorize"

           REVISION    "201407081544Z"
           DESCRIPTION
           "Add hwLocalAuthorize and hwRemoteAuthorize"

           REVISION    "201404171027Z"
           DESCRIPTION
           "Add hwAAARateTable"

           REVISION    "201404171026Z"
           DESCRIPTION
           "Add hwTotalLacOnlineNum and hwTotalLnsOnlineNum"

           REVISION    "201403241051Z"
           DESCRIPTION
           "The MIB contains objects of module AAA."

           REVISION    "201403181051Z"
           DESCRIPTION
           "The MIB contains objects of module AAA."

           REVISION    "201403061050Z"
           DESCRIPTION
           "Add hwUserGroupThresholdAlarm, hwUserGroupThresholdResume, hwUserGroupNumThreshold and hwUserGroupUsedNum"

           REVISION    "201312171030Z"
           DESCRIPTION
           "Modify hwUserDomainName, hwUserAuthenState, hwUserAcctState, hwUserAuthorState and hwOnlineFailReason in hwAAAOnlineFailRecordTable"

           REVISION    "201312131725Z"
           DESCRIPTION
           "Add hwLoginFailedTimes and hwStatisticPeriod and hwAdminLoginFailed and hwAdminLoginFailedClear"

           REVISION    "201311281651Z"
           DESCRIPTION
           "The MIB contains objects of module AAA."

           REVISION    "201310151725Z"
           DESCRIPTION
           "Add hwHistoricMaxOnlineLocalNum and hwHistoricMaxOnlineRemoteNum"

           REVISION    "201309141518Z"
           DESCRIPTION
           "The MIB contains objects of module AAA."

           REVISION    "201308082012Z"
           DESCRIPTION
           "Add hwWlanInterfaceName "

           REVISION    "201307191800Z"
           DESCRIPTION
           "Add hwAccessResourceInsufficientInbound and hwAccessResourceInsufficientOutbound"

           REVISION    "201307041709Z"
           DESCRIPTION
           "extend the scope of hwAuthenMethod "

           REVISION    "201306271719Z"
           DESCRIPTION
           "extend the scope of hwAuthenMethod "

           REVISION    "201304170919Z"
           DESCRIPTION
           "extend the scope of hwAuthenMethod "

           REVISION    "201304032222Z"
           DESCRIPTION
           "Add hwLocalUserIfAllowWeakPassword."

           REVISION    "201303151111Z"
           DESCRIPTION
           "The MIB contains objects of module AAA."
            
            ::= { huaweiMgmt 2 }

        hwAAAMibObjects OBJECT IDENTIFIER ::= { hwAaa 1 }

        hwAuthenSchemeTable OBJECT-TYPE
            SYNTAX SEQUENCE OF HwAuthenSchemeEntry
            MAX-ACCESS not-accessible
            STATUS current
            DESCRIPTION
                "The hwAuthenSchemeTable is an authentication solution table used to configure an authentication solution for users, including the addition, deletion, query, and modification operations. The default authentication solution tables are default0 and default1. The default authentication solutions can be modified but not deleted."
            ::= { hwAAAMibObjects 1 }

        hwAuthenSchemeEntry OBJECT-TYPE
            SYNTAX HwAuthenSchemeEntry
            MAX-ACCESS not-accessible
            STATUS current
            DESCRIPTION
                "The authentication scheme entry."
            INDEX { hwAuthenSchemeName }
            ::= { hwAuthenSchemeTable 1 }

        HwAuthenSchemeEntry ::=
            SEQUENCE {
                hwAuthenSchemeName
                    DisplayString,
                hwAuthenMethod
                    INTEGER,
                hwAuthenRowStatus
                    RowStatus,
                hwAuthenFailPolicy    
                        INTEGER,
                hwAuthenFailDomain
                        DisplayString,
               hwAuthenMethodNew
	  DisplayString,
               hwAuthenTypeAdminChap
                       Unsigned32,
               hwServerNoRespAcct
                       INTEGER,
               hwServerNoRespAuthor
	   INTEGER
             }

        hwAuthenSchemeName OBJECT-TYPE
            SYNTAX DisplayString (SIZE (1..32))
            MAX-ACCESS read-only
            STATUS current
            DESCRIPTION
                "This object indicates the name of an authentication solution."
            ::= { hwAuthenSchemeEntry 1 }

        hwAuthenMethod OBJECT-TYPE
            SYNTAX INTEGER
                {
                local(1),
                noauth(2),
                radius(3),
                localRadius(4),
                radiusLocal(5),
                radiusNoauth(6),
                tacacs(7),
                tacacsLocal(8),
                localTacacs(9),
                tacacsNoauth(10),
                localNoauth(11),
                radiusTacacs(12),
                tacacsRadius(13),
                localRadiusNoauth(14),
                localTacacsNoauth(15),
                radiusLocalNoauth(16),
                radiusTacacsNoauth(17),
                tacacsLocalNoauth(18),
                tacacsRadiusNoauth(19),
                localRadiusTacacs(20),
                radiusLocalTacacs(21),
                localTacacsRadius(22),
                radiusTacacsLocal(23),
                tacacsLocalRadius(24),
                tacacsRadiusLocal(25),
                localRadiusTacacsNoauth(26),
                localTacacsRadiusNoauth(27),
                radiusLocalTacacsNoauth(28),
                radiusTacacsLocalNoauth(29),
                tacacsLocalRadiusNoauth(30),
                tacacsRadiusLocalNoauth(31),
                radiusProxy(32),
                localcaseRadius(33),
                localcaseTacacs(34),
                localcaseNoauth(35),
                radiusLocalcase(36),
                tacacsLocalcase(37),
                localcaseRadiusNoauth(38),
                localcaseTacacsNoauth(39),
                localcaseRadiusTacacs(40),
                localcaseTacacsRadius(41),
                radiusLocalcaseNoauth(42),
                radiusLocalcaseTacacs(43),
                radiusTacacsLocalcase(44),
                tacacsLocalcaseNoauth(45),
                tacacsLocalcaseRadius(46),
                tacacsRadiusLocalcase(47),
                localcaseTacacsRadiusNoauth(48),
                localcaseRadiusTacacsNoauth(49),
                radiusLocalcaseTacacsNoauth(50),
                radiusTacacsLocalcaseNoauth(51),
                tacacsLocalcaseRadiusNoauth(52),
                tacacsRadiusLocalcaseNoauth(53),
                localcase(54)        
                }
            MAX-ACCESS read-create
            STATUS current
            DESCRIPTION
                "This object indicates the type of the authentication solution. The default type is radius (3), indicating RADIUS authentication."
            ::= { hwAuthenSchemeEntry 2 }

        hwAuthenRowStatus OBJECT-TYPE
            SYNTAX RowStatus
            MAX-ACCESS read-create
            STATUS current
            DESCRIPTION
                "This object indicates the row administrative status. Currently, the states of creation and deletion are supported."
            ::= { hwAuthenSchemeEntry 3 }
        
        hwAuthenFailPolicy OBJECT-TYPE
            SYNTAX INTEGER
                {
                online(1),
                offline(2)
                }
            MAX-ACCESS read-create
            STATUS current
            DESCRIPTION
                "The authentication fail policy,
                 online(1):keeping user online,
                 offline(2):making user offline. 
                "
            ::= { hwAuthenSchemeEntry 4 }
            
        hwAuthenFailDomain OBJECT-TYPE
            SYNTAX DisplayString (SIZE (1..64))
            MAX-ACCESS read-create
            STATUS current
            DESCRIPTION
                "The authentication fail domain."
            ::= { hwAuthenSchemeEntry 5 }
			
		hwAuthenMethodNew OBJECT-TYPE
			SYNTAX DisplayString (SIZE (1..16))
			MAX-ACCESS read-write
			STATUS current
			DESCRIPTION
				"Description."
			::= { hwAuthenSchemeEntry 6 } 
   
        hwAuthenTypeAdminChap OBJECT-TYPE
            SYNTAX Unsigned32 (0..4294967295)
            MAX-ACCESS read-write
            STATUS current
            DESCRIPTION
                "authentication-type radius  chap access-type
                0x00000000 all,
                0x00000001 telnet,                
                0x00000002 terminal,
                0x00000004 ssh,
                0x00000008 ftp,
                0x00000200 http"
            ::= { hwAuthenSchemeEntry 7 }

        hwServerNoRespAcct OBJECT-TYPE
            SYNTAX INTEGER
                {
                true(1),
                false(2)
                }
            MAX-ACCESS read-create
            STATUS current
            DESCRIPTION
                "Remote server no response,
                 true(1):keep accounting,
                 false(2):do not account.  
                "
            ::= { hwAuthenSchemeEntry 8 }

        hwServerNoRespAuthor OBJECT-TYPE
            SYNTAX INTEGER
                {
                true(1),
                false(2)
                }
            MAX-ACCESS read-create
            STATUS current
            DESCRIPTION
                "Remote server no response,
                 true(1):keep server authorization,
                 false(2):switch to local authorization. 
                "
            ::= { hwAuthenSchemeEntry 9 }

        hwAcctSchemeTable OBJECT-TYPE
            SYNTAX SEQUENCE OF HwAcctSchemeEntry
            MAX-ACCESS not-accessible
            STATUS current
            DESCRIPTION
                "The hwAcctSchemeTable is an accounting solution table used to complete basic configuration of an accounting solution. The default accounting solution tables are default0 and default1. The default solution can be modified but not deleted."
            ::= { hwAAAMibObjects 2 }

        hwAcctSchemeEntry OBJECT-TYPE
            SYNTAX HwAcctSchemeEntry
            MAX-ACCESS not-accessible
            STATUS current
            DESCRIPTION
                "The account scheme entry."
            INDEX { hwAcctSchemeName }
            ::= { hwAcctSchemeTable 1 }

        HwAcctSchemeEntry ::=
            SEQUENCE {
                hwAcctSchemeName
                    DisplayString,
                hwAccMethod
                    INTEGER,
                hwAcctStartFail
                    INTEGER,
                hwAcctOnlineFail
                    INTEGER,
                hwAccRealTimeInter
                    Integer32,
                hwAcctRowStatus
                    RowStatus,
                hwAcctRealTimeIntervalUnit
                    INTEGER,
                hwAcctIpSeparate
                    INTEGER
             }

        hwAcctSchemeName OBJECT-TYPE
            SYNTAX DisplayString (SIZE (1..32))
            MAX-ACCESS read-only
            STATUS current
            DESCRIPTION
                "This object indicates the name of an accounting solution."
            ::= { hwAcctSchemeEntry 1 }

        hwAccMethod OBJECT-TYPE
            SYNTAX INTEGER
                {
                noacct(2),
                radius(3),
                hwtacacs(5),
                haca(6)
                }
            MAX-ACCESS read-create
            STATUS current
            DESCRIPTION
                "This object indicates the accounting method."
            ::= { hwAcctSchemeEntry 2 }

        hwAcctStartFail OBJECT-TYPE
            SYNTAX INTEGER
                {
                none(1),
                offline(2)
                }
            MAX-ACCESS read-create
            STATUS current
            DESCRIPTION
                "The account start fail to use scheme."
            ::= { hwAcctSchemeEntry 3 }

        hwAcctOnlineFail OBJECT-TYPE
            SYNTAX INTEGER
                {
                none(1),
                offline(2)
                }
            MAX-ACCESS read-create
            STATUS current
            DESCRIPTION
                "The account realties fail to use scheme."
            ::= { hwAcctSchemeEntry 4 }

        hwAccRealTimeInter OBJECT-TYPE
            SYNTAX Integer32
            MAX-ACCESS read-create
            STATUS current
            DESCRIPTION
                "This object indicates the interval for real-time accounting. Value 0 indicates that real-time accounting is not performed. This attribute must be configured together with the hwAcctRealTimeIntervalUnit attribute."
            ::= { hwAcctSchemeEntry 5 }

        hwAcctRowStatus OBJECT-TYPE
            SYNTAX RowStatus
            MAX-ACCESS read-create
            STATUS current
            DESCRIPTION
                "The row administrate status, only supporting add or delete."
            ::= { hwAcctSchemeEntry 6 }
 hwAcctRealTimeIntervalUnit OBJECT-TYPE
            SYNTAX INTEGER
                {
                    minute(1),
                    second(2),
                    none(3)
                }
            MAX-ACCESS read-create
            STATUS current
            DESCRIPTION
               "The value of this object indicates the unit for real time accounting." 
            ::= {hwAcctSchemeEntry 7} 
  
        hwAcctIpSeparate OBJECT-TYPE
            SYNTAX INTEGER
                {
                    false(0),
                    true(1)
                }
            MAX-ACCESS read-create
            STATUS current
            DESCRIPTION
                "The mode of carrying IP in accounting packets.
                 false(0): all ip,
                 true(1): single ip. default is 0."
            ::= { hwAcctSchemeEntry 8 } 

        hwDomainTable OBJECT-TYPE
            SYNTAX SEQUENCE OF HwDomainEntry
            MAX-ACCESS not-accessible
            STATUS current
            DESCRIPTION
                "The hwDomainTable is a domain information table used to complete basic configuration of a domain, including creating, deleting, modifying, and configuring the attributes of an authentication or accounting solution in a domain."
            ::= { hwAAAMibObjects 4 }

        hwDomainEntry OBJECT-TYPE
            SYNTAX HwDomainEntry
            MAX-ACCESS not-accessible
            STATUS current
            DESCRIPTION
                "The domain table entry."
            INDEX { hwDomainName }
            ::= { hwDomainTable 1 }

        HwDomainEntry ::=
            SEQUENCE {
                hwDomainName
                    DisplayString,
                hwDomainAuthenSchemeName
                    DisplayString,
                hwDomainAcctSchemeName
                    DisplayString,
                hwDomainRadiusGroupName
                    DisplayString,
                hwDomainAccessLimitNum
                    Integer32,
                hwDomainIfSrcRoute
                    TruthValue,
                hwDomainNextHopIP
                    IpAddress,
                hwDomainIdleCutTime
                    Integer32,
                hwDomainIdleCutFlow
                    Integer32,
                hwDomainRowStatus
                    RowStatus,
                hwDomainType
                    INTEGER,
                hwDomainServiceSchemeName
                   DisplayString,
                hwDomainIdleCutType
                   INTEGER,
                hwdomainipv6nexthop
                   DisplayString,
                hwDomainForcePushUrl
                   DisplayString,
                hwDomainForcePushUrlTemplate
                   DisplayString,
                hwStateBlockFirstTimeRangeName
                   DisplayString,
                hwStateBlockSecondTimeRangeName
                   DisplayString,
                hwStateBlockThirdTimeRangeName
                   DisplayString,
                hwStateBlockForthTimeRangeName
                   DisplayString,
                hwDomainFlowStatistic
                    INTEGER,
                hwDomainAcctCopyRdsServerName
                   DisplayString	                     
             }

        hwDomainName OBJECT-TYPE
            SYNTAX DisplayString (SIZE (1..64))
            MAX-ACCESS read-only
            STATUS current
            DESCRIPTION
                "This object indicates a domain name."
            ::= { hwDomainEntry 1 }

        hwDomainAuthenSchemeName OBJECT-TYPE
            SYNTAX DisplayString (SIZE (1..32))
            MAX-ACCESS read-create
            STATUS current
            DESCRIPTION
                "This object indicates the name of an authentication solution."
            ::= { hwDomainEntry 2 }

        hwDomainAcctSchemeName OBJECT-TYPE
            SYNTAX DisplayString (SIZE (1..32))
            MAX-ACCESS read-create
            STATUS current
            DESCRIPTION
                "This object indicates the name of an accounting solution."
            ::= { hwDomainEntry 3 }

        hwDomainRadiusGroupName OBJECT-TYPE
            SYNTAX DisplayString (SIZE (0..32))
            MAX-ACCESS read-create
            STATUS current
            DESCRIPTION
                "This object indicates the group name of the hwRadiusGroupTable."
            ::= { hwDomainEntry 4 }

        hwDomainAccessLimitNum OBJECT-TYPE
            SYNTAX Integer32 (0..2147483647)
            MAX-ACCESS read-create
            STATUS current
            DESCRIPTION
                "This object indicates the maximum number of connections of an account in the current domain."
            ::= { hwDomainEntry 6 }

        hwDomainIfSrcRoute OBJECT-TYPE
            SYNTAX TruthValue
            MAX-ACCESS read-only
            STATUS current
            DESCRIPTION
                "The route of source interface."
            ::= { hwDomainEntry 7 }

        hwDomainNextHopIP OBJECT-TYPE
            SYNTAX IpAddress
            MAX-ACCESS read-create
            STATUS current
            DESCRIPTION
                "The next hop of source IP address route."
            ::= { hwDomainEntry 8 }

        hwDomainIdleCutTime OBJECT-TYPE
            SYNTAX Integer32 (0..2880)
            MAX-ACCESS read-create
            STATUS current
            DESCRIPTION
                "The cut time of idle interval."
            ::= { hwDomainEntry 9 }

        hwDomainIdleCutFlow OBJECT-TYPE
            SYNTAX Integer32 (-1..76800000)
            MAX-ACCESS read-create
            STATUS current
            DESCRIPTION
                              "The flow of idle interval, in Kbytes/min, 0 indicates idle-cut is not performed, 
                -1 indicates idle-cut is performed with 0 idle-rate."
            ::= { hwDomainEntry 10 }

        hwDomainRowStatus OBJECT-TYPE
            SYNTAX RowStatus
            MAX-ACCESS read-create
            STATUS current
            DESCRIPTION
                "This object indicates the row administrative status. The available options are addition, deletion, active, and inactive."
            ::= { hwDomainEntry 11 }
            
            
        hwDomainType OBJECT-TYPE
            SYNTAX INTEGER
                {
                normal(1),
                device(2)
                }
            MAX-ACCESS read-create
            STATUS current
            DESCRIPTION
                "The domain type."
            ::= { hwDomainEntry 12 }   
        
        hwDomainServiceSchemeName OBJECT-TYPE
          SYNTAX DisplayString (SIZE (1..32))
             MAX-ACCESS read-create
             STATUS current
             DESCRIPTION
             "The service scheme name."
            ::= { hwDomainEntry 13 }
            
        hwDomainIdleCutType OBJECT-TYPE
          SYNTAX INTEGER
              {
                both(1),
                inbound(2),
                outbound(3)
              }
             MAX-ACCESS read-write
             STATUS current
             DESCRIPTION
             "The type of idle-cut, default type is 1."
            ::= { hwDomainEntry 14 }
            
        hwdomainipv6nexthop OBJECT-TYPE
          SYNTAX DisplayString (SIZE (1..255))
             MAX-ACCESS read-write
             STATUS current
             DESCRIPTION
             "The next hop of IPv6 policy route."
            ::= { hwDomainEntry 15 }
            
        hwDomainForcePushUrl OBJECT-TYPE
            SYNTAX DisplayString (SIZE (1..200))
            MAX-ACCESS read-create
            STATUS current
            DESCRIPTION
                "The url to push."
            ::= { hwDomainEntry 16 }
        hwDomainForcePushUrlTemplate OBJECT-TYPE
            SYNTAX DisplayString (SIZE (1..31))
            MAX-ACCESS read-create
            STATUS current
            DESCRIPTION
                "The url-template to push."
            ::= { hwDomainEntry 17 }
        hwStateBlockFirstTimeRangeName OBJECT-TYPE
            SYNTAX DisplayString (SIZE (1..32))
            MAX-ACCESS read-create
            STATUS current
            DESCRIPTION
                "The first time-range name of domain block."
            ::= { hwDomainEntry 18 }
        hwStateBlockSecondTimeRangeName OBJECT-TYPE
            SYNTAX DisplayString (SIZE (1..32))
            MAX-ACCESS read-create
            STATUS current
            DESCRIPTION
                "The second time-range name of domain block."
            ::= { hwDomainEntry 19 }
        hwStateBlockThirdTimeRangeName OBJECT-TYPE
            SYNTAX DisplayString (SIZE (1..32))
            MAX-ACCESS read-create
            STATUS current
            DESCRIPTION
                "The third time-range name of domain block."
            ::= { hwDomainEntry 20 }
        hwStateBlockForthTimeRangeName OBJECT-TYPE
            SYNTAX DisplayString (SIZE (1..32))
            MAX-ACCESS read-create
            STATUS current
            DESCRIPTION
                "The forth time-range name of domain block."
            ::= { hwDomainEntry 21 }
        hwDomainFlowStatistic OBJECT-TYPE
            SYNTAX INTEGER
            {
                enable(1),
                disable(2)
            }
            MAX-ACCESS read-write
            STATUS current
            DESCRIPTION
                "flow Statistic enable."
            ::= { hwDomainEntry 22 } 
        hwDomainAcctCopyRdsServerName OBJECT-TYPE
            SYNTAX DisplayString (SIZE (1..32))
            MAX-ACCESS read-create
            STATUS current
            DESCRIPTION
                "The accounting copy radius server."
            ::= { hwDomainEntry 23 }

        hwDomainExtTable OBJECT-TYPE
            SYNTAX SEQUENCE OF HwDomainExtEntry
            MAX-ACCESS not-accessible
            STATUS current
            DESCRIPTION
                "The extended information table is used to configure the extended attributes of a domain."
            ::= { hwAAAMibObjects 5 }

        hwDomainExtEntry OBJECT-TYPE
            SYNTAX HwDomainExtEntry
            MAX-ACCESS not-accessible
            STATUS current
            DESCRIPTION
                "The domain extend entry."
            INDEX { hwDomainName }
            ::= { hwDomainExtTable 1 }

        HwDomainExtEntry ::=
            SEQUENCE {
                hwDomainPPPURL
                    DisplayString,
                hwIfDomainActive
                    TruthValue,
                hwPriority
                    Integer32,
                hwWebServerURL
                    DisplayString,                        
                hwIPPoolOneName
                    DisplayString,
                hwIPPoolTwoName
                    DisplayString,    
                hwIPPoolThreeName
                    DisplayString,    
                hwTwoLevelAcctRadiusGroupName
                    DisplayString,
                hwVPDNGroupIndex
                    Integer32,
                hwUclIndex
                    Integer32,
                hwIfPPPoeURL
                    TruthValue,
                hwUclGroupName
                    DisplayString,
                hwVpdnGroupName
                    DisplayString,
                hwDomainVrf
                    DisplayString,
                hwDomainGre
                    DisplayString,
                hwDomainRenewIPTag
                    TruthValue,
                hwPortalURL
                    DisplayString,                                    
                hwPortalServerIP
                    IpAddress,    
                hwRedirectTimesLimit
                    Integer32,
                hwDot1xTemplate
                    Integer32,
                hwWebServerIP
                    IpAddress,
                hwWebServerMode
                    Integer32,    
                hwPoolWarningThreshold
                    Integer32,
                hwTacGroupName        
                    DisplayString,
                hwServicePolicyName 
                    DisplayString,
                hwCopsGroupSSGType
                    DisplayString,
                hwDomainAuthorSchemeName
                    DisplayString,               
                hwNtvUserProfileName  
                    DisplayString,               
                hwDomainQoSProfile
                    DisplayString, 
                hwDomainZone
                    DisplayString,
                hwIfL2tpRadiusForce
                    TruthValue,
                hwDownPriority
                    Integer32,
                hwPPPForceAuthtype
                    INTEGER,
                hwDnsIPAddress 
                    IpAddress, 
                hwAdminUserPriority
                    Integer32,
                hwShapingTemplate
                    DisplayString,
                hwDomainDPIPolicyName 
                    DisplayString,
                hwCopsGroupSIGType
                    DisplayString,
                hwCopsGroupCIPNType
                    DisplayString,
                hwPCReduceCir
                    Integer32,
                hwValAcctType
                    INTEGER,
                hwValRadiusServer
                    DisplayString,
                hwValCopsServer
                    DisplayString,
                hwPCReducePir
                    Integer32,
                hwDomainInboundL2tpQoSProfile
                    DisplayString, 
                hwDomainOutboundL2tpQoSProfile    
                    DisplayString,   
                hwIfMulticastForward
                    TruthValue,
                hwMulticastVirtualSchedulRezCir
                    Integer32,
                hwMulticastVirtualSchedulRezPir
                    Integer32,    
                hwMaxMulticastListNum
                    Integer32,
                hwMultiProfile
                    DisplayString,
                hwDomainServiceType
                    INTEGER,      
                hwWebServerUrlParameter
                    TruthValue,
                hwWebServerRedirectKeyMscgName
                    DisplayString,
                hwPoratalServerUrlParameter
                    TruthValue,
                hwPoratalServerFirstUrlKeyName
                    DisplayString,
                hwPoratalServerFirstUrlKeyDefaultName
                    TruthValue,
                hwDnsSecondIPAddress 
                    IpAddress,
                hwDomainIgmpEnable
                    Integer32,                                                                                                                 
                hwIPv6PoolName
                    DisplayString,
                hwIPv6PrefixshareFlag
                    INTEGER,
                hwUserBasicServiceIPType
                    DisplayString,
                hwPriDnsIPv6Address
                    Ipv6Address,
                hwSecDnsIPv6Address
                    Ipv6Address,
                hwDualStackAccountingType
                    INTEGER,
                hwIPv6PoolWarningThreshold
                    Integer32,
                hwIPv6CPWaitDHCPv6Delay
                    Integer32,
                hwIPv6ManagedAddressFlag
                    INTEGER,
                hwIPv6CPIFIDAvailable
                    TruthValue,
                hwIPv6OtherFlag
                    INTEGER,
                hwIPv6CPAssignIFID
                    TruthValue,
                hwMultiIPv6ProfileName
                    DisplayString,     
                hwWebServerURLSlave
                    DisplayString,
                hwWebServerIPSlave
                    IpAddress,                     
                hwBindAuthWebIP
                    IpAddress,                     
                hwBindAuthWebVrf
                    DisplayString,
                hwBindAuthWebIPSlave
                    IpAddress,
                 hwBindAuthWebVrfSlave
                    DisplayString,
                hwExtVpdnGroupName
                    DisplayString,
                hwDomainUserGroupName
                    DisplayString, 
                hwAFTRName
                    DisplayString,                   
                hwDomainDhcpOpt64SepAndSeg   
                	DisplayString,
                hwDomainDhcpServerAck
                	TruthValue
             }

        hwDomainPPPURL OBJECT-TYPE
            SYNTAX DisplayString (SIZE (0..200))
            MAX-ACCESS read-write
            STATUS current
            DESCRIPTION
                "The URL of portal."
            ::= { hwDomainExtEntry 1 }

        hwIfDomainActive OBJECT-TYPE
            SYNTAX TruthValue
            MAX-ACCESS read-write
            STATUS current
            DESCRIPTION
                "This object indicates whether the domain is available."
            ::= { hwDomainExtEntry 2 }

         hwPriority OBJECT-TYPE
            SYNTAX Integer32 (0..255)
            MAX-ACCESS read-write
            STATUS current
            DESCRIPTION
                "The priority of up user."
            DEFVAL { 0 }
            ::= { hwDomainExtEntry 3 }
            
        hwWebServerURL OBJECT-TYPE
            SYNTAX DisplayString (SIZE(0..200))
            MAX-ACCESS read-write
            STATUS current
            DESCRIPTION
            "The URL of force web server."
            ::= { hwDomainExtEntry 4 }        
        
        hwIPPoolOneName OBJECT-TYPE
            SYNTAX DisplayString (SIZE(0..255))
            MAX-ACCESS read-write
            STATUS current
            DESCRIPTION
            "The IP pool name."
            ::= { hwDomainExtEntry 5 }
    
        hwIPPoolTwoName OBJECT-TYPE
            SYNTAX DisplayString (SIZE(0..255))
            MAX-ACCESS read-write
            STATUS current
            DESCRIPTION
            "The IP pool name."
            ::= { hwDomainExtEntry 6 }
            
        hwIPPoolThreeName OBJECT-TYPE
            SYNTAX DisplayString (SIZE(0..255))
            MAX-ACCESS read-write
            STATUS current
            DESCRIPTION
            "The IP pool name."
            ::= { hwDomainExtEntry 7 }    
             
        hwTwoLevelAcctRadiusGroupName OBJECT-TYPE
            SYNTAX DisplayString (SIZE(0..32))
            MAX-ACCESS read-write
            STATUS current
            DESCRIPTION
            "The radius group name."
            ::= { hwDomainExtEntry 9 }

        hwVPDNGroupIndex OBJECT-TYPE
            SYNTAX Integer32 (1..1000|65535)
            MAX-ACCESS read-write
            STATUS current
            DESCRIPTION
            "The VPDN group name."
            ::= { hwDomainExtEntry 10 }

        hwUclIndex OBJECT-TYPE
            SYNTAX  Integer32(0..1023|65535)
            MAX-ACCESS read-write
            STATUS current
            DESCRIPTION
            "UCL index"
            ::= { hwDomainExtEntry 11 }

        hwIfPPPoeURL OBJECT-TYPE
            SYNTAX TruthValue
            MAX-ACCESS read-only
            STATUS current
            DESCRIPTION
            "Whether support offering URL for PPP0E user."
            ::= { hwDomainExtEntry 12 }
            
            
            hwUclGroupName OBJECT-TYPE
            SYNTAX DisplayString (SIZE (1..32))
            MAX-ACCESS read-write
            STATUS current
            DESCRIPTION
                "The user access control group name."
            ::= { hwDomainExtEntry 13 }
                            
            hwVpdnGroupName OBJECT-TYPE
            SYNTAX DisplayString (SIZE (1..32))
            MAX-ACCESS read-write
            STATUS current
            DESCRIPTION
                "The VPDN group name."
            ::= { hwDomainExtEntry 15 }
            
            hwDomainVrf OBJECT-TYPE
            SYNTAX DisplayString (SIZE (1..31))
            MAX-ACCESS read-write
            STATUS current
            DESCRIPTION
                "The domain VPN instance name."
            ::= { hwDomainExtEntry 16 }
           hwDomainGre OBJECT-TYPE
            SYNTAX DisplayString (SIZE (1..32))
            MAX-ACCESS read-write
            STATUS current
            DESCRIPTION
                "The GRE group name"
            ::= { hwDomainExtEntry 17 }

               hwDomainRenewIPTag OBJECT-TYPE
                        SYNTAX TruthValue
                        MAX-ACCESS read-write
                        STATUS current
                        DESCRIPTION
                                "if reallocate IP address"
                        DEFVAL { false }
                        ::= { hwDomainExtEntry 18 } 

               hwPortalURL OBJECT-TYPE
                        SYNTAX DisplayString (SIZE (0..200))
                        MAX-ACCESS read-create
                        STATUS current
                        DESCRIPTION
                                "Portal server URL for user"
                        ::= { hwDomainExtEntry 19 }

               hwPortalServerIP OBJECT-TYPE
                        SYNTAX IpAddress
                        MAX-ACCESS read-create
                        STATUS current
                        DESCRIPTION
                                "Portal server IP address"
                        ::= { hwDomainExtEntry 20 }


               hwRedirectTimesLimit OBJECT-TYPE
                        SYNTAX Integer32 (1..5)
                        MAX-ACCESS read-create
                        STATUS current
                        DESCRIPTION
                                "Max times to redirect "
                        DEFVAL { 2 }
                        ::= { hwDomainExtEntry 21 }
                        
               hwDot1xTemplate OBJECT-TYPE
                        SYNTAX Integer32 (1..256)
                        MAX-ACCESS read-create
                        STATUS current
                        DESCRIPTION
                        "This object indicates the template used for the authentication of 802.1X users in a domain."
                        DEFVAL { 1 }
                        ::= { hwDomainExtEntry 22 }    
                        
                hwWebServerIP OBJECT-TYPE
            SYNTAX IpAddress
            MAX-ACCESS read-create
            STATUS current
            DESCRIPTION
            "IPadress of force web server"
            ::= { hwDomainExtEntry 23 }
        
        hwWebServerMode OBJECT-TYPE
            SYNTAX Integer32 (1..256)
            MAX-ACCESS read-create
            STATUS current
            DESCRIPTION
            "MODE of force web server"
            ::= { hwDomainExtEntry 24 }

        hwPoolWarningThreshold OBJECT-TYPE
            SYNTAX Integer32 (1..100|255)
            MAX-ACCESS read-create
            STATUS current
            DESCRIPTION
            "This object indicates the alarm threshold for the address pool bound to a domain.
            If the value is 255, it is invalid."
            DEFVAL { 255 }
            ::= { hwDomainExtEntry 25 }  
                
        hwTacGroupName  OBJECT-TYPE
            SYNTAX DisplayString (SIZE (1..32))
            MAX-ACCESS read-create
            STATUS current
            DESCRIPTION
                "This object indicates the name of the HWTACACS group in the domain.
"
            ::= { hwDomainExtEntry 26 }
        hwServicePolicyName  OBJECT-TYPE
            SYNTAX DisplayString (SIZE (1..32))
            MAX-ACCESS read-create
            STATUS current
            DESCRIPTION
                "Domain service policy name"
            ::= { hwDomainExtEntry 27 }
        hwCopsGroupSSGType  OBJECT-TYPE
            SYNTAX DisplayString (SIZE (1..32))
            MAX-ACCESS read-create
            STATUS current
            DESCRIPTION
                "Domain COPS group name"
            ::= { hwDomainExtEntry 28 }                        
            
        hwDomainAuthorSchemeName  OBJECT-TYPE
            SYNTAX DisplayString (SIZE (1..32))
            MAX-ACCESS read-create
            STATUS current
            DESCRIPTION
                "This object indicates the name of an authorization solution.
"
            ::= { hwDomainExtEntry 29 }

        hwNtvUserProfileName  OBJECT-TYPE
            SYNTAX DisplayString (SIZE (1..32))
            MAX-ACCESS read-create
            STATUS obsolete
            DESCRIPTION
                "Domain IPTV user profile"
            ::= { hwDomainExtEntry 30 }
            
        hwDomainQoSProfile  OBJECT-TYPE
            SYNTAX DisplayString (SIZE (1..32))
            MAX-ACCESS read-create
            STATUS current
            DESCRIPTION
                "Domain Qos profile"
            ::= { hwDomainExtEntry 31 }    
            
        hwDomainZone  OBJECT-TYPE
            SYNTAX DisplayString (SIZE (1..32))
            MAX-ACCESS read-create
            STATUS current
            DESCRIPTION
                "Domain FWZone"
            ::= { hwDomainExtEntry 32 }                                    
            
            hwIfL2tpRadiusForce OBJECT-TYPE
            SYNTAX TruthValue
            MAX-ACCESS read-create
            STATUS current
            DESCRIPTION
            "if force l2tp by radius"
            ::= { hwDomainExtEntry 33 }
        
        hwDownPriority OBJECT-TYPE
                    SYNTAX Integer32 (0..255)
                    MAX-ACCESS read-write
                    STATUS current
                    DESCRIPTION
                        "user down priority
                        
                        0~7,
                        trust-dscp(8),
                        trust-8021p-inner(9),
                        trust-8021p-outer(10),
                        trust-exp-inner(11),
                        trust-exp-outer(12),
                        unchangeable(15)"
                    DEFVAL { 0 }
                    ::= { hwDomainExtEntry 34 }

        
        hwPPPForceAuthtype OBJECT-TYPE
                    SYNTAX INTEGER
                        {
                        pap(0),
                        chap(1),
                        mschapv1(2),
                        mschapv2(3),
                        none(255)
                        }
                    MAX-ACCESS read-write
                    STATUS current
                    DESCRIPTION
                                "Set force authentication type for PPP "
                    ::= { hwDomainExtEntry 35 }
                    
                hwDnsIPAddress OBJECT-TYPE
            SYNTAX IpAddress
            MAX-ACCESS read-create
            STATUS current
            DESCRIPTION
            "IPadress of DNS"
            ::= { hwDomainExtEntry 36 }
            
        hwAdminUserPriority OBJECT-TYPE
            SYNTAX Integer32 (-1..15)
            MAX-ACCESS read-write
            STATUS current
            DESCRIPTION
                "This object indicates the user priority. Value -1 indicates no permission."
            ::= { hwDomainExtEntry 37 }
            
        hwShapingTemplate  OBJECT-TYPE
            SYNTAX DisplayString (SIZE (1..32))
            MAX-ACCESS read-create
            STATUS current
            DESCRIPTION
                "Shaping template"
            ::= { hwDomainExtEntry 38 }
            
        hwDomainDPIPolicyName  OBJECT-TYPE
            SYNTAX DisplayString (SIZE (1..32))
            MAX-ACCESS read-create
            STATUS current
            DESCRIPTION
                "DPI policy name"
            ::= { hwDomainExtEntry 39 }
                        
               hwCopsGroupSIGType  OBJECT-TYPE
            SYNTAX DisplayString (SIZE (1..32))
            MAX-ACCESS read-create
            STATUS current
            DESCRIPTION
                "Domain COPS group name"
            ::= { hwDomainExtEntry 40 }
                
               hwCopsGroupCIPNType  OBJECT-TYPE
            SYNTAX DisplayString (SIZE (1..32))
            MAX-ACCESS read-create
            STATUS current
            DESCRIPTION
                "Domain COPS group name"
            ::= { hwDomainExtEntry 41 }
            
                    
              hwPCReduceCir  OBJECT-TYPE
            SYNTAX Integer32 (0..1000000)
            MAX-ACCESS read-write
            STATUS current
            DESCRIPTION
                "reduce cir"
            ::= { hwDomainExtEntry 43}
            
           hwValAcctType OBJECT-TYPE
            SYNTAX INTEGER
                    {
                    none(0),
                    default(1),
                    radius(2),
                    cops(3)
                    }       
            MAX-ACCESS read-write
            STATUS current
            DESCRIPTION
            "
              value added service accounting type"
            DEFVAL {default}
            ::= { hwDomainExtEntry 44 }
            
        hwValRadiusServer OBJECT-TYPE
            SYNTAX DisplayString (SIZE (1..32))
            MAX-ACCESS read-write
            STATUS current
            DESCRIPTION
            "
             radius server"
            
            ::= { hwDomainExtEntry 45 }
            
        hwValCopsServer OBJECT-TYPE
            SYNTAX DisplayString (SIZE (1..32))
            MAX-ACCESS read-write
            STATUS current
            DESCRIPTION
            "cops server"
            ::= {hwDomainExtEntry 46 }
            
              hwPCReducePir  OBJECT-TYPE
            SYNTAX Integer32 (0..1000000)
            MAX-ACCESS read-write
            STATUS current
            DESCRIPTION
                "reduce PIR"
            ::= { hwDomainExtEntry 47}
            
          hwDomainInboundL2tpQoSProfile OBJECT-TYPE
            SYNTAX DisplayString (SIZE (1..63))
            MAX-ACCESS read-write
            STATUS current
            DESCRIPTION
                "Configure inbound L2TP QOS Profile
                 "
            ::= { hwDomainExtEntry 48}
            
          hwDomainOutboundL2tpQoSProfile OBJECT-TYPE
            SYNTAX DisplayString (SIZE (1..63))
            MAX-ACCESS read-write
            STATUS current
            DESCRIPTION
                "Configure outbound L2TP QOS Profile
                 "
            ::= { hwDomainExtEntry 49}

           hwIfMulticastForward OBJECT-TYPE
            SYNTAX TruthValue
            MAX-ACCESS read-write
            STATUS current
            DESCRIPTION
                "If multicast forward
                 "
            DEFVAL {true}     
            ::= { hwDomainExtEntry 50}    
            
           hwMulticastVirtualSchedulRezCir OBJECT-TYPE
            SYNTAX Integer32 (0 | 128..1000000)
            MAX-ACCESS read-write
            STATUS current
            DESCRIPTION
                "Multicast virtual schedule reserve Cir
                "     
            ::= { hwDomainExtEntry 51}    
            
           hwMulticastVirtualSchedulRezPir OBJECT-TYPE
            SYNTAX Integer32 (0 | 128..1000000)
            MAX-ACCESS read-write
            STATUS current
            DESCRIPTION
                "Multicast virtual schedule reserve PIR
                 "     
            ::= { hwDomainExtEntry 52}    
            
           hwMaxMulticastListNum OBJECT-TYPE
            SYNTAX Integer32 (1..512)
            MAX-ACCESS read-write
            STATUS current
            DESCRIPTION
                "Max list num
                 "     
            ::= { hwDomainExtEntry 53}
            
           hwMultiProfile OBJECT-TYPE
            SYNTAX DisplayString (SIZE(1..32))
            MAX-ACCESS read-write
            STATUS current
            DESCRIPTION
                "Multicast profile
                 "     
            ::= { hwDomainExtEntry 54}                                                            
            
               hwDomainServiceType  OBJECT-TYPE
            SYNTAX INTEGER
                    {
                    stb(0),
                    hsi(1)
                    }
            MAX-ACCESS read-write
            STATUS current
            DESCRIPTION
                "Service type,0 for HSI,1 for not HSI.
                     "
             DEFVAL {hsi}    
            ::= { hwDomainExtEntry 55 }

            hwWebServerUrlParameter OBJECT-TYPE
            SYNTAX TruthValue
            MAX-ACCESS read-write
            STATUS current
            DESCRIPTION
                "If Web Server URL Parameter is enabling
                 "
            DEFVAL {true}     
            ::= { hwDomainExtEntry 56} 
            
            hwWebServerRedirectKeyMscgName OBJECT-TYPE
            SYNTAX DisplayString (SIZE(1..32))
            MAX-ACCESS read-write
            STATUS current
            DESCRIPTION
                "Configure Web Server Redirect Key MscgName
                 "     
            ::= { hwDomainExtEntry 57} 
            
            hwPoratalServerUrlParameter  OBJECT-TYPE
            SYNTAX TruthValue
            MAX-ACCESS read-write
            STATUS current
            DESCRIPTION
                "If Portal Server UrlParameter is enabling
                 "
            DEFVAL {true}     
            ::= { hwDomainExtEntry 58} 
            
            hwPoratalServerFirstUrlKeyName  OBJECT-TYPE
            SYNTAX DisplayString (SIZE(1..32))
            MAX-ACCESS read-write
            STATUS current
            DESCRIPTION
                "The Portal Server Rollback first URL key-name
                 "     
            ::= { hwDomainExtEntry 59} 
            
            hwPoratalServerFirstUrlKeyDefaultName  OBJECT-TYPE
            SYNTAX TruthValue
            MAX-ACCESS read-write
            STATUS current
            DESCRIPTION
                "If the Portal Server Rollback first URL default name
                 "
            DEFVAL {true}     
            ::= { hwDomainExtEntry 60} 
      
     hwDnsSecondIPAddress OBJECT-TYPE
            SYNTAX IpAddress
            MAX-ACCESS read-create
            STATUS current
            DESCRIPTION
            "The Second IP address of DNS"
            ::= { hwDomainExtEntry 61 }  
            
    hwDomainIgmpEnable OBJECT-TYPE
            SYNTAX Integer32
            MAX-ACCESS read-create
            STATUS current
            DESCRIPTION
            "IGMP ENABLE"
            ::= { hwDomainExtEntry 62 }                                                                                 
     hwIPv6PoolName OBJECT-TYPE
            SYNTAX DisplayString (SIZE(0..65))
            MAX-ACCESS read-create
            STATUS current
            DESCRIPTION
            "The name of IPv6 address pool. The format to set value is : operator+pool index list. operator: 1-Add, 2-Delete"
            ::= { hwDomainExtEntry 63 }                                                                                   
             
     hwIPv6PrefixshareFlag OBJECT-TYPE
            SYNTAX INTEGER
            {
                shared(1),
                unshared(2)
            }
            MAX-ACCESS read-create
            STATUS current
            DESCRIPTION
            "The flag indicating whether the prefix is shared."
            ::= { hwDomainExtEntry 64 }                                                                                   
             
     hwUserBasicServiceIPType OBJECT-TYPE
            SYNTAX DisplayString (SIZE(0..3))
            MAX-ACCESS read-create
            STATUS current
            DESCRIPTION
            "The basic service type. UCHAR[0]-IPv4, UCHAR[1]-IPv6, UCHAR[2]-IPv6-PD. '0'-without such basic service, '1'-with such basic service."
            ::= { hwDomainExtEntry 65 }                                                                                   
             
     hwPriDnsIPv6Address OBJECT-TYPE
            SYNTAX Ipv6Address
            MAX-ACCESS read-create
            STATUS current
            DESCRIPTION
            "The IPv6 primary DNS address."
            ::= { hwDomainExtEntry 66 }                                                                                   
             
     hwSecDnsIPv6Address OBJECT-TYPE
            SYNTAX Ipv6Address
            MAX-ACCESS read-create
            STATUS current
            DESCRIPTION
            "The IPv6 secondary DNS address."
            ::= { hwDomainExtEntry 67 }                                                                                   
             
     hwDualStackAccountingType OBJECT-TYPE
            SYNTAX INTEGER
            {
                seperate(1),
                identical(2)
            }
            MAX-ACCESS read-create
            STATUS current
            DESCRIPTION
            "The flag whether to accouting stream separately for dual user."
            ::= { hwDomainExtEntry 68 }                                                                                   
             
     hwIPv6PoolWarningThreshold OBJECT-TYPE
            SYNTAX Integer32 (0..100)
            MAX-ACCESS read-create
            STATUS current
            DESCRIPTION
            "The IPv6 warning threshold. Default value is 0, indicating no warning."
            ::= { hwDomainExtEntry 69 }                                                                                   
             
     hwIPv6CPWaitDHCPv6Delay OBJECT-TYPE
            SYNTAX Integer32 (0|30..120)
            MAX-ACCESS read-create
            STATUS current
            DESCRIPTION
            "The time (in seconds) of waiting for DHCPv6 packets after IPv6CP. The default value is 60 seconds. If the value is set to 0, the device keeps wating for DHCPv6 packets."
            ::= { hwDomainExtEntry 70 }    
             
     hwIPv6ManagedAddressFlag OBJECT-TYPE
            SYNTAX INTEGER
            {
                ndra(1),
                dhcpv6(2)
            }
            MAX-ACCESS read-create
            STATUS current
            DESCRIPTION
            "The address configuration method for PPP and L2TP user."
            ::= { hwDomainExtEntry 71 }                                                                                   
             
     hwIPv6CPIFIDAvailable OBJECT-TYPE
            SYNTAX TruthValue
            MAX-ACCESS read-create
            STATUS current
            DESCRIPTION
            "The flag indicating whether PPP and L2TP user will use the interface-id of ipv6cp negotiation in DHCPv6 address allocation."
            ::= { hwDomainExtEntry 72 }                                                                                   
             
     hwIPv6OtherFlag OBJECT-TYPE
            SYNTAX INTEGER
            {
                ndra(1),
                dhcpv6(2)
            }
            MAX-ACCESS read-create
            STATUS current
            DESCRIPTION
            "The method PPP and L2TP user get configuration parameters."
            ::= { hwDomainExtEntry 73 }                                                                                   
             
     hwIPv6CPAssignIFID OBJECT-TYPE
            SYNTAX TruthValue
            MAX-ACCESS read-create
            STATUS current
            DESCRIPTION
            "The flag indicating whether BRAS assign interface-id on IPv6CP negotiation."
            ::= { hwDomainExtEntry 74 }                                                                                   
             
     hwMultiIPv6ProfileName OBJECT-TYPE
            SYNTAX DisplayString (SIZE(1..32))
            MAX-ACCESS read-create
            STATUS current
            DESCRIPTION
            "The name of multicast profile."
            ::= { hwDomainExtEntry 75 }                                                                                   
                                  
     hwWebServerURLSlave OBJECT-TYPE
            SYNTAX DisplayString (SIZE(0..200))
            MAX-ACCESS read-write
            STATUS current
            DESCRIPTION
            "The URL of slave force web server."
            ::= { hwDomainExtEntry 76 }                   
                                  
       hwWebServerIPSlave OBJECT-TYPE
            SYNTAX IpAddress
            MAX-ACCESS read-create
            STATUS current
            DESCRIPTION
            "IPadress of slave force web server."
            ::= { hwDomainExtEntry 77 } 
            
       hwBindAuthWebIP OBJECT-TYPE
            SYNTAX IpAddress
            MAX-ACCESS read-create
            STATUS current
            DESCRIPTION
            "IPadress of bind authentication web server."
            ::= { hwDomainExtEntry 78 } 

        hwBindAuthWebVrf OBJECT-TYPE
            SYNTAX DisplayString (SIZE(1..31))
            MAX-ACCESS read-write
            STATUS current
            DESCRIPTION
            "The VPN instance name of bind authentication web server."
            ::= { hwDomainExtEntry 79 } 

       hwBindAuthWebIPSlave OBJECT-TYPE
            SYNTAX IpAddress
            MAX-ACCESS read-create
            STATUS current
            DESCRIPTION
            "IPadress of slave bind authentication web server."
            ::= { hwDomainExtEntry 80 } 
                                  
       hwBindAuthWebVrfSlave OBJECT-TYPE
            SYNTAX DisplayString (SIZE(1..31))
            MAX-ACCESS read-write
            STATUS current
            DESCRIPTION
            "The VPN instance name of slave bind authentication web server."
            ::= { hwDomainExtEntry 81 }                
                         
     hwExtVpdnGroupName OBJECT-TYPE
            SYNTAX DisplayString (SIZE (1..255))
            MAX-ACCESS read-write
            STATUS current
            DESCRIPTION
                "The extended VPDN group name."
            ::= { hwDomainExtEntry 82 } 
            
     hwDomainUserGroupName OBJECT-TYPE
            SYNTAX DisplayString (SIZE (1..64))
            MAX-ACCESS read-write
            STATUS current
            DESCRIPTION
                "The user group name."
            ::= { hwDomainExtEntry 83 }                                                                                             
        hwAFTRName OBJECT-TYPE
            SYNTAX DisplayString (SIZE (1..63))
            MAX-ACCESS read-write
            STATUS current
            DESCRIPTION
                "The AFTR name."
            ::= { hwDomainExtEntry 84 }                                                                                         
                    
        hwDomainDhcpOpt64SepAndSeg OBJECT-TYPE
            SYNTAX DisplayString (SIZE (1..5))
            MAX-ACCESS read-create
            STATUS current
            DESCRIPTION
                "Option64 parse separator and segment number."
            ::= { hwDomainExtEntry 85 }  
            
        hwDomainDhcpServerAck OBJECT-TYPE
            SYNTAX TruthValue
            MAX-ACCESS read-create
            STATUS current
            DESCRIPTION
                "Whether to deal dhcp server's ack packet when user online."
            ::= { hwDomainExtEntry 86 }
                            
        hwDomainStatTable OBJECT-TYPE
            SYNTAX SEQUENCE OF HwDomainStatEntry
            MAX-ACCESS not-accessible
            STATUS current
            DESCRIPTION
                "The hwDomainStatTable is a domain information table used to collect statistics about the number of online users in a domain, domain traffic, and address pool."
            ::= { hwAAAMibObjects 6 }

        hwDomainStatEntry OBJECT-TYPE
            SYNTAX HwDomainStatEntry
            MAX-ACCESS not-accessible
            STATUS current
            DESCRIPTION
                "Domain Stat Entry"
            INDEX { hwDomainName }
            ::= { hwDomainStatTable 1 }

            HwDomainStatEntry ::=
                SEQUENCE { 
                    hwDomainAccessedNum
                        Integer32,
                    hwDomainOnlineNum
                        Integer32,
                    hwDomainOnlinePPPUser
                        Integer32,
                    hwDomainFlowDnByte
                        Counter64,
                    hwDomainFlowDnPkt
                        Counter64,
                    hwDomainFlowUpByte  
                        Counter64,
                    hwDomainFlowUpPkt
                        Counter64,
                    hwDomainIPTotalNum
                        Integer32,
                    hwDomainIPUsedNum
                        Integer32,
                    hwDomainIPConflictNum                        
                        Integer32,
                    hwDomainIPExcludeNum
                        Integer32,
                    hwDomainIPIdleNum
                        Integer32,
                    hwDomainIPUsedPercent
                        DisplayString,
                    hwDomainPPPoENum
                        Integer32,
                    hwDomainAuthenRequestsRcvNum     
                        Unsigned32,
                    hwDomainAuthenAcceptsNum     
                        Unsigned32,
                    hwDomainAuthenRejectsNum 
                        Unsigned32,
                    hwDomainAcctRequestsRcvNum 
                        Unsigned32,
                    hwDomainAcctRspSuccessNum 
                        Unsigned32,
                    hwDomainAcctRspFailuresNum 
                        Unsigned32,
                    hwDomainIPv6AddressTotalNum
                        Integer32,
                    hwDomainIPv6AddressUsedNum     
                        Integer32,
                    hwDomainIPv6AddressFreeNum     
                        Integer32,
                    hwDomainIPv6AddressConflictNum 
                        Integer32,
                    hwDomainIPv6AddressExcludeNum  
                        Integer32,
                    hwDomainIPv6AddressUsedPercent 
                        DisplayString,
                    hwDomainNDRAPrefixTotalNum     
                        Integer32,
                    hwDomainNDRAPrefixUsedNum      
                        Integer32,
                    hwDomainNDRAPrefixFreeNum      
                        Integer32,
                    hwDomainNDRAPrefixConflictNum  
                        Integer32,
                    hwDomainNDRAPrefixExcludeNum   
                        Integer32,
                    hwDomainNDRAPrefixUsedPercent  
                        DisplayString,
                    hwDomainPDPrefixTotalNum     
                        Integer32,
                    hwDomainPDPrefixUsedNum      
                        Integer32,
                    hwDomainPDPrefixFreeNum      
                        Integer32,
                    hwDomainPDPrefixConflictNum  
                        Integer32,
                    hwDomainPDPrefixExcludeNum   
                        Integer32,
                    hwDomainPDPrefixUsedPercent  
                        DisplayString,
                    hwDomainIPv6FlowDnByte
                        Counter64,
                    hwDomainIPv6FlowDnPkt
                        Counter64,
                    hwDomainIPv6FlowUpByte
                        Counter64,
                    hwDomainIPv6FlowUpPkt
                          Counter64,
                    hwDomainIPPoolStatu
                        INTEGER,
                    hwDomainIPv6PoolStatu
                        INTEGER,
                    hwDomainIPUsedPercentMax
                        Integer32,
                    hwDomainIPUsedPercentMaxOcc
                        DisplayString,
                    hwDomainIPv6UsedPercentMax
                        Integer32,
                    hwDomainIPv6UsedPercentMaxOcc
                        DisplayString,
                    hwDomainNdUsedStatu
                        INTEGER,
                    hwDomainNdUsedPercentMax
                        Integer32,
                    hwDomainNdUsedPercentMaxOcc
                        DisplayString,
                    hwDomainPdUsedStatu
                        INTEGER,
                    hwDomainPdUsedPercentMax
                        Integer32,
                    hwDomainPdUsedPercentMaxOcc
                        DisplayString
                 }
    
            hwDomainAccessedNum OBJECT-TYPE
                SYNTAX Integer32
                MAX-ACCESS read-only
                STATUS current
                DESCRIPTION
                    "This object indicates the total number of users in the domain.
"
                ::= { hwDomainStatEntry 1 }
            
            hwDomainOnlineNum OBJECT-TYPE
                SYNTAX Integer32
                MAX-ACCESS read-only
                STATUS current
                DESCRIPTION
                    "This object indicates the number of online users in the domain.
"
                ::= { hwDomainStatEntry 2 }
            
            hwDomainOnlinePPPUser OBJECT-TYPE
                SYNTAX Integer32
                MAX-ACCESS read-only
                STATUS current
                DESCRIPTION
                    "This object indicates the number of online PPP users in the domain.
"
                ::= { hwDomainStatEntry 3 }
    
            hwDomainFlowDnByte OBJECT-TYPE
                SYNTAX Counter64
                MAX-ACCESS read-only
                STATUS current
                DESCRIPTION
                    "This object indicates the number of types of outgoing packets in the domain, in kbytes.
"
                ::= { hwDomainStatEntry 4 }
            
            hwDomainFlowDnPkt OBJECT-TYPE
                SYNTAX Counter64
                MAX-ACCESS read-only
                STATUS current
                DESCRIPTION
                    "This object indicates the number of outgoing packets in the domain.
"
                ::= { hwDomainStatEntry 5 }
            
            hwDomainFlowUpByte OBJECT-TYPE
                SYNTAX Counter64
                MAX-ACCESS read-only
                STATUS current
                DESCRIPTION
                    "This object indicates the number of types of incoming packets in the domain, in kbytes.
"
                ::= { hwDomainStatEntry 6 }
            
            hwDomainFlowUpPkt OBJECT-TYPE
                SYNTAX Counter64
                MAX-ACCESS read-only
                STATUS current
                DESCRIPTION
                    "This object indicates the number of incoming packets in the domain.
"
                ::= { hwDomainStatEntry 7 }

            hwDomainIPTotalNum OBJECT-TYPE
                SYNTAX Integer32
                MAX-ACCESS read-only
                STATUS current
                DESCRIPTION
                    "This object indicates the number of configured IP addresses in the address pool.
"
                ::= { hwDomainStatEntry 8 }

            hwDomainIPUsedNum OBJECT-TYPE
                SYNTAX Integer32
                MAX-ACCESS read-only
                STATUS current
                DESCRIPTION
                    "This object indicates the number of used IP addresses.
"
                ::= { hwDomainStatEntry 9 }

            hwDomainIPConflictNum OBJECT-TYPE
                SYNTAX Integer32
                MAX-ACCESS read-only
                STATUS current
                DESCRIPTION
                    "This object indicates the number of conflicting IP addresses.
"
                ::= { hwDomainStatEntry 10 }
            hwDomainIPExcludeNum OBJECT-TYPE
                SYNTAX Integer32
                MAX-ACCESS read-only
                STATUS current
                DESCRIPTION
                    "This object indicates the number of referenced IP addresses.
"
                ::= { hwDomainStatEntry 11 }

            hwDomainIPIdleNum OBJECT-TYPE
                SYNTAX Integer32
                MAX-ACCESS read-only
                STATUS current
                DESCRIPTION
                    "This object indicates the number of idle IP addresses.
"
                ::= { hwDomainStatEntry 12 }

            hwDomainIPUsedPercent OBJECT-TYPE
                SYNTAX DisplayString (SIZE (1..64))
                MAX-ACCESS read-only
                STATUS current
                DESCRIPTION
                    "This object indicates the address usage.
"
                ::= { hwDomainStatEntry 13 }
                
            hwDomainPPPoENum OBJECT-TYPE
                SYNTAX Integer32
                MAX-ACCESS read-only
                STATUS current
                DESCRIPTION
                    "This object indicates the number of PPPoE users in the domain.
"
                ::= { hwDomainStatEntry 14 }   
                
            hwDomainAuthenRequestsRcvNum OBJECT-TYPE
                SYNTAX Unsigned32
                MAX-ACCESS read-only
                STATUS current
                DESCRIPTION
                "This object indicates the number of authentication requests in the domain.
"
                ::= { hwDomainStatEntry 15 }      
                        
            hwDomainAuthenAcceptsNum OBJECT-TYPE
                SYNTAX Unsigned32
                MAX-ACCESS read-only
                STATUS current
                DESCRIPTION
                "This object indicates the number of successful authentication requests in the domain.
"
                ::= { hwDomainStatEntry 16 }       
                        
            hwDomainAuthenRejectsNum OBJECT-TYPE
                SYNTAX Unsigned32
                MAX-ACCESS read-only
                STATUS current
                DESCRIPTION
                "This object indicates the number of failed authentication requests in the domain.
"
                ::= { hwDomainStatEntry 17 }    
            
            hwDomainAcctRequestsRcvNum OBJECT-TYPE
                SYNTAX Unsigned32
                MAX-ACCESS read-only
                STATUS current
                DESCRIPTION
                "This object indicates the number of accounting requests in the domain.
"
                ::= { hwDomainStatEntry 18 }    
                        
            hwDomainAcctRspSuccessNum OBJECT-TYPE
                SYNTAX Unsigned32
                MAX-ACCESS read-only
                STATUS current
                DESCRIPTION
                "This object indicates the number of successful accounting requests in the domain.
"
                ::= { hwDomainStatEntry 19 } 
                                    
            hwDomainAcctRspFailuresNum OBJECT-TYPE
                SYNTAX Unsigned32 
                MAX-ACCESS read-only
                STATUS current
                DESCRIPTION
                "This object indicates the number of failed accounting requests in the domain.
"
                ::= { hwDomainStatEntry 20 }
                 
            hwDomainIPv6AddressTotalNum OBJECT-TYPE
                SYNTAX Integer32 
                MAX-ACCESS read-only
                STATUS current
                DESCRIPTION
                "This object indicates the total number of IPv6 addresses in the domain."
                ::= { hwDomainStatEntry 21 } 
                        
            hwDomainIPv6AddressUsedNum OBJECT-TYPE
                SYNTAX Integer32 
                MAX-ACCESS read-only
                STATUS current
                DESCRIPTION
                "This object indicates the number of used IPv6 addresses in the domain."
                ::= { hwDomainStatEntry 22 }

            hwDomainIPv6AddressFreeNum OBJECT-TYPE
                SYNTAX Integer32 
                MAX-ACCESS read-only
                STATUS current
                DESCRIPTION
                "This object indicates the number of idle IPv6 addresses in the domain."
                ::= { hwDomainStatEntry 23 }                                         

            hwDomainIPv6AddressConflictNum OBJECT-TYPE
                SYNTAX Integer32 
                MAX-ACCESS read-only
                STATUS current
                DESCRIPTION
                "This object indicates the number of conflicting IPv6 addresses in the domain."
                ::= { hwDomainStatEntry 24 }                 

            hwDomainIPv6AddressExcludeNum OBJECT-TYPE
                SYNTAX Integer32 
                MAX-ACCESS read-only
                STATUS current
                DESCRIPTION
                "This object indicates the number of IPv6 addresses that are prohibited from being used in the domain."
                ::= { hwDomainStatEntry 25 }

            hwDomainIPv6AddressUsedPercent OBJECT-TYPE
                SYNTAX DisplayString (SIZE (1..64)) 
                MAX-ACCESS read-only
                STATUS current
                DESCRIPTION
                "This object indicates the usage of IPv6 addresses in the domain."
                ::= { hwDomainStatEntry 26 }    
                
            hwDomainNDRAPrefixTotalNum OBJECT-TYPE
                SYNTAX Integer32 
                MAX-ACCESS read-only
                STATUS current
                DESCRIPTION
                "This object indicates the total number of NDRA prefixes in the domain."
                ::= { hwDomainStatEntry 27 } 
                
            hwDomainNDRAPrefixUsedNum OBJECT-TYPE
                SYNTAX Integer32 
                MAX-ACCESS read-only
                STATUS current
                DESCRIPTION
                "This object indicates the number of used NDRA prefixes in the domain."
                ::= { hwDomainStatEntry 28 }   
 
             hwDomainNDRAPrefixFreeNum OBJECT-TYPE
                SYNTAX Integer32 
                MAX-ACCESS read-only
                STATUS current
                DESCRIPTION
                "This object indicates the number of idle NDRA prefixes in the domain."
                ::= { hwDomainStatEntry 29 } 
                
             hwDomainNDRAPrefixConflictNum OBJECT-TYPE
                SYNTAX Integer32 
                MAX-ACCESS read-only
                STATUS current
                DESCRIPTION
                "This object indicates the number of conflicting NDRA prefixes in the domain."
                ::= { hwDomainStatEntry 30 }                

              hwDomainNDRAPrefixExcludeNum OBJECT-TYPE
                SYNTAX Integer32 
                MAX-ACCESS read-only
                STATUS current
                DESCRIPTION
                "This object indicates the number of NDRA prefixes that are prohibited from being used in the domain."
                ::= { hwDomainStatEntry 31 }   
 
               hwDomainNDRAPrefixUsedPercent OBJECT-TYPE
                SYNTAX DisplayString (SIZE (1..64))  
                MAX-ACCESS read-only
                STATUS current
                DESCRIPTION
                "This object indicates the usage of NDRA prefixes in the domain."
                ::= { hwDomainStatEntry 32 }  
 
               hwDomainPDPrefixTotalNum OBJECT-TYPE
                SYNTAX Integer32 
                MAX-ACCESS read-only
                STATUS current
                DESCRIPTION
                "This object indicates the total number of PD prefixes in the domain."
                ::= { hwDomainStatEntry 33 }

               hwDomainPDPrefixUsedNum OBJECT-TYPE
                SYNTAX Integer32 
                MAX-ACCESS read-only
                STATUS current
                DESCRIPTION
                "This object indicates the number of used PD prefixes in the domain."
                ::= { hwDomainStatEntry 34 }

               hwDomainPDPrefixFreeNum OBJECT-TYPE
                SYNTAX Integer32 
                MAX-ACCESS read-only
                STATUS current
                DESCRIPTION
                "This object indicates the number of idle PD prefixes in the domain."
                ::= { hwDomainStatEntry 35 }

               hwDomainPDPrefixConflictNum OBJECT-TYPE
                SYNTAX Integer32 
                MAX-ACCESS read-only
                STATUS current
                DESCRIPTION
                "This object indicates the number of conflicting PD prefixes in the domain."
                ::= { hwDomainStatEntry 36 }

               hwDomainPDPrefixExcludeNum OBJECT-TYPE
                SYNTAX Integer32 
                MAX-ACCESS read-only
                STATUS current
                DESCRIPTION
                "This object indicates the number of PD prefixes that are prohibited from being used in the domain."
                ::= { hwDomainStatEntry 37 }

               hwDomainPDPrefixUsedPercent OBJECT-TYPE
                SYNTAX DisplayString (SIZE (1..64)) 
                MAX-ACCESS read-only
                STATUS current
                DESCRIPTION
                "This object indicates the usage of PD prefixes in the domain."
                ::= { hwDomainStatEntry 38 }

            hwDomainIPv6FlowDnByte OBJECT-TYPE
                SYNTAX Counter64
                MAX-ACCESS read-only
                STATUS current
                DESCRIPTION
                    "This object indicates the number of bytes of outgoing IPv6 packets in the domain."
                ::= { hwDomainStatEntry 39 }
            
            hwDomainIPv6FlowDnPkt OBJECT-TYPE
                SYNTAX Counter64
                MAX-ACCESS read-only
                STATUS current
                DESCRIPTION
                    "This object indicates the number of outgoing IPv6 packets in the domain."
                ::= { hwDomainStatEntry 40 }
            
            hwDomainIPv6FlowUpByte OBJECT-TYPE
                SYNTAX Counter64
                MAX-ACCESS read-only
                STATUS current
                DESCRIPTION
                    "This object indicates the number of bytes of incoming IPv6 packets in the domain."
                ::= { hwDomainStatEntry 41 }
            
            hwDomainIPv6FlowUpPkt OBJECT-TYPE
                SYNTAX Counter64
                MAX-ACCESS read-only
                STATUS current
                DESCRIPTION
                    "This object indicates the number of incoming IPv6 packets in the domain."
                ::= { hwDomainStatEntry 42 }

            hwDomainIPPoolStatu OBJECT-TYPE
                SYNTAX INTEGER
                {
                normal(0),
                upperLimit(1),
                lowerLimit(2)
                }
                MAX-ACCESS read-only
                STATUS current
                DESCRIPTION
                "IPv4 address usage state in the domain. The value 0 indicates normal address usage, the value 1 indicates that address usage exceeds the upper threshold, and the value 2 indicates that address usage falls below the lower threshold."
                ::= { hwDomainStatEntry 43 }
            hwDomainIPv6PoolStatu OBJECT-TYPE
                SYNTAX INTEGER
                {
                normal(0),
                upperLimit(1),
                lowerLimit(2)
                }
                MAX-ACCESS read-only
                STATUS current
                DESCRIPTION
                "IPv6 address usage state in the domain. The value 0 indicates normal address usage, the value 1 indicates that address usage exceeds the upper threshold, and the value 2 indicates that address usage falls below the lower threshold."
                ::= { hwDomainStatEntry 44 }
            
            hwDomainIPUsedPercentMax OBJECT-TYPE
                SYNTAX Integer32
                MAX-ACCESS read-only
                STATUS current
                DESCRIPTION
                    "Maximum IPv4 address usage in the domain."
                ::= { hwDomainStatEntry 45 }
            
            hwDomainIPUsedPercentMaxOcc OBJECT-TYPE
                SYNTAX DisplayString (SIZE (1..32))
                MAX-ACCESS read-only
                STATUS current
                DESCRIPTION
                    "Date and time when IPv4 address usage reaches the historical maximum number."
                ::= { hwDomainStatEntry 46 }
            
            hwDomainIPv6UsedPercentMax OBJECT-TYPE
                SYNTAX Integer32
                MAX-ACCESS read-only
                STATUS current
                DESCRIPTION
                    "Maximum IPv6 address usage in the domain."
                ::= { hwDomainStatEntry 47 }
            
            hwDomainIPv6UsedPercentMaxOcc OBJECT-TYPE
                SYNTAX DisplayString (SIZE (1..32))
                MAX-ACCESS read-only
                STATUS current
                DESCRIPTION
                    "Date and time when IPv6 address usage reaches the historical maximum number."
                ::= { hwDomainStatEntry 48 }
            hwDomainNdUsedStatu OBJECT-TYPE
                SYNTAX INTEGER
                {
                normal(0),
                upperLimit(1),
                lowerLimit(2)
                }
                MAX-ACCESS read-only
                STATUS current
                DESCRIPTION
                "ND address usage state."
                ::= { hwDomainStatEntry 49 }
            
            hwDomainNdUsedPercentMax OBJECT-TYPE
                SYNTAX Integer32
                MAX-ACCESS read-only
                STATUS current
                DESCRIPTION
                    "Maximum ND address usage."
                ::= { hwDomainStatEntry 50 }
            
            hwDomainNdUsedPercentMaxOcc OBJECT-TYPE
                SYNTAX DisplayString (SIZE (1..32))
                MAX-ACCESS read-only
                STATUS current
                DESCRIPTION
                    "Date and time when ND address usage reaches the historical maximum number."
                ::= { hwDomainStatEntry 51 }
            hwDomainPdUsedStatu OBJECT-TYPE
                SYNTAX INTEGER
                {
                normal(0),
                upperLimit(1),
                lowerLimit(2)
                } 
                MAX-ACCESS read-only
                STATUS current
                DESCRIPTION
                "PD address usage state."
                ::= { hwDomainStatEntry 52 }
            
            hwDomainPdUsedPercentMax OBJECT-TYPE
                SYNTAX Integer32
                MAX-ACCESS read-only
                STATUS current
                DESCRIPTION
                    "Maximum PD address usage."
                ::= { hwDomainStatEntry 53 }
            
            hwDomainPdUsedPercentMaxOcc OBJECT-TYPE
                SYNTAX DisplayString (SIZE (1..32))
                MAX-ACCESS read-only
                STATUS current
                DESCRIPTION
                    "Date and time when PD address usage reaches the historical maximum number."
                ::= { hwDomainStatEntry 54 }


                               
        hwLocalUserTable OBJECT-TYPE
            SYNTAX SEQUENCE OF HwLocalUserEntry
            MAX-ACCESS not-accessible
            STATUS current
            DESCRIPTION
                "Local user table"
            ::= { hwAAAMibObjects 10 }

        hwLocalUserEntry OBJECT-TYPE
            SYNTAX HwLocalUserEntry
            MAX-ACCESS not-accessible
            STATUS current
            DESCRIPTION
                "Local user Entry"
            INDEX { hwLocalUserName }
            ::= { hwLocalUserTable 1 }

        HwLocalUserEntry ::=
            SEQUENCE {
                hwLocalUserName
                    DisplayString,
                hwLocalUserPassword
                    DisplayString,
                hwLocalUserAccessType
                    Unsigned32,
                hwLocalUserPriority
                    Integer32,
                hwftpdirction
                    DisplayString,   
                hwQosProfileName
                    DisplayString,
                hwLocalUserRowStatus
                    RowStatus,
                    hwLocalUserIpAddress
                            IpAddress,
                    hwLocalUserVpnInstance
                            DisplayString,
               hwLocalUserAccessLimitNum
                    Unsigned32,
               hwLocalUserPasswordLifetimeMin
                    Integer32,
               hwLocalUserPasswordLifetimeMax
                    Integer32,
               hwLocalUserIfAllowWeakPassword
                    INTEGER,
   	hwLocalUserPasswordSetTime
                    DisplayString,
              hwLocalUserPasswordExpireTime
                    DisplayString,
                hwLocalUserPasswordIsExpired
                    INTEGER,
              hwLocalUserPasswordIsOrginal
                    INTEGER,
		 hwhttpdirectory
                    DisplayString  		

             }

        hwLocalUserName OBJECT-TYPE
            SYNTAX DisplayString (SIZE (1..253))
            MAX-ACCESS read-only
            STATUS current
            DESCRIPTION
                "Local user name"
            ::= { hwLocalUserEntry 1 }

        hwLocalUserPassword OBJECT-TYPE
            SYNTAX DisplayString (SIZE (0..128))
            MAX-ACCESS read-create
            STATUS current
            DESCRIPTION
                "local user's password"
            ::= { hwLocalUserEntry 2 }

        hwLocalUserAccessType OBJECT-TYPE
            SYNTAX Unsigned32 (0..4294967295)
            MAX-ACCESS read-create
            STATUS current
            DESCRIPTION
                "Local user's type
                0xFFFFFFFF all
                0x00000001 PPP                
                0x00000002 VLAN WEB
                0x00000004 VLAN,
                0x00000010 CABLE MODEM
                0x00000020 802.1X,
                0x00000040 telnet,
                0x00000080 terminals
                0x00000100 ftp,
                0x00000200 SSH,                            
                0x00000400 x25pa"
            ::= { hwLocalUserEntry 3 }

        hwLocalUserPriority OBJECT-TYPE
            SYNTAX Integer32 (0..16)
            MAX-ACCESS read-create
            STATUS current
            DESCRIPTION
                "Local user's priority
                "
            ::= { hwLocalUserEntry 4 }

        hwftpdirction OBJECT-TYPE
            SYNTAX DisplayString (SIZE (1..255))
            MAX-ACCESS read-create
            STATUS current
            DESCRIPTION
                "ftp directory"
            ::= { hwLocalUserEntry 5 }   
            
           hwQosProfileName OBJECT-TYPE
            SYNTAX DisplayString (SIZE (1..32))
            MAX-ACCESS read-create
            STATUS current
            DESCRIPTION
                "qos profile"
            ::= { hwLocalUserEntry 6 }

        hwLocalUserRowStatus OBJECT-TYPE
            SYNTAX RowStatus
            MAX-ACCESS read-create
            STATUS current
            DESCRIPTION
                "row admin status"
            ::= { hwLocalUserEntry 12 }
            
            hwLocalUserIpAddress OBJECT-TYPE
            SYNTAX IpAddress
            MAX-ACCESS read-write
            STATUS current
            DESCRIPTION
                "user IP address"
            ::= { hwLocalUserEntry 13 }
            
        hwLocalUserVpnInstance OBJECT-TYPE
            SYNTAX DisplayString (SIZE (1..31))
            MAX-ACCESS read-write
            STATUS current
            DESCRIPTION
                "VPN Instance name"
            ::= { hwLocalUserEntry 14 }
            
        hwLocalUserAccessLimitNum OBJECT-TYPE
            SYNTAX Unsigned32 (1..4294967295)
            MAX-ACCESS read-create
            STATUS current
            DESCRIPTION
                "The maximum number of access limit"
            ::= { hwLocalUserEntry 15 }

        hwLocalUserPasswordLifetimeMin OBJECT-TYPE
            SYNTAX Integer32 (0..65535)
            MAX-ACCESS read-create
            STATUS current
            DESCRIPTION
                "The minimum seconds of local user's password"
            ::= { hwLocalUserEntry 16 }
            
        hwLocalUserPasswordLifetimeMax OBJECT-TYPE
            SYNTAX Integer32 (0..65535)
            MAX-ACCESS read-create
            STATUS current
            DESCRIPTION
                "The maximum days of local user's password"
            ::= { hwLocalUserEntry 17 }
                        
        hwLocalUserIfAllowWeakPassword OBJECT-TYPE
            SYNTAX INTEGER
                {
                    notallow(1),
                    allow(2)               
                }
            MAX-ACCESS read-write
            STATUS current
            DESCRIPTION
                "Whether to allow setting weak password.  The default value is 1.
                 It is recommended that the password consist of at least 2 types of characters, 
                 including lowercase letters, uppercase letters, numerals and special characters."
            ::= { hwLocalUserEntry 18 }

         hwLocalUserPasswordSetTime OBJECT-TYPE
                  SYNTAX DisplayString (SIZE (1..64))                
                  MAX-ACCESS read-only
                 STATUS current
                 DESCRIPTION
                   "Local user password set time."
                 ::= {  hwLocalUserEntry 19  }
                 
        hwLocalUserPasswordExpireTime OBJECT-TYPE
                  SYNTAX DisplayString (SIZE (1..64))        
                 MAX-ACCESS read-only
                 STATUS current
                 DESCRIPTION
                   "Local user password expire time."
                 ::= { hwLocalUserEntry 20 }
  
         hwLocalUserPasswordIsExpired OBJECT-TYPE   
                 SYNTAX INTEGER
                  {
                    notExpired(0),
                    expired(1)               
                  }
                  MAX-ACCESS read-only
                 STATUS current
                 DESCRIPTION
                   "Local user password is expired."
                 ::= {  hwLocalUserEntry 21 }
                 
        hwLocalUserPasswordIsOrginal OBJECT-TYPE    
                 SYNTAX INTEGER
                 {
                    notOrginal(0),
                    orginal(1)               
                 }
                 MAX-ACCESS read-only
                 STATUS current
                 DESCRIPTION
                   "Local user password is orginal."
                 ::= {  hwLocalUserEntry 22 }
				 
		hwhttpdirectory OBJECT-TYPE
            SYNTAX DisplayString (SIZE (1..64))
            MAX-ACCESS read-create
            STATUS current
            DESCRIPTION
                "http directory"
            ::= { hwLocalUserEntry 23 }   		 
                        
        hwLocalUserExtTable OBJECT-TYPE
            SYNTAX SEQUENCE OF HwLocalUserExtEntry
            MAX-ACCESS not-accessible
            STATUS current
            DESCRIPTION
                "local user extend table"
            ::= { hwAAAMibObjects 11 }

        hwLocalUserExtEntry OBJECT-TYPE
            SYNTAX HwLocalUserExtEntry
            MAX-ACCESS not-accessible
            STATUS current
            DESCRIPTION
                "

                Local user table is used to save the relevant information of the local user.
                The index item is node hwLocalUserName, which can only be entered during the creation, 
                and can not be modified thereafter. When its access number is 0, it can not be deleted.
                Operation constraint description:
                1. The present user online is not allowed to be deleted.
                2. When adding new record, the username must contain a field name. 
                The format of username is 'user@domain'
                "
            INDEX { hwLocalUserName }
            ::= { hwLocalUserExtTable 1 }

        HwLocalUserExtEntry ::=
            SEQUENCE {
                hwLocalUserState
                    INTEGER,
                hwLocalUserNoCallBackVerify
                    TruthValue,
                hwLocalUserCallBackDialStr
                    DisplayString,
                hwLocalUserBlockFailTimes
                    Integer32,                       
                hwLocalUserBlockInterval  
                    Integer32,
                hwLocalUserUserGroup
                    DisplayString,
                hwLocalUserDeviceType
                    DisplayString,
                hwLocalUserExpireDate
                    DisplayString,
                hwLocalUserIdleTimeoutSecond
                    Unsigned32,
                hwLocalUserTimeRange
                    DisplayString,
                hwLocalUserIsExpired
                    INTEGER,
                hwLocalUserExpireHour
                    Integer32,
                hwLocalUserRole
                    INTEGER,
                hwLocalUserBlockTimestamp
                    DisplayString
             }

        hwLocalUserState OBJECT-TYPE
            SYNTAX INTEGER
                {
                block(0),
                active(1)
                }
            MAX-ACCESS read-write
            STATUS current
            DESCRIPTION
                "user status"
            ::= { hwLocalUserExtEntry 2 }
            
        hwLocalUserNoCallBackVerify OBJECT-TYPE
            SYNTAX TruthValue
            MAX-ACCESS read-write
            STATUS current
            DESCRIPTION
                "if verify for callback"
            ::= { hwLocalUserExtEntry 3 }
            
        hwLocalUserCallBackDialStr OBJECT-TYPE
            SYNTAX DisplayString (SIZE(1..64))
            MAX-ACCESS read-write
            STATUS current
            DESCRIPTION
                "call back number"
            ::= { hwLocalUserExtEntry 4 }
          
        hwLocalUserBlockFailTimes OBJECT-TYPE
            SYNTAX Integer32 (0..10)
            MAX-ACCESS read-create
            STATUS current
            DESCRIPTION
                "Blocking state, set the number of requests to allow the user authentication error.
                and the value of this object is invalid, 0 is displayed."    
            ::= { hwLocalUserExtEntry 5 }
      
        hwLocalUserBlockInterval OBJECT-TYPE
            SYNTAX Integer32 (0..65535)
            MAX-ACCESS read-create
            STATUS current
            DESCRIPTION
                "Blocking state, set the user authentication request to allow time between blocking,unit:minute.  
                 and the value of this object is invalid, 0 is displayed."
            ::= { hwLocalUserExtEntry 6 }
            
        hwLocalUserUserGroup OBJECT-TYPE
            SYNTAX DisplayString (SIZE(1..64))
            MAX-ACCESS read-write
            STATUS current
            DESCRIPTION
                "Local user group"
            ::= { hwLocalUserExtEntry 7 } 
            
       hwLocalUserDeviceType OBJECT-TYPE
            SYNTAX DisplayString (SIZE(1..256))
            MAX-ACCESS read-write
            STATUS current
            DESCRIPTION
                "Access user device type"
            ::= { hwLocalUserExtEntry 8 }
                         
       hwLocalUserExpireDate OBJECT-TYPE
            SYNTAX DisplayString (SIZE(1..10))
            MAX-ACCESS read-write
            STATUS current
            DESCRIPTION
                "The expiration date of a local account"
            ::= { hwLocalUserExtEntry 9 }             
             
       hwLocalUserIdleTimeoutSecond OBJECT-TYPE
            SYNTAX Unsigned32 (0..4294967295)
            MAX-ACCESS read-write
            STATUS current
            DESCRIPTION
                "The timeout period for disconnection of the user"
            ::= { hwLocalUserExtEntry 10 } 
            
       hwLocalUserTimeRange OBJECT-TYPE
            SYNTAX DisplayString (SIZE(1..32))
            MAX-ACCESS read-write
            STATUS current
            DESCRIPTION
                "The time-range of user"
            ::= { hwLocalUserExtEntry 11 } 
            
        hwLocalUserIsExpired OBJECT-TYPE   
            SYNTAX INTEGER
            {
                notExpired(0),
                expired(1)               
            }
            MAX-ACCESS read-only
            STATUS current
            DESCRIPTION
                "Local user  is expired."
            ::= {  hwLocalUserExtEntry 12 }

        hwLocalUserExpireHour OBJECT-TYPE
            SYNTAX Integer32  (0..23)
            MAX-ACCESS read-write
            STATUS current
            DESCRIPTION
                "The expiration hour of a local account"
            ::= { hwLocalUserExtEntry 13 } 
            
        hwLocalUserRole OBJECT-TYPE
            SYNTAX INTEGER
                {
                normal(0),
                guestadmin(1)
                }
            MAX-ACCESS read-write
            STATUS current
            DESCRIPTION
                "user role"
            ::= { hwLocalUserExtEntry 14 }                                                        

        
        hwLocalUserBlockTimestamp OBJECT-TYPE
            SYNTAX DisplayString (SIZE(1..32))
            MAX-ACCESS read-only
            STATUS current
            DESCRIPTION
                "Time locked in a local account."
            ::= { hwLocalUserExtEntry 15 }

        
        hwAAASetting OBJECT IDENTIFIER ::= { hwAAAMibObjects 13 }

        hwAAASettingEntry OBJECT IDENTIFIER ::= { hwAAASetting 1 }

        hwRoamChar OBJECT-TYPE
            SYNTAX DisplayString (SIZE (1..1))
            MAX-ACCESS read-write
            STATUS current
            DESCRIPTION
                "Roam char, include '/',':','*','\','<','>','|'
                "
            ::= { hwAAASettingEntry 1 }
            
        hwGlobalControl OBJECT-TYPE
            SYNTAX TruthValue
            MAX-ACCESS read-write
            STATUS current
            DESCRIPTION
                "If use default configuration. "
            ::= { hwAAASettingEntry 2 }

        hwSystemRecord OBJECT-TYPE
            SYNTAX DisplayString (SIZE (1..32))
            MAX-ACCESS read-write
            STATUS current
            DESCRIPTION
                "This object indicates the system command recording function."
            ::= { hwAAASettingEntry 3 }            

        hwOutboundRecord OBJECT-TYPE
            SYNTAX DisplayString (SIZE (1..32))
            MAX-ACCESS read-write
            STATUS current
            DESCRIPTION
                "This object indicates the outbound command recording function."
            ::= { hwAAASettingEntry 4 }    

        hwCmdRecord OBJECT-TYPE
            SYNTAX DisplayString (SIZE (1..32))
            MAX-ACCESS read-write
            STATUS current
            DESCRIPTION
                "This object indicates the command recording function."
            ::= { hwAAASettingEntry 5 }    
            
        hwPPPUserOfflineStandardize OBJECT-TYPE
            SYNTAX TruthValue
            MAX-ACCESS read-write
            STATUS current
            DESCRIPTION
                "
                This object indicates whether to report the standard cause of user logout to the RADIUS server when the user is abnormally logged out due to 'ppp-echo-fail'.
                "
            ::= { hwAAASettingEntry 6 }
        
        hwDomainNameParseDirection OBJECT-TYPE
            SYNTAX INTEGER
                {
                lefttoright(0),
                righttoleft(1)
                }
            MAX-ACCESS read-write
            STATUS current
            DESCRIPTION
                "
                This object indicates the domain name resolution sequence: 
                lefttoright(0),
                righttoleft(1)
                "
            ::= { hwAAASettingEntry 7 }
        
        hwDomainNameLocation OBJECT-TYPE
            SYNTAX INTEGER
                {
                beforedelimiter(0),
                afterdelimiter(1)
                }
            MAX-ACCESS read-write
            STATUS current
            DESCRIPTION
                "
                This object indicates the position of the domain name: 
                beforedelimiter(0),
                afterdelimiter(1)
                "
            ::= { hwAAASettingEntry 8 }
        
        hwAccessSpeedNumber OBJECT-TYPE
            SYNTAX Integer32 (0..65535)
            MAX-ACCESS read-write
            STATUS current
            DESCRIPTION
                "
                 Access Speed Number
                "
            ::= { hwAAASettingEntry 9 }
        
        hwAccessSpeedPeriod OBJECT-TYPE
            SYNTAX Integer32 (0..65535)
            MAX-ACCESS read-write
            STATUS current
            DESCRIPTION
                "
                 Access Speed Period
                "
            ::= { hwAAASettingEntry 10 }
            
        hwRealmNameChar OBJECT-TYPE
            SYNTAX DisplayString (SIZE (1..1))
            MAX-ACCESS read-write
            STATUS current
            DESCRIPTION
                "
                 Realm-name-delimiter. include @,|,:,',<,>,/,\,%
                "
            ::= { hwAAASettingEntry 11 }
            
        hwRealmParseDirection OBJECT-TYPE
            SYNTAX INTEGER
                {
                 lefttoright(0),
                 righttoleft(1)
                }
            MAX-ACCESS read-write
            STATUS current
            DESCRIPTION
                "
                 lefttoright(0),
                 righttoleft(1) .default is 0.
                "
            ::= { hwAAASettingEntry 12}
            
          hwIPOXpassword OBJECT-TYPE
            SYNTAX DisplayString(SIZE (0..128))
            MAX-ACCESS read-write
            STATUS current
            DESCRIPTION
                "
                 IPOX user's password
                "
            ::= { hwAAASettingEntry 14 }
            
            
      hwAccessDelayTransitionStep OBJECT-TYPE
            SYNTAX Integer32(0..262144)
            MAX-ACCESS read-write
            STATUS current
            DESCRIPTION
                "Access relay step,
                 "
            ::= { hwAAASettingEntry 16 }
                    
      hwAccessDelayTime OBJECT-TYPE
            SYNTAX Integer32(0..2550)
            MAX-ACCESS read-write
            STATUS current
            DESCRIPTION
                "Maximum access delay time,
                 "
            ::= { hwAAASettingEntry 17 }
      hwAccessDelayMinTime OBJECT-TYPE
            SYNTAX Integer32(0..2550)
            MAX-ACCESS read-write
            STATUS current
            DESCRIPTION
                "Minimum access delay time,
                 "
            ::= { hwAAASettingEntry 18 }
            
      hwParsePriority OBJECT-TYPE
            SYNTAX INTEGER
                {
                 domainfirst(0),
                 realmfirst(1)
                }
            MAX-ACCESS read-write
            STATUS current
            DESCRIPTION
                "Parse priority ,default is 0
                 
                "
            ::= { hwAAASettingEntry 19 }
            
      hwRealmNameLocation OBJECT-TYPE
            SYNTAX INTEGER
                {
                beforedelimiter(0),
                afterdelimiter(1)
                }
            MAX-ACCESS read-write
            STATUS current
            DESCRIPTION
                "
                
                beforedelimiter(0),
                afterdelimiter(1).default is 0.
                "
            ::= { hwAAASettingEntry 20 }
            
        hwIPOXUsernameOption82 OBJECT-TYPE
            SYNTAX INTEGER
                 {
                  none(0),
                  first(1),
                  second(2),
                  third(3),
                  fourth(4)
                }
            MAX-ACCESS read-write
            STATUS current
            DESCRIPTION
                "IPOX user name generate type, default is 0.
                "               
            ::= { hwAAASettingEntry 21 }

        hwIPOXUsernameIP OBJECT-TYPE
            SYNTAX INTEGER
                 {
                  none(0),
                  first(1),
                  second(2),
                  third(3),
                  fourth(4)
                }
            MAX-ACCESS read-write
            STATUS current
            DESCRIPTION
                "IPOX user name generate type, default is 0.
                "        
                             
            ::= { hwAAASettingEntry 22 }     
            
        hwIPOXUsernameSysname OBJECT-TYPE
            SYNTAX INTEGER
                 {
                  none(0),
                  first(1),
                  second(2),
                  third(3),
                  fourth(4)
                }
            MAX-ACCESS read-write
            STATUS current
            DESCRIPTION
                "IPOX user name generate type, default is 0.
                "        
                            
            ::= { hwAAASettingEntry 23 }   
            
         hwIPOXUsernameMAC OBJECT-TYPE
            SYNTAX INTEGER
                 {
                  none(0),
                  first(1),
                  second(2),
                  third(3),
                  fourth(4)
                }
            MAX-ACCESS read-write
            STATUS current
            DESCRIPTION
                "IPOX user name generate type ,default is 0.
                "                                  
            ::= { hwAAASettingEntry 24 }

        hwDefaultUserName OBJECT-TYPE
            SYNTAX DisplayString (SIZE(0..255))
            MAX-ACCESS read-write
            STATUS current
            DESCRIPTION
            "Configure default user name type"
            ::= { hwAAASettingEntry 25 }

      hwNasSerial OBJECT-TYPE
            SYNTAX DisplayString (SIZE(1..31))
            MAX-ACCESS read-write
            STATUS current
            DESCRIPTION
            "Configure NAS serial number"
            ::= { hwAAASettingEntry 26 }

      hwAAAPasswordRepeatNumber OBJECT-TYPE
            SYNTAX Integer32(0..12)
            MAX-ACCESS read-write
            STATUS current
            DESCRIPTION
                "Check to times of password can't repeat"
            ::= { hwAAASettingEntry 27 }                 
            
      hwAAAPasswordRemindDay OBJECT-TYPE
            SYNTAX Integer32(1..90)
            MAX-ACCESS read-write
            STATUS current
            DESCRIPTION
                "Remind days before password expired"
            ::= { hwAAASettingEntry 28 }   
 
      hwOnlineUserNumLowerLimitThreshold OBJECT-TYPE
            SYNTAX Integer32(0..99|255)
            MAX-ACCESS read-write
            STATUS current
            DESCRIPTION
                "The online user lower limit warning threshold"
            DEFVAL { 255 }
            ::= { hwAAASettingEntry 29 } 
            
      hwOnlineUserNumUpperLimitThreshold OBJECT-TYPE
            SYNTAX Integer32(1..100|255)
            MAX-ACCESS read-write
            STATUS current
            DESCRIPTION
                "The online user upper limit warning threshold"
            DEFVAL { 255 }
            ::= { hwAAASettingEntry 30 }
      
      hwTriggerLoose OBJECT-TYPE
            SYNTAX Unsigned32(0..1440|4294967295)
            MAX-ACCESS read-write
            STATUS current
            DESCRIPTION
                "Access trigger loose time"
            DEFVAL { 120 }
            ::= { hwAAASettingEntry 31 }
	    
      hwOfflineSpeedNumber OBJECT-TYPE
            SYNTAX Integer32 (50..256)
            MAX-ACCESS read-write
            STATUS current
            DESCRIPTION
                "
                 Offline Speed Number
                "
            ::= { hwAAASettingEntry 32 }	    
                  
      hwIPOXpasswordKeyType OBJECT-TYPE
        SYNTAX INTEGER
        {
           simple(1),
           cipher(2)
        }MAX-ACCESS read-write
        STATUS current
        DESCRIPTION
               "IPOX user's password type."
        DEFVAL { cipher }   
        ::= { hwAAASettingEntry 33 }
             
      hwReauthorizeEnable OBJECT-TYPE
            SYNTAX INTEGER
                {
                enable(1),
                disable(2)
                }
            MAX-ACCESS read-write
            STATUS current
            DESCRIPTION
                "
                This object indicates whether to allow administrator to modify user's user-group by command line : 
                enable(1),
                disable(2)
                "
            ::= { hwAAASettingEntry 34 }

        hwDomainNameDelimiter OBJECT-TYPE
            SYNTAX DisplayString (SIZE (1..1))
            MAX-ACCESS read-write
            STATUS current
            DESCRIPTION
                "
                 Domain-name-delimiter. include \ / : < > | @ ' %
                 It can not be same with hwDomainNameSecurityDelimiter.
                "
            ::= { hwAAASettingEntry 35 }
            
        hwDomainNameSecurityDelimiter OBJECT-TYPE
            SYNTAX DisplayString (SIZE (1..1))
            MAX-ACCESS read-write
            STATUS current
            DESCRIPTION
                "
                 Domain-name-security-delimiter. include \ / : < > | @ ' %
                 It can not be same with hwDomainNameDelimiter.
                "
            ::= { hwAAASettingEntry 36 }    

        -- 1.3.6.1.4.1.2011.5.2.1.13.1.37
        hwGlobalAuthEventAuthFailResponseFail OBJECT-TYPE
                SYNTAX INTEGER
                {
                        enable(1),
                        disable(2)
                }
                MAX-ACCESS read-write
                STATUS current
                DESCRIPTION
                        "Description."
                ::= { hwAAASettingEntry 37 }

        -- 1.3.6.1.4.1.2011.5.2.1.13.1.38
        hwGlobalAuthEventAuthFailVlan OBJECT-TYPE
                SYNTAX Integer32 (0..4094)
                MAX-ACCESS read-write
                STATUS current
                DESCRIPTION
                        "Description."
                ::= { hwAAASettingEntry 38 }

        -- 1.3.6.1.4.1.2011.5.2.1.13.1.39
        hwGlobalAuthEventAuthenServerDownResponseFail OBJECT-TYPE
                SYNTAX INTEGER
                {
                        enable(1),
                        disable(2)
                }
                MAX-ACCESS read-write
                STATUS current
                DESCRIPTION
                        "Description."
                ::= { hwAAASettingEntry 39 }

        -- 1.3.6.1.4.1.2011.5.2.1.13.1.40
        hwGlobalAuthEventAuthenServerDownVlan OBJECT-TYPE
                SYNTAX Integer32 (0..4094)
                MAX-ACCESS read-write
                STATUS current
                DESCRIPTION
                        "Description."
                ::= { hwAAASettingEntry 40 }

        -- 1.3.6.1.4.1.2011.5.2.1.13.1.41
        hwGlobalAuthEventClientNoResponseVlan OBJECT-TYPE
                SYNTAX Integer32 (0..4094)
                MAX-ACCESS read-write
                STATUS current
                DESCRIPTION
                        "Description."
                ::= { hwAAASettingEntry 41 }

        -- 1.3.6.1.4.1.2011.5.2.1.13.1.42
        hwGlobalAuthEventPreAuthVlan OBJECT-TYPE
                SYNTAX Integer32 (0..4094)
                MAX-ACCESS read-write
                STATUS current
                DESCRIPTION
                        "Description."
                ::= { hwAAASettingEntry 42 }

        -- 1.3.6.1.4.1.2011.5.2.1.13.1.43
        hwGlobalAuthEventAuthFailUserGroup OBJECT-TYPE
                SYNTAX OCTET STRING (SIZE (0..64))
                MAX-ACCESS read-write
                STATUS current
                DESCRIPTION
                        "Description."
                ::= { hwAAASettingEntry 43 }

        -- 1.3.6.1.4.1.2011.5.2.1.13.1.44
        hwGlobalAuthEventAuthenServerDownUserGroup OBJECT-TYPE
                SYNTAX OCTET STRING (SIZE (0..64))
                MAX-ACCESS read-write
                STATUS current
                DESCRIPTION
                        "Description."
                ::= { hwAAASettingEntry 44 }

        -- 1.3.6.1.4.1.2011.5.2.1.13.1.45
        hwGlobalAuthEventClientNoResponseUserGroup OBJECT-TYPE
                SYNTAX OCTET STRING (SIZE (0..64))
                MAX-ACCESS read-write
                STATUS current
                DESCRIPTION
                        "Description."
                ::= { hwAAASettingEntry 45 }

        -- 1.3.6.1.4.1.2011.5.2.1.13.1.46
        hwGlobalAuthEventPreAuthUserGroup OBJECT-TYPE
                SYNTAX OCTET STRING (SIZE (0..64))
                MAX-ACCESS read-write
                STATUS current
                DESCRIPTION
                        "Description."
                ::= { hwAAASettingEntry 46 }

      hwAuthorModifyMode OBJECT-TYPE
            SYNTAX INTEGER
                {
                overlay(0),
                modify(1)
                }
            MAX-ACCESS read-write
            STATUS current
            DESCRIPTION
                "
                 The update mode for user authorization information: 
                overlay(0),
                modify(1)
                "
            ::= { hwAAASettingEntry 47 }

        hwLocalRetryInterval OBJECT-TYPE
            SYNTAX Integer32 (5..65535)
            MAX-ACCESS read-write
            STATUS current
            DESCRIPTION
                "
                 The retry interval of a local account.
                "
            ::= { hwAAASettingEntry 48 }
            
        hwLocalRetryTime OBJECT-TYPE
            SYNTAX Integer32 (3..65535)
            MAX-ACCESS read-write
            STATUS current
            DESCRIPTION
                "
                 The consecutive authentication failure count.
                "
            ::= { hwAAASettingEntry 49 }

        hwLocalBlockTime OBJECT-TYPE
            SYNTAX Integer32 (5..65535)
            MAX-ACCESS read-write
            STATUS current
            DESCRIPTION
                "
                 The local account locking duration.
                "
            ::= { hwAAASettingEntry 50 }
            
        hwRemoteRetryInterval OBJECT-TYPE
            SYNTAX Integer32 (5..65535)
            MAX-ACCESS read-write
            STATUS current
            DESCRIPTION
                "
                 The authentication retry interval.
                 If it is administrator, the node is replaced with hwRemoteAdminRetryInterval.
                 If it is access-user, the node is replaced with hwRemoteAccessRetryInterval.      
                "
            ::= { hwAAASettingEntry 51 }

        hwRemoteRetryTime OBJECT-TYPE
            SYNTAX Integer32 (3..65535)
            MAX-ACCESS read-write
            STATUS current
            DESCRIPTION
                "
                 The maximum number of consecutive authentication failures.
                 If it is administrator, the node is replaced with hwRemoteAdminRetryTime.
                 If it is access-user, the node is replaced with hwRemoteAccessRetryTime.
                "
            ::= { hwAAASettingEntry 52 }

        hwRemoteBlockTime OBJECT-TYPE
            SYNTAX Integer32 (5..65535)
            MAX-ACCESS read-write
            STATUS current
            DESCRIPTION
                "
                 The account locking period.
                 If it is administrator, the node is replaced with hwRemoteAdminBlockTime.
                 If it is access-user, the node is replaced with hwRemoteAccessBlockTime.
                "
            ::= { hwAAASettingEntry 53 }
                                                
       hwBlockDisable OBJECT-TYPE
            SYNTAX INTEGER
                {
                localuser(0),
                remoteuser(1),
                localremoteuser(2)
                }
            MAX-ACCESS read-write
            STATUS current
            DESCRIPTION
                "
                 Disable the account locking function for user: 
                 localuser(0),
                 remoteuser(1),
                 localremoteuser(2)
                "
            ::= { hwAAASettingEntry 54 }
       
      hwTotalAuthReqNumPortal OBJECT-TYPE
            SYNTAX Unsigned32 (0..4294967295)
            MAX-ACCESS read-write
            STATUS current
            DESCRIPTION
                "the number of AUTH num portal"
            ::= { hwAAASettingEntry 55} 

      hwTotalAuthReqNumMac OBJECT-TYPE
            SYNTAX Unsigned32 (0..4294967295)
            MAX-ACCESS read-write
            STATUS current
            DESCRIPTION
                "the number of AUTH num mac"
            ::= { hwAAASettingEntry 56 } 

      hwTotalAuthReqNumDot1x OBJECT-TYPE
            SYNTAX Unsigned32 (0..4294967295)
            MAX-ACCESS read-write
            STATUS current
            DESCRIPTION
                "the number of AUTH num Dot1x"
            ::= { hwAAASettingEntry 57} 

      hwChgPswVertifyFlag OBJECT-TYPE
            SYNTAX INTEGER 
                {  
                    enable(1),
                    disable(2)
                }
            MAX-ACCESS read-write
            STATUS current
            DESCRIPTION
                "change password verify flag"
            ::= { hwAAASettingEntry 58}	   
             
      hwLamPswComplexityCheckMethod OBJECT-TYPE
            SYNTAX INTEGER 
                {  
                    standard(0),
                    threeofkinds(1),
                    nocheck(2)
                }
            MAX-ACCESS read-write
            STATUS current
            DESCRIPTION
                "local-user password check method"
            ::= { hwAAASettingEntry 59}

        hwRemoteAccessRetryInterval OBJECT-TYPE
            SYNTAX Integer32 (5..65535)
            MAX-ACCESS read-write
            STATUS current
            DESCRIPTION
                "
                 The access-user authentication retry interval.
                "
            ::= { hwAAASettingEntry 60 }
		
      hwRemoteAccessRetryTime OBJECT-TYPE
            SYNTAX Integer32 (3..65535)
            MAX-ACCESS read-write
            STATUS current
            DESCRIPTION
                "
                 The maximum number of consecutive access-user authentication failures.
                "
            ::= { hwAAASettingEntry 61 }

      hwRemoteAccessBlockTime OBJECT-TYPE
            SYNTAX Integer32 (5..65535)
            MAX-ACCESS read-write
            STATUS current
            DESCRIPTION
                "
                 The access-user account locking period.
                "
            ::= { hwAAASettingEntry 62 }
			
      hwRemoteAdminRetryInterval OBJECT-TYPE
            SYNTAX Integer32 (5..65535)
            MAX-ACCESS read-write
            STATUS current
            DESCRIPTION
                "
                 The administrator authentication retry interval.
                "
            ::= { hwAAASettingEntry 63 }
		
      hwRemoteAdminRetryTime OBJECT-TYPE
            SYNTAX Integer32 (3..65535)
            MAX-ACCESS read-write
            STATUS current
            DESCRIPTION
                "
                 The maximum number of consecutive administrator authentication failures.
                "
            ::= { hwAAASettingEntry 64 }

      hwRemoteAdminBlockTime OBJECT-TYPE
            SYNTAX Integer32 (5..65535)
            MAX-ACCESS read-write
            STATUS current
            DESCRIPTION
                "
                 The administrator account locking period.
                "
            ::= { hwAAASettingEntry 65 }

     hwPassChangeOfflineEnable OBJECT-TYPE
            SYNTAX Integer32 (0..1)
            MAX-ACCESS read-write
            STATUS current
            DESCRIPTION
                "
                 The administrator account change password and log out. 
                "
            ::= { hwAAASettingEntry 66 }

        hwAAAStat OBJECT IDENTIFIER ::= { hwAAAMibObjects 14 }

        hwAAAStatEntry OBJECT IDENTIFIER ::= { hwAAAStat 1 }

        hwTotalOnlineNum OBJECT-TYPE
            SYNTAX Unsigned32 (0..4294967295)
            MAX-ACCESS read-only
            STATUS current
            DESCRIPTION
                "This object indicates the total number of online users."
            ::= { hwAAAStatEntry 1 }

        hwTotalPPPoeOnlineNum OBJECT-TYPE
            SYNTAX Unsigned32 (0..4294967295)
            MAX-ACCESS read-only
            STATUS current
            DESCRIPTION
                "This object indicates the total number of online PPPoE users."
            ::= { hwAAAStatEntry 2 }

        hwTotalPPPoAOnlineNum OBJECT-TYPE
            SYNTAX Unsigned32 (0..4294967295)
            MAX-ACCESS read-only
            STATUS current
            DESCRIPTION
                "This object indicates the total number of online PPPoA users."
            ::= { hwAAAStatEntry 3 }

        hwTotalftpOnlineNum OBJECT-TYPE
            SYNTAX Unsigned32 (0..4294967295)
            MAX-ACCESS read-only
            STATUS current
            DESCRIPTION
                "This object indicates the total number of online FTP users."
            ::= { hwAAAStatEntry 4 }

        hwTotalsshOnlineNum OBJECT-TYPE
            SYNTAX Unsigned32 (0..4294967295)
            MAX-ACCESS read-only
            STATUS current
            DESCRIPTION
                "This object indicates the total number of online SSH users."
            ::= { hwAAAStatEntry 5 }

        hwTotaltelnetOnlineNum OBJECT-TYPE
            SYNTAX Unsigned32 (0..4294967295)
            MAX-ACCESS read-only
            STATUS current
            DESCRIPTION
                "This object indicates the total number of online Telnet users."
            ::= { hwAAAStatEntry 6 }

        hwTotalVLANOnlineNum OBJECT-TYPE
            SYNTAX Unsigned32 (0..4294967295)
            MAX-ACCESS read-only
            STATUS current
            DESCRIPTION
                "This object indicates the total number of online VLAN users."
            ::= { hwAAAStatEntry 7 }
                
        hwHistoricMaxOnlineNum OBJECT-TYPE
            SYNTAX Unsigned32 (0..4294967295)
            MAX-ACCESS read-only
            STATUS current
            DESCRIPTION
                "This object indicates the total number of historical online users."
            ::= { hwAAAStatEntry 8 }
            
        hwResetHistoricMaxOnlineNum OBJECT-TYPE
            SYNTAX INTEGER
                    {
                    reset(0)                    
                    }
            MAX-ACCESS read-write
            STATUS current
            DESCRIPTION
                "This object indicates the clearance of the maximum number of historical online users."
            ::= { hwAAAStatEntry 9 }
        hwResetOfflineReasonStatistic OBJECT-TYPE
            SYNTAX INTEGER
                    {
                    reset(0)                    
                    }
            MAX-ACCESS read-write
            STATUS current
            DESCRIPTION
                "This object indicates the clearance of statistics about the causes of historical user offline."
            ::= { hwAAAStatEntry 10 }
            
        hwResetOnlineFailReasonStatistic OBJECT-TYPE
            SYNTAX INTEGER
                    {
                    reset(0)                    
                    }
            MAX-ACCESS read-write
            STATUS current
            DESCRIPTION
                "This object indicates the clearance of statistics about the causes of user online failures."
            ::= { hwAAAStatEntry 11 }
            
        hwMaxPPPoeOnlineNum OBJECT-TYPE
            SYNTAX Unsigned32 (0..4294967295)
            MAX-ACCESS read-only
            STATUS current
            DESCRIPTION
                "This object indicates the maximum number of online PPPoE users."
            ::= { hwAAAStatEntry 12 }
        
        hwTotalPortalServerUserNum OBJECT-TYPE
            SYNTAX Unsigned32 (0..4294967295)
            MAX-ACCESS read-only
            STATUS current
            DESCRIPTION
                "This object indicates the current number of online users with portal authentication."
            ::= { hwAAAStatEntry 13 }
            
        hwMaxPortalServerUserNum OBJECT-TYPE
            SYNTAX Unsigned32 (0..4294967295)
            MAX-ACCESS read-only
            STATUS current
            DESCRIPTION
                "This object indicates the maximum number of online users with portal authentication."
            ::= { hwAAAStatEntry 14 }

        hwTotalIPv4OnlineNum OBJECT-TYPE
            SYNTAX Unsigned32 (0..4294967295)
            MAX-ACCESS read-only
            STATUS current
            DESCRIPTION
                "This object indicates the total number of online IPv4 users."
            ::= { hwAAAStatEntry 15 }

        hwTotalIPv6OnlineNum OBJECT-TYPE
            SYNTAX Unsigned32 (0..4294967295)
            MAX-ACCESS read-only
            STATUS current
            DESCRIPTION
                "This object indicates the total number of online IPv6 users."
            ::= { hwAAAStatEntry 16 }

        hwTotalDualStackOnlineNum OBJECT-TYPE
            SYNTAX Unsigned32 (0..4294967295)
            MAX-ACCESS read-only
            STATUS current
            DESCRIPTION
                "This object indicates the total number of online IPv4/IPv6 users."
            ::= { hwAAAStatEntry 17 }   

        hwTotalIPv4FlowDnByte OBJECT-TYPE
            SYNTAX Counter64
            MAX-ACCESS read-only
            STATUS current
            DESCRIPTION
                "This object indicates the number of bytes of outgoing IPv4 packets on the host."
            ::= { hwAAAStatEntry 18 }

        hwTotalIPv4FlowDnPkt OBJECT-TYPE
            SYNTAX Counter64
            MAX-ACCESS read-only
            STATUS current
            DESCRIPTION
                "This object indicates the number of outgoing IPv4 packets on the host."
            ::= { hwAAAStatEntry 19 }
 
         hwTotalIPv4FlowUpByte OBJECT-TYPE
            SYNTAX Counter64
            MAX-ACCESS read-only
            STATUS current
            DESCRIPTION
                "This object indicates the number of bytes of incoming IPv4 packets on the host."
            ::= { hwAAAStatEntry 20 }
            
         hwTotalIPv4FlowUpPkt OBJECT-TYPE
            SYNTAX Counter64
            MAX-ACCESS read-only
            STATUS current
            DESCRIPTION
                "This object indicates the number of incoming IPv4 packets on the host."
            ::= { hwAAAStatEntry 21 }

        hwTotalIPv6FlowDnByte OBJECT-TYPE
            SYNTAX Counter64
            MAX-ACCESS read-only
            STATUS current
            DESCRIPTION
                "This object indicates the number of bytes of outgoing IPv6 packets on the host."
            ::= { hwAAAStatEntry 22 }

        hwTotalIPv6FlowDnPkt OBJECT-TYPE
            SYNTAX Counter64
            MAX-ACCESS read-only
            STATUS current
            DESCRIPTION
                "This object indicates the number of outgoing IPv6 packets on the host."
            ::= { hwAAAStatEntry 23 }
 
         hwTotalIPv6FlowUpByte OBJECT-TYPE
            SYNTAX Counter64
            MAX-ACCESS read-only
            STATUS current
            DESCRIPTION
                "This object indicates the number of bytes of incoming IPv6 packets on the host."
            ::= { hwAAAStatEntry 24 }
            
         hwTotalIPv6FlowUpPkt OBJECT-TYPE
            SYNTAX Counter64
            MAX-ACCESS read-only
            STATUS current
            DESCRIPTION
                "This object indicates the number of incoming IPv6 packets on the host."
            ::= { hwAAAStatEntry 25 }
            
        hwHistoricMaxOnlineAcctReadyNum OBJECT-TYPE
            SYNTAX Unsigned32 (0..4294967295)
            MAX-ACCESS read-only
            STATUS current
            DESCRIPTION
                "This object indicates the maximum number of online users with successful charging records in the system."
            ::= { hwAAAStatEntry 26 }
            
       hwPubicLacUserNum OBJECT-TYPE
            SYNTAX Unsigned32 (0..4294967295)
            MAX-ACCESS read-only
            STATUS current
            DESCRIPTION
                "This object indicates the number of LAC users on the public network."
            ::= { hwAAAStatEntry 27 }

        hwHistoricMaxOnlineLocalNum OBJECT-TYPE
            SYNTAX Unsigned32 (0..4294967295)
            MAX-ACCESS read-only
            STATUS current
            DESCRIPTION
                "This object indicates the maximum number of historical online RUI local users and common users recorded in the system.
"
            ::= { hwAAAStatEntry 28 }

        hwHistoricMaxOnlineRemoteNum OBJECT-TYPE
            SYNTAX Unsigned32 (0..4294967295)
            MAX-ACCESS read-only
            STATUS current
            DESCRIPTION
                "This object indicates the maximum number of historical online RUI remote users recorded in the system.
"
            ::= { hwAAAStatEntry 29 }
            
        hwTotalLacOnlineNum OBJECT-TYPE
            SYNTAX Unsigned32 (0..4294967295)
            MAX-ACCESS read-only
            STATUS current
            DESCRIPTION
                "This object indicates the number of online LAC users.
"
            ::= { hwAAAStatEntry 30 }
            
        hwTotalLnsOnlineNum OBJECT-TYPE
            SYNTAX Unsigned32 (0..4294967295)
            MAX-ACCESS read-only
            STATUS current
            DESCRIPTION
                "This object indicates the number of online LNS users.
"
            ::= { hwAAAStatEntry 31 }
            
        hwTotalWlsOnlineNum OBJECT-TYPE
            SYNTAX Unsigned32 (0..4294967295)
            MAX-ACCESS read-only
            STATUS current
            DESCRIPTION
                "This object indicates the total number of online wireless users.
"
            ::= { hwAAAStatEntry 32 }    
 
        hwTotalWrdOnlineNum OBJECT-TYPE
            SYNTAX Unsigned32 (0..4294967295)
            MAX-ACCESS read-only
            STATUS current
            DESCRIPTION
                "This object indicates the total number of online wired users.
"
            ::= { hwAAAStatEntry 33 }   

      hwDhcpUserOnlineFailCount OBJECT-TYPE
            SYNTAX Unsigned32 (0..4294967295)
            MAX-ACCESS read-write
            STATUS current
            DESCRIPTION
                "This object indicates the number of DHCP user online failures.
"
            ::= { hwAAAStatEntry 34 }    

      hwTotalFamilyUserByUsernameOnlineNum OBJECT-TYPE
            SYNTAX Unsigned32 (0..4294967295)
            MAX-ACCESS read-only
            STATUS current
            DESCRIPTION
                "The number of family users by username, counted only when the user domain has the user-max-session configuration or the RADIUS server has delivered the Port-Limit attribute, and the same username is counted only once. "
            ::= { hwAAAStatEntry 35 }     

      hwDhcpUserOnlineV6FailCount OBJECT-TYPE
            SYNTAX Unsigned32 (0..4294967295)
            MAX-ACCESS read-write
            STATUS current
            DESCRIPTION
                "the number of dhcp online V6fail users"
            ::= { hwAAAStatEntry 36 }              

      hwHistoricMaxOnlineNumDate OBJECT-TYPE
            SYNTAX DisplayString (SIZE(1..32))
            MAX-ACCESS read-only
            STATUS current
            DESCRIPTION
                "Date and time when the number of access users reaches the maximum number."
            ::= { hwAAAStatEntry 37 } 		

			

        hwAccessTable OBJECT-TYPE
            SYNTAX SEQUENCE OF HwAccessEntry
            MAX-ACCESS not-accessible
            STATUS current
            DESCRIPTION
                "The hwAccessTable is a function access table used to display user access information."
            ::= { hwAAAMibObjects 15 }

        hwAccessEntry OBJECT-TYPE
            SYNTAX HwAccessEntry
            MAX-ACCESS not-accessible
            STATUS current
            DESCRIPTION
                "access entry

                The access table is used to query the property of online users. The index item node is hwAccessIndex.
                Notice: Read operation is not allowed for all the items in this table.
                1. The index of hwAccessTable also uses hwAccessIndex, get operation only 
                    supports the standard get operation with hwAccessIndex as its index.
                2. To prevent too much interaction, get next operation does use the standard operation that uses hwAccessIndex as its index.
                "
            INDEX { hwAccessIndex }
            ::= { hwAccessTable 1 }

        HwAccessEntry ::=
            SEQUENCE {
                hwAccessIndex
                    Integer32,
                hwAccessUserName
                    DisplayString,
                hwAccessPortType
                    INTEGER,
                hwAccessPriority
                    Integer32,
                hwAccessSlotNo
                    Integer32,
                hwAccessSubSlotNo
                    Integer32,
                hwAccessPortNo
                    Integer32,
                hwAccessVLANID
                    Integer32,
                hwAccessPVC
                    Integer32,
                hwAccessAuthenMethod
                    INTEGER,
                hwAccessAcctMethod
                    INTEGER,
                hwAccessIPAddress
                    IpAddress,                    
                hwAccessVRF
                    DisplayString,
                hwAccessMACAddress
                    MacAddress,
                hwAccessIfIdleCut
                    TruthValue,
                hwAccessIdleCutTime
                    Unsigned32,
                hwAccessIdleCutFlow
                    Integer32,
                hwAccessTimeLimit
                    Unsigned32,
                hwAccessTotalFlow64Limit
                    Counter64,
                hwAccessStartTime
                    DateAndTime,
                hwAccessCARIfUpActive
                    TruthValue,
                hwAccessCARIfDnActive
                    TruthValue,
                hwAccessUpFlow64
                    Counter64,
                hwAccessDnFlow64
                    Counter64,
                hwAccessUpPacket64
                    Counter64,
                hwAccessDnPacket64
                    Counter64,
                hwAccessCARUpCIR
                    Unsigned32,
                hwAccessCARUpPIR
                    Unsigned32,
                hwAccessCARUpCBS
                    Unsigned32,
                hwAccessCARUpPBS
                    Unsigned32,
                hwAccessCARDnCIR
                    Unsigned32,
                hwAccessCARDnPIR
                    Unsigned32,
                hwAccessCARDnCBS
                    Unsigned32,
                hwAccessCARDnPBS
                    Unsigned32,            
                hwAccessDownPriority
                    Integer32,    
--                hwAccessQinqVlanID
--                    Integer32,
--                hwAccessUserVlanID
--                    Integer32                    
                hwAccessQosProfile
                    DisplayString,
                hwAccessInterface
                    DisplayString,
                hwAccessIPv6IFID
                    Ipv6AddressIfIdentifier,
                hwAccessIPv6WanAddress
                    Ipv6Address,
                hwAccessIPv6WanPrefix
                    Ipv6AddressPrefix,
                hwAccessIPv6LanPrefix
                    Ipv6AddressPrefix,
                hwAccessIPv6LanPrefixLen
                    Integer32,
                hwAccessBasicIPType
                    DisplayString,
                hwAccessIPv6WaitDelay
                    Integer32,
                hwAccessIPv6ManagedAddressFlag
                    INTEGER,
                hwAccessIPv6CPIFIDAvailable
                    TruthValue,
                hwAccessIPv6OtherFlag
                    INTEGER,
                hwAccessIPv6CPAssignIFID
                    TruthValue,
                hwAccessLineID
                    DisplayString,
                hwAccessIPv6UpFlow64
                    Counter64,
                hwAccessIPv6DnFlow64
                    Counter64,
                hwAccessIPv6UpPacket64
                    Counter64,
                hwAccessIPv6DnPacket64
                    Counter64,               
                hwAccessDeviceName
                    DisplayString,
                hwAccessDeviceMACAddress
                    MacAddress,
                hwAccessDevicePortName
                    OCTET STRING,
                hwAccessAPID     
                    Unsigned32,
                hwAccessQinQVLANID
                    Integer32,
                hwAccessOption82CircuitID
                    OCTET STRING,
                hwAccessOption82RemoteID
                    OCTET STRING,
                hwAccessSessionTimeout
                    Unsigned32, 
                hwAccessISPVLAN
                    Integer32, 
                hwAccessISPInterface
                    OCTET STRING
             }

        hwAccessIndex OBJECT-TYPE
            SYNTAX Integer32 (0..2147483647)
            MAX-ACCESS read-only
            STATUS current
            DESCRIPTION
                "This object indicates the index of a user."
            ::= { hwAccessEntry 1 }

        hwAccessUserName OBJECT-TYPE
            SYNTAX DisplayString (SIZE (1..253))
            MAX-ACCESS read-only
            STATUS current
            DESCRIPTION
                "This object indicates the name of the user."
            ::= { hwAccessEntry 3 }

        hwAccessPortType OBJECT-TYPE
            SYNTAX INTEGER
                {
                all(1),
                ppp(2),
                vlan(3),
                vlanweb(4),
                vlanportal(5),
                vlan8021x(6),
                telnet(7),
                ftp(8),
                ssh(9),
                igmp(10)
                }
            MAX-ACCESS read-only
            STATUS current
            DESCRIPTION
                "access port type
                1:all
                2:PPP
                3:VLAN
                4:WEB of VLAN
                5:Portal of VLAN
                6:802.1X
                7:telnet
                8:ftp
                9:SSH
                10:igmp"
            ::= { hwAccessEntry 5 }

        hwAccessPriority OBJECT-TYPE
            SYNTAX Integer32 (0..15|255)
            MAX-ACCESS read-only
            STATUS current
            DESCRIPTION
                "This object indicates the access priority of the user.
"
            ::= { hwAccessEntry 6 } 
            
        hwAccessSlotNo OBJECT-TYPE
            SYNTAX Integer32
            MAX-ACCESS read-only
            STATUS current
            DESCRIPTION
                "This object indicates the slot ID of the user."
            ::= { hwAccessEntry 8 }

        hwAccessSubSlotNo OBJECT-TYPE
            SYNTAX Integer32
            MAX-ACCESS read-only
            STATUS current
            DESCRIPTION
                "This object indicates the sub-slot ID of the user."
            ::= { hwAccessEntry 9 }

        hwAccessPortNo OBJECT-TYPE
            SYNTAX Integer32
            MAX-ACCESS read-only
            STATUS current
            DESCRIPTION
                "This object indicates the port number of the user."
            ::= { hwAccessEntry 10 }

        hwAccessVLANID OBJECT-TYPE
            SYNTAX Integer32 
            MAX-ACCESS read-only
            STATUS current
            DESCRIPTION
                "This object indicates the VLAN information of the user."
            ::= { hwAccessEntry 11 }

        hwAccessPVC OBJECT-TYPE
            SYNTAX Integer32
            MAX-ACCESS read-only
            STATUS current
            DESCRIPTION
                "This object indicates the VPI VCI information of the user.
"
            ::= { hwAccessEntry 12 }

        hwAccessAuthenMethod OBJECT-TYPE
            SYNTAX INTEGER
                {
                    local(1),
                    noauth(2),
                    radius(3),
                    localRadius(4),
                    radiusLocal(5),
                    radiusNoauth(6),
                    tacacs(7),
                    localTacacs(8),
                    tacacsLocal(9),
                    tacacsNone(10)         
                }
            MAX-ACCESS read-only
            STATUS current
            DESCRIPTION
                "This object indicates the authentication method of the user. The available options are local, noauth, radius, localRadius, radiusLocal, radiusNoauth, tacacs, localTacacs, tacacsLocal, and tacacsNone.
"
            ::= { hwAccessEntry 13 }

        hwAccessAcctMethod OBJECT-TYPE
            SYNTAX INTEGER
                {
                local(1),
                radius(2),               
                noacct(3),
                localradiusboth(4),
                hwtacacs(5),
                localhwtacacsboth(6)
                }
            MAX-ACCESS read-only
            STATUS current
            DESCRIPTION
                "This object indicates the accounting method of the user, The available options are local, radius, noacct, localradiusboth, hwtacacs, and localhwtacacsboth.
"
            ::= { hwAccessEntry 14 }

        hwAccessIPAddress OBJECT-TYPE
            SYNTAX IpAddress
            MAX-ACCESS read-only
            STATUS current
            DESCRIPTION
                "This object indicates the IP address of the user.
"
            ::= { hwAccessEntry 15 } 
            
      hwAccessVRF OBJECT-TYPE
            SYNTAX DisplayString (SIZE (1..31))
            MAX-ACCESS read-only
            STATUS current
            DESCRIPTION
                "This object indicates the VRF name of the user.
"
            ::= { hwAccessEntry 16 }

         hwAccessMACAddress OBJECT-TYPE
            SYNTAX MacAddress
            MAX-ACCESS read-only
            STATUS current
            DESCRIPTION
                "This object indicates the MAC address of the user.
"
            ::= { hwAccessEntry 17 }
        

        hwAccessIfIdleCut OBJECT-TYPE
            SYNTAX TruthValue
            MAX-ACCESS read-only
            STATUS current
            DESCRIPTION
                "This object indicates whether idle cut is used.
"
            ::= { hwAccessEntry 18 }

        hwAccessIdleCutTime OBJECT-TYPE
            SYNTAX Unsigned32
            MAX-ACCESS read-only
            STATUS current
            DESCRIPTION
                "This object indicates the idle cut interval.
"
            ::= { hwAccessEntry 19 }

        hwAccessIdleCutFlow OBJECT-TYPE
            SYNTAX Integer32
            MAX-ACCESS read-only
            STATUS current
            DESCRIPTION
                "This object indicates the idle cut traffic.
"
            ::= { hwAccessEntry 20 }

        hwAccessTimeLimit OBJECT-TYPE
            SYNTAX Unsigned32
            MAX-ACCESS read-only
            STATUS current
            DESCRIPTION
                "This object indicates the online duration limit of the user.
"
            ::= { hwAccessEntry 21 }

        hwAccessTotalFlow64Limit OBJECT-TYPE
            SYNTAX Counter64
            MAX-ACCESS read-only
            STATUS current
            DESCRIPTION
                "This object indicates the remaining traffic (64 bit) of the user.
"
            ::= { hwAccessEntry 22 }

        hwAccessStartTime OBJECT-TYPE
            SYNTAX DateAndTime
            MAX-ACCESS read-only
            STATUS current
            DESCRIPTION
                "This object indicates the access time of the user.
"
            ::= { hwAccessEntry 25 }

        hwAccessCARIfUpActive OBJECT-TYPE
            SYNTAX TruthValue
            MAX-ACCESS read-only
            STATUS current
            DESCRIPTION
                "This object indicates the upstream rate limit control."
            ::= { hwAccessEntry 27 }


        hwAccessCARIfDnActive OBJECT-TYPE
            SYNTAX TruthValue
            MAX-ACCESS read-only
            STATUS current
            DESCRIPTION
                "This object indicates the downstream rate limit control.
"
            ::= { hwAccessEntry 31 }

        hwAccessUpFlow64 OBJECT-TYPE
            SYNTAX Counter64
            MAX-ACCESS read-only
            STATUS current
            DESCRIPTION
                "This object indicates the number of bytes of upstream packets, in 64 bytes.
"
            ::= { hwAccessEntry 36 }

        hwAccessDnFlow64 OBJECT-TYPE
            SYNTAX Counter64
            MAX-ACCESS read-only
            STATUS current
            DESCRIPTION
                "This object indicates the number of bytes of downstream packets, in 64 bytes.
"
            ::= { hwAccessEntry 37 }

        hwAccessUpPacket64 OBJECT-TYPE
            SYNTAX Counter64
            MAX-ACCESS read-only
            STATUS current
            DESCRIPTION
                "This object indicates the number of upstream packets."
            ::= { hwAccessEntry 38 }

        hwAccessDnPacket64 OBJECT-TYPE
            SYNTAX Counter64
            MAX-ACCESS read-only
            STATUS current
            DESCRIPTION
                "This object indicates the number of downstream packets.
"
            ::= { hwAccessEntry 39 }

        hwAccessCARUpCIR OBJECT-TYPE
            SYNTAX Unsigned32 (0..10000000)
            MAX-ACCESS read-only
            STATUS current
            DESCRIPTION
                "This object indicates the average upstream traffic rate, in kbit/s.
"
            ::= { hwAccessEntry 45 }

        hwAccessCARUpPIR OBJECT-TYPE
            SYNTAX Unsigned32 (0..10000000)
            MAX-ACCESS read-only
            STATUS current
            DESCRIPTION
                "This object indicates the peak upstream traffic rate, in kbit/s.
"
            ::= { hwAccessEntry 46 }

         hwAccessCARUpCBS OBJECT-TYPE
            SYNTAX Unsigned32 (0..4294967295)
            MAX-ACCESS read-only
            STATUS current
            DESCRIPTION
                "This object indicates the upstream CBS, in bytes.
"
            ::= { hwAccessEntry 47 }

            
         hwAccessCARUpPBS OBJECT-TYPE
            SYNTAX Unsigned32 (0..4294967295)
            MAX-ACCESS read-only
            STATUS current
            DESCRIPTION
                "This object indicates the upstream PBS, in bytes.
"
            ::= { hwAccessEntry 48 }
            
          hwAccessCARDnCIR OBJECT-TYPE
            SYNTAX Unsigned32 (0..10000000)
            MAX-ACCESS read-only
            STATUS current
            DESCRIPTION
                "This object indicates the average downstream traffic rate, in kbit/s.
"
            ::= { hwAccessEntry 49 }

        hwAccessCARDnPIR OBJECT-TYPE
            SYNTAX Unsigned32 (0..10000000)
            MAX-ACCESS read-only
            STATUS current
            DESCRIPTION
                "This object indicates the peak downstream traffic rate, in kbit/s.
"
            ::= { hwAccessEntry 50 }

        hwAccessCARDnCBS OBJECT-TYPE
            SYNTAX Unsigned32 (0..4294967295)
            MAX-ACCESS read-only
            STATUS current
            DESCRIPTION
                "This object indicates the downstream CBS, in bytes.
"
            ::= { hwAccessEntry 51 }

            
       hwAccessCARDnPBS OBJECT-TYPE
            SYNTAX Unsigned32 (0..4294967295)
            MAX-ACCESS read-only
            STATUS current
            DESCRIPTION
                "This object indicates the downstream PBS, in bytes.
"
            ::= { hwAccessEntry 52 }


      hwAccessDownPriority OBJECT-TYPE
            SYNTAX Integer32 (0..15|255)
            MAX-ACCESS read-only
            STATUS current
            DESCRIPTION
                "This object indicates the downstream priority.
"
            ::= { hwAccessEntry 53 }

--        hwAccessQinqVlanID OBJECT-TYPE
--            SYNTAX Integer32 (0..4094)
--            MAX-ACCESS read-only
--            STATUS current
--            DESCRIPTION
--                "qinq vlan"
--            ::= { hwAccessEntry 54 }

--        hwAccessUserVlanID OBJECT-TYPE
--            SYNTAX Integer32 (0..4094)
--            MAX-ACCESS read-only
--            STATUS current
--            DESCRIPTION
--                "user VLAN"
--            ::= { hwAccessEntry 55 }

        hwAccessQosProfile OBJECT-TYPE
            SYNTAX DisplayString (SIZE (1..63))
            MAX-ACCESS read-create
            STATUS current
            DESCRIPTION
                "This object indicates the QoS profile.
"
            ::= { hwAccessEntry 56 }

        hwAccessInterface OBJECT-TYPE
            SYNTAX DisplayString (SIZE (1..63))
            MAX-ACCESS read-only
            STATUS current
            DESCRIPTION
                "This object indicates the user access interface.
"
            ::= { hwAccessEntry 57 }

        hwAccessIPv6IFID OBJECT-TYPE
            SYNTAX Ipv6AddressIfIdentifier
            MAX-ACCESS read-only
            STATUS current
            DESCRIPTION
                "This object indicates the interface ID negotiated by IPv6CP for the PPPoE or L2TP user."
            ::= { hwAccessEntry 58 }

        hwAccessIPv6WanAddress OBJECT-TYPE
            SYNTAX Ipv6Address
            MAX-ACCESS read-only
            STATUS current
            DESCRIPTION
                "This object indicates the WAN interface address of the user."
            ::= { hwAccessEntry 59 }

        hwAccessIPv6WanPrefix OBJECT-TYPE
            SYNTAX Ipv6AddressPrefix
            MAX-ACCESS read-only
            STATUS current
            DESCRIPTION
                "This object indicates the WAN interface prefix of the user."
            ::= { hwAccessEntry 60 }

        hwAccessIPv6LanPrefix OBJECT-TYPE
            SYNTAX Ipv6AddressPrefix
            MAX-ACCESS read-only
            STATUS current
            DESCRIPTION
                "This object indicates the LAN interface address of the user."
            ::= { hwAccessEntry 61 }

        hwAccessIPv6LanPrefixLen OBJECT-TYPE
            SYNTAX Integer32 (0..128)
            MAX-ACCESS read-only
            STATUS current
            DESCRIPTION
                "This object indicates the LAN interface prefix of the user."
            ::= { hwAccessEntry 62 }

        hwAccessBasicIPType OBJECT-TYPE
            SYNTAX DisplayString (SIZE (1..3))
            MAX-ACCESS read-only
            STATUS current
            DESCRIPTION
                "This object indicates the IP address type by using which domain users can go online. The available options are UCHAR[0]-IPv4, UCHAR[1]-IPv6, and UCHAR[2]-IPv6-PD. Value 0 indicates that domain users do not use this IP address type for access. Value 1 indicates that domain users use this IP address type for access."
            ::= { hwAccessEntry 63 }

        hwAccessIPv6WaitDelay OBJECT-TYPE
            SYNTAX Integer32 (0|30..120)
            MAX-ACCESS read-only
            STATUS current
            DESCRIPTION
                "This object indicates the time used for waiting for DHCPv6 packets after IPv6 CP is performed."
            ::= { hwAccessEntry 64 }

        hwAccessIPv6ManagedAddressFlag OBJECT-TYPE
            SYNTAX INTEGER
            {
                ndra(1),
                dhcpv6(2),
                invalid(255)
            }
            MAX-ACCESS read-only
            STATUS current
            DESCRIPTION
                "This object indicates the IPv6 address allocation mode for PPPoE and L2TP users."
            ::= { hwAccessEntry 65 }

        hwAccessIPv6CPIFIDAvailable OBJECT-TYPE
            SYNTAX TruthValue
            MAX-ACCESS read-only
            STATUS current
            DESCRIPTION
                "This object indicates whether to use the interface ID negotiated by IPv6CP as the interface ID for allocating IP addresses when PPPoE and L2TP users use DHCPv6 to allocate IP addresses."
            ::= { hwAccessEntry 66 }

        hwAccessIPv6OtherFlag OBJECT-TYPE
            SYNTAX INTEGER
            {
                ndra(1),
                dhcpv6(2),
                invalid(255)
            }
            MAX-ACCESS read-only
            STATUS current
            DESCRIPTION
                "This object indicates the information allocation mode for PPPoE, L2TP, and IPoE users."
            ::= { hwAccessEntry 67 }

        hwAccessIPv6CPAssignIFID OBJECT-TYPE
            SYNTAX TruthValue
            MAX-ACCESS read-only
            STATUS current
            DESCRIPTION
                "This object indicates whether the interface ID of the user is available for IPv6CP negotiation."
            ::= { hwAccessEntry 68 }

        hwAccessLineID OBJECT-TYPE
            SYNTAX DisplayString (SIZE (0..255))
            MAX-ACCESS read-only
            STATUS current
            DESCRIPTION
                "This object indicates the access line ID."
            ::= { hwAccessEntry 69 }

        hwAccessIPv6UpFlow64 OBJECT-TYPE
            SYNTAX Counter64
            MAX-ACCESS read-only
            STATUS current
            DESCRIPTION
                "This object indicates the number of bytes of upstream IPv6 packets."
            ::= { hwAccessEntry 70 }

        hwAccessIPv6DnFlow64 OBJECT-TYPE
            SYNTAX Counter64
            MAX-ACCESS read-only
            STATUS current
            DESCRIPTION
                "This object indicates the number of bytes of downstream IPv6 packets."
            ::= { hwAccessEntry 71 }

        hwAccessIPv6UpPacket64 OBJECT-TYPE
            SYNTAX Counter64
            MAX-ACCESS read-only
            STATUS current
            DESCRIPTION
                "This object indicates the number of upstream IPv6 packets."
            ::= { hwAccessEntry 72 }

        hwAccessIPv6DnPacket64 OBJECT-TYPE
            SYNTAX Counter64
            MAX-ACCESS read-only
            STATUS current
            DESCRIPTION
                "This object indicates the number of downstream IPv6 packets."
            ::= { hwAccessEntry 73 }  
            
        hwAccessDeviceName OBJECT-TYPE
            SYNTAX DisplayString (SIZE (1..255))
            MAX-ACCESS read-only
            STATUS current
            DESCRIPTION
                "access device name"
            ::= { hwAccessEntry 74 }
            
        hwAccessDeviceMACAddress OBJECT-TYPE
            SYNTAX MacAddress
            MAX-ACCESS read-only
            STATUS current
            DESCRIPTION
                "Access device Mac address"
            ::= { hwAccessEntry 75 }
            
        hwAccessDevicePortName OBJECT-TYPE
            SYNTAX OCTET STRING
            MAX-ACCESS read-only
            STATUS current
            DESCRIPTION
                "Interface Name of Access device."
            ::= { hwAccessEntry 76 }
            
       hwAccessAPID OBJECT-TYPE
            SYNTAX Unsigned32 (0..4294836225)
            MAX-ACCESS read-only
            STATUS current
            DESCRIPTION
                "Access wiless device AP Id"
            ::= { hwAccessEntry 77 }

       hwAccessQinQVLANID OBJECT-TYPE
            SYNTAX Integer32 (0..4094)
            MAX-ACCESS read-only
            STATUS current
            DESCRIPTION
                "Access QINQ VLAN ID"
            ::= { hwAccessEntry 78 }
			
		hwAccessOption82CircuitID OBJECT-TYPE
            SYNTAX OCTET STRING (SIZE (1..256))
            MAX-ACCESS read-only
            STATUS current
            DESCRIPTION
                "Access Option82 CircuitID"
            ::= { hwAccessEntry 79 }
		
		hwAccessOption82RemoteID OBJECT-TYPE
            SYNTAX OCTET STRING (SIZE (1..256))
            MAX-ACCESS read-only
            STATUS current
            DESCRIPTION
                "Access Option82 RemoteID"
            ::= { hwAccessEntry 80 }
		
		hwAccessSessionTimeout OBJECT-TYPE
            SYNTAX Unsigned32 (0..4294967295)
            MAX-ACCESS read-only
            STATUS current
            DESCRIPTION
                "Access Session Timeout"
            ::= { hwAccessEntry 81 }
		
		hwAccessISPVLAN OBJECT-TYPE
            SYNTAX Integer32 (0..4094)
            MAX-ACCESS read-only
            STATUS current
            DESCRIPTION
                "Access ISP VLAN"
            ::= { hwAccessEntry 82 }
		
		hwAccessISPInterface OBJECT-TYPE
            SYNTAX OCTET STRING (SIZE (1..63))
            MAX-ACCESS read-only
            STATUS current
            DESCRIPTION
                "Access ISP Interface"
            ::= { hwAccessEntry 83 }
		
        hwAccessExtTable OBJECT-TYPE
            SYNTAX SEQUENCE OF HwAccessExtEntry
            MAX-ACCESS not-accessible
            STATUS current
            DESCRIPTION
                "hwAccessExtTable is a table of extended access information."
            ::= { hwAAAMibObjects 16 }

        hwAccessExtEntry OBJECT-TYPE
            SYNTAX HwAccessExtEntry
            MAX-ACCESS not-accessible
            STATUS current
            DESCRIPTION
                "access extend entry"
            INDEX { hwAccessIndex }
            ::= { hwAccessExtTable 1 }

            HwAccessExtEntry ::=
                SEQUENCE { 
                    hwAccessUCLGroup
                        Integer32,
                    hwAuthenticationState
                        Integer32,
                    hwAuthorizationState
                        Integer32,
                    hwAccountingState
                        Integer32,
                    hwAccessDomainName
                        DisplayString,
                    hwIdleTimeLength
                        Integer32,
                    hwAcctSessionID
                        DisplayString,
                    hwAccessStartAcctTime
                        DateAndTime,
                    hwAccessNormalServerGroup
                        DisplayString,
                    hwAccessDomainAcctCopySeverGroup
                        DisplayString,
                    hwAccessPVlanAcctCopyServerGroup
                        DisplayString,
                    hwAccessCurAuthenPlace
                        INTEGER,
                    hwAccessActionFlag
                        INTEGER,
                    hwAccessAuthtype
                        INTEGER,
                    hwAccessType
                        INTEGER,
                    hwAccessOnlineTime
                        Unsigned32,
                    hwAccessGateway
                        IpAddress,
                    hwAccessSSID
                        DisplayString,
                    hwAccessAPMAC
                        MacAddress,
                    hwAccessDomain
                        DisplayString,
                    hwAccessCurAccountingPlace
                        INTEGER,
                    hwAccessCurAuthorPlace
                        INTEGER,
                    hwAccessUserGroup
                        DisplayString,
                    hwAccessResourceInsufficientInbound
                        Integer32,
                    hwAccessResourceInsufficientOutbound
                        Integer32,
                    hwAccessAuthorizetype
                        INTEGER,
                    hwAccessBakeState
                    INTEGER,
                    hwAccessDeviceType
                    DisplayString
                 }
    
            hwAccessUCLGroup OBJECT-TYPE
                SYNTAX Integer32 (0..1023|65535)
                MAX-ACCESS read-only
                STATUS current
                DESCRIPTION
                    "This object indicates the user group ID."
                ::= { hwAccessExtEntry 2 }
                        
            hwAuthenticationState OBJECT-TYPE
                SYNTAX Integer32 (1..4)
                MAX-ACCESS read-only
                STATUS current
                DESCRIPTION
                    "
                    This object indicates the status of the authentication status machine.
                    "
                ::= { hwAccessExtEntry 4 }
            
            hwAuthorizationState OBJECT-TYPE
                SYNTAX Integer32 (1..4)
                MAX-ACCESS read-only
                STATUS current
                DESCRIPTION
                    "
                    This object indicates the status of the authorization status machine.
                    "
                ::= { hwAccessExtEntry 5 }
            
            hwAccountingState OBJECT-TYPE
                SYNTAX Integer32 (1..7)
                MAX-ACCESS read-only
                STATUS current
                DESCRIPTION
                    "
                    This object indicates the status of the accounting status machine.
                    "
                ::= { hwAccessExtEntry 6 }
            
            hwAccessDomainName OBJECT-TYPE
                SYNTAX DisplayString (SIZE (1..64))
                MAX-ACCESS read-only
                STATUS current
                DESCRIPTION
                    " 
                    This object indicates the domain where the user resides.
                    "
                ::= { hwAccessExtEntry 7 }
            
            hwIdleTimeLength OBJECT-TYPE
                SYNTAX Integer32 (0..2147483647)
                MAX-ACCESS read-only
                STATUS current
                DESCRIPTION
                    "
                    This object indicates the time when the idle status starts,its unit is seconds.
                    "
                ::= { hwAccessExtEntry 8 }
            
            hwAcctSessionID OBJECT-TYPE
                SYNTAX DisplayString (SIZE (0..44))
                MAX-ACCESS read-only
                STATUS current
                DESCRIPTION
                    "
                    This object indicates the ID of an accounting session.
                    "
                ::= { hwAccessExtEntry 9 }
            
            hwAccessStartAcctTime OBJECT-TYPE
                SYNTAX DateAndTime
                MAX-ACCESS read-only
                STATUS current
                DESCRIPTION
                    "
                    This object indicates the time when the current account starts accounting.
                    "
                ::= { hwAccessExtEntry 10 }
            
            hwAccessNormalServerGroup OBJECT-TYPE
                SYNTAX DisplayString (SIZE (1..32))
                MAX-ACCESS read-only
                STATUS current
                DESCRIPTION
                    "This object indicates the name of the RADIUS server group for common authentication and accounting. Value "--" indicates that this attribute is not configured."
                ::= { hwAccessExtEntry 11 }
            
            hwAccessDomainAcctCopySeverGroup OBJECT-TYPE
                SYNTAX DisplayString (SIZE (1..32))
                MAX-ACCESS read-only
                STATUS current
                DESCRIPTION
                    "This object indicates the name of the RADIUS server group configured in a domain to which accounting packets are copied. Value "--" indicates that this attribute is not configured."
                ::= { hwAccessExtEntry 12 }
            
            hwAccessPVlanAcctCopyServerGroup OBJECT-TYPE
                SYNTAX DisplayString (SIZE (1..32))
                MAX-ACCESS read-only
                STATUS current
                DESCRIPTION
                    "This object indicates the name of the RADIUS server group on a port to which accounting packets are copied to. Value "--" indicates that this attribute is not configured."
                ::= { hwAccessExtEntry 13 }
            
            hwAccessCurAuthenPlace OBJECT-TYPE
                SYNTAX INTEGER
                    {
                    none(0),
                    local(1),
                    radius(2),
                    tacacs(3)
                    }
                MAX-ACCESS read-only
                STATUS current
                DESCRIPTION
                    "
                    This object indicates the current authentication space. The available options are none(0), local(1), radius(2), and tacacs(3).
                    "
                ::= { hwAccessExtEntry 14 }

            hwAccessActionFlag OBJECT-TYPE
                SYNTAX INTEGER
                    {
                    idle(0),
                    newuserauth(1),
                    reauth(2),
                    logout(3),
                    leaving(4),
                    authmodify(5),
                    connectup(6)
                    }
                MAX-ACCESS read-only
                STATUS current
                DESCRIPTION
                    "
                    This object indicates an action. The available options are idle(0), newuserauth(1), reauth(2), logout(3), leaving(4), authmodify(5), and connectup(6).
                    "
                ::= { hwAccessExtEntry 15 }
            
            hwAccessAuthtype OBJECT-TYPE
                SYNTAX INTEGER
                    {
                    none(0),
                    ppp(1),
                    dot1x(2),
                    web(3),
                    bind(4),
                    fast(5),
                    wlan(6),
                    admin(7),
                    tunnel(8),
                    mac(9)
                    }
                MAX-ACCESS read-only
                STATUS current
                DESCRIPTION
                    "
                    This object indicates the authentication type of the user. The available options are none(0), ppp(1), dot1x(2), web(3), bind(4), fast(5), wlan(6), admin(7), and tunnel(8).
                    "
                ::= { hwAccessExtEntry 16 }
            
            hwAccessType OBJECT-TYPE
                SYNTAX INTEGER
                    {
                    telnet(1),
                    terminal(2),
                    ssh(3),
                    ftp(4),
                    x25pad(5),
                    ppp(6),
                    pppoe(7),
                    pppoeovlan(8),
                    pppoa(9),
                    pppoeoa(10),                                  
                    pppolns(11),
                    ordinaryvlan(12),
                    eap(13),
                    pnp(14),
                    ip(15),
                    staticvlan(16),
                    layer2leasedline(17),
                    layer2leasedlineuser(18),
                    layer3leasedline(19),
                    pppoeleasedline(20),
                    nmsleasedline(21),
                    proxyleasedline(22),
                    relayleasedline(23),
                    e1pos(24), 
                    lactunnel(25),
                    lnstunnel(26),
                    mip(27),
                    deviceuser(28),
                    pppoeor(29),
                    pppoeovlanor(30),
                    ordinaryvlanor(31),
                    http(32),
                    web(33),
                    wlan(34),
                    mac(35),
                    vm(36)
                    }
                MAX-ACCESS read-only
                STATUS current
                DESCRIPTION
                    "The access type.
                    "
                ::= { hwAccessExtEntry 17 }
        
            hwAccessOnlineTime OBJECT-TYPE
                SYNTAX Unsigned32 (0..4294967295)
                MAX-ACCESS read-only
                STATUS current
                DESCRIPTION
                    "  This object indicates the online time of the user.
                    "
                ::= { hwAccessExtEntry 18 }
                     
            hwAccessDomain OBJECT-TYPE
                SYNTAX DisplayString (SIZE (1..64))
                MAX-ACCESS read-write
                STATUS current
                DESCRIPTION
                    "The user domain"
                ::= { hwAccessExtEntry 19 } 
			    
            hwAccessGateway OBJECT-TYPE
                SYNTAX IpAddress
                MAX-ACCESS read-only
                STATUS current
                DESCRIPTION
                    "The user access gateway"
                ::= { hwAccessExtEntry 20 }
			
            hwAccessSSID OBJECT-TYPE
                SYNTAX DisplayString (SIZE (1..32))
                MAX-ACCESS read-write
                STATUS current
                DESCRIPTION
                    "The user access SSID"
                ::= { hwAccessExtEntry 21 }
			
            hwAccessAPMAC OBJECT-TYPE
                SYNTAX MacAddress
                MAX-ACCESS read-only
                STATUS current
                DESCRIPTION
                    "The user access APMAC"
                ::= { hwAccessExtEntry 22 }  
			
            hwAccessCurAccountingPlace OBJECT-TYPE
                SYNTAX INTEGER
                    {
                    none(1),
                    radius(2),
                    tacacs(3)
                    }
                MAX-ACCESS read-only
                STATUS current
                DESCRIPTION
                    "The user accounting method."
                ::= { hwAccessExtEntry 23 }
			
            hwAccessCurAuthorPlace OBJECT-TYPE
                SYNTAX INTEGER
                    {
                    none(1),
                    local(2),
                    ifauthen(3),
                    tacacs(4)
                    }
                MAX-ACCESS read-only
                STATUS current
                DESCRIPTION
                    "The user authorization method."
                ::= { hwAccessExtEntry 24 }
			
            hwAccessUserGroup OBJECT-TYPE
                SYNTAX DisplayString (SIZE (1..64))
                MAX-ACCESS read-write
                STATUS current
                DESCRIPTION
                    "The user group"
                ::= { hwAccessExtEntry 25 }  
                                      
            hwAccessResourceInsufficientInbound OBJECT-TYPE
                SYNTAX Integer32  (0..1)
                MAX-ACCESS read-only
                STATUS current
                DESCRIPTION
                    "This object indicates whether the requested upstream resources are insufficient. Value 1 indicates that the resources are insufficient. Value 0 indicates that the resources are sufficient.  
"
                ::= { hwAccessExtEntry 26 }

            hwAccessResourceInsufficientOutbound OBJECT-TYPE
                SYNTAX Integer32  (0..1)
                MAX-ACCESS read-only
                STATUS current
                DESCRIPTION
                    "This object indicates whether the requested downstream resources are insufficient. Value 1 indicates that the resources are insufficient. Value 0 indicates that the resources are sufficient.  
"
                ::= { hwAccessExtEntry 27 }
	
            hwAccessAuthorizetype OBJECT-TYPE
                SYNTAX INTEGER
                    {
                    running(0),
                    preAuthen(1),
                    clientNoResp(2),
                    failAuthorized(3),
                    webServerDown(4),
                    aaaServerDown(5),
                    sussess(6),
                    open(7)
                    }
                MAX-ACCESS read-only
                STATUS current
                DESCRIPTION
                    "The user status."
                ::= { hwAccessExtEntry 28 }

            hwAccessBakeState OBJECT-TYPE
                SYNTAX INTEGER
                    {
                    independent(0),
                    master(1),
                    slave(2),
                    switching(3)
                    }
                MAX-ACCESS read-only
                STATUS current
                DESCRIPTION
                    "The user bake status."
                ::= { hwAccessExtEntry 29 }

         hwAccessDeviceType OBJECT-TYPE
            SYNTAX DisplayString (SIZE (0..32))
            MAX-ACCESS read-write
            STATUS current
            DESCRIPTION
                "Description."
            ::= { hwAccessExtEntry 30 }
        
        hwAcctSchemeExtTable OBJECT-TYPE
            SYNTAX SEQUENCE OF HwAcctSchemeExtEntry
            MAX-ACCESS not-accessible
            STATUS current
            DESCRIPTION
                "account Scheme Ext Table."
            ::= { hwAAAMibObjects 19 }
        
        hwAcctSchemeExtEntry OBJECT-TYPE
            SYNTAX HwAcctSchemeExtEntry
            MAX-ACCESS not-accessible
            STATUS current               
            DESCRIPTION
                "account Scheme Ext entry."
            INDEX { hwAcctSchemeName }
            ::= { hwAcctSchemeExtTable 1 }
        
        HwAcctSchemeExtEntry ::=
            SEQUENCE { 
            hwIfRealtimeAcct
                TruthValue,
            hwRealtimeFailMaxnum
                Integer32,
            hwStartFailOnlineIfSendInterim
                        TruthValue
            }
        
        hwIfRealtimeAcct OBJECT-TYPE
            SYNTAX TruthValue
            MAX-ACCESS read-write
            STATUS current
            DESCRIPTION
            "   
              if need realties account."
            DEFVAL { false }
            ::= { hwAcctSchemeExtEntry 1 }

        hwRealtimeFailMaxnum OBJECT-TYPE
            SYNTAX Integer32 (1..255)
            MAX-ACCESS read-write
            STATUS current
            DESCRIPTION
                "
                Permit time of realties account fail."
            DEFVAL { 3 }
            ::= { hwAcctSchemeExtEntry 2 }
            
                hwStartFailOnlineIfSendInterim OBJECT-TYPE
            SYNTAX TruthValue
            MAX-ACCESS read-write
            STATUS current
            DESCRIPTION
                "
                if send interim accounting packet after accounting start fail "
            DEFVAL { false }
            ::= { hwAcctSchemeExtEntry 4 }            
        
        hwBillPoolTable OBJECT IDENTIFIER ::= { hwAAAMibObjects 21 }
        
        hwBillsPoolVolume OBJECT-TYPE
            SYNTAX Integer32
            MAX-ACCESS read-only
            STATUS current
            DESCRIPTION
                "
                This object indicates the capacity of the bill pool.
                "
            ::= { hwBillPoolTable 1 }
        
        hwBillsPoolNum OBJECT-TYPE
            SYNTAX Integer32
            MAX-ACCESS read-only
            STATUS current
            DESCRIPTION
                "
                This object indicates the number of current bills.
                "
            ::= { hwBillPoolTable 2 }
        
        hwBillsPoolAlarmThreshold OBJECT-TYPE
            SYNTAX Integer32 (50..100)
            MAX-ACCESS read-write
            STATUS current
            DESCRIPTION
                "
                This object indicates the alarm threshold,default is 75.
                "
            ::= { hwBillPoolTable 3 }
        
        hwBillsPoolBackupMode OBJECT-TYPE
            SYNTAX INTEGER
                {
                nobackup(1),
                tftpmode(2),
                hdmode(3),
                cfcardmode(4)
                }
            MAX-ACCESS read-write
            STATUS current
            DESCRIPTION
                "
                This object indicates the backup mode,default is 4.
                "
            ::= { hwBillPoolTable 4 }
        
        hwBillsPoolBackupInterval OBJECT-TYPE
            SYNTAX Integer32 (1..65535)
            MAX-ACCESS read-write
            STATUS current
            DESCRIPTION
                "
                This object indicates the interval for regular backup,default is 1440.
                "
            ::= { hwBillPoolTable 5 }
        
        hwBillsPoolBackupNow OBJECT-TYPE
            SYNTAX Integer32 (1)
            MAX-ACCESS read-write
            STATUS current
            DESCRIPTION
                "
                This object indicates the instruction for immediate backup,default is 1.
                "
            ::= { hwBillPoolTable 6 }
        
        hwBillsPoolReset OBJECT-TYPE
            SYNTAX Integer32 (1)
            MAX-ACCESS read-write
            STATUS current
            DESCRIPTION
                "
                This object indicates that all bills in the bill pool are cleared. 
                The resetting operation is dangerous,default is 1.
                "
            ::= { hwBillPoolTable 7 }

        hwBillTFTPTable OBJECT IDENTIFIER ::= { hwAAAMibObjects 22 }
        
        hwBillsTFTPSrvIP OBJECT-TYPE
            SYNTAX IpAddress
            MAX-ACCESS read-write
            STATUS current
            DESCRIPTION
                "
                This object indicates the IP address of the TFTP server. 
                The value is 0 when the system is initialized.
                "
            ::= { hwBillTFTPTable 1 }
        
        hwBillsTFTPMainFileName OBJECT-TYPE
            SYNTAX DisplayString (SIZE (0..30))
            MAX-ACCESS read-write
            STATUS current
            DESCRIPTION
                "The tftp main file name of Bills."
            ::= { hwBillTFTPTable 2 }        
                            
            HwUclGrpEntry ::=
            SEQUENCE {
                hwUclGrpName
                    DisplayString,
                hwUclGrpRowStatus
                    RowStatus
             }
                
            hwUclGrpTable OBJECT-TYPE
                        SYNTAX SEQUENCE OF HwUclGrpEntry
                        MAX-ACCESS not-accessible
            STATUS current
            DESCRIPTION
                "User Group Table"
            ::= { hwAAAMibObjects 25 }
            hwUclGrpEntry OBJECT-TYPE
            SYNTAX HwUclGrpEntry
            MAX-ACCESS not-accessible
            STATUS current
            DESCRIPTION
                "User Group Entry"
            INDEX { hwUclGrpName }
            ::= { hwUclGrpTable 1 }
            
            hwUclGrpName OBJECT-TYPE
            SYNTAX DisplayString (SIZE (1..32))
            MAX-ACCESS read-write
            STATUS current
            DESCRIPTION
                "User Group name"
            ::= { hwUclGrpEntry 1 }
            
            hwUclGrpRowStatus OBJECT-TYPE
            SYNTAX RowStatus
            MAX-ACCESS read-create
            STATUS current
            DESCRIPTION
                "row admin status,only Add or Del"
            ::= { hwUclGrpEntry 2 }
            
            hwIPAccessTable OBJECT-TYPE
                  SYNTAX SEQUENCE OF HwIPAccessEntry
                  MAX-ACCESS not-accessible
                  STATUS current  
                  DESCRIPTION
                    "The hwIpAccessTable is an IP query access table used to query the access table index based on user IP addresses and VPN instances."
                  ::= { hwAAAMibObjects 27 }
        
            hwIPAccessEntry OBJECT-TYPE
                  SYNTAX HwIPAccessEntry
                  MAX-ACCESS not-accessible
                  STATUS current
                  DESCRIPTION
                            "IP Query Access Entry
                            "
                        INDEX { hwIPAccessIPaddress ,hwIPAccessVRF}
                        ::= { hwIPAccessTable 1 }
        
                    HwIPAccessEntry ::=
                        SEQUENCE { 
                            hwIPAccessIPaddress
                                IpAddress,
                            hwIPAccessCID
                                Integer32,
                            hwIPAccessVRF  
                                DisplayString                                       
                          }

                    hwIPAccessIPaddress OBJECT-TYPE
                        SYNTAX IpAddress
                        MAX-ACCESS read-only
                        STATUS current
                        DESCRIPTION
                            "This object indicates the IP address of the user.
"
                        ::= { hwIPAccessEntry 1 }


                    hwIPAccessCID OBJECT-TYPE
                        SYNTAX Integer32
                        MAX-ACCESS read-only
                        STATUS current
                        DESCRIPTION
                            "This object indicates the user access index.
"
                        ::= { hwIPAccessEntry 2 }    
                                    
                    hwIPAccessVRF OBJECT-TYPE
                        SYNTAX DisplayString (SIZE (1..31))    
                        MAX-ACCESS read-only
                        STATUS current
                        DESCRIPTION
                            "This object indicates the name of the VPN instance to which user access belongs.
"
                        ::= { hwIPAccessEntry 3 }    
                        
            
            hwAAAMibTrap OBJECT IDENTIFIER ::= { hwAaa 2 }    
            hwAAATrapOid OBJECT IDENTIFIER ::= { hwAAAMibTrap 1 }
            

        hwDomainIndex OBJECT-TYPE
            SYNTAX Integer32 (0..1152)
            MAX-ACCESS accessible-for-notify
            STATUS current
            DESCRIPTION
                "Domain Index"
            ::= { hwAAATrapOid 1 }     
            
        hwHdFreeamount OBJECT-TYPE
            SYNTAX Integer32 
            MAX-ACCESS accessible-for-notify
            STATUS current
            DESCRIPTION
                "Hard disk Free Amount"
            ::= { hwAAATrapOid 2 }         
            
        hwHdWarningThreshold OBJECT-TYPE
            SYNTAX Integer32 
            MAX-ACCESS accessible-for-notify
            STATUS current
            DESCRIPTION
                "Hard disk warning threshold"
            ::= { hwAAATrapOid 3 }
         hwUserSlot OBJECT-TYPE
                   SYNTAX Integer32
                   MAX-ACCESS accessible-for-notify
            STATUS current
            DESCRIPTION
                "Slot"
            ::= { hwAAATrapOid 4 }
        hwUserSlotMaxNumThreshold OBJECT-TYPE
                       SYNTAX Integer32
                       MAX-ACCESS accessible-for-notify
                   STATUS current
                   DESCRIPTION
                         "hwUserSlotMaxNumThreshold"
                  ::= { hwAAATrapOid 5 }
      hwOnlineUserNumThreshold OBJECT-TYPE
                       SYNTAX Integer32
                       MAX-ACCESS accessible-for-notify
                   STATUS current
                   DESCRIPTION
                         "hwOnlineUserNumThreshold"
                  ::= { hwAAATrapOid 6}
          hwMaxUserThresholdType OBJECT-TYPE
                   SYNTAX Integer32
                   MAX-ACCESS accessible-for-notify
            STATUS current
            DESCRIPTION
                "hwMaxUserThresholdType"
            ::= { hwAAATrapOid 7 }
       
          hwRbpChangeName OBJECT-TYPE
                    SYNTAX DisplayString (SIZE (1..33))
                    MAX-ACCESS accessible-for-notify
            STATUS current
            DESCRIPTION
                "hwRbpChangeName"
            ::= { hwAAATrapOid 8 }
 
          hwRbpOldState OBJECT-TYPE
            SYNTAX INTEGER
            {
                init(0),
                master(1),
                backup(2)
            }
            MAX-ACCESS accessible-for-notify
            STATUS current
            DESCRIPTION
                "hwRbpOldState"
            ::= { hwAAATrapOid 9 }

          hwRbpNewState OBJECT-TYPE
            SYNTAX INTEGER
            {
                init(0),
                master(1),
                backup(2)
            }
            MAX-ACCESS accessible-for-notify
            STATUS current
            DESCRIPTION
                "hwRbpNewState"
            ::= { hwAAATrapOid 10 }
 
          hwRbpChangeReason OBJECT-TYPE
                    SYNTAX DisplayString (SIZE (1..33))
                    MAX-ACCESS accessible-for-notify
            STATUS current
            DESCRIPTION
                "hwRbpChangeReason"
            ::= { hwAAATrapOid 11 }
                                                           
          hwRbsName OBJECT-TYPE
                    SYNTAX DisplayString (SIZE (1..33))
                    MAX-ACCESS accessible-for-notify
            STATUS current
            DESCRIPTION
                "This object indicates the RBS name.
"
            ::= { hwAAATrapOid 12 }
                                   
          hwRbsDownReason OBJECT-TYPE
                    SYNTAX DisplayString (SIZE (1..65))
                    MAX-ACCESS accessible-for-notify
            STATUS current
            DESCRIPTION
                "This object indicates the cause of disconnection.
"
            ::= { hwAAATrapOid 13 }
            
          hwPolicyRouteThreshold OBJECT-TYPE
                    SYNTAX Integer32
                    MAX-ACCESS accessible-for-notify
            STATUS current
            DESCRIPTION
                "hwPolicyRouteThreshold"
            ::= { hwAAATrapOid 14 }
            
          hwPolicyRoute OBJECT-TYPE
                    SYNTAX DisplayString (SIZE (1..255))
                    MAX-ACCESS accessible-for-notify
            STATUS current
            DESCRIPTION
                "hwPolicyRoute"
            ::= { hwAAATrapOid 15 }


            hwRemoteDownloadAclUsedValue OBJECT-TYPE
                    SYNTAX Integer32
                    MAX-ACCESS accessible-for-notify
            STATUS current
            DESCRIPTION
                "The used number of remote download ACL."
            ::= { hwAAATrapOid 16 }

            hwRemoteDownloadAclThresholdValue OBJECT-TYPE
                    SYNTAX Integer32
                    MAX-ACCESS accessible-for-notify
            STATUS current
            DESCRIPTION
                "The threshold value of remote download ACL."
            ::= { hwAAATrapOid 17 }

          hwLoginFailedTimes OBJECT-TYPE
                    SYNTAX Integer32
                    MAX-ACCESS accessible-for-notify
            STATUS current
            DESCRIPTION
                "This object indicates the number of login failures within a specified period.
"
            ::= { hwAAATrapOid 18 }
            
          hwStatisticPeriod OBJECT-TYPE
                    SYNTAX Integer32
                    MAX-ACCESS accessible-for-notify
            STATUS current
            DESCRIPTION
                "Statistic period to count login failed times"
            ::= { hwAAATrapOid 19 }
            
           hwUserGroupNumThreshold OBJECT-TYPE
                    SYNTAX Integer32
                    MAX-ACCESS accessible-for-notify
            STATUS current
            DESCRIPTION
                "This object indicates the length of the time span of the alarm indicating consecutive login failures of the administrative user."
            ::= { hwAAATrapOid 20 }

            hwUserGroupUsedNum OBJECT-TYPE
                    SYNTAX Integer32
                    MAX-ACCESS accessible-for-notify
            STATUS current
            DESCRIPTION
                "The used number of user-group index."
            ::= { hwAAATrapOid 21 }

            hwAAACpuUsage OBJECT-TYPE                                                                                                                                        
                    SYNTAX Integer32                                                                                                                                              
                    MAX-ACCESS accessible-for-notify                                                                                                                              
            STATUS current                                                                                                                                                        
            DESCRIPTION                                                                                                                                                           
                "Cpu usage."                                                                                                                            
            ::= { hwAAATrapOid 22 }   
            
            hwAAAUserResourceUsage OBJECT-TYPE                                                                                                                                        
                    SYNTAX Integer32                                                                                                                                              
                    MAX-ACCESS accessible-for-notify                                                                                                                              
            STATUS current                                                                                                                                                        
            DESCRIPTION                                                                                                                                                           
                "User resource usage."                                                                                                                            
            ::= { hwAAATrapOid 23 }
            
            hwAAASessionGroupUpperLimitThreshold OBJECT-TYPE
                    SYNTAX Integer32(1..100|255)
                    MAX-ACCESS accessible-for-notify
            STATUS current
            DESCRIPTION
                    "The session-group users upper limit warning threshold"
            DEFVAL { 255 }
            ::= { hwAAATrapOid 24 }
            
            hwAAASessionGroupLowerLimitThreshold OBJECT-TYPE
                    SYNTAX Integer32 (0..99|255)
                    MAX-ACCESS accessible-for-notify
            STATUS current
            DESCRIPTION
                "The session-group users lower limit warning threshold"
            DEFVAL { 255 }
            ::= { hwAAATrapOid 25 }
            
            hwAAASessionUpperLimitThreshold OBJECT-TYPE
            SYNTAX Integer32(1..100|255)
            MAX-ACCESS accessible-for-notify
            STATUS current
            DESCRIPTION
                "The online sessions upper limit warning threshold"
            DEFVAL { 255 }
            ::= { hwAAATrapOid 26 }        

            hwAAASessionLowerLimitThreshold OBJECT-TYPE
            SYNTAX Integer32(0..99|255)
            MAX-ACCESS accessible-for-notify
            STATUS current
            DESCRIPTION
                "The online sessions lower limit warning threshold"
            DEFVAL { 255 }
            ::= { hwAAATrapOid 27 }            

           hwAAATimerExpireMajorLevelThreshold OBJECT-TYPE
                     SYNTAX Unsigned32 (1..100)
                     MAX-ACCESS accessible-for-notify
           STATUS current
           DESCRIPTION
                   "Major alarm threshold for resources occupied by real-time accounting services"
           ::= { hwAAATrapOid 28 }

          hwAAATimerExpireMajorLevelResumeThreshold OBJECT-TYPE
                   SYNTAX Unsigned32 (1..100)
                   MAX-ACCESS accessible-for-notify
          STATUS current
          DESCRIPTION
                   "Major alarm clear threshold for resources occupied by real-time accounting services"
          ::= { hwAAATrapOid 29 }
          
          hwAAATimerExpireCriticalLevelThreshold OBJECT-TYPE
                  SYNTAX Unsigned32 (1..100)
                  MAX-ACCESS accessible-for-notify
          STATUS current
          DESCRIPTION
                   "Critical alarm threshold for resources occupied by real-time accounting services"
           ::= { hwAAATrapOid 30 }

          hwAAATimerExpireCriticalLevelResumeThreshold OBJECT-TYPE
                 SYNTAX Unsigned32 (1..100)
                 MAX-ACCESS accessible-for-notify
          STATUS current
          DESCRIPTION
                "Critical alarm clear threshold for resources occupied by real-time accounting services"
          ::= { hwAAATrapOid 31 }

		-- 1.3.6.1.4.1.2011.5.2.2.1.32
		hwMacMovedQuietUserSpec OBJECT-TYPE
			SYNTAX Integer32
			MAX-ACCESS accessible-for-notify
			STATUS current
			DESCRIPTION
				"The  mac moved quiet user spec ."
			::= { hwAAATrapOid 32 }

		
		-- 1.3.6.1.4.1.2011.5.2.2.1.33
		hwMacMovedUserPercentage OBJECT-TYPE
			SYNTAX Integer32
			MAX-ACCESS accessible-for-notify
			STATUS current
			DESCRIPTION
				"The  mac moved quiet user percentage ."
			::= { hwAAATrapOid 33 }

		
		-- 1.3.6.1.4.1.2011.5.2.2.1.34
		hwLowerMacMovedUserPercentage OBJECT-TYPE
			SYNTAX Integer32
			MAX-ACCESS accessible-for-notify
			STATUS current
			DESCRIPTION
				"The configuration of mac moved quiet user lower percentage."
			::= { hwAAATrapOid 34 }
		
		-- 1.3.6.1.4.1.2011.5.2.2.1.35
		hwUpperMacMovedUserPercentage OBJECT-TYPE
			SYNTAX Integer32
			MAX-ACCESS accessible-for-notify
			STATUS current
			DESCRIPTION
				"The configuration of mac moved quiet user  upper percentage."
			::= { hwAAATrapOid 35 }
 
          hwAAAChasisIPv6AddressThreshold OBJECT-TYPE
                 SYNTAX Unsigned32 (0..100)
                 MAX-ACCESS accessible-for-notify
          STATUS current
          DESCRIPTION
                "The number of IPv6 addresses on the device reached the threshold."
          ::= { hwAAATrapOid 36 }

          hwAAASlotIPv6AddressThreshold OBJECT-TYPE
                 SYNTAX Unsigned32 (0..100)
                 MAX-ACCESS accessible-for-notify
          STATUS current
          DESCRIPTION
                "The number of IPv6 addresses on the slot reached the threshold."
          ::= { hwAAATrapOid 37 }
				 
	    hwPwdVdtyLeftDays OBJECT-TYPE
                    SYNTAX Integer32 (0..365) 
                    MAX-ACCESS accessible-for-notify
            STATUS current
            DESCRIPTION
                "Password validity left days"
            ::= { hwAAATrapOid 38 }

           hwOnlineFailNum OBJECT-TYPE
                    SYNTAX Unsigned32 
                    MAX-ACCESS accessible-for-notify
            STATUS current
            DESCRIPTION
                "Online fail number"
            ::= { hwAAATrapOid 39 }
            
        hwOnlineSuccessPercentage OBJECT-TYPE
                    SYNTAX Unsigned32 
                    MAX-ACCESS accessible-for-notify
            STATUS current
            DESCRIPTION
                "Online success percentage"
            ::= { hwAAATrapOid 40 }

         hwCUUserSlot OBJECT-TYPE
                   SYNTAX DisplayString (SIZE (1..64))
                   MAX-ACCESS accessible-for-notify
            STATUS current
            DESCRIPTION
                "Specifies a board ID in CP and UP separation scenarios"
            ::= { hwAAATrapOid 41 }

             hwAAASessionUpperLimitCpThreshold OBJECT-TYPE
            SYNTAX Integer32(1..100|255)
            MAX-ACCESS accessible-for-notify
            STATUS current
            DESCRIPTION
                "The online sessions upper limit warning threshold"
            DEFVAL { 255 }
            ::= { hwAAATrapOid 42 }

            hwAAASessionUpperLimitCpInstanceId OBJECT-TYPE
            SYNTAX Integer32(0..128)
            MAX-ACCESS accessible-for-notify
            STATUS current
            DESCRIPTION
                "This object indicates the form of a equipment"
            ::= { hwAAATrapOid 43 }

            hwAAASessionLowerLimitCpThreshold OBJECT-TYPE
            SYNTAX Integer32(0..99|255)
            MAX-ACCESS accessible-for-notify
            STATUS current
            DESCRIPTION
                "The online sessions lower limit warning threshold"
            DEFVAL { 255 }
            ::= { hwAAATrapOid 44 }

            hwAAASessionLowerLimitCpInstanceId OBJECT-TYPE
            SYNTAX Integer32(0..128)
            MAX-ACCESS accessible-for-notify
            STATUS current
            DESCRIPTION
                "This object indicates the form of a equipment"
            ::= { hwAAATrapOid 45 }

         hwOnlineUserNumLowerLimitCpThreshold OBJECT-TYPE
              SYNTAX Integer32(0..99|255)
              MAX-ACCESS accessible-for-notify
              STATUS current
              DESCRIPTION
                  "The online user lower limit warning threshold"
              DEFVAL { 255 }
              ::= { hwAAATrapOid 46 }            

         hwOnlineUserNumLowerLimitCpInstanceId OBJECT-TYPE
              SYNTAX Integer32(0..128)
              MAX-ACCESS accessible-for-notify
              STATUS current
              DESCRIPTION
                  "This object indicates the form of a equipment"
              ::= { hwAAATrapOid 47 }               

         hwOnlineUserNumUpperLimitCpThreshold OBJECT-TYPE
               SYNTAX Integer32(1..100|255)
               MAX-ACCESS accessible-for-notify
               STATUS current
               DESCRIPTION
                   "The online user upper limit warning threshold"
               DEFVAL { 255 }
               ::= { hwAAATrapOid 48 }
       
         hwOnlineUserNumUpperLimitCpInstanceId OBJECT-TYPE
               SYNTAX Integer32(0..128)
               MAX-ACCESS accessible-for-notify
               STATUS current
               DESCRIPTION
                   "This object indicates the form of a equipment"
               ::= { hwAAATrapOid 49 }

            hwRemoteDownloadAclCpUsedValue OBJECT-TYPE
                    SYNTAX Integer32
                    MAX-ACCESS accessible-for-notify
            STATUS current
            DESCRIPTION
                "The used number of remote download ACL."
            ::= { hwAAATrapOid 50 }

            hwRemoteDownloadAclCpThresholdValue OBJECT-TYPE
                    SYNTAX Integer32
                    MAX-ACCESS accessible-for-notify
            STATUS current
            DESCRIPTION
                "The threshold value of remote download ACL."
            ::= { hwAAATrapOid 51 }

            hwRemoteDownloadAclCpInstanceId OBJECT-TYPE
                    SYNTAX Integer32
                    MAX-ACCESS accessible-for-notify
            STATUS current
            DESCRIPTION
                "This object indicates the form of a equipment"
            ::= { hwAAATrapOid 52 }            

			hwInterfaceName OBJECT-TYPE  
				SYNTAX DisplayString (SIZE (1..64))  
				MAX-ACCESS accessible-for-notify
			STATUS current  
			DESCRIPTION  
					"This object indicates a interface name"  
			::= { hwAAATrapOid 53 }  
			
			hwInterfaceUserNum OBJECT-TYPE
                SYNTAX Integer32(0..65535)
                MAX-ACCESS accessible-for-notify
            STATUS current
            DESCRIPTION
                "This object indicates the user number of a interface"
            ::= { hwAAATrapOid 54 } 
			
			hwInterfaceUserNumThreshold OBJECT-TYPE
                SYNTAX Integer32(0..65535)
                MAX-ACCESS accessible-for-notify
            STATUS current
            DESCRIPTION
                "This object indicates the alarm threshold for the user number of a interface"
            ::= { hwAAATrapOid 55 } 
			 
			hwBackupProtectionType OBJECT-TYPE  
			    SYNTAX DisplayString (SIZE (1..64))  
			    MAX-ACCESS accessible-for-notify
			STATUS current  
			DESCRIPTION  
				"This object indicates the type of the backup protection"  
			::= { hwAAATrapOid 56 }  

			hwBackupProtectionAlarmLevel OBJECT-TYPE  
				SYNTAX DisplayString (SIZE (1..64))  
				MAX-ACCESS accessible-for-notify
			STATUS current  
			DESCRIPTION  
					"This object indicates the level of alarm"  
			::= { hwAAATrapOid 57 }  

                hwCuUpId OBJECT-TYPE
                SYNTAX Integer32 (0..283648)
                MAX-ACCESS accessible-for-notify
                STATUS current
                DESCRIPTION
                    "UP ID"
                ::= { hwAAATrapOid 58 }	

            hwInterfaceIfIndex OBJECT-TYPE
                SYNTAX Integer32
                MAX-ACCESS accessible-for-notify
            STATUS current
            DESCRIPTION
                    "This object indicates a interface index"
                ::= { hwAAATrapOid 59 }	

            hwInterfaceIfName OBJECT-TYPE
                SYNTAX DisplayString (SIZE (1..64))
                MAX-ACCESS accessible-for-notify
            STATUS current
            DESCRIPTION
                    "This object indicates a interface name"
                ::= { hwAAATrapOid 60 }		

			hwUserAccessInterface OBJECT-TYPE  
					SYNTAX DisplayString (SIZE (1..64))  
					MAX-ACCESS accessible-for-notify
				STATUS current  
				DESCRIPTION  
						"This object indicates a interface name"  
				::= { hwAAATrapOid 61 }  	
				
            hwUserAccessIndex OBJECT-TYPE
					SYNTAX Integer32
					MAX-ACCESS accessible-for-notify
				STATUS current
				DESCRIPTION
						"This object indicates a user index"
                ::= { hwAAATrapOid 62 }	
				
			hwUserAccessMAC OBJECT-TYPE  
					SYNTAX DisplayString (SIZE (1..64))  
					MAX-ACCESS accessible-for-notify
				STATUS current  
				DESCRIPTION  
						"This object indicates a user MAC"  
				::= { hwAAATrapOid 63 }  

            
            hwUserNameIndexUsage OBJECT-TYPE
                SYNTAX Unsigned32 (0..100)
                MAX-ACCESS accessible-for-notify
                STATUS current
                DESCRIPTION
                    "The usage of username index"
                ::= { hwAAATrapOid 64 }
				
            hwAAAInstanceId OBJECT-TYPE
                SYNTAX Unsigned32 
                MAX-ACCESS accessible-for-notify
                STATUS current
                DESCRIPTION
                    "The instance id"
                ::= { hwAAATrapOid 65 }

	   hwNACMaxUserSlot OBJECT-TYPE
            SYNTAX DisplayString (SIZE(1..32))
            MAX-ACCESS read-only
            STATUS current
            DESCRIPTION
            "Slot"    
            ::= { hwAAATrapOid 66 }
            
			hwNACMaxUserNum OBJECT-TYPE
            SYNTAX Integer32
            MAX-ACCESS accessible-for-notify
            STATUS current
            DESCRIPTION
                "The number of nac users."   
            ::= { hwAAATrapOid 67 }    
            
            hwNACMaxPercentage OBJECT-TYPE
            SYNTAX Integer32
            MAX-ACCESS accessible-for-notify
            STATUS current
            DESCRIPTION
                "The number of nac alarm percentage."   
            ::= { hwAAATrapOid 68 }	

            hwAAALnsUserOnlineNum OBJECT-TYPE
            SYNTAX Unsigned32
            MAX-ACCESS accessible-for-notify
            STATUS current
            DESCRIPTION
                "The number of LNS users on the device."   
            ::= { hwAAATrapOid 69 } 

            hwAAALnsUserMaxNum OBJECT-TYPE
            SYNTAX Unsigned32
            MAX-ACCESS accessible-for-notify
            STATUS current
            DESCRIPTION
                "The maximum number of LNS users on the device."   
            ::= { hwAAATrapOid 70 } 

            hwOperatorName OBJECT-TYPE
	    SYNTAX DisplayString (SIZE(1..253))
	    MAX-ACCESS accessible-for-notify
            STATUS current
            DESCRIPTION
                "The type of the operator login."   
            ::= { hwAAATrapOid 71 } 
			
	    hwAAAUserName OBJECT-TYPE
	    SYNTAX DisplayString (SIZE(1..253))
	    MAX-ACCESS accessible-for-notify
            STATUS current
            DESCRIPTION
                "The aaa username."   
            ::= { hwAAATrapOid 72 } 

        -- 1.3.6.1.4.1.2011.5.2.2.1.73
        hwPPPMaxUserSlot OBJECT-TYPE
        SYNTAX DisplayString (SIZE(1..32))
        MAX-ACCESS read-only
            STATUS current
            DESCRIPTION
                "Slot."   
            ::= { hwAAATrapOid 73 } 

        -- 1.3.6.1.4.1.2011.5.2.2.1.74
        hwPPPMaxUserNum OBJECT-TYPE
        SYNTAX Integer32
        MAX-ACCESS accessible-for-notify
            STATUS current
            DESCRIPTION
                "The number of ppp users."   
            ::= { hwAAATrapOid 74 } 

        -- 1.3.6.1.4.1.2011.5.2.2.1.75
        hwPPPMaxPercentage OBJECT-TYPE
        SYNTAX Integer32
        MAX-ACCESS accessible-for-notify
            STATUS current
            DESCRIPTION
                "The number of ppp alarm percentage."   
            ::= { hwAAATrapOid 75 } 

        -- 1.3.6.1.4.1.2011.5.2.2.1.76
        hwMacQuietUserSpec OBJECT-TYPE
            SYNTAX Integer32
            MAX-ACCESS accessible-for-notify
            STATUS current
            DESCRIPTION
                "The  mac quiet user spec ."
            ::= { hwAAATrapOid 76 }


        -- 1.3.6.1.4.1.2011.5.2.2.1.77
        hwMacUserPercentage OBJECT-TYPE
            SYNTAX Integer32
            MAX-ACCESS accessible-for-notify
            STATUS current
            DESCRIPTION
               "The quiet mac user percentage ."
            ::= { hwAAATrapOid 77 }


        -- 1.3.6.1.4.1.2011.5.2.2.1.78
        hwLowerMacUserPercentage OBJECT-TYPE
            SYNTAX Integer32
            MAX-ACCESS accessible-for-notify
            STATUS current
            DESCRIPTION
                "The configuration of mac quiet mac user lower percentage."
            ::= { hwAAATrapOid 78 }

        -- 1.3.6.1.4.1.2011.5.2.2.1.79
        hwUpperMacUserPercentage OBJECT-TYPE
        SYNTAX Integer32
        MAX-ACCESS accessible-for-notify
        STATUS current
        DESCRIPTION
            "The configuration of quiet mac user  upper percentage."
        ::= { hwAAATrapOid 79 }   
        
        -- 1.3.6.1.4.1.2011.5.2.2.1.80
        hwQuietUserType OBJECT-TYPE
        SYNTAX Integer32
        MAX-ACCESS accessible-for-notify
        STATUS current
        DESCRIPTION
            "The authenticaiton type of quiet user."
        ::= { hwAAATrapOid 80 }   

        -- 1.3.6.1.4.1.2011.5.2.2.1.81
        hwQuietUserCurrentThreshold OBJECT-TYPE
        SYNTAX Integer32
        MAX-ACCESS accessible-for-notify
        STATUS current
        DESCRIPTION
            "The current alarm threshold of quiet user for certain authenticaiton type."
        ::= { hwAAATrapOid 81 }   

        -- 1.3.6.1.4.1.2011.5.2.2.1.82
        hwQuietUserCurrentNum OBJECT-TYPE
        SYNTAX Integer32
        MAX-ACCESS accessible-for-notify
        STATUS current
        DESCRIPTION
            "The current quiet user number for certain authentication type."
        ::= { hwAAATrapOid 82 }   

        -- 1.3.6.1.4.1.2011.5.2.2.1.83
        hwQuietUserLowerLimitThreshold OBJECT-TYPE
        SYNTAX Integer32
        MAX-ACCESS accessible-for-notify
        STATUS current
        DESCRIPTION
            "The lower alarm threshold of quiet user for certain authenticaiton type."
        ::= { hwAAATrapOid 83 }   
        
        -- 1.3.6.1.4.1.2011.5.2.2.1.84
        hwQuietUserUpperLimitThreshold OBJECT-TYPE
        SYNTAX Integer32
        MAX-ACCESS accessible-for-notify
        STATUS current
        DESCRIPTION
            "The higher alarm threshold of quiet user for certain authenticaiton type."
        ::= { hwAAATrapOid 84 }   
		
        -- 1.3.6.1.4.1.2011.5.2.2.1.85
        hwQuietPortIfName OBJECT-TYPE
        SYNTAX DisplayString (SIZE(1..253))
        MAX-ACCESS accessible-for-notify
        STATUS current
        DESCRIPTION
            "The interface index of quiet user alarm."
        ::= { hwAAATrapOid 85 }   

        -- 1.3.6.1.4.1.2011.5.2.2.1.86
        hwQuietPortCurrentThreshold OBJECT-TYPE
        SYNTAX Integer32
        MAX-ACCESS accessible-for-notify
        STATUS current
        DESCRIPTION
            "The current alarm threshold of quiet user for certain authenticaiton type."
        ::= { hwAAATrapOid 86 }   

        -- 1.3.6.1.4.1.2011.5.2.2.1.87
        hwQuietPortUserNum OBJECT-TYPE
        SYNTAX Integer32
        MAX-ACCESS accessible-for-notify
        STATUS current
        DESCRIPTION
            "The current quiet user number on port for certain authentication type."
        ::= { hwAAATrapOid 87 }   

        -- 1.3.6.1.4.1.2011.5.2.2.1.88
        hwQuietPortLowerLimitThreshold OBJECT-TYPE
        SYNTAX Integer32
        MAX-ACCESS accessible-for-notify
        STATUS current
        DESCRIPTION
            "The lower alarm threshold of quiet user on port for certain authenticaiton type."
        ::= { hwAAATrapOid 88 }   

        -- 1.3.6.1.4.1.2011.5.2.2.1.89
        hwQuietPortUpperLimitThreshold OBJECT-TYPE
        SYNTAX Integer32
        MAX-ACCESS accessible-for-notify
        STATUS current
        DESCRIPTION
            "The higher alarm threshold of quiet user on port for certain authenticaiton type."
        ::= { hwAAATrapOid 89 }   

        -- 1.3.6.1.4.1.2011.5.2.2.1.90
        hwGroupNum OBJECT-TYPE
        SYNTAX Integer32
        MAX-ACCESS accessible-for-notify
        STATUS current
        DESCRIPTION
            "The amount of dynamic ucl group"
        ::= { hwAAATrapOid 90 }
        
        -- 1.3.6.1.4.1.2011.5.2.2.1.91
        hwMaxUclGroupIpNumAlarmRate OBJECT-TYPE
        SYNTAX Integer32
        MAX-ACCESS accessible-for-notify
        STATUS current
        DESCRIPTION
            "The number of dynamic ucl group percentage"
        ::= { hwAAATrapOid 91 }     
        
        -- 1.3.6.1.4.1.2011.5.2.2.1.92
        hwIPGroupServiceIPAddress OBJECT-TYPE
        SYNTAX DisplayString (SIZE(1..128))
        MAX-ACCESS accessible-for-notify
        STATUS current
        DESCRIPTION
            "The service ip address of ip group service."   
        ::= { hwAAATrapOid 92 }   
        
        -- 1.3.6.1.4.1.2011.5.2.2.1.93
        hwIPGroupServicePortName OBJECT-TYPE
        SYNTAX Integer32
        MAX-ACCESS accessible-for-notify
        STATUS current
        DESCRIPTION
            "The port name of ip group service"
        ::= { hwAAATrapOid 93 }  
        
        -- 1.3.6.1.4.1.2011.5.2.2.1.94
        hwPkiDomain OBJECT-TYPE
        SYNTAX DisplayString (SIZE(1..128))
        MAX-ACCESS accessible-for-notify
        STATUS current
        DESCRIPTION
            "The pki domain name of ip group service."   
        ::= { hwAAATrapOid 94 }    

        		-- 1.3.6.1.4.1.2011.5.2.2.1.95
        hwHacaStateChangeServerIp OBJECT-TYPE
        SYNTAX OCTET STRING (SIZE (1..40))
        MAX-ACCESS accessible-for-notify
        STATUS current
        DESCRIPTION
            "This object indicates the IP address of the HACA server."
        ::= { hwAAATrapOid 95 }

		-- 1.3.6.1.4.1.2011.5.2.2.1.96
        hwHacaStateChangeServerPortNum OBJECT-TYPE
        SYNTAX Integer32
        MAX-ACCESS accessible-for-notify
        STATUS current
        DESCRIPTION
            "This object indicates the port number of the HACA server."
        ::= { hwAAATrapOid 96 }

            hwAAATrapsDefine OBJECT IDENTIFIER ::= { hwAAAMibTrap 2 }

        hwAAATraps OBJECT IDENTIFIER ::= { hwAAATrapsDefine 0 }
        hwUserIPAllocAlarm NOTIFICATION-TYPE
            OBJECTS {hwDomainIndex, hwDomainName, hwPoolWarningThreshold}
            STATUS current
            DESCRIPTION
                "
                1. Notification/alarm name: Rbs up 2. Notification/alarm generation cause: TCP connection 3. Restoration suggestion: Matching information of hwRbsDown.
                "
            ::= { hwAAATraps 1 }
        
        hwUserSlotMaxNum NOTIFICATION-TYPE 
                OBJECTS { hwUserSlot,hwUserSlotMaxNumThreshold }
            STATUS current
            DESCRIPTION
                "
                 This object indicates the alarm threshold of the number of users who can go online from the board in a specified slot.
                "
            ::= { hwAAATraps 2 } 
            
         hwOnlineUserNumAlarm NOTIFICATION-TYPE 
                OBJECTS { hwOnlineUserNumThreshold }
            STATUS current
            DESCRIPTION
                "
                1 Notice/Trap name:  Reach the max online user
                2 Notice/Trap generation cause:  the online user number reach the limit
                3 Repair suggestions:
                upgrade your machine, or change to another board which can support more user

                "
            ::= { hwAAATraps 3 }         
        hwSetUserQosProfileFail NOTIFICATION-TYPE
            OBJECTS { hwAccessIndex,hwAccessUserName,hwAccessQosProfile }
            STATUS current
            DESCRIPTION
                "
                1 Notice/Trap name:  Set User's QOS Profile Fail
                2 Notice/Trap generation cause:  Set User's QOS Profile Fail
                3 Repair suggestions:
                    Check The Valid of Profile Name or User 

                "
            ::= { hwAAATraps 4 }
         
          hwUserMaxNum NOTIFICATION-TYPE
            OBJECTS {hwMaxUserThresholdType,hwUserSlot,hwUserSlotMaxNumThreshold}
            STATUS current
            DESCRIPTION
                "
                This object indicates the alarm threshold of the number of users who can go online from a specified device.
                "
            ::= { hwAAATraps 5 }
     
          hwRbpStateChange NOTIFICATION-TYPE            
            OBJECTS {hwRbpChangeName,hwRbpOldState,hwRbpNewState,hwRbpChangeReason}
            STATUS current
            DESCRIPTION
                "
                1 Notice/Trap name:  Rbp state changed
                2 Notice/Trap generation cause:  Rbp state changed 
                3 Repair suggestions:
                    If the change is unexpected, please check the links between master and backup devices according to the change reason. 

                "
            ::= { hwAAATraps 6 }

          hwRbsDown NOTIFICATION-TYPE           
            OBJECTS {hwRbsName,hwRbsDownReason}
            STATUS current
            DESCRIPTION
                "
                1. Notification/alarm name: Rbs down
                2. Notification/alarm generation cause: TCP shutdown due to pucHwRbsDownReason
                3. Restoration suggestion: Check the link according to the cause.
                "
            ::= { hwAAATraps 7 }
            
          hwRbsUp NOTIFICATION-TYPE           
            OBJECTS {hwRbsName}
            STATUS current
            DESCRIPTION
                "
                1. Notification/alarm name: Rbs up 
                2. Notification/alarm generation cause: TCP connection 
                3. Restoration suggestion: Matching information of hwRbsDown
                "
            ::= { hwAAATraps 8 }

        hwUserIPv6AddressAllocAlarm NOTIFICATION-TYPE
            OBJECTS {hwDomainIndex, hwDomainName, hwIPv6PoolWarningThreshold}
            STATUS current
            DESCRIPTION
                "
                This object indicates that the proportion of the IPv6 addresses allocated in the domain to the total number of IPv6 addresses has reached the threshold.
                "
            ::= { hwAAATraps 9 }
        hwUserNDRAPrefixAllocAlarm NOTIFICATION-TYPE
            OBJECTS {hwDomainIndex, hwDomainName, hwIPv6PoolWarningThreshold}
            STATUS current
            DESCRIPTION
                "
                This object indicates that the proportion of the IPv6 prefixes allocated in NDRA mode in the domain to the total number of IPv6 prefixes has reached the threshold.
                "
            ::= { hwAAATraps 10 }
        hwUserDelegationPrefixAllocAlarm NOTIFICATION-TYPE
            OBJECTS {hwDomainIndex, hwDomainName, hwIPv6PoolWarningThreshold}
            STATUS current
            DESCRIPTION
                "
This object indicates that the proportion of the IPv6 prefixes allocated in DHCPv6-PD mode in the domain to the total number of IPv6 prefixes has reached the threshold.
                "
            ::= { hwAAATraps 11 }
            
        hwUserIPAllocAlarmResume NOTIFICATION-TYPE
            OBJECTS {hwDomainIndex, hwDomainName, hwPoolWarningThreshold}
            STATUS current
            DESCRIPTION
                "
This object indicates that the IP address usage of the domain falls below the threshold.
                "
            ::= { hwAAATraps 12 }
        
        hwUserIPv6AddressAllocAlarmResume NOTIFICATION-TYPE
            OBJECTS {hwDomainIndex, hwDomainName, hwIPv6PoolWarningThreshold}
            STATUS current
            DESCRIPTION
                "
This object indicates that the IPv6 address usage of the domain falls below the threshold.
                "
            ::= { hwAAATraps 13 }    
            
        hwUserNDRAPrefixAllocAlarmResume NOTIFICATION-TYPE
            OBJECTS {hwDomainIndex, hwDomainName, hwIPv6PoolWarningThreshold}
            STATUS current
            DESCRIPTION
                "
This object indicates that the IPv6 NDRA prefix usage of the domain falls below the threshold.
                "
            ::= { hwAAATraps 14 } 
            
        hwUserDelegationPrefixAllocAlarmResume NOTIFICATION-TYPE
            OBJECTS {hwDomainIndex, hwDomainName, hwIPv6PoolWarningThreshold}
            STATUS current
            DESCRIPTION
                "
This object indicates that the IPv6 DHCPv6-PD prefix usage of the domain falls below the threshold.
                "
            ::= { hwAAATraps 15 } 

        hwOnlineUserNumUpperLimitAlarm NOTIFICATION-TYPE
            OBJECTS { hwOnlineUserNumUpperLimitThreshold }
            STATUS current
            DESCRIPTION
                "                                   
This object indicates the alarm generated when the number of users on the host exceeds the upper limit.
                "
            ::= { hwAAATraps 16 }   
                     
        hwOnlineUserNumUpperLimitResume NOTIFICATION-TYPE
            OBJECTS { hwOnlineUserNumUpperLimitThreshold }
            STATUS current
            DESCRIPTION
                "                                   
This object indicates that the alarm generated when the number of users on the host exceeds the upper limit is cleared.
                "
            ::= { hwAAATraps 17 }   
                     
        hwOnlineUserNumLowerLimitAlarm NOTIFICATION-TYPE
            OBJECTS { hwOnlineUserNumLowerLimitThreshold }
            STATUS current
            DESCRIPTION
                "                                   
This object indicates the alarm generated when the number of users on the host exceeds the lower limit.
                "
            ::= { hwAAATraps 18 }    
            
        hwOnlineUserNumLowerLimitResume NOTIFICATION-TYPE
            OBJECTS { hwOnlineUserNumLowerLimitThreshold }
            STATUS current
            DESCRIPTION
                "                                   
This object indicates that the alarm generated when the number of users on the host exceeds the lower limit is cleared.
                "
            ::= { hwAAATraps 19 }
            
        hwIPLowerlimitWarningAlarm NOTIFICATION-TYPE
            OBJECTS {hwDomainIndex, hwDomainName, hwPoolLowerLimitWarningThreshold}
            STATUS current
            DESCRIPTION
                "
This object indicates the alarm generated when the number of IP addresses in the domain exceeds the lower limit.
                "
            ::= { hwAAATraps 20 }  
            
        hwIPLowerlimitWarningResume NOTIFICATION-TYPE
            OBJECTS {hwDomainIndex, hwDomainName, hwPoolLowerLimitWarningThreshold}
            STATUS current
            DESCRIPTION
                "
This object indicates that the alarm generated when the number of IP addresses in the domain exceeds the lower limit is cleared.
                "
            ::= { hwAAATraps 21 }
             
        hwIPv6AddressLowerlimitWarningAlarm NOTIFICATION-TYPE
            OBJECTS {hwDomainIndex, hwDomainName, hwIPv6PoolLowerLimitWarningThreshold}
            STATUS current
            DESCRIPTION
                "
This object indicates the alarm generated when the number of IPv6 addresses in the domain exceeds the lower limit.
                "
            ::= { hwAAATraps 22 }  
            
        hwIPv6AddressLowerlimitWarningResume NOTIFICATION-TYPE
            OBJECTS {hwDomainIndex, hwDomainName, hwIPv6PoolLowerLimitWarningThreshold}
            STATUS current
            DESCRIPTION
                "
This object indicates that the alarm generated when the number of IPv6 addresses in the domain exceeds the lower limit is cleared.
                "
            ::= { hwAAATraps 23 }

        hwIPv6NDRAPrefixLowerlimitWarningAlarm NOTIFICATION-TYPE
            OBJECTS {hwDomainIndex, hwDomainName, hwIPv6PoolLowerLimitWarningThreshold}
            STATUS current
            DESCRIPTION
                "
This object indicates the alarm generated when the number of IPv6 NDRA prefixes in the domain exceeds the lower limit.
                "
            ::= { hwAAATraps 24 }  
            
        hwIPv6NDRAPrefixLowerlimitWarningResume NOTIFICATION-TYPE
            OBJECTS {hwDomainIndex, hwDomainName, hwIPv6PoolLowerLimitWarningThreshold}
            STATUS current
            DESCRIPTION
                "
This object indicates that the alarm generated when the number of IPv6 NDRA prefixes in the domain exceeds the lower limit is cleared.
                "
            ::= { hwAAATraps 25 }

        hwIPv6PDPrefixLowerlimitWarningAlarm NOTIFICATION-TYPE
            OBJECTS {hwDomainIndex, hwDomainName, hwIPv6PoolLowerLimitWarningThreshold}
            STATUS current
            DESCRIPTION
                "
This object indicates the alarm generated when the number of IPv6 PD prefixes in the domain exceeds the lower limit.
                "
            ::= { hwAAATraps 26 }  
            
        hwIPv6PDPrefixLowerlimitWarningResume NOTIFICATION-TYPE
            OBJECTS {hwDomainIndex, hwDomainName, hwIPv6PoolLowerLimitWarningThreshold}
            STATUS current
            DESCRIPTION
                "
This object indicates that the alarm generated when the number of IPv6 PD prefixes in the domain exceeds the lower limit is cleared.
                "
            ::= { hwAAATraps 27 }
                            
        hwPolicyRouteSlotMaxNum NOTIFICATION-TYPE
            OBJECTS {hwAccessSlotNo, hwPolicyRouteThreshold, hwAccessIndex, hwPolicyRoute}
            STATUS current
            DESCRIPTION
                "
                1 Notice/Trap name:  Policy route reach max value by slot
                2 Notice/Trap generation cause:  Policy route have reached the max value. 
                3 Repair suggestions: NA. 
                "
            ::= { hwAAATraps 28 }
            
            hwRemoteDownloadAclThresholdAlarm NOTIFICATION-TYPE
            OBJECTS {hwRemoteDownloadAclUsedValue,hwRemoteDownloadAclThresholdValue}
            STATUS current
            DESCRIPTION
                "
                1 Notice/Trap name:  The number of remote traffic classifier reached the threshold.
                2 Notice/Trap generation cause:  The number of remote traffic classifier reached the threshold. 
                3 Repair suggestions: NA. 
                "
            ::= { hwAAATraps 29 }
            
            hwRemoteDownloadAclThresholdResume NOTIFICATION-TYPE
            OBJECTS {hwRemoteDownloadAclUsedValue,hwRemoteDownloadAclThresholdValue}
            STATUS current
            DESCRIPTION
                "
                1 Notice/Trap name:  The number of remote traffic classifier below the threshold.
                2 Notice/Trap generation cause:  The number of remote traffic classifier below the threshold. 
                3 Repair suggestions: NA. 
                "
            ::= { hwAAATraps 30 }

            hwAdminLoginFailed NOTIFICATION-TYPE
            OBJECTS { hwLoginFailedTimes,hwStatisticPeriod }
            STATUS current
            DESCRIPTION
                "
                1. Notification/trap name: The administrator login failure frequently occurs. 
                2. Notification/trap generation cause: The number of login failures of the administrator is close to the threshold. 
                3. Restoration suggestion: Use a valid account to login to the device to enhance system security.
                "
            ::= { hwAAATraps 31 }
               
            hwAdminLoginFailedClear NOTIFICATION-TYPE
            OBJECTS { hwLoginFailedTimes,hwStatisticPeriod }
            STATUS current
            DESCRIPTION
                "
                1. Notification/trap name: The administrator login failure occurs not frequently. 
                2. Notification/trap generation cause: The number of login failures of the administrator is less than the threshold. 
                3. Restoration suggestion: N/A
                "
            ::= { hwAAATraps 32 }  
            
            hwUserGroupThresholdAlarm NOTIFICATION-TYPE
            OBJECTS {hwUserGroupNumThreshold,hwUserGroupUsedNum}
            STATUS current
            DESCRIPTION
                "
                1 Notice/Trap name:  The number of user groups reached the threshold.
                2 Notice/Trap generation cause:  The number of user groups reached the threshold. 
                3 Repair suggestions: NA. 
                "
            ::= { hwAAATraps 33 }
            
            hwUserGroupThresholdResume NOTIFICATION-TYPE
            OBJECTS {hwUserGroupNumThreshold,hwUserGroupUsedNum}
            STATUS current
            DESCRIPTION
                "
                1 Notice/Trap name:  The number of user groups fell below 90% of a specified alarm threshold.
                2 Notice/Trap generation cause:  The number of user groups fell below 90% of a specified alarm threshold. 
                3 Repair suggestions: NA. 
                "
            ::= { hwAAATraps 34 }
            
            hwEDSGLicenseExpireAlarm NOTIFICATION-TYPE
            STATUS current
            DESCRIPTION
                "
This object indicates the alarm about EDSG license exhaustion.
                "
            ::= { hwAAATraps 35 }
            
            hwEDSGLicenseExpireResume NOTIFICATION-TYPE
            STATUS current
            DESCRIPTION
                "
This object indicates that the alarm about EDSG license exhaustion is cleared.
                "
            ::= { hwAAATraps 36 }
            
            hwAAAAccessUserResourceOrCpuAlarm NOTIFICATION-TYPE
            OBJECTS {hwUserSlot,hwAAACpuUsage,hwAAAUserResourceUsage}
            STATUS current
            DESCRIPTION
                "
                 This object indicates that an alarm is generated when the user resource or CPU usage on a board exceeds the alarm threshold. 
                "
            ::= { hwAAATraps 37 }
            
            hwAAAAccessUserResourceOrCpuResume NOTIFICATION-TYPE
            OBJECTS {hwUserSlot,hwAAACpuUsage,hwAAAUserResourceUsage}
            STATUS current
            DESCRIPTION
                "
                This object indicates that a clear alarm is generated when the user resource or CPU usage on a board falls below the clear alarm threshold. 
                "
            ::= { hwAAATraps 38 }
            
            hwAAASessionGroupUpperLimitAlarm NOTIFICATION-TYPE
            OBJECTS { hwAAASessionGroupUpperLimitThreshold }
            STATUS current
            DESCRIPTION
                "
                1 Notice/Trap name:  Reach Session-group Upper Limit 
                2 Notice/Trap generation cause:  The number of session-group users reached the upper limit of the device.
                3 Repair suggestions:  Check your machine.
                "
            ::= { hwAAATraps 39 }  
            
            hwAAASessionGroupUpperLimitResume NOTIFICATION-TYPE
            OBJECTS { hwAAASessionGroupUpperLimitThreshold }
            STATUS current
            DESCRIPTION
                "
                1 Notice/Trap name:  Session-group Upper Limit Recovery
                2 Notice/Trap generation cause:   The number of session-group users fell below the upper limit of the device.
                3 Repair suggestions: NA
                "
            ::= { hwAAATraps 40 }      

            hwAAASessionGroupLowerLimitAlarm NOTIFICATION-TYPE
            OBJECTS { hwAAASessionGroupLowerLimitThreshold }
            STATUS current
            DESCRIPTION
                "
                1 Notice/Trap name:  Fell Below Session-group Lower Limit 
                2 Notice/Trap generation cause:  The number of session-group users fell below the lower limit of the device .
                3 Repair suggestions:
                       Check your machine.
                "
            ::= { hwAAATraps 41 } 
            
            hwAAASessionGroupLowerLimitResume NOTIFICATION-TYPE
            OBJECTS { hwAAASessionGroupLowerLimitThreshold }
            STATUS current
            DESCRIPTION
                "
                1 Notice/Trap name:  Session-group Lower Limit Recovery
                2 Notice/Trap generation cause:   The number of session-group users on the device reached the lower limit of the device.
                3 Repair suggestions: NA
                "
            ::= { hwAAATraps 42 }            
            
            hwAAAOnlineSessoinUpperLimitAlarm NOTIFICATION-TYPE
            OBJECTS { hwAAASessionUpperLimitThreshold }
            STATUS current
            DESCRIPTION
                "
                1 Notice/Trap name:  Reach Online Sessions Upper Limit
                2 Notice/Trap generation cause:  The number of session reached the upper limit of the device.
                3 Repair suggestions:  Check your machine.
                "
            ::= { hwAAATraps 43 }  

            hwAAAOnlineSessoinUpperLimitResume NOTIFICATION-TYPE
            OBJECTS { hwAAASessionUpperLimitThreshold }
            STATUS current
            DESCRIPTION
                "
                1 Notice/Trap name:  Online Sessions Upper Limit Recovery
                2 Notice/Trap generation cause:  The number of sessions fell below the upper limit of the device..
                3 Repair suggestions: NA
                "
            ::= { hwAAATraps 44 }      
            
            hwAAAOnlineSessoinLowerLimitAlarm NOTIFICATION-TYPE
            OBJECTS { hwAAASessionLowerLimitThreshold }
            STATUS current
            DESCRIPTION
                "
                1 Notice/Trap name:  Fell Below Online Sessions Lower Limit 
                2 Notice/Trap generation cause:  The number of sessions  fell below the lower limit of the device.
                3 Repair suggestions: Check your machine.
                "
            ::= { hwAAATraps 45 }            

            hwAAAOnlineSessoinLowerLimitResume NOTIFICATION-TYPE
            OBJECTS { hwAAASessionLowerLimitThreshold }
            STATUS current
            DESCRIPTION
                "
                1 Notice/Trap name:  Online Sessions Lower Limit Recovery
                2 Notice/Trap generation cause: The number of sessions  reached the lower limit of the device.
                3 Repair suggestions: NA
                "
            ::= { hwAAATraps 46 }     

            hwAAASlotOnlineUserNumAlarm NOTIFICATION-TYPE
            OBJECTS { hwUserSlot, hwUserSlotMaxNumThreshold }
            STATUS current
            DESCRIPTION
                "
                1 Notice/Trap name:  Reach Slot Online Users Upper Limit 
                2 Notice/Trap generation cause:  The number of users reached the upper limit of the board.
                3 Repair suggestions:  Please change to another board which can support more sessions.
                "
            ::= { hwAAATraps 47 }              
            
            hwAAASlotOnlineUserNumResume NOTIFICATION-TYPE
            OBJECTS { hwUserSlot, hwUserSlotMaxNumThreshold}
            STATUS current
            DESCRIPTION
                "
                1 Notice/Trap name:  Slot Online Users Upper Limit Recovery
                2 Notice/Trap generation cause:   The number of users fell below the upper limit of the board.
                3 Repair suggestions: NA
                "
            ::= { hwAAATraps 48 }  						
				           
          hwAAATimerExpireMajorLevelAlarm NOTIFICATION-TYPE
          OBJECTS { hwAAATimerExpireMajorLevelThreshold }
          STATUS current
          DESCRIPTION
              "
                1 Notice/Trap name:  The resource occupied by real-time accounting services reached the major alarm threshold.
                2 Notice/Trap generation cause:  The resource occupied by real-time accounting services reached the major alarm threshold. 
                3 Repair suggestions: NA. 
               "
          ::= { hwAAATraps 49 } 

         hwAAATimerExpireMajorLevelResume NOTIFICATION-TYPE
         OBJECTS { hwAAATimerExpireMajorLevelResumeThreshold }
         STATUS current
         DESCRIPTION
            "
            1 Notice/Trap name:  The resource occupied by real-time accounting services reached the major alarm clear threshold.
            2 Notice/Trap generation cause:  The resource occupied by real-time accounting services reached the major alarm clear threshold. 
            3 Repair suggestions: NA. 
            "
         ::= { hwAAATraps 50 } 

         hwAAATimerExpireCriticalLevelAlarm NOTIFICATION-TYPE
         OBJECTS { hwAAATimerExpireCriticalLevelThreshold }
         STATUS current
         DESCRIPTION
             "
             1 Notice/Trap name:  The resource occupied by real-time accounting services reached the critical alarm threshold.
             2 Notice/Trap generation cause:  The resource occupied by real-time accounting services reached the critical alarm threshold. 
             3 Repair suggestions: NA. 
             "
          ::= { hwAAATraps 51 }  

         hwAAATimerExpireCriticalLevelResume NOTIFICATION-TYPE
         OBJECTS { hwAAATimerExpireCriticalLevelResumeThreshold }
         STATUS current
         DESCRIPTION
             "
            1 Notice/Trap name:  The resource occupied by real-time accounting services reached the critical alarm clear threshold.
            2 Notice/Trap generation cause:  The resource occupied by real-time accounting services reached the critical alarm clear threshold. 
            3 Repair suggestions: NA. 
            "
         ::= { hwAAATraps 52 }  
	-- 1.3.6.1.4.1.2011.5.2.2.3.1.53
	hwMacMovedQuietMaxUserAlarm NOTIFICATION-TYPE
            OBJECTS { hwMacMovedQuietUserSpec, hwMacMovedUserPercentage, hwLowerMacMovedUserPercentage, hwUpperMacMovedUserPercentage }
	    STATUS current
	    DESCRIPTION 
	    "                          
                         1Notice/Trap name:  The mac moved quiet user percentage has reached the mac move quiet user alarm threshold.
                         2 Notice/Trap generation cause:  The mac moved quiet user percentage has reached the mac move quiet user alarm threshold. 
                         3 Repair suggestions: NA. 
                        "	
         ::= { hwAAATraps 53 }

		
	-- 1.3.6.1.4.1.2011.5.2.2.3.1.54
	hwMacMovedQuietUserClearAlarm NOTIFICATION-TYPE
	    OBJECTS { hwMacMovedQuietUserSpec, hwMacMovedUserPercentage, hwLowerMacMovedUserPercentage, hwUpperMacMovedUserPercentage }
	    STATUS current
	    DESCRIPTION 
	    "                          
                         1Notice/Trap name:  The mac moved quiet user percentage has reached mac moved quiet user alarm clear threshold.
                         2 Notice/Trap generation cause:  The mac moved quiet user percentage has reached mac moved quiet user alarm clear threshold. 
                         3 Repair suggestions: NA. 
                        "	
           ::= { hwAAATraps 54 }

         hwAAAChasisIPv6AddressThresholdAlarm NOTIFICATION-TYPE
         OBJECTS { hwAAAChasisIPv6AddressThreshold }
         STATUS current
         DESCRIPTION
             "
            1 Notice/Trap name:  The number of IPv6 addresses reached the upper limit of the device.
            2 Notice/Trap generation cause:  The number of IPv6 addresses reached the upper limit of the device. 
            3 Repair suggestions: NA. 
            "
         ::= { hwAAATraps 55 }  

         hwAAAChasisIPv6AddressThresholdResume NOTIFICATION-TYPE
         OBJECTS { hwAAAChasisIPv6AddressThreshold }
         STATUS current
         DESCRIPTION
             "
            1 Notice/Trap name:  The number of IPv6 addresses fell below the lower limit of the device.
            2 Notice/Trap generation cause:  The number of IPv6 addresses fell below the lower limit of the device. 
            3 Repair suggestions: NA.
            "
         ::= { hwAAATraps 56 }  

         hwAAASlotIPv6AddressThresholdAlarm NOTIFICATION-TYPE
         OBJECTS { hwUserSlot, hwAAASlotIPv6AddressThreshold }
         STATUS current
         DESCRIPTION
             "
            1 Notice/Trap name:  The number of IPv6 addresses on the slot reached the upper limit of the device.
            2 Notice/Trap generation cause:  The number of IPv6 addresses on the slot reached the upper limit of the device.
            3 Repair suggestions: NA.
            "
         ::= { hwAAATraps 57 }  

         hwAAASlotIPv6AddressThresholdResume NOTIFICATION-TYPE
         OBJECTS { hwUserSlot, hwAAASlotIPv6AddressThreshold }
         STATUS current
         DESCRIPTION
             "
            1 Notice/Trap name:  The number of IPv6 addresses on the slot fell below the lower limit of the device.
            2 Notice/Trap generation cause:  The number of IPv6 addresses on the slot fell below the lower limit of the device.
            3 Repair suggestions: NA.
            "
         ::= { hwAAATraps 58 }  

        hwAAAAdminUserAuthenWithoutDomainName NOTIFICATION-TYPE
          STATUS current
         DESCRIPTION
             "
             1 Notice/Trap name:  Performing remote authentication on administrators whose user names do not contain domain names brings security risks.
             2 Notice/Trap generation cause:  Performing remote authentication on administrators whose user names do not contain domain names brings security risks.
             3 Repair suggestions: Configuring the device in the admin domain to send user names with domain names to the remote authen server. 
             "
          ::= { hwAAATraps 59 }  
		  		  		  		  
        hwUserMaxNumResume NOTIFICATION-TYPE
         OBJECTS {hwMaxUserThresholdType,hwUserSlot,hwUserSlotMaxNumThreshold}
         STATUS current
         DESCRIPTION
             "
This object indicates the clear alarm when the number of users on the board or host falls below the threshold.
             "
          ::= { hwAAATraps 60 } 
          
        hwUserSlotMaxNumResume NOTIFICATION-TYPE
         OBJECTS { hwUserSlot,hwUserSlotMaxNumThreshold }
         STATUS current
         DESCRIPTION
             "
This object indicates the clear alarm when the number of users on the board falls below the threshold.
             "
          ::= { hwAAATraps 61 }

        hwUserOnlineFailAlarm NOTIFICATION-TYPE
         OBJECTS { hwUserSlot, hwOnlineFailNum, hwOnlineSuccessPercentage }
         STATUS current
         DESCRIPTION
             "
             1 Notice/Trap name:  User Login Failure.
             2 Notice/Trap generation cause:  The number of user login failures reached the number that can trigger detection and debugging. 
             3 Repair suggestions: Collect alarm, log, and configuration information, and contact Huawei technical support personnel.
             "
          ::= { hwAAATraps 62 }

          hwCUUserMaxNum NOTIFICATION-TYPE
            OBJECTS {hwMaxUserThresholdType,hwCUUserSlot,hwUserSlotMaxNumThreshold}
            STATUS current
            DESCRIPTION
                "
                The number of users on the board/device reached the threshold.
                 "
            ::= { hwAAATraps 63}

        hwCUUserMaxNumResume NOTIFICATION-TYPE
         OBJECTS {hwMaxUserThresholdType,hwCUUserSlot,hwUserSlotMaxNumThreshold}
         STATUS current
         DESCRIPTION
             "
             The number of users on the board/device fell below the threshold.
             "
          ::= { hwAAATraps 64} 

        hwCUUserSlotMaxNum NOTIFICATION-TYPE 
                OBJECTS { hwCUUserSlot,hwUserSlotMaxNumThreshold }
            STATUS current
            DESCRIPTION
                "
                The number of users on the board reached the alarm threshold.
                "
            ::= { hwAAATraps 65} 
          
        hwCUUserSlotMaxNumResume NOTIFICATION-TYPE
         OBJECTS { hwCUUserSlot,hwUserSlotMaxNumThreshold }
         STATUS current
         DESCRIPTION
             "
             The number of users on the board fell below the threshold.
             "
          ::= { hwAAATraps 66}

            hwCUAAAAccessUserResourceOrCpuAlarm NOTIFICATION-TYPE
            OBJECTS {hwCUUserSlot,hwAAACpuUsage,hwAAAUserResourceUsage}
            STATUS current
            DESCRIPTION
                "
                This object indicates that an alarm is generated when the user resource or CPU usage on a board exceeds the alarm threshold. 
                "
            ::= { hwAAATraps 67 }
            
            hwCUAAAAccessUserResourceOrCpuResume NOTIFICATION-TYPE
            OBJECTS {hwCUUserSlot,hwAAACpuUsage,hwAAAUserResourceUsage}
            STATUS current
            DESCRIPTION
                "
                This object indicates that a clear alarm is generated when the user resource or CPU usage on a board falls below the clear alarm threshold. 
                "
            ::= { hwAAATraps 68 }

         hwCUAAASlotIPv6AddressThresholdAlarm NOTIFICATION-TYPE
         OBJECTS { hwCUUserSlot, hwAAASlotIPv6AddressThreshold }
         STATUS current
         DESCRIPTION
             "
             This object indicates that  an alarm is generated when a large number of users went online,  and the number of IPv6 addresses used on the board reached the configured upper threshold.
            "
         ::= { hwAAATraps 69 }  

         hwCUAAASlotIPv6AddressThresholdResume NOTIFICATION-TYPE
         OBJECTS { hwCUUserSlot, hwAAASlotIPv6AddressThreshold }
         STATUS current
         DESCRIPTION
             "
             This object indicates that a clear alarm is generated when  the number of IPv6 addresses used for online users on the device fell below the lower threshold. 
            "
         ::= { hwAAATraps 70 }  

	 hwAAAOnlineSessoinUpperLimitCpAlarm NOTIFICATION-TYPE
            OBJECTS { hwAAASessionUpperLimitCpThreshold,hwAAASessionUpperLimitCpInstanceId }
            STATUS current
            DESCRIPTION
               "This object indicates that the alarm generated when the number of session reached the upper limit of the device."
            ::= { hwAAATraps 71 }

            hwAAAOnlineSessoinUpperLimitCpResume NOTIFICATION-TYPE
            OBJECTS { hwAAASessionUpperLimitCpThreshold,hwAAASessionUpperLimitCpInstanceId }
            STATUS current
            DESCRIPTION
                "This object indicates that the alarm generated when the number of sessions fell below the upper limit of the device."
            ::= { hwAAATraps 72 }
          
            hwAAAOnlineSessoinLowerLimitCpAlarm NOTIFICATION-TYPE
            OBJECTS { hwAAASessionLowerLimitCpThreshold,hwAAASessionLowerLimitCpInstanceId }
            STATUS current
            DESCRIPTION
                "This object indicates that the alarm generated when the number of sessions  fell below the lower limit of the device."
            ::= { hwAAATraps 73 }

            hwAAAOnlineSessoinLowerLimitCpResume NOTIFICATION-TYPE
            OBJECTS { hwAAASessionLowerLimitCpThreshold,hwAAASessionLowerLimitCpInstanceId }
            STATUS current
            DESCRIPTION
                "This object indicates that the alarm generated when the number of sessions reached the lower limit of the device."
            ::= { hwAAATraps 74 }
          
        hwOnlineUserNumLowerLimitCpAlarm NOTIFICATION-TYPE
            OBJECTS { hwOnlineUserNumLowerLimitCpThreshold,hwOnlineUserNumLowerLimitCpInstanceId }
            STATUS current
            DESCRIPTION
                " This object indicates that the alarm generated when the number of users on the host exceeds the lower limit."
            ::= { hwAAATraps 75 }           

        hwOnlineUserNumLowerLimitCpResume NOTIFICATION-TYPE
            OBJECTS { hwOnlineUserNumLowerLimitCpThreshold,hwOnlineUserNumLowerLimitCpInstanceId }
            STATUS current
            DESCRIPTION
                " This object indicates that the alarm generated when the number of users on the host exceeds the lower limit is cleared."
            ::= { hwAAATraps 76 } 

        hwOnlineUserNumUpperLimitCpAlarm NOTIFICATION-TYPE
            OBJECTS { hwOnlineUserNumUpperLimitCpThreshold,hwOnlineUserNumUpperLimitCpInstanceId }
            STATUS current
            DESCRIPTION
                "This object indicates that the alarm generated when the number of users on the host exceeds the upper limit."
            ::= { hwAAATraps 77 }   
                     
        hwOnlineUserNumUpperLimitCpResume NOTIFICATION-TYPE
            OBJECTS { hwOnlineUserNumUpperLimitCpThreshold,hwOnlineUserNumUpperLimitCpInstanceId }
            STATUS current
            DESCRIPTION
                "This object indicates that the alarm generated when the number of users on the host exceeds the upper limit is cleared."
            ::= { hwAAATraps 78 }  

            hwRemoteDownloadAclThresholdCpAlarm NOTIFICATION-TYPE
            OBJECTS {hwRemoteDownloadAclCpUsedValue,hwRemoteDownloadAclCpThresholdValue,hwRemoteDownloadAclCpInstanceId }
            STATUS current
            DESCRIPTION
                "This object indicates that the alarm generated when the number of remote traffic classifier reached the threshold."
            ::= { hwAAATraps 79 }
            
            hwRemoteDownloadAclThresholdCpResume NOTIFICATION-TYPE
            OBJECTS {hwRemoteDownloadAclCpUsedValue,hwRemoteDownloadAclCpThresholdValue,hwRemoteDownloadAclCpInstanceId }
            STATUS current
            DESCRIPTION
                "This object indicates that the alarm generated when the number of remote traffic classifier below the threshold."
            ::= { hwAAATraps 80 }
          			
		hwAAANoBackupInterfaceAlarm NOTIFICATION-TYPE   
			OBJECTS { hwInterfaceName,hwInterfaceUserNum,hwInterfaceUserNumThreshold,hwBackupProtectionType,hwBackupProtectionAlarmLevel }  
			STATUS current  
			DESCRIPTION  
				"This object indicates that an alarm is generated to prompt a customer to configure backup protection on an interface when the number of users with no backup protection configured on the interface reaches the threshold."
			::= { hwAAATraps 81 }  	
        
        hwCUIPv6AddressLowerlimitAlarm NOTIFICATION-TYPE
            OBJECTS {hwDomainIndex, hwDomainName, hwIPv6PoolLowerLimitWarningThreshold, hwCuUpId}
            STATUS current
            DESCRIPTION
                "
                This object indicates the alarm generated when the number of IPv6 addresses in the domain exceeds the lower limit.
                "
            ::= { hwAAATraps 83 }  
        hwCUIPv6AddressLowerlimitResume NOTIFICATION-TYPE
            OBJECTS {hwDomainIndex, hwDomainName, hwIPv6PoolLowerLimitWarningThreshold, hwCuUpId}
            STATUS current
            DESCRIPTION
                "
                This object indicates that the alarm generated when the number of IPv6 addresses in the domain exceeds the lower limit is cleared.
                "
            ::= { hwAAATraps 84 }
        hwCUIPv6NDRAPrefixLowerlimitAlarm NOTIFICATION-TYPE
            OBJECTS {hwDomainIndex, hwDomainName, hwIPv6PoolLowerLimitWarningThreshold, hwCuUpId}
            STATUS current
            DESCRIPTION
                "
               This object indicates the alarm generated when the number of IPv6 NDRA prefixes in the domain exceeds the lower limit.
                "
            ::= { hwAAATraps 85 }  
        hwCUIPv6NDRAPrefixLowerlimitResume NOTIFICATION-TYPE
            OBJECTS {hwDomainIndex, hwDomainName, hwIPv6PoolLowerLimitWarningThreshold, hwCuUpId}
            STATUS current
            DESCRIPTION
                "
                This object indicates that the alarm generated when the number of IPv6 NDRA prefixes in the domain exceeds the lower limit is cleared.
                "
            ::= { hwAAATraps 86 }
        hwCUIPv6PDPrefixLowerlimitAlarm NOTIFICATION-TYPE
            OBJECTS {hwDomainIndex, hwDomainName, hwIPv6PoolLowerLimitWarningThreshold, hwCuUpId}
            STATUS current
            DESCRIPTION
                "
                This object indicates the alarm generated when the number of IPv6 PD prefixes in the domain exceeds the lower limit.
                "
            ::= { hwAAATraps 87 }  
        hwCUIPv6PDPrefixLowerlimitResume NOTIFICATION-TYPE
            OBJECTS {hwDomainIndex, hwDomainName, hwIPv6PoolLowerLimitWarningThreshold, hwCuUpId}
            STATUS current
            DESCRIPTION
                "
                This object indicates that the alarm generated when the number of IPv6 PD prefixes in the domain exceeds the lower limit is cleared.
                "
            ::= { hwAAATraps 88 }
        hwCUUserDelegationPrefixAllocAlarm NOTIFICATION-TYPE
            OBJECTS {hwDomainIndex, hwDomainName, hwIPv6PoolWarningThreshold, hwCuUpId}
            STATUS current
            DESCRIPTION
                "
               This object indicates that the proportion of the IPv6 prefixes allocated in DHCPv6-PD mode in the domain to the total number of IPv6 prefixes has reached the threshold.
                "
            ::= { hwAAATraps 89 }
        hwCUUserDelegationPrefixAllocAlarmResume NOTIFICATION-TYPE
            OBJECTS {hwDomainIndex, hwDomainName, hwIPv6PoolWarningThreshold, hwCuUpId}
            STATUS current
            DESCRIPTION
                "
                This object indicates that the IPv6 DHCPv6-PD prefix usage of the domain falls below the threshold.
                "
            ::= { hwAAATraps 90 } 
        hwCUUserIPAllocAlarm NOTIFICATION-TYPE
            OBJECTS {hwDomainIndex, hwDomainName, hwPoolWarningThreshold, hwCuUpId}
            STATUS current
            DESCRIPTION
                "
                This object indicates that the IP address usage of the domain has reached the threshold.
                "
            ::= { hwAAATraps 91 }
        hwCUUserIPAllocAlarmResume NOTIFICATION-TYPE
            OBJECTS {hwDomainIndex, hwDomainName, hwPoolWarningThreshold, hwCuUpId}
            STATUS current
            DESCRIPTION
                "
                This object indicates that the IP address usage of the domain falls below the threshold.
                "
            ::= { hwAAATraps 92 }
        hwCUUserIPv6AddressAllocAlarm NOTIFICATION-TYPE
            OBJECTS {hwDomainIndex, hwDomainName, hwIPv6PoolWarningThreshold, hwCuUpId}
            STATUS current
            DESCRIPTION
                "
                This object indicates that the proportion of the IPv6 addresses allocated in the domain to the total number of IPv6 addresses has reached the threshold.
                "
            ::= { hwAAATraps 93 }         
        hwCUUserIPv6AddressAllocAlarmResume NOTIFICATION-TYPE
            OBJECTS {hwDomainIndex, hwDomainName, hwIPv6PoolWarningThreshold, hwCuUpId}
            STATUS current
            DESCRIPTION
                "
                This object indicates that the IPv6 address usage of the domain falls below the threshold.
                "
            ::= { hwAAATraps 94 }  
        hwCUUserNDRAPrefixAllocAlarm NOTIFICATION-TYPE
            OBJECTS {hwDomainIndex, hwDomainName, hwIPv6PoolWarningThreshold, hwCuUpId}
            STATUS current
            DESCRIPTION
                "
                This object indicates that the proportion of the IPv6 prefixes allocated in NDRA mode in the domain to the total number of IPv6 prefixes has reached the threshold.
                "
            ::= { hwAAATraps 95 }
        hwCUUserNDRAPrefixAllocAlarmResume NOTIFICATION-TYPE
            OBJECTS {hwDomainIndex, hwDomainName, hwIPv6PoolWarningThreshold, hwCuUpId}
            STATUS current
            DESCRIPTION
                "
                This object indicates that the IPv6 NDRA prefix usage of the domain falls below the threshold.
                "
            ::= { hwAAATraps 96 }    

        hwCUIPLowerlimitAlarm NOTIFICATION-TYPE
            OBJECTS {hwDomainIndex, hwDomainName, hwPoolLowerLimitWarningThreshold, hwCuUpId}
            STATUS current
            DESCRIPTION
                "
                This object indicates the alarm generated when the number of IP addresses in the domain exceeds the lower limit.
                "
            ::= { hwAAATraps 97 } 		

        hwCUIPLowerlimitWarningResume NOTIFICATION-TYPE
            OBJECTS {hwDomainIndex, hwDomainName, hwPoolLowerLimitWarningThreshold, hwCuUpId}
            STATUS current
            DESCRIPTION
                "
                This object indicates that the alarm generated when the number of IP addresses in the domain exceeds the lower limit is cleared.
                "
            ::= { hwAAATraps 98 }

       hwIpStaticUserMixedInsertAlarm NOTIFICATION-TYPE
            OBJECTS { hwInterfaceIfIndex,hwInterfaceIfName }  
            STATUS current  
            DESCRIPTION  
               "This object indicates that an alarm is generated The Eth-Trunk of IP static user contains member ports on different types of cards.
               "
            ::= { hwAAATraps 99 }  
			
		hwAAASlaveTrafficUserAlarm NOTIFICATION-TYPE   
			OBJECTS { hwUserAccessInterface,hwUserAccessIndex,hwUserAccessMAC }  
			STATUS current  
			DESCRIPTION  
				"This object indicates that an alarm is generated user traffic is sent on the BAS interface of the backup device."
			::= { hwAAATraps 100 }  		
       
       hwCUUserOnlineFailAlarm NOTIFICATION-TYPE
         OBJECTS { hwCUUserSlot, hwOnlineFailNum, hwOnlineSuccessPercentage }
         STATUS current
         DESCRIPTION
             "
             1 Notice/Trap name:  User Login Failure.
             2 Notice/Trap generation cause:  The number of user login failures reached the number that can trigger detection and debugging. 
             3 Repair suggestions: Collect alarm, log, and configuration information, and contact Huawei technical support personnel.
             "
          ::= { hwAAATraps 101 }

       hwUserNameIndexAllocAlarm NOTIFICATION-TYPE
            OBJECTS {hwUserNameIndexUsage}
            STATUS current
            DESCRIPTION
                "
                This object indicates that the usage of username index exceeds the threshold.
                "
            ::= { hwAAATraps 102 }
		
       hwUserNameIndexAllocAlarmResume NOTIFICATION-TYPE
            OBJECTS {hwUserNameIndexUsage}
            STATUS current
            DESCRIPTION
                "
                This object indicates that the alarm generated when the usage of username falls below the threshold is cleared.
                "
            ::= { hwAAATraps 103 }		
			
       hwCUUserNameIndexAllocAlarm NOTIFICATION-TYPE
            OBJECTS {hwAAAInstanceId, hwUserNameIndexUsage}
            STATUS current
            DESCRIPTION
                "
                This object indicates that the usage of username index exceeds the threshold.
                "
            ::= { hwAAATraps 104 }
		
       hwCUUserNameIndexAllocAlarmResume NOTIFICATION-TYPE
            OBJECTS {hwAAAInstanceId, hwUserNameIndexUsage}
            STATUS current
            DESCRIPTION
                "
                This object indicates that the alarm generated when the usage of username falls below the threshold is cleared.
                "
            ::= { hwAAATraps 105 }	

	 hwNacUserClearAlarm NOTIFICATION-TYPE
			OBJECTS { hwNACMaxUserSlot, hwNACMaxUserNum, hwNACMaxPercentage }
			STATUS current
			DESCRIPTION 
				"This object indicates that the nac users less than the resume threshold. "
			::= { hwAAATraps 106 }

	   hwNacMaxUserAlarm NOTIFICATION-TYPE
	        OBJECTS { hwNACMaxUserSlot, hwNACMaxUserNum, hwNACMaxPercentage }
			STATUS current
			DESCRIPTION 
				"This object indicates that the nac users exceeds the threshold"
			::= { hwAAATraps 107 }				
  
        hwAAALnsUserNumOverLimitAlarm NOTIFICATION-TYPE
            OBJECTS { hwAAAInstanceId, hwAAALnsUserOnlineNum, hwAAALnsUserMaxNum }
            STATUS current
            DESCRIPTION 
                    "This object indicates that the number of LNS users on the device is over the limit"
            ::= { hwAAATraps 108 } 

        hwAAALnsUserNumOverLimitResume NOTIFICATION-TYPE
            OBJECTS { hwAAAInstanceId, hwAAALnsUserOnlineNum, hwAAALnsUserMaxNum }
            STATUS current
            DESCRIPTION 
                    "This object indicates that the number of LNS users on the device fell bellow the the limit"
            ::= { hwAAATraps 109 } 

        hwAAACUDomainNatStateAlarm NOTIFICATION-TYPE
            OBJECTS { hwDomainIndex, hwDomainName, hwCuUpId}
            STATUS current
            DESCRIPTION 
                    "This object indicates that an alarm is generated when nat instances with and without a static source tracing algorithm enabled were bound to the domain."
            ::= { hwAAATraps 110} 

        hwAAACUDomainNatStateResume NOTIFICATION-TYPE
            OBJECTS { hwDomainIndex, hwDomainName, hwCuUpId }
            STATUS current
            DESCRIPTION 
                    "This object indicates that a clear alarm is generated when nat instances without a static source tracing algorithm enabled were bound to the domain."
            ::= { hwAAATraps 111} 

	hwChangePasswordAlarm NOTIFICATION-TYPE
	    OBJECTS { hwOperatorName,hwAAAUserName }
	    STATUS current
	    DESCRIPTION 
		    "This object indicates that local account password has been modified."
	    ::= { hwAAATraps 112 }

       hwAdminDefaultPasswordAlarm NOTIFICATION-TYPE
			STATUS current
			DESCRIPTION 
				"This object indicates that local account admin use default password."
			::= { hwAAATraps 115 }

        hwPPPMaxUserAlarm NOTIFICATION-TYPE
        OBJECTS { hwPPPMaxUserSlot,hwPPPMaxUserNum,hwPPPMaxPercentage }
        STATUS current
        DESCRIPTION 
            "This object indicates that the PPP users exceeds the threshold"
        ::= { hwAAATraps 116 }

        hwPPPMaxUserClearAlarm NOTIFICATION-TYPE
        OBJECTS { hwPPPMaxUserSlot,hwPPPMaxUserNum,hwPPPMaxPercentage }
        STATUS current
        DESCRIPTION 
            "This object indicates that the PPP users less than the resume threshold."
        ::= { hwAAATraps 117 }

        hwMacQuietMaxUserAlarm NOTIFICATION-TYPE
        OBJECTS { hwMacQuietUserSpec,hwMacUserPercentage,hwLowerMacUserPercentage,hwUpperMacUserPercentage }
        STATUS current
        DESCRIPTION 
            "            1Notice/Trap name:  The mac quiet user percentage has reached the mac quiet user alarm threshold.
                         2 Notice/Trap generation cause:  The mac quiet user percentage has reached the mac quiet user alarm threshold. 
                         3 Repair suggestions: NA."
        ::= { hwAAATraps 118 }

        hwMacQuietUserClearAlarm NOTIFICATION-TYPE
        OBJECTS { hwMacQuietUserSpec, hwMacUserPercentage,hwLowerMacUserPercentage,hwUpperMacUserPercentage}
        STATUS current
        DESCRIPTION 
            "             1Notice/Trap name:  The mac quiet user percentage has reached mac quiet user alarm clear threshold.
                         2 Notice/Trap generation cause:  The mac quiet user percentage has reached mac quiet user alarm clear threshold. 
                         3 Repair suggestions: NA. "
        ::= { hwAAATraps 119 }     
        
        hwQuietUserClearAlarm NOTIFICATION-TYPE
        OBJECTS { hwQuietUserType, hwQuietUserCurrentThreshold, hwQuietUserCurrentNum, hwQuietUserLowerLimitThreshold, hwQuietUserUpperLimitThreshold}
        STATUS current
        DESCRIPTION 
            "            1 Notice/Trap name: The quiet max User alarm is cleared.
                         2 Notice/Trap generation cause: The quiet user percentage has fallen below the user alarm clear threshold. 
                         3 Repair suggestions: NA. "
        ::= { hwAAATraps 120 }     

        hwQuietUserMaxAlarm NOTIFICATION-TYPE
        OBJECTS { hwQuietUserType, hwQuietUserCurrentThreshold, hwQuietUserCurrentNum, hwQuietUserLowerLimitThreshold, hwQuietUserUpperLimitThreshold}
        STATUS current
        DESCRIPTION 
            "            1 Notice/Trap name: The number of quiet users is reaching the max.
                         2 Notice/Trap generation cause: The quiet user percentage has reached the upper threshold. 
                         3 Repair suggestions: NA. "
        ::= { hwAAATraps 121 }     

        hwQuietPortClearAlarm NOTIFICATION-TYPE
        OBJECTS { hwQuietUserType, hwQuietPortIfName, hwQuietPortCurrentThreshold, hwQuietPortUserNum, hwQuietPortLowerLimitThreshold, hwQuietPortUpperLimitThreshold}
        STATUS current
        DESCRIPTION 
            "            1 Notice/Trap name: The quiet max user alarm on port is cleared.
                         2 Notice/Trap generation cause:  The quiet user percentage on port has fallen below the user alarm clear threshold. 
                         3 Repair suggestions: NA. "
        ::= { hwAAATraps 122 }     

        hwQuietPortMaxAlarm NOTIFICATION-TYPE
        OBJECTS { hwQuietUserType, hwQuietPortIfName, hwQuietPortCurrentThreshold, hwQuietPortUserNum, hwQuietPortLowerLimitThreshold, hwQuietPortUpperLimitThreshold}
        STATUS current
        DESCRIPTION 
            "            1 Notice/Trap name: The number of quiet users on port is reaching the max.
                         2 Notice/Trap generation cause: The quiet user percentage on port has reached the upper threshold. 
                         3 Repair suggestions: NA. "
        ::= { hwAAATraps 123 }

        hwMaxUclGroupIpNumAlarm NOTIFICATION-TYPE
        OBJECTS { hwGroupNum, hwMaxUclGroupIpNumAlarmRate}
        STATUS current
        DESCRIPTION 
            "            1 Notice/Trap name:  The dynamic ucl group configuration percentage has reached dynamic ucl group num alarm threshold.
                         2 Notice/Trap generation cause:  The dynamic ucl group configuration percentage has reached dynamic ucl group num alarm threshold. 
                         3 Repair suggestions: NA. "
        ::= { hwAAATraps 124 }   
        
        hwMaxUclGroupIpNumClearAlarm NOTIFICATION-TYPE
        OBJECTS { hwGroupNum, hwMaxUclGroupIpNumAlarmRate}
        STATUS current
        DESCRIPTION 
            "            1 Notice/Trap name:  The dynamic ucl group configuration percentage has fallen down the dynamic ucl group num alarm clear threshold.
                         2 Notice/Trap generation cause:  The dynamic ucl group configuration percentage has fallen down the dynamic ucl group num alarm clear threshold. 
                         3 Repair suggestions: NA. "
        ::= { hwAAATraps 125 }         
       
        hwIPGroupChannelUp NOTIFICATION-TYPE
        OBJECTS { hwIPGroupServiceIPAddress, hwIPGroupServicePortName, hwPkiDomain}
        STATUS current
        DESCRIPTION 
            "            1 Notice/Trap name:  The state of ip group channel turns to up.
                         2 Notice/Trap generation cause: The state of ip group channel turns to up. 
                         3 Repair suggestions: NA. "
        ::= { hwAAATraps 126 }

        hwIPGroupChannelDown NOTIFICATION-TYPE
        OBJECTS { hwIPGroupServiceIPAddress, hwIPGroupServicePortName, hwPkiDomain}
        STATUS current
        DESCRIPTION 
            "            1 Notice/Trap name:  The state of ip group channel turns to down.
                         2 Notice/Trap generation cause: The state of ip group channel turns to down. 
                         3 Repair suggestions: NA. "
        ::= { hwAAATraps 127 }

        hwHacaChannelUp NOTIFICATION-TYPE
        OBJECTS { hwHacaStateChangeServerIp,hwHacaStateChangeServerPortNum }
        STATUS current
        DESCRIPTION 
            "This object indicates that the HACA channel is Up."
        ::= { hwAAATraps 128 }

        hwHacaChannelDown NOTIFICATION-TYPE
        OBJECTS { hwHacaStateChangeServerIp,hwHacaStateChangeServerPortNum }
        STATUS current
        DESCRIPTION 
            "This object indicates that the HACA channel is Down."
        ::= { hwAAATraps 129 }



        hwLAMTrapsDefine OBJECT IDENTIFIER ::= { hwAAAMibTrap 3 }

        hwLAMTraps OBJECT IDENTIFIER ::= { hwLAMTrapsDefine 0 }
        hwHarddiskoverflow NOTIFICATION-TYPE
            OBJECTS { hwHdFreeamount,hwHdWarningThreshold }
            STATUS current
            DESCRIPTION
                "
                1 Notice/Trap name:  Reach IP address Allocable Threshold 
                2 Notice/Trap generation cause:  reach the threshold set at domain 
                3 Repair suggestions:
                    Check whether to renew configuring the BAS IP pool
                    Add new IP pool to this domain .

                "
            ::= { hwLAMTraps 1 }

        hwHarddiskReachThreshold NOTIFICATION-TYPE
            OBJECTS { hwHdFreeamount,hwHdWarningThreshold }
            STATUS current
            DESCRIPTION
                "
                1 Notice/Trap name:  Reach IP address Allocable Threshold 
                2 Notice/Trap generation cause:  reach the threshold set at domain 
                3 Repair suggestions:
                    Check whether to renew configuring the BAS IP pool
                    Add new IP pool to this domain .

                "
            ::= { hwLAMTraps 2 }
      hwHarddiskOK NOTIFICATION-TYPE
            OBJECTS { hwHdFreeamount,hwHdWarningThreshold }
            STATUS current
            DESCRIPTION
                "
                1 Notice/Trap name:  Reach IP address Allocable Threshold 
                2 Notice/Trap generation cause:  reach the threshold set at domain 
                3 Repair suggestions:
                    Check whether to renew configuring the BAS IP pool
                    Add new IP pool to this domain .

                "
            ::= { hwLAMTraps 3 }
        hwCachetoFTPFail NOTIFICATION-TYPE
            STATUS current
            DESCRIPTION
                "
                1 Notice/Trap name:  Reach IP address Allocable Threshold 
                2 Notice/Trap generation cause:  reach the threshold set at domain 
                3 Repair suggestions:
                    Check whether to renew configuring the BAS IP pool
                    Add new IP pool to this domain .

                "
            ::= { hwLAMTraps 4 }
     hwHDtoFTPFail NOTIFICATION-TYPE
            STATUS current
            DESCRIPTION
                "
                1 Notice/Trap name:  Reach IP address Allocable Threshold 
                2 Notice/Trap generation cause:  reach the threshold set at domain 
                3 Repair suggestions:
                    Check whether to renew configuring the BAS IP pool
                    Add new IP pool to this domain .

                "
            ::= { hwLAMTraps 5 } 
			
	 hwAAAUserPwdWillExpire NOTIFICATION-TYPE
            OBJECTS { hwLocalUserName,hwPwdVdtyLeftDays }
            STATUS current
            DESCRIPTION
                "
                1 Notice/Trap name:  Local user password will expire
                2 Notice/Trap generation cause:  Local user doesnot change password 
                3 Repair suggestions:
                    NA
                "
            ::= { hwLAMTraps 6 }
			
	 hwAAAUserPwdExpired NOTIFICATION-TYPE
            OBJECTS { hwLocalUserName }
            STATUS current
            DESCRIPTION
                "
                1 Notice/Trap name:  Local user password had expired
                2 Notice/Trap generation cause:  Local user doesnot change password always
                3 Repair suggestions:
                    NA
                "
            ::= { hwLAMTraps 7 }			
            
        hwCutAccessUserTable OBJECT IDENTIFIER  ::= { hwAAAMibObjects 28 }
        
        hwCutStartUserID OBJECT-TYPE
            SYNTAX Integer32 
                      MAX-ACCESS read-write
                      STATUS current
                      DESCRIPTION
                          "Start User CID"
                      ::= { hwCutAccessUserTable 1 }

        hwCutEndUserID OBJECT-TYPE
            SYNTAX Integer32 
                      MAX-ACCESS read-write
                     STATUS current
                      DESCRIPTION
                          "End User CID"
                      ::= { hwCutAccessUserTable 2 }

        hwCutIPaddress OBJECT-TYPE
            SYNTAX IpAddress
                      MAX-ACCESS read-write
                      STATUS current
                      DESCRIPTION
                          "User IP Address"
                      ::= { hwCutAccessUserTable 3 }

        hwCutMacAddres OBJECT-TYPE
            SYNTAX MacAddress
                      MAX-ACCESS read-write
                      STATUS current
                      DESCRIPTION
                          "User MAC Address"
                      ::= { hwCutAccessUserTable 4 }

        hwCutUserName OBJECT-TYPE
            SYNTAX DisplayString (SIZE (1..253))
                      MAX-ACCESS read-write
                      STATUS current
                      DESCRIPTION
                          "User Access Name"
                      ::= { hwCutAccessUserTable 5 }

        hwCutUserAttri OBJECT-TYPE
                SYNTAX INTEGER
                    {
                    all(0),
                    noauth(1),
                    local(2),                    
                    radiusauth(3),
                    hwtacacs(4)
                    }
                    MAX-ACCESS read-write
                    STATUS current
                      DESCRIPTION
                          "User Authentication attribute"
                      ::= { hwCutAccessUserTable 6 }

        hwCutDomain OBJECT-TYPE
            SYNTAX DisplayString (SIZE (1..64))
                      MAX-ACCESS read-write
                      STATUS current
                      DESCRIPTION
                          "domain name"
                      ::= { hwCutAccessUserTable 7 }

        hwCutIPPoolName OBJECT-TYPE
            SYNTAX DisplayString (SIZE (1..128))
                      MAX-ACCESS read-write
                      STATUS current
                      DESCRIPTION
                          "IP Pool Name"
                      ::= { hwCutAccessUserTable 8 }

        hwCutIfIndex OBJECT-TYPE
            SYNTAX Integer32
            MAX-ACCESS read-write
            STATUS current
            DESCRIPTION
                "IFNET Index"
            ::= { hwCutAccessUserTable 9 }    

        hwCutVlanID OBJECT-TYPE
            SYNTAX Integer32 (0..268308478)
            MAX-ACCESS read-write
            STATUS current
            DESCRIPTION
                "VLAN ID"
            ::= { hwCutAccessUserTable 10 }    
            
        hwCutVPI OBJECT-TYPE
            SYNTAX Integer32(0..255)
            MAX-ACCESS read-write
            STATUS current
            DESCRIPTION
                "VPI
    
                 VPI"
            ::= { hwCutAccessUserTable 11 }    
            
        hwCutVCI OBJECT-TYPE
            SYNTAX Integer32(0..2047)
            MAX-ACCESS read-write
            STATUS current
            DESCRIPTION
                "VCI
    
                 VCI"
            ::= { hwCutAccessUserTable 12 }
                
        hwCutVRF OBJECT-TYPE
            SYNTAX DisplayString (SIZE (1..31))    
            MAX-ACCESS read-write
            STATUS current
            DESCRIPTION
                 "User VRF"
            ::= { hwCutAccessUserTable 13 }
			
        hwCutAccessInterface OBJECT-TYPE
            SYNTAX DisplayString (SIZE (1..63))    
            MAX-ACCESS read-write
            STATUS current
            DESCRIPTION
                 "The user access interface"
            ::= { hwCutAccessUserTable 14 }
			
        hwCutUserSSID OBJECT-TYPE
            SYNTAX DisplayString (SIZE (1..32))    
            MAX-ACCESS read-write
            STATUS current
            DESCRIPTION
                 "The user access SSID"
            ::= { hwCutAccessUserTable 15 }
			
        hwCutAccessSlot OBJECT-TYPE
            SYNTAX Integer32    
            MAX-ACCESS read-write
            STATUS current
            DESCRIPTION
                 "The user access slot"
            ::= { hwCutAccessUserTable 16 }
              
        hwCutUserGroup OBJECT-TYPE
            SYNTAX DisplayString (SIZE (1..64))    
            MAX-ACCESS read-write
            STATUS current
            DESCRIPTION
                 "The user group"
            ::= { hwCutAccessUserTable 17 }
			
--        hwCutQinqVlanID OBJECT-TYPE
--            SYNTAX Integer32(0..4094)
--            MAX-ACCESS read-write
--            STATUS current
--            DESCRIPTION
--                "qinq vlan ID
--    
--                 QINQ VLAN ID"
--            ::= { hwCutAccessUserTable 14 }    
            
--        hwCutUserVlanID OBJECT-TYPE
--            SYNTAX Integer32(0..4094)
--            MAX-ACCESS read-write
--            STATUS current
--            DESCRIPTION
--                "user vlan ID"
--            ::= { hwCutAccessUserTable 15 }    

        hwAAACallRate OBJECT IDENTIFIER ::= { hwAAAMibObjects 29 }
        
        hwAAAUserPPP OBJECT IDENTIFIER ::= { hwAAACallRate 1 }
        
        hwTotalConnectNum OBJECT-TYPE
            SYNTAX Counter32 
            MAX-ACCESS read-only
            STATUS current
            DESCRIPTION
                "This object indicates the total number of connections.
"
            ::= { hwAAAUserPPP 1 }
       hwTotalSuccessNum OBJECT-TYPE
            SYNTAX Counter32 
            MAX-ACCESS read-only
            STATUS current
            DESCRIPTION
                "This object indicates the number of successful connections.
"
            ::= { hwAAAUserPPP 2 }
     hwTotalLCPFailNum OBJECT-TYPE
            SYNTAX Counter32 
            MAX-ACCESS read-only
            STATUS current
            DESCRIPTION
                "This object indicates the number of access failures at the LCP stage.
"
            ::= { hwAAAUserPPP 3 }
    hwTotalAuthenFailNum OBJECT-TYPE
            SYNTAX Counter32 
            MAX-ACCESS read-only
            STATUS current
            DESCRIPTION
                "This object indicates the number of access failures at the authentication stage.
"
            ::= { hwAAAUserPPP 4 }   
     hwTotalNCPFailNum OBJECT-TYPE
            SYNTAX Counter32 
            MAX-ACCESS read-only
            STATUS current
            DESCRIPTION
                "This object indicates the number of access failures at the NCP stage.
"
            ::= { hwAAAUserPPP 5 }
    hwTotalIPAllocFailNum OBJECT-TYPE
            SYNTAX Counter32 
            MAX-ACCESS read-only
            STATUS current
            DESCRIPTION
                "This object indicates the number of access failures at the address allocation stage.
"
            ::= { hwAAAUserPPP 6 }
     hwTotalOtherPPPFailNum OBJECT-TYPE
            SYNTAX Counter32 
            MAX-ACCESS read-only
            STATUS current
            DESCRIPTION
                "This object indicates the number of access failures due to other reasons.
"
            ::= { hwAAAUserPPP 7 }   
     hwTotalPPPFailNum OBJECT-TYPE
            SYNTAX Counter32 
            MAX-ACCESS read-only
            STATUS current
            DESCRIPTION
                "the number of all fail access ppp user"
            ::= { hwAAAUserPPP 8 }           
      hwAAAUserWebandFast OBJECT IDENTIFIER ::= { hwAAACallRate 2 }
        
        hwTotalWebConnectNum OBJECT-TYPE
            SYNTAX Counter32 
            MAX-ACCESS read-only
            STATUS current
            DESCRIPTION
                "This object indicates the total number of web and fast connections.
"
            ::= { hwAAAUserWebandFast 1 }
       hwTotalSuccessWebConnectNum OBJECT-TYPE
            SYNTAX Counter32 
            MAX-ACCESS read-only
            STATUS current
            DESCRIPTION
                "This object indicates the number of successful web and fast connections.
"
            ::= { hwAAAUserWebandFast 2 }
            
     hwAAAUserDot1X OBJECT IDENTIFIER ::= { hwAAACallRate 3 }
        
        hwTotalDot1XConnectNum OBJECT-TYPE
            SYNTAX Counter32 
            MAX-ACCESS read-only
            STATUS current
            DESCRIPTION
                "the number of access all dot1x user"
            ::= { hwAAAUserDot1X 1 }
       hwTotalSuccessDot1XConnectNum OBJECT-TYPE
            SYNTAX Counter32 
            MAX-ACCESS read-only
            STATUS current
            DESCRIPTION
                "the number of all success access dot1x user"
            ::= { hwAAAUserDot1X 2 }
            
      hwAAAUserBind OBJECT IDENTIFIER ::= { hwAAACallRate 4 }
        
        hwTotalBindConnectNum OBJECT-TYPE
            SYNTAX Counter32 
            MAX-ACCESS read-only
            STATUS current
            DESCRIPTION
                "This object indicates the total number of bind connections.
"
            ::= { hwAAAUserBind 1 }
       hwTotalSuccessBindConnectNum OBJECT-TYPE
            SYNTAX Counter32 
            MAX-ACCESS read-only
            STATUS current
            DESCRIPTION
                "This object indicates the number of successful bind connections.
"
            ::= { hwAAAUserBind 2 }    
            

          
        hwAuthorSchemeTable OBJECT-TYPE
            SYNTAX SEQUENCE OF HwAuthorSchemeEntry
            MAX-ACCESS not-accessible
            STATUS current
            DESCRIPTION
                "authorization Scheme Table"
            ::= { hwAAAMibObjects 8 }
        hwAuthorSchemeEntry OBJECT-TYPE
            SYNTAX HwAuthorSchemeEntry
            MAX-ACCESS not-accessible
            STATUS current
            DESCRIPTION
                "authorization Scheme Entry"
            INDEX { hwAuthorSchemeName }
            ::= { hwAuthorSchemeTable 1 }
        HwAuthorSchemeEntry ::=
            SEQUENCE {
                hwAuthorSchemeName
                    DisplayString,
                hwAuthorMethod
                    INTEGER,
                hwAuthorRowStatus
                    RowStatus,
				hwAuthorMethodNew
					DisplayString
             }
        hwAuthorSchemeName OBJECT-TYPE
            SYNTAX DisplayString (SIZE (1..32))
            MAX-ACCESS read-only
            STATUS current
            DESCRIPTION
                "This object indicates the name of an authorization solution.
"
            ::= { hwAuthorSchemeEntry 1 }
        hwAuthorMethod OBJECT-TYPE
            SYNTAX INTEGER
                {
                none(1),
                local(2),
                hwtacacs(3),
                ifauthenticated(4),
                hwtacacsnone(5),
                hwtacacslocal(6),
                hwtacacsifauthenticated(7),
                localnone(8),
                localhwtacacs(9),
                localifauthenticated(10),
                ifauthenticatednone(11),
                ifauthenticatedlocal(12),
                ifauthenticatedhwtacacs(13),
                localhwtacacsnone(14),
                localifauthenticatednone(15),
                hwtacacslocalnone(16),
                hwtacacsifauthenticatednone(17),
                ifauthenticatedlocalnone(18),
                ifauthenticatedhwtacacsnone(19),
                localhwtacacsifauthenticated(20),
                localifauthenticatedhwtacacs(21),
                hwtacaslocalifauthenticated(22),
                hwtacacsifauthenticatedlocal(23),
                ifauthenticatedlocalhwtacacs(24),
                ifauthenticatedhwtacacslocal(25),
                localhwtacacsifauthenticatednone(26),
                localifauthenticatedhwtacacsnone(27),
                hwtacaslocalifauthenticatednone(28),
                hwtacacsifauthenticatedlocalnone(29),
                ifauthenticatedlocalhwtacacsnone(30),
                ifauthenticatedhwtacacslocalnone(31),
                localcase(32),
                hwtacacsLocalcase(33),
                localcasenone(34),
                localcasecasehwtacacs(35),
                localcaseifauthenticated(36),
                ifauthenticatedLocalcase(37), 
                localcasehwtacacsnone(38),
                localcaseifauthenticatednone(39),
                hwtacacsLocalcasenone(40),
                ifauthenticatedLocalcasenone(41),
                localcasehwtacacsifauthenticated(42),
                localcaseifauthenticatedhwtacacs(43),
                hwtacacsLocalcaseifauthenticated(44),
                hwtacacsifauthenticatedLocalcase(45),
                ifauthenticatedLocalcasehwtacacs(46),
                ifauthenticatedhwtacacsLocalcase(47),
                localcasehwtacacsifauthenticatednone(48), 
                localcaseifauthenticatedhwtacacsnone(49), 
                hwtacacsLocalcaseifauthenticatednone(50), 
                hwtacacsifauthenticatedLocalcasenone(51), 
                ifauthenticatedLocalcasehwtacacsnone(52), 
                ifauthenticatedhwtacacsLocalcasenone(53)                 
                }
            MAX-ACCESS read-create
            STATUS current
            DESCRIPTION
                "This object indicates the authorization mode.
                "
            ::= { hwAuthorSchemeEntry 2 }
        hwAuthorRowStatus OBJECT-TYPE
            SYNTAX RowStatus
            MAX-ACCESS read-create
            STATUS current
            DESCRIPTION
                "This object indicates the row administrative status. Currently, the states of creation and deletion are supported.
"
            ::= { hwAuthorSchemeEntry 3 }
		
		hwAuthorMethodNew OBJECT-TYPE
			SYNTAX DisplayString (SIZE (1..16))
			MAX-ACCESS read-write
			STATUS current
			DESCRIPTION
				"Description."
			::= { hwAuthorSchemeEntry 4 }
            
        hwRecordSchemeTable OBJECT-TYPE
            SYNTAX SEQUENCE OF HwRecordSchemeEntry
            MAX-ACCESS not-accessible
            STATUS current
            DESCRIPTION
                "The hwRecordSchemeTable is a recording solution table used to configure a recording solution, including the solution name and TAC template name. The configuration includes addition, modification, deletion, and query of the recording solution."
            ::= { hwAAAMibObjects 30 }

        hwRecordSchemeEntry OBJECT-TYPE
            SYNTAX HwRecordSchemeEntry
            MAX-ACCESS not-accessible
            STATUS current
            DESCRIPTION
                "record Scheme Entry"
            INDEX { hwRecordSchemeName }
            ::= { hwRecordSchemeTable 1 }

        HwRecordSchemeEntry ::=
            SEQUENCE {
                hwRecordSchemeName
                    DisplayString,
                hwRecordTacGroupName
                    DisplayString,
                hwRecordRowStatus
                    RowStatus
             }

        hwRecordSchemeName OBJECT-TYPE
            SYNTAX DisplayString (SIZE (1..32))
            MAX-ACCESS read-only
            STATUS current
            DESCRIPTION
                "This object indicates the name of a recording solution.
"
            ::= { hwRecordSchemeEntry 1 }

        hwRecordTacGroupName OBJECT-TYPE
            SYNTAX DisplayString (SIZE (1..32))
            MAX-ACCESS read-create
            STATUS current
            DESCRIPTION
                "This object indicates the name of the HWTACACS server template used by the recording solution.
"
            ::= { hwRecordSchemeEntry 2 }

        hwRecordRowStatus OBJECT-TYPE
            SYNTAX RowStatus
            MAX-ACCESS read-create
            STATUS current
            DESCRIPTION
                "This object indicates the row administrative status. Currently, the states of creation and deletion are supported.
"
            ::= { hwRecordSchemeEntry 3 }    
            
            
         hwMACAccessTable OBJECT-TYPE
            SYNTAX SEQUENCE OF HwMACAccessEntry
            MAX-ACCESS not-accessible
            STATUS current  
            DESCRIPTION
                "The hwMACAccessTable is a MAC query access table used to query the indexes of access tables based on users' MAC addresses."
            ::= { hwAAAMibObjects 31 }
        
            hwMACAccessEntry OBJECT-TYPE
                  SYNTAX HwMACAccessEntry
                  MAX-ACCESS not-accessible
                  STATUS current
                  DESCRIPTION
                            "MAC Query Access Entry
                            "
                        INDEX { hwMACAccessMACAddress }
                        ::= { hwMACAccessTable 1 }
        
                    HwMACAccessEntry ::=
                        SEQUENCE { 
                            hwMACAccessMACAddress
                                MacAddress,
                            hwMACAccessCID
                                Integer32                 
                        }

                    hwMACAccessMACAddress OBJECT-TYPE
                        SYNTAX MacAddress
                        MAX-ACCESS read-only
                        STATUS current
                        DESCRIPTION
                            "This object indicates the MAC address of the user.
"
                        ::= { hwMACAccessEntry 1 }


                    hwMACAccessCID OBJECT-TYPE
                        SYNTAX Integer32
                        MAX-ACCESS read-only
                        STATUS current
                        DESCRIPTION
                            "This object indicates the user access index.
"
                        ::= { hwMACAccessEntry 2 }    
                                
                
            hwSlotConnectNumTable OBJECT-TYPE
            SYNTAX SEQUENCE OF HwSlotConnectNumEntry
            MAX-ACCESS not-accessible
            STATUS current 
            DESCRIPTION
                "This table is used to collect statistics about the number of users who go online from the board."
            ::= { hwAAAMibObjects 32 }
        
            hwSlotConnectNumEntry OBJECT-TYPE
                  SYNTAX HwSlotConnectNumEntry
                  MAX-ACCESS not-accessible
                  STATUS current
                  DESCRIPTION
                            "Slot Query Online Number Entry
                            "
                        INDEX { hwSlotConnectNumSlot }
                        ::= { hwSlotConnectNumTable 1 }
        
                    HwSlotConnectNumEntry ::=
                        SEQUENCE { 
                            hwSlotConnectNumSlot
                                Integer32,
                            hwSlotConnectNumOnlineNum
                                Integer32,
                            hwSlotConnectNumMaxOnlineNum
                                Integer32,
                            hwSlotConnectNumMaxOnlineAcctReadyNum
                                Integer32,
                            hwSlotConnectNumIPv4OnlineNum
                                Integer32,
                            hwSlotConnectNumIPv6OnlineNum
                                Integer32,
                            hwSlotConnectNumDualOnlineNum
                                Integer32,
                            hwSlotConnectNumMaxOnlineNumDate
                                DisplayString,
                            hwSlotConnectNumMaxOnlineAcctRNumDate
                                DisplayString

                        }

                    hwSlotConnectNumSlot OBJECT-TYPE
                        SYNTAX Integer32 (0..2147483647)
                        MAX-ACCESS read-only
                        STATUS current
                        DESCRIPTION
                            "This object indicates the slot ID of the device.
"
                        ::= { hwSlotConnectNumEntry 1 }


                    hwSlotConnectNumOnlineNum OBJECT-TYPE
                        SYNTAX Integer32
                        MAX-ACCESS read-only
                        STATUS current
                        DESCRIPTION
                            "This object indicates the number of users who go online from the board.
"
                        ::= { hwSlotConnectNumEntry 2 }
                        
                    hwSlotConnectNumMaxOnlineNum OBJECT-TYPE
                        SYNTAX Integer32
                        MAX-ACCESS read-only
                        STATUS current
                        DESCRIPTION
                            "This object indicates the maximum number of users who go online (including users who are going online and users who are going offline) from the board after the device is started.
"
                        ::= { hwSlotConnectNumEntry 3 }   
                    hwSlotConnectNumMaxOnlineAcctReadyNum OBJECT-TYPE
                       SYNTAX Integer32
                        MAX-ACCESS read-only
                        STATUS current
                        DESCRIPTION
                            "This object indicates the maximum number of users who go online from the board with correct accounting statistics after the device is started.
"
                        ::= { hwSlotConnectNumEntry 4 }  
                    hwSlotConnectNumIPv4OnlineNum OBJECT-TYPE
                       SYNTAX Integer32
                        MAX-ACCESS read-only
                        STATUS current
                        DESCRIPTION
                            "This object indicates the number of online IPv4 users on the board in this slot."
                        ::= { hwSlotConnectNumEntry 5 }
                    hwSlotConnectNumIPv6OnlineNum OBJECT-TYPE
                       SYNTAX Integer32
                        MAX-ACCESS read-only
                        STATUS current
                        DESCRIPTION
                            "This object indicates the number of online IPv4 users on the board in this slot."
                        ::= { hwSlotConnectNumEntry 6 }
                    hwSlotConnectNumDualOnlineNum OBJECT-TYPE
                       SYNTAX Integer32
                        MAX-ACCESS read-only
                        STATUS current
                        DESCRIPTION
                            "This object indicates the number of online dual-stack users on the board in this slot."
                        ::= { hwSlotConnectNumEntry 7 }
                    hwSlotConnectNumMaxOnlineNumDate OBJECT-TYPE
                       SYNTAX DisplayString (SIZE (1..32))
                        MAX-ACCESS read-only
                        STATUS current
                        DESCRIPTION
                            "This object indicates the date and time when the number of access users reaches the historic maximum number."
                        ::= { hwSlotConnectNumEntry 8 }
                    hwSlotConnectNumMaxOnlineAcctRNumDate OBJECT-TYPE
                       SYNTAX DisplayString (SIZE (1..32))
                        MAX-ACCESS read-only
                        STATUS current
                        DESCRIPTION
                            "This object indicates the date and time when the number of accounting-ready users reaches the historic maximum number."
                        ::= { hwSlotConnectNumEntry 9 }                           
            
            
            hwSlotCardConnectNumTable OBJECT-TYPE
            SYNTAX SEQUENCE OF HwSlotCardConnectNumEntry
            MAX-ACCESS not-accessible
            STATUS current 
            DESCRIPTION
                "This table is used to collect statistics about the number of users who go online from the subcard in the slot."
            ::= { hwAAAMibObjects 33 }
        
            hwSlotCardConnectNumEntry OBJECT-TYPE
                  SYNTAX HwSlotCardConnectNumEntry
                  MAX-ACCESS not-accessible
                  STATUS current
                  DESCRIPTION
                            "Slot Card Query Online Number Entry
                            "
                        INDEX { hwSlotCardConnectNumSlot, hwSlotCardConnectNumCard }
                        ::= { hwSlotCardConnectNumTable 1 }
        
                    HwSlotCardConnectNumEntry ::=
                        SEQUENCE { 
                            hwSlotCardConnectNumSlot
                                Integer32,
                            hwSlotCardConnectNumCard
                                Integer32,                              
                            hwSlotCardConnectNumOnlineNum
                                Integer32,
                            hwSlotCardConnectNumIPv4OnlineNum
                                Integer32,                  
                            hwSlotCardConnectNumIPv6OnlineNum
                                Integer32,
                            hwSlotCardConnectNumDualOnlineNum
                                Integer32,
                            hwSlotCardConnectNumNoAuthNum
                                Integer32,
                            hwSlotCardConnectNumPPPAuthNum
                                Integer32,
                            hwSlotCardConnectNum8021xAuthNum
                                Integer32,
                            hwSlotCardConnectNumWebAuthNum
                                Integer32,
                            hwSlotCardConnectNumBindAuthNum
                                Integer32,
                            hwSlotCardConnectNumFastAuthNum
                                Integer32,
                            hwSlotCardConnectNumWlanAuthNum
                                Integer32,
                            hwSlotCardConnectNumAdminAuthNum
                                Integer32,
                            hwSlotCardConnectNumTunnelAuthNum
                                Integer32,
                            hwSlotCardConnectNumMIPAuthNum
                                Integer32
                                                                              
                        }

                    hwSlotCardConnectNumSlot OBJECT-TYPE
                        SYNTAX Integer32 (0..2147483647)
                        MAX-ACCESS read-only
                        STATUS current
                        DESCRIPTION
                            "This object indicates the slot ID of the device.
"
                        ::= { hwSlotCardConnectNumEntry 1 }
                    
                    hwSlotCardConnectNumCard OBJECT-TYPE
                        SYNTAX Integer32 
                        MAX-ACCESS read-only
                        STATUS current
                        DESCRIPTION
                            "This object indicates the subcard ID of the device.
"
                        ::= { hwSlotCardConnectNumEntry 2 }

                    hwSlotCardConnectNumOnlineNum OBJECT-TYPE
                        SYNTAX Integer32
                        MAX-ACCESS read-only
                        STATUS current
                        DESCRIPTION
                            "This object indicates the number of online users on the slot.
"
                        ::= { hwSlotCardConnectNumEntry 3 }    
                        
                    hwSlotCardConnectNumIPv4OnlineNum OBJECT-TYPE
                        SYNTAX Integer32
                        MAX-ACCESS read-only
                        STATUS current
                        DESCRIPTION
                            "This object indicates the number of online IPv4 users on the slot.
"
                        ::= { hwSlotCardConnectNumEntry 4 }    
                    
                    hwSlotCardConnectNumIPv6OnlineNum OBJECT-TYPE
                        SYNTAX Integer32
                        MAX-ACCESS read-only
                        STATUS current
                        DESCRIPTION
                            "This object indicates the number of online IPv6 users on the slot.
"
                        ::= { hwSlotCardConnectNumEntry 5 }    
                    
                    hwSlotCardConnectNumDualOnlineNum OBJECT-TYPE
                        SYNTAX Integer32
                        MAX-ACCESS read-only
                        STATUS current
                        DESCRIPTION
                            "This object indicates the number of online dual-stack users on the slot.
"
                        ::= { hwSlotCardConnectNumEntry 6 }    
                    
                    hwSlotCardConnectNumNoAuthNum OBJECT-TYPE
                        SYNTAX Integer32
                        MAX-ACCESS read-only
                        STATUS current
                        DESCRIPTION
                            "This object indicates the number of online users that are not authenticated on the slot.
"
                        ::= { hwSlotCardConnectNumEntry 7 }
                        
                    hwSlotCardConnectNumPPPAuthNum OBJECT-TYPE
                        SYNTAX Integer32
                        MAX-ACCESS read-only
                        STATUS current
                        DESCRIPTION
                            "This object indicates the number of online users on the slot who have passed PPP authentication.
"
                        ::= { hwSlotCardConnectNumEntry 8 }
                        
                    hwSlotCardConnectNum8021xAuthNum OBJECT-TYPE
                        SYNTAX Integer32
                        MAX-ACCESS read-only
                        STATUS current
                        DESCRIPTION
                            "This object indicates the number of online users on the slot who have passed 802.1x authentication.
"
                        ::= { hwSlotCardConnectNumEntry 9 }
                    
                    hwSlotCardConnectNumWebAuthNum OBJECT-TYPE
                        SYNTAX Integer32
                        MAX-ACCESS read-only
                        STATUS current
                        DESCRIPTION
                            "This object indicates the number of online users on the slot who have passed web authentication.
"
                        ::= { hwSlotCardConnectNumEntry 10 }
                    
                    hwSlotCardConnectNumBindAuthNum OBJECT-TYPE
                        SYNTAX Integer32
                        MAX-ACCESS read-only
                        STATUS current
                        DESCRIPTION
                            "This object indicates the number of online users on the slot who have passed binding authentication.
"
                        ::= { hwSlotCardConnectNumEntry 11 }
                    
                    hwSlotCardConnectNumFastAuthNum OBJECT-TYPE
                        SYNTAX Integer32
                        MAX-ACCESS read-only
                        STATUS current
                        DESCRIPTION
                            "This object indicates the number of online users on the slot who have passed fast authentication.
"
                        ::= { hwSlotCardConnectNumEntry 12 }    
                    
                    hwSlotCardConnectNumWlanAuthNum OBJECT-TYPE
                        SYNTAX Integer32
                        MAX-ACCESS read-only
                        STATUS current
                        DESCRIPTION
                            "This object indicates the number of online users on the slot who have passed WLAN authentication.
"
                        ::= { hwSlotCardConnectNumEntry 13 }    
                    
                    hwSlotCardConnectNumAdminAuthNum OBJECT-TYPE
                        SYNTAX Integer32
                        MAX-ACCESS read-only
                        STATUS current
                        DESCRIPTION
                            "This object indicates the number of online users on the slot who have passed administrator authentication.
"
                        ::= { hwSlotCardConnectNumEntry 14 }    
                    
                    hwSlotCardConnectNumTunnelAuthNum OBJECT-TYPE
                        SYNTAX Integer32
                        MAX-ACCESS read-only
                        STATUS current
                        DESCRIPTION
                            "This object indicates the number of online users on the slot who have passed tunnel authentication.
"
                        ::= { hwSlotCardConnectNumEntry 15 }    
                    
                    hwSlotCardConnectNumMIPAuthNum OBJECT-TYPE
                        SYNTAX Integer32
                        MAX-ACCESS read-only
                        STATUS current
                        DESCRIPTION
                            "This object indicates the number of online users on the slot who have passed MIP authentication.
"
                        ::= { hwSlotCardConnectNumEntry 16 }    
                                       
            
                          
              hwOfflineReasonStatTable OBJECT-TYPE
            SYNTAX SEQUENCE OF HwOfflineReasonStatEntry
            MAX-ACCESS not-accessible
            STATUS current         
             DESCRIPTION
                "hwOfflineReasonStatTable is used to collect statistics on the offline reasons of users."
           
            ::= { hwAAAMibObjects 34 }
        
            hwOfflineReasonStatEntry OBJECT-TYPE
                  SYNTAX HwOfflineReasonStatEntry
                  MAX-ACCESS not-accessible
                  STATUS current
                  DESCRIPTION
                            "Offline and online fail reason statistic  Entry
                            
                            "
                        INDEX { hwOfflineReason }
                        ::= {  hwOfflineReasonStatTable 1 }
        
                    HwOfflineReasonStatEntry ::=
                        SEQUENCE { 
                            hwOfflineReason
                             Integer32,
                            hwOfflineReasonStatistic
                                Integer32,
                            hwOnlineFailReasonStatistic
                                Integer32       
                        }

                    hwOfflineReason OBJECT-TYPE
                        SYNTAX Integer32 (1..65535)
                        MAX-ACCESS read-only
                        STATUS current
                        DESCRIPTION
                            "This object indicates statistics about the causes of user online failures and user offline. Possible causes are that users' proactive going offline, session timeout, and idle cut.
                             "
                        ::= { hwOfflineReasonStatEntry 1 }

                  
                     hwOfflineReasonStatistic OBJECT-TYPE
                        SYNTAX Integer32 
                        MAX-ACCESS read-only
                        STATUS current
                        DESCRIPTION
                            "This object indicates statistics about the causes of user offline.
                            "
                        ::= {hwOfflineReasonStatEntry 2 }
            
            
         hwOnlineFailReasonStatistic OBJECT-TYPE
            SYNTAX Integer32 
            MAX-ACCESS read-only
            STATUS current
            DESCRIPTION
                "This object indicates statistics about the causes of user online failures."
            ::= { hwOfflineReasonStatEntry 3 }
                                  
            hwMulticastListTable OBJECT-TYPE
            SYNTAX SEQUENCE OF HwMulticastListEntry
            MAX-ACCESS not-accessible
            STATUS current  
            DESCRIPTION
                "The multicast list table
                                 "
            ::= { hwAAAMibObjects 35 }
        
            hwMulticastListEntry OBJECT-TYPE
                  SYNTAX HwMulticastListEntry
                  MAX-ACCESS not-accessible
                  STATUS current
                  DESCRIPTION
                            "multicast list
                            
                            "
                        INDEX { hwMulticastListIndex }
                        ::= {  hwMulticastListTable 1 }
        
                    HwMulticastListEntry ::=
                        SEQUENCE { 
                            hwMulticastListIndex
                                Integer32,
                            hwMulticastListName
                                DisplayString,
                            hwMulticastListSourceIp
                                IpAddress,
                            hwMulticastListSourceIpMask
                                Integer32,
                            hwMulticastListGroupIp
                                IpAddress,
                            hwMulticastListGroupIpMask
                                Integer32,
                            hwMulticastListVpnInstance
                                DisplayString,
                            hwMulticastListRowStatus
                                RowStatus    
                        }

                  hwMulticastListIndex OBJECT-TYPE
                        SYNTAX Integer32 (0..8191)
                        MAX-ACCESS read-only
                        STATUS current
                        DESCRIPTION
                        "Multicast list index
                                 "
                    ::= {hwMulticastListEntry 1 }
            
                 hwMulticastListName OBJECT-TYPE
                        SYNTAX DisplayString (SIZE (1..32))
                        MAX-ACCESS read-create
                        STATUS current
                        DESCRIPTION
                            "Multicast list name
                
                             "
                        ::= { hwMulticastListEntry 2 }            
            
                 hwMulticastListSourceIp OBJECT-TYPE
                        SYNTAX IpAddress 
                        MAX-ACCESS read-create
                        STATUS current
                        DESCRIPTION
                        "Multicast list source IP address
                         
                         "
                ::= { hwMulticastListEntry 3 }
            
                 hwMulticastListSourceIpMask OBJECT-TYPE
                        SYNTAX Integer32 (0..32) 
                        MAX-ACCESS read-create
                        STATUS current
                        DESCRIPTION
                        "Multicast list source IP mask
                        
                        "
                ::= { hwMulticastListEntry 4 }        

                 hwMulticastListGroupIp OBJECT-TYPE
                        SYNTAX IpAddress 
                        MAX-ACCESS read-create
                        STATUS current
                        DESCRIPTION
                        "Multicast list group IP address
                                
                        "
                ::= { hwMulticastListEntry 5 }   
                                     
                 hwMulticastListGroupIpMask OBJECT-TYPE
                    SYNTAX Integer32 (0..32) 
                    MAX-ACCESS read-create
                    STATUS current
                    DESCRIPTION
                        "Multicast list group IP mask
                                 
                         "
                ::= { hwMulticastListEntry 6 }
  
                 hwMulticastListVpnInstance OBJECT-TYPE
                    SYNTAX DisplayString (SIZE (1..31)) 
                    MAX-ACCESS read-create
                    STATUS current
                    DESCRIPTION
                        "Multicast list VPN instance
                                 
                         "
                ::= { hwMulticastListEntry 7 }
            
                 hwMulticastListRowStatus OBJECT-TYPE
                    SYNTAX RowStatus
                    MAX-ACCESS read-create
                    STATUS current
                    DESCRIPTION
                        "row admin status,only Add or Delete
                
                         "
                ::= { hwMulticastListEntry 8 }    
            
            hwMulticastProfileTable OBJECT-TYPE
                SYNTAX SEQUENCE OF HwMulticastProfileEntry
                MAX-ACCESS not-accessible
                STATUS current  
            DESCRIPTION
                "The multicast profile table
                                 "
                ::= { hwAAAMibObjects 36 }
        
            hwMulticastProfileEntry OBJECT-TYPE
                  SYNTAX HwMulticastProfileEntry
                  MAX-ACCESS not-accessible
                  STATUS current
                  DESCRIPTION
                            "multicast profile
                            
                            "
                        INDEX { hwMulticastProfileIndex }
                        ::= {  hwMulticastProfileTable 1 }
        
                    HwMulticastProfileEntry ::=
                        SEQUENCE { 
                            hwMulticastProfileIndex
                                Integer32,
                            hwMulticastProfileName
                                DisplayString,
                            hwMulticastProfileRowStatus
                                RowStatus    
                        }

                    hwMulticastProfileIndex OBJECT-TYPE
                        SYNTAX Integer32 (0..1023)
                        MAX-ACCESS read-only
                        STATUS current
                        DESCRIPTION
                            "Multicast profile index
                
                             "
                        ::= { hwMulticastProfileEntry 1 }
                        
                    hwMulticastProfileName OBJECT-TYPE
                        SYNTAX DisplayString (SIZE (1..32))
                        MAX-ACCESS read-create
                        STATUS current
                        DESCRIPTION
                            "Multicast profile name
                
                             "
                        ::= { hwMulticastProfileEntry 2 }
                        
                     hwMulticastProfileRowStatus OBJECT-TYPE
                        SYNTAX RowStatus
                        MAX-ACCESS read-create
                        STATUS current
                        DESCRIPTION
                            "row admin status, only Add or Delete
                
                             "
                        ::= { hwMulticastProfileEntry 3 }
            
        hwMulticastProfileExtTable OBJECT-TYPE
                SYNTAX SEQUENCE OF HwMulticastProfileExtEntry
                MAX-ACCESS not-accessible
                STATUS current  
            DESCRIPTION
                "The multicast profile ext table"
                ::= { hwAAAMibObjects 37 }
        
            hwMulticastProfileExtEntry OBJECT-TYPE
                  SYNTAX HwMulticastProfileExtEntry
                  MAX-ACCESS not-accessible
                  STATUS current
                  DESCRIPTION
                            "multicast profile extern table
                            
                            "
                        INDEX { hwMulticastProfileIndex, hwMulticastListIndex }
                        ::= {  hwMulticastProfileExtTable 1 }
        
                    HwMulticastProfileExtEntry ::=
                        SEQUENCE { 
                            hwMulticastListBindName
                                DisplayString,
                            hwMulticastProfileExtRowStatus
                                RowStatus    
                        }
                        
                    hwMulticastListBindName OBJECT-TYPE
                        SYNTAX DisplayString (SIZE (1..32))
                        MAX-ACCESS read-create
                        STATUS current
                        DESCRIPTION
                            "Multicast list name
                
                             "
                        ::= { hwMulticastProfileExtEntry 1 }
                        
                     hwMulticastProfileExtRowStatus OBJECT-TYPE
                        SYNTAX RowStatus
                        MAX-ACCESS read-create
                        STATUS current
                        DESCRIPTION
                            "row admin status,only Add or Del
                
                             "
                        ::= { hwMulticastProfileExtEntry 2 }    
        
        
            hwServiceSchemeTable OBJECT-TYPE
                SYNTAX SEQUENCE OF HwServiceSchemeEntry
                MAX-ACCESS not-accessible
                STATUS current    
            DESCRIPTION
                "The  table of this service scheme "
                
                ::= { hwAAAMibObjects 38 }
        
            hwServiceSchemeEntry OBJECT-TYPE
                  SYNTAX HwServiceSchemeEntry
                  MAX-ACCESS not-accessible
                  STATUS current
                  DESCRIPTION
                            "Service scheme entry.                          
                            "
                        INDEX { hwServiceSchemeName }
                        ::= {  hwServiceSchemeTable 1 }
        
                    HwServiceSchemeEntry ::=
                        SEQUENCE { 
                            hwServiceSchemeName
                                DisplayString,
                            hwServiceSchemeNextHopIp
                                 IpAddress,
                            hwServiceSchemeUserPriority
                                 Integer32,
                            hwServiceSchemeIdleCutTime
                                 Integer32,
                            hwServiceSchemeIdleCutFlow  
                                 Unsigned32, 
                            hwServiceSchemeDnsFirst
                                 IpAddress, 
                            hwServiceSchemeDnsSecond
                                 IpAddress,     
                            hwSrvSchemeAdminUserPriority
                                 Integer32,                            
                            hwSrvSchemeIpPoolOneName
                                 DisplayString,
                            hwSrvSchemeIpPoolTwoName
                                 DisplayString,
                            hwSrvSchemeIpPoolThreeName
                                 DisplayString,
                            hwServiceSchemeRowStatus
                                 RowStatus,
                            hwServiceSchemeIdleCutType
                                 INTEGER,
                            hwServiceSchemeIdleCutFlowValue  
                                Unsigned32,
                            hwLocalAuthorize
                            	DisplayString,
                            hwRemoteAuthorize
				DisplayString,
                            hwServiceSchemeRedirectACL
                            	DisplayString,
	        hwServiceSchemePriority   
                           	    Integer32,
                            hwServiceSchemeRedirectIPv6ACL
                                           DisplayString  
                        }
                        
                    hwServiceSchemeName OBJECT-TYPE
                        SYNTAX DisplayString (SIZE (1..32))
                        MAX-ACCESS read-only
                        STATUS current
                        DESCRIPTION
                            "Service scheme name."
                        ::= { hwServiceSchemeEntry 1 }
    
                    hwServiceSchemeNextHopIp OBJECT-TYPE
                       SYNTAX IpAddress
                       MAX-ACCESS read-write
                       STATUS current
                       DESCRIPTION
                           "The next hop of source IP address route."
                       ::= { hwServiceSchemeEntry 11 }
                  
                   hwServiceSchemeUserPriority OBJECT-TYPE
                      SYNTAX Integer32 (0..255)
                      MAX-ACCESS read-write
                      STATUS current
                      DESCRIPTION
                          "The priority of up user."
                         DEFVAL { 0 }
                       ::= { hwServiceSchemeEntry 12 }
    
                   hwServiceSchemeIdleCutTime OBJECT-TYPE                      
                      SYNTAX Integer32 (0..1440)                          
                      MAX-ACCESS read-write                           
                      STATUS current                           
                      DESCRIPTION                           
                          "The cut time of idle interval."                 
                      ::= { hwServiceSchemeEntry 13 }                           
                                                
                  hwServiceSchemeIdleCutFlow OBJECT-TYPE                      
                     SYNTAX Unsigned32(0..4294967295)                      
                     MAX-ACCESS read-write                           
                     STATUS current                           
                     DESCRIPTION                           
                     "The flow of idle interval, in Kbytes."        
                     ::= { hwServiceSchemeEntry 14 }
                   
                  hwServiceSchemeDnsFirst OBJECT-TYPE
                     SYNTAX IpAddress
                     MAX-ACCESS read-write
                     STATUS current
                     DESCRIPTION
                     "The first DNS server."
                     ::= { hwServiceSchemeEntry 15 }
                  
                  hwServiceSchemeDnsSecond OBJECT-TYPE
                     SYNTAX IpAddress
                     MAX-ACCESS read-write
                     STATUS current
                     DESCRIPTION
                     "The second DNS server."
                     ::= { hwServiceSchemeEntry 16 }
                  
                  hwSrvSchemeAdminUserPriority OBJECT-TYPE
                    SYNTAX Integer32 (-1..15)
                    MAX-ACCESS read-write
                    STATUS current
                    DESCRIPTION
                    "Priority of admin user."
                     ::= { hwServiceSchemeEntry 17 }
                 
                 hwSrvSchemeIpPoolOneName OBJECT-TYPE
                    SYNTAX DisplayString (SIZE(0..255))
                    MAX-ACCESS read-write
                    STATUS current
                    DESCRIPTION
                    "The IP pool name."
                    ::= { hwServiceSchemeEntry 18 }
                 
                hwSrvSchemeIpPoolTwoName OBJECT-TYPE
                  SYNTAX DisplayString (SIZE(0..255))
                  MAX-ACCESS read-write
                  STATUS current
                  DESCRIPTION
                  "The IP pool name."
                  ::= { hwServiceSchemeEntry 19 }

               hwSrvSchemeIpPoolThreeName OBJECT-TYPE
                 SYNTAX DisplayString (SIZE(0..255))
                 MAX-ACCESS read-write
                 STATUS current
                 DESCRIPTION
                "The IP pool name."
                ::= { hwServiceSchemeEntry 20 }
                    
               hwServiceSchemeRowStatus OBJECT-TYPE
                 SYNTAX RowStatus
                 MAX-ACCESS read-create
                 STATUS current
                 DESCRIPTION
                   "The row administration status, only supporting add or delete."
                 ::= { hwServiceSchemeEntry 51 }

              hwServiceSchemeIdleCutType OBJECT-TYPE 
				SYNTAX INTEGER
				{
                      inbound(1),
                      outbound(2),
                      both(3),
					  none(4)
					}
             	MAX-ACCESS read-write
             	STATUS current
             	DESCRIPTION
             	"The type of idle-cut, default type is 4."
            	::= { hwServiceSchemeEntry 52 }

                hwServiceSchemeIdleCutFlowValue OBJECT-TYPE                      
                     SYNTAX Unsigned32(1..4294967295)                       
                     MAX-ACCESS read-write                           
                     STATUS current                           
                     DESCRIPTION                           
                     "The flow of idle , in Kbytes."        
                     ::= { hwServiceSchemeEntry 53 }  

          	  hwLocalAuthorize OBJECT-TYPE 
                     SYNTAX DisplayString (SIZE (1..64))				
             	MAX-ACCESS read-write
             	STATUS current
             	DESCRIPTION
             	"LocalAuthorize type:ucl-group vlan car acl priority."
            	::= { hwServiceSchemeEntry 54 }
                     
                     
     hwRemoteAuthorize OBJECT-TYPE 
                     SYNTAX DisplayString (SIZE (1..64))			
             	MAX-ACCESS read-write
             	STATUS current
             	DESCRIPTION
             	"RemoteAuthorize type:ucl-group car acl priority."
            	::= { hwServiceSchemeEntry 55 }              
                         
     
      hwServiceSchemeRedirectACL OBJECT-TYPE 
                SYNTAX DisplayString (SIZE (1..64))		
        	MAX-ACCESS read-write
        	STATUS current
        	DESCRIPTION
        	"RedirectAcl : HW Redirect Acl Value."
       		::= { hwServiceSchemeEntry 56 }    

       hwServiceSchemePriority OBJECT-TYPE
             SYNTAX Integer32(0..1)
             MAX-ACCESS read-write
             STATUS current
             DESCRIPTION
                  "ServiceSchemePriority."
             ::= { hwServiceSchemeEntry 57 }
	     	 
       hwServiceSchemeRedirectIPv6ACL OBJECT-TYPE 
            SYNTAX DisplayString (SIZE (1..64))		
        	MAX-ACCESS read-write
        	STATUS current
        	DESCRIPTION
        	"RedirectV6Acl : HW Redirect V6 Acl Value."
             ::= { hwServiceSchemeEntry 58 }

        hwDhcpOpt121RouteTable OBJECT-TYPE
            SYNTAX SEQUENCE OF HwDhcpOpt121RouteEntry
            MAX-ACCESS not-accessible
            STATUS current
            DESCRIPTION
                "This table is used to query information about DHCP Option 121 configured for all domains."
            ::= { hwAAAMibObjects 39 }
            
        hwDhcpOpt121RouteEntry OBJECT-TYPE
            SYNTAX HwDhcpOpt121RouteEntry
            MAX-ACCESS not-accessible
            STATUS current
            DESCRIPTION
                "The dhcp option121 routing entry."
            INDEX { hwDomainName, hwDhcpOpt121RouteDestIp, hwDhcpOpt121RouteMask, hwDhcpOpt121RouteNextHop }
            ::= { hwDhcpOpt121RouteTable 1 }
            
        HwDhcpOpt121RouteEntry ::=
            SEQUENCE {
                hwDhcpOpt121RouteDestIp     IpAddress,
                hwDhcpOpt121RouteMask       Integer32,
                hwDhcpOpt121RouteNextHop    IpAddress,
                hwDhcpOpt121RouteRowStatus  RowStatus
             }
         
            
        hwDhcpOpt121RouteDestIp OBJECT-TYPE
            SYNTAX IpAddress
            MAX-ACCESS read-only
            STATUS current
            DESCRIPTION
                "This object indicates the destination address."
            ::= { hwDhcpOpt121RouteEntry 1 }
            
        hwDhcpOpt121RouteMask OBJECT-TYPE
            SYNTAX Integer32 (0..32)
            MAX-ACCESS read-only
            STATUS current
            DESCRIPTION
                "This object indicates the mask."
            ::= { hwDhcpOpt121RouteEntry 2 }    
            
        hwDhcpOpt121RouteNextHop OBJECT-TYPE
            SYNTAX IpAddress
            MAX-ACCESS read-only
            STATUS current
            DESCRIPTION
                "This object indicates the gateway address."
            ::= { hwDhcpOpt121RouteEntry 3 }
            
        hwDhcpOpt121RouteRowStatus OBJECT-TYPE
            SYNTAX RowStatus
            MAX-ACCESS read-create
            STATUS current
            DESCRIPTION
                "This object indicates the activation status of DHCP Option 21 configured in the domain."
            ::= { hwDhcpOpt121RouteEntry 4 }
                                            
        --  ============== begin : added by w00127306 for V6R3C01 ==============   
        --  ============== hwAccessDelayPerSlotTable ==============                                         
        hwAccessDelayPerSlotTable OBJECT-TYPE
            SYNTAX SEQUENCE OF HwAccessDelayPerSlotEntry
            MAX-ACCESS not-accessible
            STATUS current
            DESCRIPTION
                "hwAccessDelayPerSlotTable"
            ::= { hwAAAMibObjects 40 }     
            
        hwAccessDelayPerSlotEntry OBJECT-TYPE
            SYNTAX HwAccessDelayPerSlotEntry
            MAX-ACCESS not-accessible
            STATUS current
            DESCRIPTION
                "HwAccessDelayPerSlotEntry"
            INDEX { hwAccessDelayPerSlotSlot }
            ::= { hwAccessDelayPerSlotTable 1 }
                                                 
        HwAccessDelayPerSlotEntry ::=
            SEQUENCE {
                hwAccessDelayPerSlotSlot               Integer32,
                hwAccessDelayPerSlotTransitionStep     Integer32,
                hwAccessDelayPerSlotMaxTime            Integer32,
                hwAccessDelayPerSlotMinTime            Integer32,
                hwAccessDelayPerSlotRowStatus          RowStatus
             }

        hwAccessDelayPerSlotSlot OBJECT-TYPE
            SYNTAX Integer32 (1..16)
            MAX-ACCESS read-only
            STATUS current
            DESCRIPTION
                "hwAccessDelayPerSlotSlot"
            ::= { hwAccessDelayPerSlotEntry 1 }    
            
        hwAccessDelayPerSlotTransitionStep OBJECT-TYPE
            SYNTAX Integer32 (1..262144)
            MAX-ACCESS read-create
            STATUS current
            DESCRIPTION
                "hwAccessDelayPerSlotTransitionStep"
            ::= { hwAccessDelayPerSlotEntry 2 }   
            
        hwAccessDelayPerSlotMaxTime OBJECT-TYPE
            SYNTAX Integer32 (0..2550)
            MAX-ACCESS read-create
            STATUS current
            DESCRIPTION
                "hwAccessDelayPerSlotMaxTime"
            ::= { hwAccessDelayPerSlotEntry 3 }            
                                                    
        hwAccessDelayPerSlotMinTime OBJECT-TYPE
            SYNTAX Integer32 (0..2550)
            MAX-ACCESS read-create
            STATUS current
            DESCRIPTION
                "hwAccessDelayPerSlotMinTime"
            ::= { hwAccessDelayPerSlotEntry 4 }            
                                                  
        hwAccessDelayPerSlotRowStatus OBJECT-TYPE
            SYNTAX RowStatus
            MAX-ACCESS read-create
            STATUS current
            DESCRIPTION
                "hwDhcpOpt121RouteRowStatus"
            ::= { hwAccessDelayPerSlotEntry 5 }  
            
        --  ============== hwVpnAccessUserStatTable ============== 
        hwVpnAccessUserStatTable OBJECT-TYPE
            SYNTAX SEQUENCE OF HwVpnAccessUserStatEntry
            MAX-ACCESS not-accessible
            STATUS current
            DESCRIPTION
                "This table displays statistics about various types of users that access the Internet using a VPN."
            ::= { hwAAAMibObjects 41 }     
            
        hwVpnAccessUserStatEntry OBJECT-TYPE
            SYNTAX HwVpnAccessUserStatEntry
            MAX-ACCESS not-accessible
            STATUS current
            DESCRIPTION
                "HwAccessDelayPerSlotEntry"
            INDEX { hwUserType, hwVpnAccessUserStatVpnName }
            ::= { hwVpnAccessUserStatTable 1 }
                                                 
        HwVpnAccessUserStatEntry ::=
            SEQUENCE {
                hwUserType                    INTEGER,
                hwVpnAccessUserStatVpnName    DisplayString,
                hwVpnAccessUserStatUserStat   Integer32
             }

        hwUserType OBJECT-TYPE
            SYNTAX INTEGER
                {
                pppoe(1),
                pppoa(2),
                dhcp(3),
                lns(4),
                lac(5),
                ipv4(6),
                ipv6(7),
                dualStack(8),
                all(9)
                }
            MAX-ACCESS read-only
            STATUS current
            DESCRIPTION
                "This object indicates a user type. The available options are pppoe(1), pppoa(2), dhcp(3), lns(4), lac(5), ipv4(6), ipv6(7), dual-stack(8), and all(9)."
            ::= { hwVpnAccessUserStatEntry 1 }

                      
        hwVpnAccessUserStatVpnName OBJECT-TYPE
            SYNTAX DisplayString (SIZE (1..32))
            MAX-ACCESS read-only
            STATUS current
            DESCRIPTION
                "This object indicates the VPN name.
"
            ::= { hwVpnAccessUserStatEntry 2 }
                                                          
        hwVpnAccessUserStatUserStat OBJECT-TYPE
            SYNTAX Integer32 (0..2147483647)
            MAX-ACCESS read-only
            STATUS current
            DESCRIPTION
                "This object indicates the number of users of a specified type in the VPN.
"
            ::= { hwVpnAccessUserStatEntry 3 }   

        --  ============== hwInterfaceAccessUserStatTable ==============  
        hwInterfaceAccessUserStatTable OBJECT-TYPE
            SYNTAX SEQUENCE OF HwInterfaceAccessUserStatEntry
            MAX-ACCESS not-accessible
            STATUS current
            DESCRIPTION
                "This table displays statistics about various types of users that access from a specified interface."
            ::= { hwAAAMibObjects 42 }     
            
        hwInterfaceAccessUserStatEntry OBJECT-TYPE
            SYNTAX HwInterfaceAccessUserStatEntry
            MAX-ACCESS not-accessible
            STATUS current
            DESCRIPTION
                "HwInterfaceAccessUserStatEntry"
            INDEX { hwUserType, hwInterfaceAccessUserStatInterfaceIndex }
            ::= { hwInterfaceAccessUserStatTable 1 }
                                                 
        HwInterfaceAccessUserStatEntry ::=
            SEQUENCE {
                hwInterfaceAccessUserStatInterfaceIndex    Unsigned32,
                hwInterfaceAccessUserStatUserStat          Integer32
             }
                      
        hwInterfaceAccessUserStatInterfaceIndex OBJECT-TYPE
            SYNTAX Unsigned32 (0..4294967295)
            MAX-ACCESS read-only
            STATUS current
            DESCRIPTION
                "This object indicates the interface index.
"
            ::= { hwInterfaceAccessUserStatEntry 1 }
                                                          
        hwInterfaceAccessUserStatUserStat OBJECT-TYPE
            SYNTAX Integer32 (0..2147483647)
            MAX-ACCESS read-only
            STATUS current
            DESCRIPTION
                "This object indicates the number of users of a specified type on the interface.
"
            ::= { hwInterfaceAccessUserStatEntry 2 }                                                                    

        --  ============== hwDomainAccessUserStatTable ============== 
        hwDomainAccessUserStatTable OBJECT-TYPE
            SYNTAX SEQUENCE OF HwDomainAccessUserStatEntry
            MAX-ACCESS not-accessible
            STATUS current
            DESCRIPTION
                "This table displays statistics about various types of access users in a specified domain."
            ::= { hwAAAMibObjects 43 }     
            
        hwDomainAccessUserStatEntry OBJECT-TYPE
            SYNTAX HwDomainAccessUserStatEntry
            MAX-ACCESS not-accessible
            STATUS current
            DESCRIPTION
                "HwDomainAccessUserStatEntry"
            INDEX { hwUserType, hwDomainName  }
            ::= { hwDomainAccessUserStatTable 1 }
                                                 
        HwDomainAccessUserStatEntry ::=
            SEQUENCE {
                hwDomainAccessUserStatUserStat                Integer32
             }
                      
        hwDomainAccessUserStatUserStat OBJECT-TYPE
            SYNTAX Integer32 (0..2147483647)
            MAX-ACCESS read-only
            STATUS current
            DESCRIPTION
                "This object indicates the number of users of a specified type in the domain.
"
            ::= { hwDomainAccessUserStatEntry 1 }         

        --  ============== hwSlotAccessUserStatTable ==============  
        hwSlotAccessUserStatTable OBJECT-TYPE
            SYNTAX SEQUENCE OF HwSlotAccessUserStatEntry
            MAX-ACCESS not-accessible
            STATUS current
            DESCRIPTION
                "This table displays statistics about various types of users that access from a specified board."
            ::= { hwAAAMibObjects 44 }     
            
        hwSlotAccessUserStatEntry OBJECT-TYPE
            SYNTAX HwSlotAccessUserStatEntry
            MAX-ACCESS not-accessible
            STATUS current
            DESCRIPTION
                "HwSlotAccessUserStatEntry"
            INDEX { hwUserType, hwSlotAccessUserStatSlot }
            ::= { hwSlotAccessUserStatTable 1 }
                                                 
        HwSlotAccessUserStatEntry ::=
            SEQUENCE {
                hwSlotAccessUserStatSlot                   Integer32,
                hwSlotAccessUserStatUserStat               Integer32
             }
                      
        hwSlotAccessUserStatSlot OBJECT-TYPE
            SYNTAX Integer32 (0..2147483647)
            MAX-ACCESS read-only
            STATUS current
            DESCRIPTION
                "This object indicates the board number.
"
            ::= { hwSlotAccessUserStatEntry 1 }
                                                          
        hwSlotAccessUserStatUserStat OBJECT-TYPE
            SYNTAX Integer32 (0..2147483647)
            MAX-ACCESS read-only
            STATUS current
            DESCRIPTION
                "This object indicates the number of users of a specified type on the board.
"
            ::= { hwSlotAccessUserStatEntry 2 }         
                                                           
        --  ============== end : added by w00127306 for V6R3C01 ==============                          
        hwDomainIncludePoolGroupTable OBJECT-TYPE
            SYNTAX SEQUENCE OF HwDomainIncludePoolGroupEntry
            MAX-ACCESS not-accessible
            STATUS current
            DESCRIPTION
                "Configure a pool group in the specified domain."
            ::= { hwAAAMibObjects 45 }
            
        hwDomainIncludePoolGroupEntry OBJECT-TYPE
            SYNTAX HwDomainIncludePoolGroupEntry
            MAX-ACCESS not-accessible
            STATUS current
            DESCRIPTION
                "Configure a pool group in the specified domain."
            INDEX { hwDomainName, hwDomainIncludeIPPoolGroupName }
            ::= { hwDomainIncludePoolGroupTable 1 }
            
        HwDomainIncludePoolGroupEntry ::=
            SEQUENCE {
                hwDomainIncludeIPPoolGroupName       DisplayString,
                hwDomainIncludeIPPoolGroupRowStates  RowStatus
             }
                    
        hwDomainIncludeIPPoolGroupName OBJECT-TYPE
            SYNTAX DisplayString (SIZE(1..128))
            MAX-ACCESS read-only
            STATUS current
            DESCRIPTION
                "The pool group name."
            ::= { hwDomainIncludePoolGroupEntry 1 }
            
        hwDomainIncludeIPPoolGroupRowStates OBJECT-TYPE
                 SYNTAX RowStatus
                 MAX-ACCESS read-create
                 STATUS current
                 DESCRIPTION
                   "The row administration status, only supporting add or delete."
                 ::= { hwDomainIncludePoolGroupEntry 2 } 
                 
        hwDomainIPPoolMoveToTable OBJECT-TYPE
            SYNTAX SEQUENCE OF HwDomainIPPoolMoveToEntry
            MAX-ACCESS not-accessible
            STATUS current
            DESCRIPTION
                "Change the priority of pool group in the specified domain."
            ::= { hwAAAMibObjects 46 }
            
        hwDomainIPPoolMoveToEntry OBJECT-TYPE
            SYNTAX HwDomainIPPoolMoveToEntry
            MAX-ACCESS not-accessible
            STATUS current
            DESCRIPTION
                "Change the priority of pool group in the specified domain."
            INDEX { hwDomainName, hwDomainIncludeIPPoolName }
            ::= { hwDomainIPPoolMoveToTable 1 }
            
        HwDomainIPPoolMoveToEntry ::=
            SEQUENCE {
                hwDomainIncludeIPPoolName       DisplayString,
                hwDomainIncludeIPPoolMoveto     Integer32
             }
                    
        hwDomainIncludeIPPoolName OBJECT-TYPE
            SYNTAX DisplayString (SIZE(1..128))
            MAX-ACCESS read-only
            STATUS current
            DESCRIPTION
                "The pool group name."
            ::= { hwDomainIPPoolMoveToEntry 1 }
            
        hwDomainIncludeIPPoolMoveto OBJECT-TYPE
                 SYNTAX Integer32 (0..1024)
                 MAX-ACCESS read-write
                 STATUS current
                 DESCRIPTION
                   "The position of the pool group."
                 ::= { hwDomainIPPoolMoveToEntry 2 }
                 
     
        hwDomainExt2Table OBJECT-TYPE
            SYNTAX SEQUENCE OF HwDomainExt2Entry
            MAX-ACCESS not-accessible
            STATUS current
            DESCRIPTION
                "The domain extend table."
            ::= { hwAAAMibObjects 47 }

        hwDomainExt2Entry OBJECT-TYPE
            SYNTAX HwDomainExt2Entry
            MAX-ACCESS not-accessible
            STATUS current
            DESCRIPTION
                "The domain extend entry."
            INDEX { hwDomainName }
            ::= { hwDomainExt2Table 1 }

        HwDomainExt2Entry ::=
            SEQUENCE {
                hwRedKeyUserMac
                    DisplayString,
                hwIfUserMacSimple
                    TruthValue,
                hwPoolLowerLimitWarningThreshold
                    Integer32,
                hwIPv6PoolLowerLimitWarningThreshold
                    Integer32,
                hwAAADomainInboundQoSProfile
                    DisplayString, 
                hwAAADomainOutboundQoSProfile    
                    DisplayString,
                hwAAADomainInboundVPNInstance
                    DisplayString
                 }
                 
        hwRedKeyUserMac OBJECT-TYPE
            SYNTAX DisplayString (SIZE(1..32))
            MAX-ACCESS read-write
            STATUS current
            DESCRIPTION
                "Configure Web Server Redirect Key UserMacAdress."     
            ::= { hwDomainExt2Entry 1}   
            
        hwIfUserMacSimple OBJECT-TYPE
            SYNTAX TruthValue
            MAX-ACCESS read-write
            STATUS current
            DESCRIPTION
                "if encrypt Web Server Redirect Key UserMacAdress "
            DEFVAL { true }
            ::= { hwDomainExt2Entry 2 }            

        hwPoolLowerLimitWarningThreshold OBJECT-TYPE
            SYNTAX Integer32(0..99|255)
            MAX-ACCESS read-only
            STATUS current
            DESCRIPTION
                "The IP lower limit warning threshold."
            DEFVAL { 255 }
            ::= { hwDomainExt2Entry 3 }
     
        hwIPv6PoolLowerLimitWarningThreshold OBJECT-TYPE
            SYNTAX Integer32(0..99|255)
            MAX-ACCESS read-only
            STATUS current
            DESCRIPTION
                "The IPv6 lower limit warning threshold."
            DEFVAL { 255 }
            ::= { hwDomainExt2Entry 4 } 

         hwAAADomainInboundQoSProfile OBJECT-TYPE
            SYNTAX DisplayString (SIZE (1..64))
            MAX-ACCESS read-write
            STATUS current
            DESCRIPTION
                "Configure inbound QOS Profile
                 "
            ::= { hwDomainExt2Entry 5}
            
        hwAAADomainOutboundQoSProfile OBJECT-TYPE
            SYNTAX DisplayString (SIZE (1..64))
            MAX-ACCESS read-write
            STATUS current
            DESCRIPTION
                "Configure outbound QOS Profile
                 "
            ::= { hwDomainExt2Entry 6}
	
            hwAAADomainInboundVPNInstance OBJECT-TYPE
            SYNTAX DisplayString (SIZE (1..31))
            MAX-ACCESS read-write
            STATUS current
            DESCRIPTION
                "The domain inbound VPN instance name
                "
            ::= { hwDomainExt2Entry 7}

        hwAAAOnlineFailRecordTable OBJECT-TYPE
            SYNTAX SEQUENCE OF HwAAAOnlineFailRecordEntry
            MAX-ACCESS not-accessible
            STATUS current
            DESCRIPTION
                "This table is used to query the causes of user online failures."
            ::= { hwAAAMibObjects 48 }

        hwAAAOnlineFailRecordEntry OBJECT-TYPE
            SYNTAX HwAAAOnlineFailRecordEntry
            MAX-ACCESS not-accessible
            STATUS current
            DESCRIPTION
                "The online fail record entry."
            INDEX { hwAAAOnlineFailIndex }
            ::= { hwAAAOnlineFailRecordTable 1 }

        HwAAAOnlineFailRecordEntry ::=
            SEQUENCE {
                hwAAAOnlineFailIndex
                    Integer32,
                hwUserName
                    DisplayString,
                hwUserDomainName
                    DisplayString,
                hwUserMAC
                    MacAddress,
                hwUserAccessType
                    DisplayString,
                hwUserInterface
                    DisplayString,
                hwUserAccessPVC
                    DisplayString,
                hwUserAccessPeVlan
                    Integer32,
                hwUserAccessCeVlan
                    Integer32,
                hwUserIPAddress
                    IpAddress,
                hwUserIPv6NDRAPrefix
                    Ipv6AddressPrefix, 
                hwUserIPv6Address
                    Ipv6Address,
                hwUserIPv6PDPrefix
                    Ipv6AddressPrefix,
                hwUserIPv6PDPrefixLength
                    Integer32,   
                hwUserID
                    Integer32,
                hwUserAuthenState
                    INTEGER,
                hwUserAcctState
                    INTEGER,
                hwUserAuthorState
                    INTEGER,
                hwUserLoginTime
                    DateAndTime,
                hwOnlineFailReason
                    DisplayString,
                hwReplyMessage
                    DisplayString
                }

        hwAAAOnlineFailIndex OBJECT-TYPE
                 SYNTAX Integer32
                 MAX-ACCESS read-only
                 STATUS current
                 DESCRIPTION
                   "This object indicates the index of the cause of a user online failure."
                 ::= { hwAAAOnlineFailRecordEntry 1 }

        hwUserName OBJECT-TYPE
                 SYNTAX DisplayString (SIZE(1..253))
                 MAX-ACCESS read-only
                 STATUS current
                 DESCRIPTION
                   "This object indicates the user name."
                 ::= { hwAAAOnlineFailRecordEntry 2 }

        hwUserDomainName OBJECT-TYPE
                 SYNTAX DisplayString (SIZE(0..64))
                 MAX-ACCESS read-only
                 STATUS current
                 DESCRIPTION
                   "This object indicates a domain name."
                 ::= { hwAAAOnlineFailRecordEntry 3 }

        hwUserMAC OBJECT-TYPE
                 SYNTAX MacAddress
                 MAX-ACCESS read-only
                 STATUS current
                 DESCRIPTION
                   "This object indicates the MAC address of the user."
                 ::= { hwAAAOnlineFailRecordEntry 4 }
        
         hwUserAccessType OBJECT-TYPE
                 SYNTAX DisplayString (SIZE(1..64))
                 MAX-ACCESS read-only
                 STATUS current
                 DESCRIPTION
                   "This object indicates the access type of the user."
                 ::= { hwAAAOnlineFailRecordEntry 5 }

        hwUserInterface OBJECT-TYPE
                 SYNTAX DisplayString (SIZE(1..63))
                 MAX-ACCESS read-only
                 STATUS current
                 DESCRIPTION
                   "This object indicates the access interface of the user."
                 ::= { hwAAAOnlineFailRecordEntry 6 }
        
        hwUserAccessPVC OBJECT-TYPE
                 SYNTAX DisplayString (SIZE(1..63))
                 MAX-ACCESS read-only
                 STATUS current
                 DESCRIPTION
                   "This object indicates the PVC of the user."
                 ::= { hwAAAOnlineFailRecordEntry 7 }                                  

        hwUserAccessPeVlan OBJECT-TYPE
                 SYNTAX Integer32
                 MAX-ACCESS read-only
                 STATUS current
                 DESCRIPTION
                   "This object indicates the PE VLAN of the user."
                 ::= { hwAAAOnlineFailRecordEntry 8 }
                 
        hwUserAccessCeVlan OBJECT-TYPE
                 SYNTAX Integer32
                 MAX-ACCESS read-only
                 STATUS current
                 DESCRIPTION
                   "This object indicates the CE VLAN of the user."
                 ::= { hwAAAOnlineFailRecordEntry 9 }

        hwUserIPAddress OBJECT-TYPE
                 SYNTAX IpAddress
                 MAX-ACCESS read-only
                 STATUS current
                 DESCRIPTION
                   "This object indicates the IP address of the user."
                 ::= { hwAAAOnlineFailRecordEntry 10 }
                 
        hwUserIPv6NDRAPrefix OBJECT-TYPE
                 SYNTAX Ipv6AddressPrefix
                 MAX-ACCESS read-only
                 STATUS current
                 DESCRIPTION
                   "This object indicates the IPv6 NDRA prefix of the user."
                 ::= { hwAAAOnlineFailRecordEntry 11 }

        hwUserIPv6Address OBJECT-TYPE
                 SYNTAX Ipv6Address
                 MAX-ACCESS read-only
                 STATUS current
                 DESCRIPTION
                   "This object indicates the IPv6 address of the user."
                 ::= { hwAAAOnlineFailRecordEntry 12 }
        
        hwUserIPv6PDPrefix OBJECT-TYPE
                 SYNTAX Ipv6AddressPrefix
                 MAX-ACCESS read-only
                 STATUS current
                 DESCRIPTION
                   "This object indicates the IPv6 PD prefix of the user."
                 ::= { hwAAAOnlineFailRecordEntry 13 }
        
       hwUserIPv6PDPrefixLength OBJECT-TYPE
            SYNTAX Integer32 (0..128)
            MAX-ACCESS read-only
            STATUS current
            DESCRIPTION
                "This object indicates the length of the IPv6 PD prefix of the user."
                ::= { hwAAAOnlineFailRecordEntry 14 }

        hwUserID OBJECT-TYPE
                 SYNTAX Integer32
                 MAX-ACCESS read-only
                 STATUS current
                 DESCRIPTION
                   "This object indicates the index of the user."
                 ::= { hwAAAOnlineFailRecordEntry 15 }

        hwUserAuthenState OBJECT-TYPE
                 SYNTAX INTEGER
                 {
                     authIdle(0),
                     authWait(1),
                     authed(2),
                     unknown(255)
                 }
                 MAX-ACCESS read-only
                 STATUS current
                 DESCRIPTION
                   "This object indicates the authentication status of the user."
                 ::= { hwAAAOnlineFailRecordEntry 16 }
                 
        hwUserAcctState OBJECT-TYPE
                 SYNTAX INTEGER
                 {
                     acctIdle(3),
                     acctReady(4),
                     acctStartWait(5),
                     acctAccting(6),
                     acctLeavingFlowQuery(7),
                     acctStopWait(8),
                     acctSendForceStopWait(12),
                     unknown(255)
                 }
                 MAX-ACCESS read-only
                 STATUS current
                 DESCRIPTION
                   "This object indicates the accounting status of the user."
                 ::= { hwAAAOnlineFailRecordEntry 17 }
                 
        hwUserAuthorState OBJECT-TYPE
                 SYNTAX INTEGER
                 {
                     success(0),
                     authorIdle(9),
                     authorUserAckWait(10),
                     authorServerAckWait(11),
                     unknown(255)
                 }
                 MAX-ACCESS read-only
                 STATUS current
                 DESCRIPTION
                   "This object indicates the authorization status of the user."
                 ::= { hwAAAOnlineFailRecordEntry 18 }
                 
        hwUserLoginTime OBJECT-TYPE
                 SYNTAX DateAndTime
                 MAX-ACCESS read-only
                 STATUS current
                 DESCRIPTION
                   "This object indicates the online time of the user."
                 ::= { hwAAAOnlineFailRecordEntry 19 }
                 
        hwOnlineFailReason OBJECT-TYPE
                 SYNTAX DisplayString (SIZE(1..80))
                 MAX-ACCESS read-only
                 STATUS current
                 DESCRIPTION
                   "This object indicates the cause of a user online failure."
                 ::= { hwAAAOnlineFailRecordEntry 20 }
                 
        hwReplyMessage OBJECT-TYPE
                 SYNTAX DisplayString (SIZE(1..63))
                 MAX-ACCESS read-only
                 STATUS current
                 DESCRIPTION
                   "This object indicates a reply message."
                 ::= { hwAAAOnlineFailRecordEntry 21 }                 
                                               
        hwUserLogTable OBJECT IDENTIFIER ::= { hwAAAMibObjects 49 }

        hwUserLogEntry OBJECT IDENTIFIER ::= { hwUserLogTable 1 }

        hwUserLogAccess OBJECT-TYPE
            SYNTAX TruthValue
            MAX-ACCESS read-write
            STATUS current
            DESCRIPTION
                "User log access"
            ::= { hwUserLogEntry 1 }
            
        hwUserLogIPAddress OBJECT-TYPE
            SYNTAX IpAddress
            MAX-ACCESS read-write
            STATUS current
            DESCRIPTION
                "User log server IP address"
            ::= { hwUserLogEntry 2 }
            
        hwUserLogPort OBJECT-TYPE
            SYNTAX Integer32 (1..65535)
            MAX-ACCESS read-write
            STATUS current
            DESCRIPTION
                "User log server port"
            ::= { hwUserLogEntry 3 }  
            
        hwUserLogVersion OBJECT-TYPE
            SYNTAX Integer32 (1..2)
            MAX-ACCESS read-write
            STATUS current
            DESCRIPTION
                "User log server version"
            ::= { hwUserLogEntry 4 } 
           
        hwShowUserLogStatistic OBJECT-TYPE
            SYNTAX Integer32
            MAX-ACCESS read-only
            STATUS current
            DESCRIPTION
                "Show user log statistic"
            ::= { hwUserLogEntry 5 } 
            
        hwResetUserLogStatistic OBJECT-TYPE
            SYNTAX INTEGER
            {
                reset(0)                    
            }
            MAX-ACCESS read-only
            STATUS current
            DESCRIPTION
                "Reset user log statistic"
            ::= { hwUserLogEntry 6 } 
           
                   
         hwReauthorizeTable OBJECT-TYPE
            SYNTAX SEQUENCE OF HwReauthorizeEntry
            MAX-ACCESS not-accessible
            STATUS current
            DESCRIPTION
                "Change user's user-group by username."
            ::= { hwAAAMibObjects 50 }
            
        hwReauthorizeEntry OBJECT-TYPE
            SYNTAX HwReauthorizeEntry
            MAX-ACCESS not-accessible
            STATUS current
            DESCRIPTION
                "Change user's user-group by username."
            INDEX { hwReauthorizeUsername }
            ::= { hwReauthorizeTable 1 }
            
        HwReauthorizeEntry ::=
            SEQUENCE {
                hwReauthorizeUsername       DisplayString,
                hwReauthorizeUsergroup   DisplayString
             }
                    
        hwReauthorizeUsername OBJECT-TYPE
            SYNTAX DisplayString (SIZE(1..253))
            MAX-ACCESS read-only
            STATUS current
            DESCRIPTION
                "The user's username."
            ::= { hwReauthorizeEntry 1 }
            
        hwReauthorizeUsergroup OBJECT-TYPE
                 SYNTAX DisplayString (SIZE(1..32))
                 MAX-ACCESS read-write
                 STATUS current
                 DESCRIPTION
                   "The user's user-group."
                 ::= { hwReauthorizeEntry 2 }

       hwUserGroupTable OBJECT-TYPE
            SYNTAX SEQUENCE OF HwUserGroupEntry
            MAX-ACCESS not-accessible
            STATUS current
            DESCRIPTION
                "The user group table."
            ::= { hwAAAMibObjects 51 }

        hwUserGroupEntry OBJECT-TYPE
            SYNTAX HwUserGroupEntry
            MAX-ACCESS not-accessible
            STATUS current
            DESCRIPTION
                "The user group entry."
            INDEX { hwUserGroupIndex }
            ::= { hwUserGroupTable 1 }

        HwUserGroupEntry ::=
            SEQUENCE {
                hwUserGroupIndex    Integer32,
                hwUserGroupName    DisplayString,
                hwAclId    DisplayString,
                hwQoSProfileName    DisplayString,
                hwInterIsolateFlag    INTEGER,
                hwInnerIsolateFlag    INTEGER,
                hwUserGroupRowStatus    RowStatus,
                hwUserVlan    Integer32,
                hw8021pRemark     Integer32,
                hwDscpRemark     Integer32,
                hwExpRemark     Integer32,
                hwLpRemark     Integer32,
                hwUserGroupCarCir    Unsigned32,
                hwUserGroupCarPir    Unsigned32,
                hwUserGroupCarCbs    Unsigned32,
                hwUserGroupCarPbs    Unsigned32,
                hwUserGroupEnable     INTEGER,
                hwUserGroupCarInBoundCir    Unsigned32,
                hwUserGroupCarInBoundPir    Unsigned32,
                hwUserGroupCarInBoundCbs    Unsigned32,
                hwUserGroupCarInBoundPbs    Unsigned32,
                hwUserGroupUserVlanPool     DisplayString,
                hwAcl6Id                    DisplayString,
                hwUserGroupPriority         Integer32
             }
	hwUserGroupIndex OBJECT-TYPE
	    SYNTAX      Integer32(1..128)
	    MAX-ACCESS  read-only
	    STATUS      current
	    DESCRIPTION
	        "User group index."
	    ::={ hwUserGroupEntry 1 }
    
       hwUserGroupName OBJECT-TYPE
            SYNTAX DisplayString (SIZE (1..64))
            MAX-ACCESS read-create
            STATUS current
            DESCRIPTION
                "User group name."
            ::= { hwUserGroupEntry 2 }
            
        hwAclId OBJECT-TYPE
            SYNTAX DisplayString (SIZE (1..64))
            MAX-ACCESS read-create
            STATUS current
            DESCRIPTION
                "Specify acl id."
            ::= { hwUserGroupEntry 3 }

        hwQoSProfileName OBJECT-TYPE
            SYNTAX DisplayString (SIZE (1..31))
            MAX-ACCESS read-create
            STATUS current
            DESCRIPTION
                "Specify QoS Profile."
            ::= { hwUserGroupEntry 4 }

        hwInterIsolateFlag OBJECT-TYPE
            SYNTAX INTEGER
			            {
			            	true(1),
			            	false(2)
			            }
            MAX-ACCESS read-create
            STATUS current
            DESCRIPTION
                "Specify Inter Isolate Flag."
            ::= { hwUserGroupEntry 5 }
            
         hwInnerIsolateFlag OBJECT-TYPE
            SYNTAX INTEGER
			            {
			            	true(1),
			            	false(2)
			            }
            MAX-ACCESS read-create
            STATUS current
            DESCRIPTION
                "Specify Inner Isolate Flag."
            ::= { hwUserGroupEntry 6 }
            
				 hwUserGroupRowStatus OBJECT-TYPE
				    SYNTAX      RowStatus
				    MAX-ACCESS  read-create
				    STATUS      current
				    DESCRIPTION
				        "RowStatus."
				    ::={ hwUserGroupEntry 7 }              	
	
        hwUserVlan OBJECT-TYPE
            SYNTAX      Integer32(0..4094)
            MAX-ACCESS read-create
            STATUS current
            DESCRIPTION
                "Specify User Vlan."
            ::= { hwUserGroupEntry 8 }            
				
        hw8021pRemark OBJECT-TYPE
            SYNTAX      Integer32(-1..7)
            MAX-ACCESS read-create
            STATUS current
            DESCRIPTION
                "Specify 8021p Remark."
            ::= { hwUserGroupEntry 9 } 
            
        hwDscpRemark OBJECT-TYPE
            SYNTAX      Integer32(-1..63)
            MAX-ACCESS read-create
            STATUS current
            DESCRIPTION
                "Specify Dscp Remark."
            ::= { hwUserGroupEntry 10 }
            
        hwExpRemark OBJECT-TYPE
            SYNTAX      Integer32(-1..7)
            MAX-ACCESS read-create
            STATUS current
            DESCRIPTION
                "Specify Exp Remark."
            ::= { hwUserGroupEntry 11 }
            
          hwLpRemark OBJECT-TYPE
            SYNTAX      Integer32(-1..7)
            MAX-ACCESS read-create
            STATUS current
            DESCRIPTION
                "Specify Lp Remark."
            ::= { hwUserGroupEntry 12 }
             
        hwUserGroupCarCir OBJECT-TYPE
            SYNTAX      Unsigned32
            MAX-ACCESS  read-write
            STATUS      current
            DESCRIPTION
                "User group commited information rate."
            ::={ hwUserGroupEntry 13 }

        hwUserGroupCarPir OBJECT-TYPE
            SYNTAX      Unsigned32
            MAX-ACCESS  read-write
            STATUS      current
            DESCRIPTION
                "User group peak information rate ."
            ::={ hwUserGroupEntry 14 }
				
        hwUserGroupCarCbs OBJECT-TYPE
            SYNTAX      Unsigned32
            MAX-ACCESS  read-write
            STATUS      current
            DESCRIPTION
                "User group commited burst size."
            ::={ hwUserGroupEntry 15 }
				
        hwUserGroupCarPbs OBJECT-TYPE
            SYNTAX      Unsigned32
            MAX-ACCESS  read-write
            STATUS      current
            DESCRIPTION
                "User group peak burst size ."
            ::={ hwUserGroupEntry 16 }

        -- 1.3.6.1.4.1.2011.5.2.1.51.1.17
        hwUserGroupEnable OBJECT-TYPE
            SYNTAX INTEGER
            {
                enable(1),
                disable(2)
            }
            MAX-ACCESS read-write
            STATUS current
            DESCRIPTION
                "Description."
            ::= { hwUserGroupEntry 17 }

        hwUserGroupCarInBoundCir OBJECT-TYPE
            SYNTAX      Unsigned32
            MAX-ACCESS  read-write
            STATUS      current
            DESCRIPTION
                "User group commited information rate."
            ::={ hwUserGroupEntry 18 }

        hwUserGroupCarInBoundPir OBJECT-TYPE
            SYNTAX      Unsigned32
            MAX-ACCESS  read-write
            STATUS      current
            DESCRIPTION
                "User group peak information rate ."
            ::={ hwUserGroupEntry 19 }
				
        hwUserGroupCarInBoundCbs OBJECT-TYPE
            SYNTAX      Unsigned32
            MAX-ACCESS  read-write
            STATUS      current
            DESCRIPTION
                "User group commited burst size."
            ::={ hwUserGroupEntry 20 }
				
        hwUserGroupCarInBoundPbs OBJECT-TYPE
            SYNTAX      Unsigned32
            MAX-ACCESS  read-write
            STATUS      current
            DESCRIPTION
                "User group peak burst size ."
            ::={ hwUserGroupEntry 21 }

        hwUserGroupUserVlanPool OBJECT-TYPE
        	SYNTAX DisplayString (SIZE (1..31))
            MAX-ACCESS read-create
            STATUS current
            DESCRIPTION
                "Specify Vlan Pool."
            ::= { hwUserGroupEntry 22 }
                                          
        
        hwAcl6Id OBJECT-TYPE
            SYNTAX DisplayString (SIZE (1..64))
            MAX-ACCESS read-create
            STATUS current
            DESCRIPTION
                "The ACL6 number configured under the user group. ACL is separated by space and each ACL must be created on the device. ."
            ::= { hwUserGroupEntry 23 }

        -- 1.3.6.1.4.1.2011.5.2.1.51.1.24
        hwUserGroupPriority OBJECT-TYPE
             SYNTAX Integer32(0..1)
             MAX-ACCESS read-write
             STATUS current
             DESCRIPTION
                  "UserGroupPriority."
             ::= { hwUserGroupEntry 24 }
        
        hwAAAOfflineRecordTable OBJECT-TYPE
            SYNTAX SEQUENCE OF HwAAAOfflineRecordEntry
            MAX-ACCESS not-accessible
            STATUS current
            DESCRIPTION
                "The offline record table."
            ::= { hwAAAMibObjects 52 }

        hwAAAOfflineRecordEntry OBJECT-TYPE
            SYNTAX HwAAAOfflineRecordEntry
            MAX-ACCESS not-accessible
            STATUS current
            DESCRIPTION
                "The offline record entry."
            INDEX { hwAAAOfflineIndex }
            ::= { hwAAAOfflineRecordTable 1 }

        HwAAAOfflineRecordEntry ::=
            SEQUENCE {
                hwAAAOfflineIndex
                    Unsigned32,
                hwOfflineRecordUserName
                    DisplayString,
                hwOfflineRecordDomainName
                    DisplayString,
                hwOfflineRecordUserMAC
                    MacAddress,
                hwOfflineRecordAccessType
                    DisplayString,
                hwOfflineRecordInterface
                    DisplayString,
                hwOfflineRecordAccessPeVlan
                    Integer32,
                hwOfflineRecordAccessCeVlan
                    Integer32,
                hwOfflineRecordIPAddress
                    IpAddress,
                hwOfflineRecordUserID
                    Integer32,
                hwOfflineRecordUserLoginTime
                    DateAndTime,
                hwOfflineRecordUserLogoutTime
                    DateAndTime,                    
                hwOfflineRecordOfflineReason
                    DisplayString,
                hwOfflineRecordStackTypeFlag
                    DisplayString,
                hwOfflineRecordAccessPVC
                    DisplayString,
                hwOfflineRecordIPv6NDRAPrefix
                    Ipv6AddressPrefix,
                hwOfflineRecordIPv6Address
                    Ipv6Address,
                hwOfflineRecordIPv6PDPrefix
                    Ipv6AddressPrefix,
                hwOfflineRecordUserAuthenState
                    INTEGER,
                hwOfflineRecordUserAcctState
                    INTEGER,
                hwOfflineRecordUserAuthorState
                    INTEGER,
                hwOfflineRecordIPv6PDPrefixLength
                    Integer32,
                hwOfflineRecordAPID
                    Unsigned32,
                hwOfflineRecordAPMAC
                    MacAddress,
                hwOfflineRecordSSID
                    DisplayString,
                hwOfflineRecordASID
                    Unsigned32,
                hwOfflineRecordASMAC
                    MacAddress,
                hwOfflineRecordASIfname
                    DisplayString
                }

        hwAAAOfflineIndex OBJECT-TYPE
                 SYNTAX Unsigned32 (0..4294967295)
                 MAX-ACCESS read-only
                 STATUS current
                 DESCRIPTION
                   "The index of offline record."
                 ::= { hwAAAOfflineRecordEntry 1 }

        hwOfflineRecordUserName OBJECT-TYPE
                 SYNTAX DisplayString (SIZE(1..253))
                 MAX-ACCESS read-only
                 STATUS current
                 DESCRIPTION
                   "The user name."
                 ::= { hwAAAOfflineRecordEntry 2 }

        hwOfflineRecordDomainName OBJECT-TYPE
                 SYNTAX DisplayString (SIZE(1..64))
                 MAX-ACCESS read-only
                 STATUS current
                 DESCRIPTION
                   "The domain name."
                 ::= { hwAAAOfflineRecordEntry 3 }

        hwOfflineRecordUserMAC OBJECT-TYPE
                 SYNTAX MacAddress
                 MAX-ACCESS read-only
                 STATUS current
                 DESCRIPTION
                   "The user MAC address."
                 ::= { hwAAAOfflineRecordEntry 4 }
        
         hwOfflineRecordAccessType OBJECT-TYPE
                 SYNTAX DisplayString (SIZE(1..64))
                 MAX-ACCESS read-only
                 STATUS current
                 DESCRIPTION
                   "The user access type."
                 ::= { hwAAAOfflineRecordEntry 5 }

        hwOfflineRecordInterface OBJECT-TYPE
                 SYNTAX DisplayString (SIZE(1..63))
                 MAX-ACCESS read-only
                 STATUS current
                 DESCRIPTION
                   "The user interface."
                 ::= { hwAAAOfflineRecordEntry 6 }                           

        hwOfflineRecordAccessPeVlan OBJECT-TYPE
                 SYNTAX Integer32
                 MAX-ACCESS read-only
                 STATUS current
                 DESCRIPTION
                   "The user pevlan."
                 ::= { hwAAAOfflineRecordEntry 7 }
                 
        hwOfflineRecordAccessCeVlan OBJECT-TYPE
                 SYNTAX Integer32
                 MAX-ACCESS read-only
                 STATUS current
                 DESCRIPTION
                   "The user cevlan."
                 ::= { hwAAAOfflineRecordEntry 8 }

        hwOfflineRecordIPAddress OBJECT-TYPE
                 SYNTAX IpAddress
                 MAX-ACCESS read-only
                 STATUS current
                 DESCRIPTION
                   "The user ip address."
                 ::= { hwAAAOfflineRecordEntry 9 }
                            
        hwOfflineRecordUserID OBJECT-TYPE
                 SYNTAX Integer32
                 MAX-ACCESS read-only
                 STATUS current
                 DESCRIPTION
                   "The user index."
                 ::= { hwAAAOfflineRecordEntry 10 }
                 
        hwOfflineRecordUserLoginTime OBJECT-TYPE
                 SYNTAX DateAndTime
                 MAX-ACCESS read-only
                 STATUS current
                 DESCRIPTION
                   "The user login time."
                 ::= { hwAAAOfflineRecordEntry 11 }
                 
         hwOfflineRecordUserLogoutTime OBJECT-TYPE
                 SYNTAX DateAndTime
                 MAX-ACCESS read-only
                 STATUS current
                 DESCRIPTION
                   "The user logout time."
                 ::= { hwAAAOfflineRecordEntry 12 }                
                 
        hwOfflineRecordOfflineReason OBJECT-TYPE
                 SYNTAX DisplayString (SIZE(1..80))
                 MAX-ACCESS read-only
                 STATUS current
                 DESCRIPTION
                   "The offline reason."
                 ::= { hwAAAOfflineRecordEntry 13 }	

        hwOfflineRecordStackTypeFlag OBJECT-TYPE
                 SYNTAX DisplayString (SIZE(0..32))
                 MAX-ACCESS read-only
                 STATUS current
                 DESCRIPTION
                   "The user Stack type."
                 ::= { hwAAAOfflineRecordEntry 14 }
		 
         hwOfflineRecordAccessPVC OBJECT-TYPE
                 SYNTAX DisplayString (SIZE(1..63))
                 MAX-ACCESS read-only
                 STATUS current
                 DESCRIPTION
                   "The user PVC."
                 ::= { hwAAAOfflineRecordEntry 15 }   
		 
        hwOfflineRecordIPv6NDRAPrefix OBJECT-TYPE
                 SYNTAX Ipv6AddressPrefix
                 MAX-ACCESS read-only
                 STATUS current
                 DESCRIPTION
                   "The user ipv6 NDRA prefix."
                 ::= { hwAAAOfflineRecordEntry 16 }

        hwOfflineRecordIPv6Address OBJECT-TYPE
                 SYNTAX Ipv6Address
                 MAX-ACCESS read-only
                 STATUS current
                 DESCRIPTION
                   "The user ipv6 address."
                 ::= { hwAAAOfflineRecordEntry 17 }
        
        hwOfflineRecordIPv6PDPrefix OBJECT-TYPE
                 SYNTAX Ipv6AddressPrefix
                 MAX-ACCESS read-only
                 STATUS current
                 DESCRIPTION
                   "The user ipv6 PD prefix."
                 ::= { hwAAAOfflineRecordEntry 18 }
	
       hwOfflineRecordUserAuthenState OBJECT-TYPE
                 SYNTAX INTEGER
                 {
                     authIdle(0),
                     authWait(1),
                     authed(2),
                     unknown(255)
                 }
                 MAX-ACCESS read-only
                 STATUS current
                 DESCRIPTION
                   "The user authentication state."




                 ::= { hwAAAOfflineRecordEntry 19 }
                 
        hwOfflineRecordUserAcctState OBJECT-TYPE
                 SYNTAX INTEGER
                 {
                     acctIdle(3),
                     acctReady(4),
                     acctStartWait(5),
                     acctAccting(6),
                     acctLeavingFlowQuery(7),
                     acctStopWait(8),
                     acctSendForceStopWait(12),
                     unknown(255)
                 }
                 MAX-ACCESS read-only
                 STATUS current
                 DESCRIPTION
                   "The user accounting state."
                 ::= { hwAAAOfflineRecordEntry 20 }
                 
        hwOfflineRecordUserAuthorState OBJECT-TYPE
                 SYNTAX INTEGER
                 {
                     success(0), 
                     authorIdle(9),
                     authorUserAckWait(10),
                     authorServerAckWait(11),
                     unknown(255)
                 }
                 MAX-ACCESS read-only
                 STATUS current
                 DESCRIPTION
                   "The user authorizatoin state."
                 ::= { hwAAAOfflineRecordEntry 21 }	

        hwOfflineRecordIPv6PDPrefixLength OBJECT-TYPE
                 SYNTAX Integer32 (0..128)
                 MAX-ACCESS read-only
                 STATUS current
                 DESCRIPTION
                 "The user ipv6 PD prefix length."
                 ::= { hwAAAOfflineRecordEntry 22}

        

        hwOfflineRecordAPID OBJECT-TYPE
            SYNTAX Unsigned32
            MAX-ACCESS read-only
            STATUS current
            DESCRIPTION
                "If the wireless user displays the AP ID, the wired user displays the 0x0FFFF."
            ::= { hwAAAOfflineRecordEntry 23 }

        
        hwOfflineRecordAPMAC OBJECT-TYPE
            SYNTAX MacAddress
            MAX-ACCESS read-only
            STATUS current
            DESCRIPTION
                "The MAC address of AP."
            ::= { hwAAAOfflineRecordEntry 24 }

        
        hwOfflineRecordSSID OBJECT-TYPE
            SYNTAX DisplayString (SIZE (0..32))
            MAX-ACCESS read-only
            STATUS current
            DESCRIPTION
                "SSID."
            ::= { hwAAAOfflineRecordEntry 25 }

        
        hwOfflineRecordASID OBJECT-TYPE
            SYNTAX Unsigned32
            MAX-ACCESS read-only
            STATUS current
            DESCRIPTION
                "ID of AS."
            ::= { hwAAAOfflineRecordEntry 26 }

        
        hwOfflineRecordASMAC OBJECT-TYPE
            SYNTAX MacAddress
            MAX-ACCESS read-only
            STATUS current
            DESCRIPTION
                "The MAC address of AS."
            ::= { hwAAAOfflineRecordEntry 27 }

        
        hwOfflineRecordASIfname OBJECT-TYPE
            SYNTAX DisplayString (SIZE (1..63))
            MAX-ACCESS read-only
            STATUS current
            DESCRIPTION
                "The name of the interface of AS."
            ::= { hwAAAOfflineRecordEntry 28 }

        
        hwGlobalDhcpOpt64SepAndSeg OBJECT-TYPE
            SYNTAX DisplayString (SIZE (1..5))
            MAX-ACCESS read-create
            STATUS current
            DESCRIPTION
                "The global option64 parse separator and segment number."
            ::= { hwAAAMibObjects 53 }  
            
        hwGlobalDhcpServerAck OBJECT-TYPE
            SYNTAX TruthValue            
            MAX-ACCESS read-create
            STATUS current
            DESCRIPTION
                "The global whether to deal dhcp server's ack packet when user online."
            ::= { hwAAAMibObjects 54 }

        -- 1.3.6.1.4.1.2011.5.2.1.55
       hwAuthEventCfgTable OBJECT-TYPE
               SYNTAX SEQUENCE OF HwAuthEventCfgEntry
               MAX-ACCESS not-accessible
               STATUS current
               DESCRIPTION
                       "Description."
               ::= { hwAAAMibObjects 55 }

        -- 1.3.6.1.4.1.2011.5.2.1.55.1
        hwAuthEventCfgEntry OBJECT-TYPE
                SYNTAX HwAuthEventCfgEntry
                MAX-ACCESS not-accessible
                STATUS current
                DESCRIPTION
                        "Description."
                INDEX { hwAuthEventPortIndex }
                ::= { hwAuthEventCfgTable 1 }

		
        HwAuthEventCfgEntry ::=
                SEQUENCE { 
                        hwAuthEventPortIndex
                                Unsigned32,
                        hwAuthEventAuthFailResponseFail
                                INTEGER,
                        hwAuthEventAuthFailVlan
                                Integer32,
                        hwAuthEventAuthenServerDownResponseFail
                                INTEGER,
                        hwAuthEventAuthenServerDownVlan
                                Integer32,
                        hwAuthEventClientNoResponseVlan
                                Integer32,
                        hwAuthEventPreAuthVlan
                                Integer32,
                        hwAuthEventAuthFailUserGroup
                                OCTET STRING,
                        hwAuthEventAuthenServerDownUserGroup
                                OCTET STRING,
                        hwAuthEventClientNoResponseUserGroup
                                OCTET STRING,
                        hwAuthEventPreAuthUserGroup
                                OCTET STRING
                         }

        -- 1.3.6.1.4.1.2011.5.2.1.55.1.1
        hwAuthEventPortIndex OBJECT-TYPE
                SYNTAX Unsigned32 (0..4294967295)
                MAX-ACCESS read-only
                STATUS current
                DESCRIPTION
                        "Description."
                ::= { hwAuthEventCfgEntry 1 }
		
        -- 1.3.6.1.4.1.2011.5.2.1.55.1.2
        hwAuthEventAuthFailResponseFail OBJECT-TYPE
                SYNTAX INTEGER
                {
                        enable(1),
                        disabel(2)
                }
                MAX-ACCESS read-write
                STATUS current
                DESCRIPTION
                        "Description."
                ::= { hwAuthEventCfgEntry 2 }

        -- 1.3.6.1.4.1.2011.5.2.1.55.1.3
        hwAuthEventAuthFailVlan OBJECT-TYPE
                SYNTAX Integer32 (0..4094)
                MAX-ACCESS read-write
                STATUS current
                DESCRIPTION
                        "Description."
                ::= { hwAuthEventCfgEntry 3 }

        -- 1.3.6.1.4.1.2011.5.2.1.55.1.4
        hwAuthEventAuthenServerDownResponseFail OBJECT-TYPE
                SYNTAX INTEGER
                {
                        enable(1),
                        disable(2)
                }
                MAX-ACCESS read-write
                STATUS current
                DESCRIPTION
                        "Description."
                ::= { hwAuthEventCfgEntry 4 }

        -- 1.3.6.1.4.1.2011.5.2.1.55.1.5
        hwAuthEventAuthenServerDownVlan OBJECT-TYPE
                SYNTAX Integer32 (0..4094)
                MAX-ACCESS read-write
                STATUS current
                DESCRIPTION
                        "Description."
        ::= { hwAuthEventCfgEntry 5 }

        -- 1.3.6.1.4.1.2011.5.2.1.55.1.6
        hwAuthEventClientNoResponseVlan OBJECT-TYPE
                SYNTAX Integer32 (0..4094)
                MAX-ACCESS read-write
                STATUS current
                DESCRIPTION
                        "Description."
                ::= { hwAuthEventCfgEntry 6 }

        -- 1.3.6.1.4.1.2011.5.2.1.55.1.7
        hwAuthEventPreAuthVlan OBJECT-TYPE
                SYNTAX Integer32 (0..4094)
                MAX-ACCESS read-write
                STATUS current
                DESCRIPTION
                        "Description."
                ::= { hwAuthEventCfgEntry 7 }

        -- 1.3.6.1.4.1.2011.5.2.1.55.1.8
        hwAuthEventAuthFailUserGroup OBJECT-TYPE
                SYNTAX OCTET STRING (SIZE (0..64))
                MAX-ACCESS read-write
                STATUS current
                DESCRIPTION
                        "Description."
                ::= { hwAuthEventCfgEntry 8 }

        -- 1.3.6.1.4.1.2011.5.2.1.55.1.9
        hwAuthEventAuthenServerDownUserGroup OBJECT-TYPE
                SYNTAX OCTET STRING (SIZE (0..64))
                MAX-ACCESS read-write
                STATUS current
                DESCRIPTION
                        "Description."
                ::= { hwAuthEventCfgEntry 9 }

        -- 1.3.6.1.4.1.2011.5.2.1.55.1.10
        hwAuthEventClientNoResponseUserGroup OBJECT-TYPE
                SYNTAX OCTET STRING (SIZE (0..64))
                MAX-ACCESS read-write
                STATUS current
                DESCRIPTION
                        "Description."
                ::= { hwAuthEventCfgEntry 10 }

        -- 1.3.6.1.4.1.2011.5.2.1.55.1.11
        hwAuthEventPreAuthUserGroup OBJECT-TYPE
                SYNTAX OCTET STRING (SIZE (0..64))
                MAX-ACCESS read-write
                STATUS current
                DESCRIPTION
                        "Description."
                ::= { hwAuthEventCfgEntry 11 }					
 

        hwWlanInterfaceTable OBJECT-TYPE
            SYNTAX SEQUENCE OF HwWlanInterfaceEntry
            MAX-ACCESS not-accessible
            STATUS current
            DESCRIPTION
                "Description."
            ::= { hwAAAMibObjects 56 }

        hwWlanInterfaceEntry OBJECT-TYPE
            SYNTAX HwWlanInterfaceEntry
            MAX-ACCESS not-accessible
            STATUS current
            DESCRIPTION
                "Description."
            INDEX { hwWlanInterfaceIndex }
            ::= { hwWlanInterfaceTable 1 }

       HwWlanInterfaceEntry ::=
            SEQUENCE {
                hwWlanInterfaceIndex
                    Unsigned32,
                hwWlanInterfaceName
                    DisplayString,
                hwWlanInterfaceDomainNameDelimiter
                    DisplayString,
                hwWlanInterfaceDomainNameSecurityDelimiter
                    DisplayString,
                hwWlanInterfaceDomainNameParseDirection
                    INTEGER,
                hwWlanInterfaceDomainNameLocation
                    INTEGER
                }

        hwWlanInterfaceIndex OBJECT-TYPE
                 SYNTAX Unsigned32 (0..4294967295)
                 MAX-ACCESS read-only
                 STATUS current
                 DESCRIPTION
                   "The index of wlan interface."
                 ::= { hwWlanInterfaceEntry 1 }
                 
        hwWlanInterfaceName OBJECT-TYPE
                 SYNTAX DisplayString (SIZE(1..64))
                 MAX-ACCESS read-write
                 STATUS current
                 DESCRIPTION
                   "The name of wlan interface."
                 ::= { hwWlanInterfaceEntry 2 }
                 
        hwWlanInterfaceDomainNameDelimiter OBJECT-TYPE
                 SYNTAX DisplayString (SIZE(1..1))
                 MAX-ACCESS read-write
                 STATUS current
                 DESCRIPTION
                   "
                    Domain name delimiter of interface. include \ / : < > | @ ' %
 	                  It can not be same with hwWlanInterfaceDomainNameSecurityDelimiter.
 	                 "
                 ::= { hwWlanInterfaceEntry 3 }

        hwWlanInterfaceDomainNameSecurityDelimiter OBJECT-TYPE
                 SYNTAX DisplayString (SIZE(1..1))
                 MAX-ACCESS read-write
                 STATUS current
                 DESCRIPTION
                   "
                    Domain name delimiter of interface. include \ / : < > | @ ' %
 	                  It can not be same with hwWlanInterfaceDomainNameDelimiter.
 	                 "
                 ::= { hwWlanInterfaceEntry 4 }

        hwWlanInterfaceDomainNameParseDirection OBJECT-TYPE
                 SYNTAX INTEGER
                 {
                  lefttoright(0),
                  righttoleft(1),
                  invalid(2)
                 }
                 MAX-ACCESS read-write
                 STATUS current
                 DESCRIPTION
                   "
                    The domain name resolution sequence of interface: 
 	                  lefttoright(0),
 	                  righttoleft(1)
                   "
                 ::= { hwWlanInterfaceEntry 5 }
        
         hwWlanInterfaceDomainNameLocation OBJECT-TYPE
                 SYNTAX INTEGER
                 {
                  beforedelimiter(0),
                  afterdelimiter(1),
                  invalid(2)
                 }
                 MAX-ACCESS read-write
                 STATUS current
                 DESCRIPTION
                   "
                    The domain name position of interface: 
 	                  beforedelimiter(0),
 	                  afterdelimiter(1)
                   "
                 ::= { hwWlanInterfaceEntry 6 }
    

        hwAuthorCmdTable OBJECT-TYPE
            SYNTAX SEQUENCE OF HwAuthorCmdEntry
            MAX-ACCESS not-accessible
            STATUS current
            DESCRIPTION
                "Description."
            ::= { hwAAAMibObjects 57 }

        hwAuthorCmdEntry OBJECT-TYPE
            SYNTAX HwAuthorCmdEntry
            MAX-ACCESS not-accessible
            STATUS current
            DESCRIPTION
                "Description."
            INDEX { hwAuthorSchemeName, hwAuthorCmdLevel }
            ::= { hwAuthorCmdTable 1 }

       HwAuthorCmdEntry ::=
            SEQUENCE {
                hwAuthorCmdLevel
                    Integer32,
                hwAuthorCmdMode
                    INTEGER,
               hwAuthorCmdRowStatus
                    RowStatus
                }

        hwAuthorCmdLevel OBJECT-TYPE
            SYNTAX Integer32 (0..15)
            MAX-ACCESS read-only
            STATUS current
            DESCRIPTION
                "authorization command level"
            ::= { hwAuthorCmdEntry 1 }
                              
        hwAuthorCmdMode OBJECT-TYPE
            SYNTAX INTEGER
                {
                hwtacacs(0),
                hwtacacsnone(1),
                hwtacacslocal(2),
                hwtacacslocalnone(3)                                
                }
            MAX-ACCESS read-create
            STATUS current
            DESCRIPTION
                "authorization command method
                "
            ::= { hwAuthorCmdEntry 2 }
            
        hwAuthorCmdRowStatus OBJECT-TYPE
            SYNTAX RowStatus
            MAX-ACCESS read-create
            STATUS current
            DESCRIPTION
                "The authorization command method status, only supporting add or delete."
            ::= { hwAuthorCmdEntry 3 }      
            
            
            
            
        hwAAARateTable OBJECT-TYPE
            SYNTAX SEQUENCE OF HwAAARateEntry
            MAX-ACCESS not-accessible
            STATUS current
            DESCRIPTION
                "Tariff package table."
            ::= { hwAAAMibObjects 58 }

        hwAAARateEntry OBJECT-TYPE
            SYNTAX HwAAARateEntry
            MAX-ACCESS not-accessible
            STATUS current
            DESCRIPTION
                "Tariff package entry."
            INDEX { hwAAARateDirection,hwAAARateType }
            ::= { hwAAARateTable 1 }

       HwAAARateEntry ::=
            SEQUENCE {
                hwAAARateDirection
                    INTEGER,
                hwAAARateType
                    Integer32,
                hwAAARateRealPeak
                    Integer32,
                hwAAARateRealAverage
                    Integer32,
                hwAAARateRealUsedCount
                    Integer32,
                hwAAARateRealPercent 
                    Integer32
                }

        hwAAARateDirection OBJECT-TYPE
                 SYNTAX INTEGER
                  {
                   inbound(1),
                   outbound(2)                               
                }
                 MAX-ACCESS read-only
                 STATUS current
                 DESCRIPTION
                   "Tariff direction."
                 ::= { hwAAARateEntry 1 }
                 
        hwAAARateType OBJECT-TYPE
                 SYNTAX Integer32
                 MAX-ACCESS read-only
                 STATUS current
                 DESCRIPTION
                   "Tariff package type."
                 ::= { hwAAARateEntry 2 }
                 
        hwAAARateRealPeak OBJECT-TYPE
                 SYNTAX Integer32
                 MAX-ACCESS read-only
                 STATUS current
                 DESCRIPTION
                   "The highest average rate."
                 ::= { hwAAARateEntry 3 }

        hwAAARateRealAverage OBJECT-TYPE
                 SYNTAX Integer32
                 MAX-ACCESS read-only
                 STATUS current
                 DESCRIPTION
                   "The actual average rate."
                 ::= { hwAAARateEntry 4 }

        hwAAARateRealUsedCount OBJECT-TYPE
                 SYNTAX Integer32
                 MAX-ACCESS read-only
                 STATUS current
                 DESCRIPTION
                   "The number of users."
                 ::= { hwAAARateEntry 5 }
        
         hwAAARateRealPercent OBJECT-TYPE
                 SYNTAX  Integer32 (0..100)
                 MAX-ACCESS read-only
                 STATUS current
                 DESCRIPTION
                   "Users rate accounted for the total bandwidth ratio, ratio range of 0-100."
                 ::= { hwAAARateEntry 6 }          

         hwLocalUserPwPolicyAdmin OBJECT IDENTIFIER ::= { hwAAAMibObjects 59 }
       hwLocalUserPwPolicyAdminEntry OBJECT IDENTIFIER ::= { hwLocalUserPwPolicyAdmin 1 }

               
       hwAdminEnable OBJECT-TYPE
                 SYNTAX   INTEGER
             {
	 disable(0),
	enable(1)
               }        
                 MAX-ACCESS read-write
                 STATUS current
                 DESCRIPTION
                   "Is Local user pw-policy enable."
                 ::= {  hwLocalUserPwPolicyAdminEntry 1 }
                 
        hwAdminExpire OBJECT-TYPE
                 SYNTAX Integer32(0..999)
                 MAX-ACCESS read-write
                 STATUS current
                 DESCRIPTION
                   "Pw expire time."
                 ::= {  hwLocalUserPwPolicyAdminEntry 2 }
                 
        hwAdminPwHistroyRecordNum OBJECT-TYPE
                 SYNTAX Integer32 (0..12)
                 MAX-ACCESS read-write
                 STATUS current
                 DESCRIPTION
                   "Pw Histroy Record Num."
                 ::= {  hwLocalUserPwPolicyAdminEntry 3 }

        hwAdminAlertBefore OBJECT-TYPE
                 SYNTAX Integer32  (0..999)
                 MAX-ACCESS read-write
                 STATUS current
                 DESCRIPTION
                   "Alert time before pw expire."
                 ::= {  hwLocalUserPwPolicyAdminEntry 4 }
         
        hwAdminAlertOrginal OBJECT-TYPE
                 SYNTAX INTEGER
                  {
	 disable(0),
	enable(1)
               }        				     					 								               
               MAX-ACCESS read-write
                 STATUS current
                 DESCRIPTION
                   "Is original pw changed."
                 ::= {  hwLocalUserPwPolicyAdminEntry 5 }                                      
                                  
       hwLocalUserPwPolicyAcc OBJECT IDENTIFIER ::= { hwAAAMibObjects 60 }
       hwLocalUserPwPolicyAccEntry OBJECT IDENTIFIER ::= { hwLocalUserPwPolicyAcc 1 }

       hwAccEnable OBJECT-TYPE
                 SYNTAX INTEGER
                 {
	 disable(0),
	enable(1)
               }                 
                 MAX-ACCESS read-write
                 STATUS current
                 DESCRIPTION
                   "Is Local user pwpolicy enable."
                 ::= {  hwLocalUserPwPolicyAccEntry 1 }
                 
        hwAccPwHistroyRecordNum OBJECT-TYPE
                 SYNTAX Integer32(0..12)
                 MAX-ACCESS read-write
                 STATUS current
                 DESCRIPTION
                   "Pw Histroy Record Num."
                 ::= {  hwLocalUserPwPolicyAccEntry 2 }                                 
    
        hwAAADomainIPPoolTable OBJECT-TYPE
            SYNTAX SEQUENCE OF HwAAADomainIPPoolEntry
            MAX-ACCESS not-accessible
            STATUS current
            DESCRIPTION
                "The pool of domain table."
            ::= { hwAAAMibObjects 61 }

        hwAAADomainIPPoolEntry OBJECT-TYPE
            SYNTAX HwAAADomainIPPoolEntry
            MAX-ACCESS not-accessible
            STATUS current
            DESCRIPTION
                "The pool of domain entry."
            INDEX { hwDomainName,hwAAADomainIPPoolName }
            ::= { hwAAADomainIPPoolTable 1 }

       HwAAADomainIPPoolEntry ::=
            SEQUENCE {
                hwAAADomainIPPoolName OCTET STRING,
                hwAAADomainIPPoolIndex Integer32,
                hwAAADomainIPPoolConstantIndex Integer32,  
                hwAAADomainIPPoolPosition Integer32,
                hwAAADomainIPPoolRowStatus RowStatus
                }

        hwAAADomainIPPoolName OBJECT-TYPE
                 SYNTAX OCTET STRING (SIZE (1..128))
                 MAX-ACCESS read-only
                 STATUS current
                 DESCRIPTION
                   "The pool name."
                 ::= { hwAAADomainIPPoolEntry 1 } 
                
        hwAAADomainIPPoolIndex OBJECT-TYPE
                 SYNTAX Integer32
                 MAX-ACCESS read-only
                 STATUS current
                 DESCRIPTION
                   "The IP pool index."
                 ::= { hwAAADomainIPPoolEntry 2 } 
                         
        hwAAADomainIPPoolConstantIndex OBJECT-TYPE
                 SYNTAX Integer32
                 MAX-ACCESS read-only
                 STATUS current
                 DESCRIPTION
                   "The IP pool constant index."
                 ::= { hwAAADomainIPPoolEntry 3 }                 
       
       hwAAADomainIPPoolPosition OBJECT-TYPE
                 SYNTAX Integer32(1..4096)
                 MAX-ACCESS read-write
                 STATUS current
                 DESCRIPTION
                   "The IP pool position in domain."
                 ::= { hwAAADomainIPPoolEntry 4 }                 
                 
       hwAAADomainIPPoolRowStatus OBJECT-TYPE
                SYNTAX RowStatus
                MAX-ACCESS read-create
                STATUS current
                DESCRIPTION
                    "The row administration status, only supporting add or delete."
                ::= { hwAAADomainIPPoolEntry 50 }
        
        userAuthenProfileTable OBJECT-TYPE
     			SYNTAX SEQUENCE OF UserAuthenProfileEntry
            	MAX-ACCESS not-accessible
            	STATUS current
            	DESCRIPTION
                	"The authentication profile table."
            	::= { hwAAAMibObjects 62 }
             			
        userAuthenProfileEntry OBJECT-TYPE
            SYNTAX UserAuthenProfileEntry
            MAX-ACCESS not-accessible
            STATUS current
            DESCRIPTION
                "The authentication profile entry."
            INDEX { userAuthenProfileName }
            ::= { userAuthenProfileTable 1 }

        UserAuthenProfileEntry ::=
            SEQUENCE {
                userAuthenProfileName
                    OCTET STRING,
                userAuthenProfileDot1xAccessProfileName
                    OCTET STRING,
                userAuthenProfileMacAuthenAccessProfileName
                    OCTET STRING,
                userAuthenProfilePortalAccessProfileName
                    OCTET STRING,
                userAuthenProfileSingleAccess
                    TruthValue,
                userAuthenProfilePreAuthenServiceSchemeName
                    OCTET STRING,
                userAuthenProfilePreAuthenUserGroupName
                    OCTET STRING,
                userAuthenProfilePreAuthenVLAN
                    Integer32,
                userAuthenProfileAuthenFailAuthorServiceSchemeName
                    OCTET STRING,
                userAuthenProfileAuthenFailAuthorUserGroupName
                    OCTET STRING,
                userAuthenProfileAuthenFailAuthorVLAN
                    Integer32,
                userAuthenProfileAuthenServerDownServiceSchemeName
                    OCTET STRING,
                userAuthenProfileAuthenServerDownUserGroupName
                    OCTET STRING,
                userAuthenProfileAuthenServerDownVLAN
                    Integer32,
                userAuthenProfileAuthenServerDownResponseSuccess
                    TruthValue,
                userAuthenProfileAuthenServerUpReauthen
                    TruthValue,
                userAuthenProfileMacAuthenFirst
                    TruthValue,
                userAuthenProfileMACBypass
                    TruthValue,
                userAuthenProfileDot1xForceDomain
                    OCTET STRING,
                userAuthenProfileMACAuthenForceDomain
                    OCTET STRING,
                userAuthenProfilePortalForceDomain
                    OCTET STRING,
                userAuthenProfileDot1xDefaultDomain
                    OCTET STRING,
                userAuthenProfileMACAuthenDefaultDomain
                    OCTET STRING,
                userAuthenProfilePortalDefaultDomain
                    OCTET STRING,
                userAuthenProfileDefaultDomain
                    OCTET STRING,
                userAuthenProfileForceDomain
                    OCTET STRING,
                userAuthenProfileDomainNameDelimiter
                    OCTET STRING,
                userAuthenProfileDomainNameLocation
                    INTEGER,
                userAuthenProfileDomainNameParseDirection
                    INTEGER,
                userAuthenProfileSecurityNameDelimiter
                    OCTET STRING,
                userAuthenProfilePreAuthenReAuthenTimer
                    Integer32,
                userAuthenProfileAuthenFailReAuthenTimer
                    Integer32,
                userAuthenProfilePreAuthenAgingTime
                    Integer32,
                userAuthenProfileAuthenFailAgingTime
                    Integer32,
                userAuthenProfileFreeRuleName
                    OCTET STRING,
                userAuthenProfileAuthenSchemeName
                    OCTET STRING,
                userAuthenProfileAuthorSchemeName
                    OCTET STRING,
                userAuthenProfileAcctSchemeName
                    OCTET STRING,
                userAuthenProfileServiceSchemeName
                    OCTET STRING,
                userAuthenProfileUserGroupName
                    OCTET STRING,
                userAuthenProfileRadiusServerName
                    OCTET STRING,
                userAuthenProfileHwtacacsServerName
                    OCTET STRING,
                userAuthenProfileAuthenticationMode
                    INTEGER,
                userAuthenProfileMaxUser
                    Integer32,
                userAuthenProfileArpDetect
                    TruthValue,
                userAuthenProfileArpDetectTimer
                    Integer32,
                userAuthenProfileRowStatus
                    RowStatus,
                userAuthenProfilePermitDomain
                    OCTET STRING,
                userAuthenProfileAuthenticationMaxUser
                    Integer32,
                userAuthenProfileAuthenFailAuthorResponseSuccess
                    TruthValue,
                userAuthenProfileIpAddrInAcctStart
                    TruthValue,
                userAuthenProfileAccoutingStartAckPermitArp
                    TruthValue,
                userAuthenProfileWebDescription
                    OCTET STRING,
                userAuthenProfileIpTrigger
                    TruthValue,
               userAuthenProfileForcePushUrlTemplate
                    OCTET STRING,
               userAuthenProfileForcePushUrl
                    OCTET STRING,
                userAuthenProfileAccountingOfRoam
                    TruthValue,
                userAuthenProfileAccountingOfUpdateIP
                    TruthValue,
                userAuthenProfileAccountingOfUpdateInfo
                    TruthValue,
                userAuthenProfileNoIPCheck
                    TruthValue,
                userAuthenProfileLdapServerName
                    OCTET STRING,
                userAuthenProfileAdServerName
                    OCTET STRING,
                userAuthenProfileRoamAccountingMode
                    INTEGER,
                userAuthenProfileMacFirstForce
                    TruthValue,
                userAuthenProfileHacaServerName
                    OCTET STRING,
                userAuthenProfileAcctRdsServerName
                    OCTET STRING                                  
             }

        userAuthenProfileName OBJECT-TYPE
            SYNTAX OCTET STRING (SIZE (1..31))
            MAX-ACCESS read-only
            STATUS current
            DESCRIPTION
                "The authentication profile name."
            ::= { userAuthenProfileEntry 1 }
            
        userAuthenProfileDot1xAccessProfileName OBJECT-TYPE    
            SYNTAX OCTET STRING (SIZE (1..31))
            MAX-ACCESS read-create
            STATUS current
            DESCRIPTION
                "The dot1x access profile name."
            ::= { userAuthenProfileEntry 2 }
            
        userAuthenProfileMacAuthenAccessProfileName OBJECT-TYPE    
            SYNTAX OCTET STRING (SIZE (1..31))
            MAX-ACCESS read-create
            STATUS current
            DESCRIPTION
                "The mac-authen access profile name."
            ::= { userAuthenProfileEntry 3 }  
            
        userAuthenProfilePortalAccessProfileName OBJECT-TYPE    
            SYNTAX OCTET STRING (SIZE (1..31))
            MAX-ACCESS read-create
            STATUS current
            DESCRIPTION
                "The portal access profile name."
            ::= { userAuthenProfileEntry 4 }
       
       userAuthenProfileSingleAccess OBJECT-TYPE
            SYNTAX TruthValue
            MAX-ACCESS read-create
            STATUS current
            DESCRIPTION
                "The portal access profile name."
            ::= { userAuthenProfileEntry 5 }            
       userAuthenProfilePreAuthenServiceSchemeName OBJECT-TYPE    
            SYNTAX OCTET STRING (SIZE (1..32))
            MAX-ACCESS read-create
            STATUS current
            DESCRIPTION
                "The pre-authen service scheme name."
            ::= { userAuthenProfileEntry 6 } 
           
        userAuthenProfilePreAuthenUserGroupName OBJECT-TYPE    
            SYNTAX OCTET STRING (SIZE (1..64))
            MAX-ACCESS read-create
            STATUS current
            DESCRIPTION
               "The pre-authen user group or ucl group name.
                This object is shared by a user group and ucl group name.
                The value for a user group name rangs from 1 to 64, and the value for a ucl group name ranges from 1 to 31."
            ::= { userAuthenProfileEntry 7 }   
            
        userAuthenProfilePreAuthenVLAN OBJECT-TYPE    
            SYNTAX Integer32 (0..4094)
            MAX-ACCESS read-create
            STATUS current
            DESCRIPTION
                "The pre-authen VLAN."
            ::= { userAuthenProfileEntry 8 } 
            
        userAuthenProfileAuthenFailAuthorServiceSchemeName OBJECT-TYPE    
            SYNTAX OCTET STRING (SIZE (1..32))
            MAX-ACCESS read-create
            STATUS current
            DESCRIPTION
                "The authen-fail service scheme name."
            ::= { userAuthenProfileEntry 9 } 
            
        userAuthenProfileAuthenFailAuthorUserGroupName OBJECT-TYPE    
            SYNTAX OCTET STRING (SIZE (1..64))
            MAX-ACCESS read-create
            STATUS current
            DESCRIPTION
                "The authen-fail user group or ucl group name.
                This object is shared by a user group and ucl group name.
                The value for a user group name rangs from 1 to 64, and the value for a ucl group name ranges from 1 to 31."
            ::= { userAuthenProfileEntry 10 }
        
        userAuthenProfileAuthenFailAuthorVLAN OBJECT-TYPE    
            SYNTAX Integer32 (0..4094)
            MAX-ACCESS read-create
            STATUS current
            DESCRIPTION
                "The authen-fail VLAN."
            ::= { userAuthenProfileEntry 11 }
            
        userAuthenProfileAuthenServerDownServiceSchemeName OBJECT-TYPE    
            SYNTAX OCTET STRING (SIZE (1..32))
            MAX-ACCESS read-create
            STATUS current
            DESCRIPTION
                "The authen-server-down service scheme name."
            ::= { userAuthenProfileEntry 12 }
            
        userAuthenProfileAuthenServerDownUserGroupName OBJECT-TYPE    
            SYNTAX OCTET STRING (SIZE (1..64))
            MAX-ACCESS read-create
            STATUS current
            DESCRIPTION
               "The authen-server-down user group or ucl group name.
                This object is shared by a user group and ucl group name.
                The value for a user group name rangs from 1 to 64, and the value for a ucl group name ranges from 1 to 31."
            ::= { userAuthenProfileEntry 13 }
            
        userAuthenProfileAuthenServerDownVLAN OBJECT-TYPE    
            SYNTAX Integer32 (0..4094)
            MAX-ACCESS read-create
            STATUS current
            DESCRIPTION
                "The authen-server-down VLAN."
            ::= { userAuthenProfileEntry 14 }    
            
        userAuthenProfileAuthenServerDownResponseSuccess OBJECT-TYPE
            SYNTAX TruthValue
            MAX-ACCESS read-create
            STATUS current
            DESCRIPTION
                "The authen-server-down response success."
            ::= { userAuthenProfileEntry 15 }

        userAuthenProfileAuthenServerUpReauthen OBJECT-TYPE
        	SYNTAX TruthValue
            MAX-ACCESS read-create
            STATUS current
            DESCRIPTION
                "The authen-server-up reauthentication."
            ::= { userAuthenProfileEntry 16 }
        
        userAuthenProfileMacAuthenFirst OBJECT-TYPE
            SYNTAX TruthValue
            MAX-ACCESS read-create
            STATUS current
            DESCRIPTION
                "The mac-authen first switch."
            ::= { userAuthenProfileEntry 17 }
        
        userAuthenProfileMACBypass OBJECT-TYPE
            SYNTAX TruthValue
            MAX-ACCESS read-create
            STATUS current
            DESCRIPTION
                "The mac bypass switch."
            ::= { userAuthenProfileEntry 18 }
        
        userAuthenProfileDot1xForceDomain OBJECT-TYPE  
            SYNTAX OCTET STRING (SIZE (1..64))
            MAX-ACCESS read-create
            STATUS current
            DESCRIPTION
                "The force domain for dot1x."
            ::= { userAuthenProfileEntry 19 } 
            
        userAuthenProfileMACAuthenForceDomain OBJECT-TYPE  
            SYNTAX OCTET STRING (SIZE (1..64))
            MAX-ACCESS read-create
            STATUS current
            DESCRIPTION
                "The force domain for MAC authen."
            ::= { userAuthenProfileEntry 20 }   
        
        userAuthenProfilePortalForceDomain OBJECT-TYPE  
            SYNTAX OCTET STRING (SIZE (1..64))
            MAX-ACCESS read-create
            STATUS current
            DESCRIPTION
                "The force domain for portal."
            ::= { userAuthenProfileEntry 21 }
            
        userAuthenProfileDot1xDefaultDomain OBJECT-TYPE  
            SYNTAX OCTET STRING (SIZE (1..64))
            MAX-ACCESS read-create
            STATUS current
            DESCRIPTION
                "The default domain for dot1x."
            ::= { userAuthenProfileEntry 22 } 
            
        userAuthenProfileMACAuthenDefaultDomain OBJECT-TYPE  
            SYNTAX OCTET STRING (SIZE (1..64))
            MAX-ACCESS read-create
            STATUS current
            DESCRIPTION
                "The default domain for MAC authen."
            ::= { userAuthenProfileEntry 23 }
            
        userAuthenProfilePortalDefaultDomain OBJECT-TYPE  
            SYNTAX OCTET STRING (SIZE (1..64))
            MAX-ACCESS read-create
            STATUS current
            DESCRIPTION
                "The default domain for portal."
            ::= { userAuthenProfileEntry 24 } 
            
        userAuthenProfileDefaultDomain OBJECT-TYPE   
            SYNTAX OCTET STRING (SIZE (1..64))
        	MAX-ACCESS read-create
            STATUS current
            DESCRIPTION
                "The default domain."
            ::= { userAuthenProfileEntry 25 }   
                
        userAuthenProfileForceDomain OBJECT-TYPE   
            SYNTAX OCTET STRING (SIZE (1..64))
        	MAX-ACCESS read-create
            STATUS current
            DESCRIPTION
                "The force domain."
            ::= { userAuthenProfileEntry 26 }
            
        userAuthenProfileDomainNameDelimiter OBJECT-TYPE
            SYNTAX OCTET STRING (SIZE (1..1))
        	MAX-ACCESS read-create
            STATUS current
            DESCRIPTION
                "Domain name delimiter."
            ::= { userAuthenProfileEntry 27 }  
            
        userAuthenProfileDomainNameLocation OBJECT-TYPE
            SYNTAX INTEGER
            {
            	domainnamepositionahead    (0),
            	domainnamepositionbehind   (1),
            	domainnamepositioninvalid  (2)
            }
        	MAX-ACCESS read-create
            STATUS current
            DESCRIPTION
                "Domain name location."
            ::= { userAuthenProfileEntry 28 }  
            
        userAuthenProfileDomainNameParseDirection OBJECT-TYPE
            SYNTAX INTEGER
            {
            	domainparselefttoright    (0),
            	domainparserighttoleft    (1),
            	domainparseinvalid        (2)
            }
        	MAX-ACCESS read-create
            STATUS current
            DESCRIPTION
                "Domain name parse direction."
            ::= { userAuthenProfileEntry 29 }

        userAuthenProfileSecurityNameDelimiter OBJECT-TYPE
        	SYNTAX OCTET STRING (SIZE (1..1))
        	MAX-ACCESS read-create
            STATUS current
            DESCRIPTION
                "The security name delimiter."
            ::= { userAuthenProfileEntry 30 }
        
        userAuthenProfilePreAuthenReAuthenTimer OBJECT-TYPE
        	SYNTAX Integer32 (0|30..7200)
        	MAX-ACCESS read-create 
        	STATUS current
            DESCRIPTION
                "The reauthenticate time for pre-authen."
            ::= { userAuthenProfileEntry 31 }   
            
        userAuthenProfileAuthenFailReAuthenTimer OBJECT-TYPE
        	SYNTAX Integer32 (0|30..7200)
        	MAX-ACCESS read-create 
        	STATUS current
            DESCRIPTION
                "The reauthenticate time for authen-fail."
            ::= { userAuthenProfileEntry 32 }
            
        userAuthenProfilePreAuthenAgingTime OBJECT-TYPE
        	SYNTAX Integer32 (0|60..4294860)
        	MAX-ACCESS read-create 
        	STATUS current
            DESCRIPTION
                "The aging time for pre-authen."
            ::= { userAuthenProfileEntry 33 }   
            
        userAuthenProfileAuthenFailAgingTime OBJECT-TYPE
        	SYNTAX Integer32 (0|60..4294860)
        	MAX-ACCESS read-create 
        	STATUS current
            DESCRIPTION
                "The aging time for authen-fail."
            ::= { userAuthenProfileEntry 34 } 
            
        userAuthenProfileFreeRuleName OBJECT-TYPE
        	SYNTAX OCTET STRING (SIZE (1..31))
        	MAX-ACCESS read-create
            STATUS current
            DESCRIPTION
                "The free rule name."
            ::= { userAuthenProfileEntry 35 }
            
        userAuthenProfileAuthenSchemeName OBJECT-TYPE
            SYNTAX OCTET STRING (SIZE (1..32))
        	MAX-ACCESS read-create
            STATUS current
            DESCRIPTION
                "The authentication scheme name."
            ::= { userAuthenProfileEntry 36 }
            
        userAuthenProfileAuthorSchemeName OBJECT-TYPE
            SYNTAX OCTET STRING (SIZE (1..32))
        	MAX-ACCESS read-create
            STATUS current
            DESCRIPTION
                "The authorization scheme name."
            ::= { userAuthenProfileEntry 37 }
            
        userAuthenProfileAcctSchemeName OBJECT-TYPE
            SYNTAX OCTET STRING (SIZE (1..32))
        	MAX-ACCESS read-create
            STATUS current
            DESCRIPTION
                "The accouting scheme name."
            ::= { userAuthenProfileEntry 38 }
            
        userAuthenProfileServiceSchemeName OBJECT-TYPE
            SYNTAX OCTET STRING (SIZE (1..32))
        	MAX-ACCESS read-create
            STATUS current
            DESCRIPTION
                "The service scheme name."
            ::= { userAuthenProfileEntry 39 }
        
        userAuthenProfileUserGroupName OBJECT-TYPE
        	SYNTAX OCTET STRING (SIZE (1..64))
        	MAX-ACCESS read-create
            STATUS current
            DESCRIPTION
                "The user group name."
            ::= { userAuthenProfileEntry 40 } 
            
        userAuthenProfileRadiusServerName OBJECT-TYPE
            SYNTAX OCTET STRING (SIZE (1..32))
        	MAX-ACCESS read-create
            STATUS current
            DESCRIPTION
                "The radius server name."
            ::= { userAuthenProfileEntry 41 }
            
        userAuthenProfileHwtacacsServerName OBJECT-TYPE
            SYNTAX OCTET STRING (SIZE (1..32))
        	MAX-ACCESS read-create
            STATUS current
            DESCRIPTION
                "The hwtacacs server name."
            ::= { userAuthenProfileEntry 42 }
            
        userAuthenProfileAuthenticationMode OBJECT-TYPE
            SYNTAX INTEGER
            { 
            	singleterminal(0),
            	singlevoicewithdata(1),
            	multishare(2),
            	multiterminal(3)            	
            }
        	MAX-ACCESS read-create
            STATUS current
            DESCRIPTION
                "The authentication mode."
            ::= { userAuthenProfileEntry 43 }
            
        userAuthenProfileMaxUser OBJECT-TYPE        
            SYNTAX Integer32
        	MAX-ACCESS read-create
            STATUS current
            DESCRIPTION
                "The max user number."
            ::= { userAuthenProfileEntry 44 }
            
        userAuthenProfileArpDetect OBJECT-TYPE        
            SYNTAX TruthValue
        	MAX-ACCESS read-create
            STATUS current
            DESCRIPTION
                "The arp detect switch."
            ::= { userAuthenProfileEntry 45 }
            
        userAuthenProfileArpDetectTimer OBJECT-TYPE
        	SYNTAX Integer32 (5..7200)
        	MAX-ACCESS read-create
            STATUS current
            DESCRIPTION
                "The arp detect period."
            ::= { userAuthenProfileEntry 46 }
                 
        userAuthenProfileRowStatus OBJECT-TYPE
        	SYNTAX RowStatus
            MAX-ACCESS read-create
            STATUS current
            DESCRIPTION
                "The row administration status, only supporting add or delete."
            ::= { userAuthenProfileEntry 47 }    
            
        userAuthenProfilePermitDomain OBJECT-TYPE    
        	SYNTAX OCTET STRING (SIZE (1..259))
        	MAX-ACCESS read-create
            STATUS current
            DESCRIPTION
                "The permit domain."
            ::= { userAuthenProfileEntry 48 }
		
		userAuthenProfileAuthenticationMaxUser OBJECT-TYPE    
        	SYNTAX Integer32 (1..512)
        	MAX-ACCESS read-create
            STATUS current
            DESCRIPTION
                "Wlan ess max user."
            ::= { userAuthenProfileEntry 49 }

         userAuthenProfileAuthenFailAuthorResponseSuccess OBJECT-TYPE
                    SYNTAX TruthValue
                    MAX-ACCESS read-create
                    STATUS current
                    DESCRIPTION
                         "The authen-fail response success."
                   ::= { userAuthenProfileEntry 50 }
        	
         userAuthenProfileIpAddrInAcctStart OBJECT-TYPE
                    SYNTAX TruthValue
                    MAX-ACCESS read-create
                    STATUS current
                    DESCRIPTION
                         "The IP address in accounting start packet."
                   ::= { userAuthenProfileEntry 51 }

         userAuthenProfileAccoutingStartAckPermitArp OBJECT-TYPE
                    SYNTAX TruthValue
                    MAX-ACCESS read-create
                    STATUS current
                    DESCRIPTION
                         "Permit ARP after account start ack."
                   ::= { userAuthenProfileEntry 52 }

        userAuthenProfileWebDescription OBJECT-TYPE    
        	SYNTAX OCTET STRING (SIZE (1..16))
        	MAX-ACCESS read-create
                 STATUS current
                 DESCRIPTION
                 "The description of authentication profile for the web user."
                ::= { userAuthenProfileEntry 53 } 

         userAuthenProfileIpTrigger OBJECT-TYPE
                    SYNTAX TruthValue
                    MAX-ACCESS read-create
                    STATUS current
                    DESCRIPTION
                         "Trigger portal authentication after learning ip."
                   ::= { userAuthenProfileEntry 54 }

        
                
        userAuthenProfileForcePushUrlTemplate OBJECT-TYPE
            SYNTAX OCTET STRING (SIZE (0..31))
            MAX-ACCESS read-create
            STATUS current
            DESCRIPTION
                "Force push URL template name."
            ::= { userAuthenProfileEntry 55 }

        userAuthenProfileForcePushUrl OBJECT-TYPE
            SYNTAX OCTET STRING (SIZE (0..200))
            MAX-ACCESS read-create
            STATUS current
            DESCRIPTION
                "Force push URL."
            ::= { userAuthenProfileEntry 56 }


        userAuthenProfileAccountingOfRoam OBJECT-TYPE
            SYNTAX TruthValue
            MAX-ACCESS read-create
            STATUS current
            DESCRIPTION
                "Roaming triggers real time billing."
            ::= { userAuthenProfileEntry 57 }

        
        userAuthenProfileAccountingOfUpdateIP OBJECT-TYPE
            SYNTAX TruthValue
            MAX-ACCESS read-create
            STATUS current
            DESCRIPTION
                "IP address update triggering billing."
            ::= { userAuthenProfileEntry 58 }

        
        userAuthenProfileAccountingOfUpdateInfo OBJECT-TYPE
            SYNTAX TruthValue
            MAX-ACCESS read-create
            STATUS current
            DESCRIPTION
                "Information update triggers billing."
            ::= { userAuthenProfileEntry 59 }

        
        userAuthenProfileNoIPCheck OBJECT-TYPE
            SYNTAX TruthValue
            MAX-ACCESS read-create
            STATUS current
            DESCRIPTION
                "Do not check IP address conflict."
            ::= { userAuthenProfileEntry 60 }
		
		userAuthenProfileLdapServerName OBJECT-TYPE
            SYNTAX OCTET STRING (SIZE (0..32))
        	MAX-ACCESS read-create
            STATUS current
            DESCRIPTION
                "The ldap server name."
            ::= { userAuthenProfileEntry 61 }
		userAuthenProfileAdServerName OBJECT-TYPE
            SYNTAX OCTET STRING (SIZE (0..32))
        	MAX-ACCESS read-create
            STATUS current
            DESCRIPTION
                "The ad server name."
            ::= { userAuthenProfileEntry 62 }
        		
		-- 1.3.6.1.4.1.2011.5.2.1.62.1.63
		userAuthenProfileRoamAccountingMode OBJECT-TYPE
			SYNTAX INTEGER
				{
				updateSessionMode(1),
				nonUpdateSessionMode(2)
				}
			MAX-ACCESS read-write
			STATUS current
			DESCRIPTION
				"Description."
			::= { userAuthenProfileEntry 63 }

         userAuthenProfileMacFirstForce OBJECT-TYPE
            SYNTAX TruthValue
            MAX-ACCESS read-create
            STATUS current
            DESCRIPTION
                "Force to do Mac Authentication First."
            ::= { userAuthenProfileEntry 64 }
            
        userAuthenProfileHacaServerName OBJECT-TYPE
            SYNTAX OCTET STRING (SIZE (0..32))
        	MAX-ACCESS read-create
            STATUS current
            DESCRIPTION
                "The HACA server name."
            ::= { userAuthenProfileEntry 65 }

        userAuthenProfileAcctRdsServerName OBJECT-TYPE
            SYNTAX OCTET STRING (SIZE (1..32))
        	MAX-ACCESS read-create
            STATUS current
            DESCRIPTION
                "The Accounting-copy RADIUS server name."
            ::= { userAuthenProfileEntry 66 }
			
        userAuthenticationFreeRuleTable OBJECT-TYPE
     	SYNTAX SEQUENCE OF UserAuthenticationFreeRuleEntry
            	MAX-ACCESS not-accessible
            	STATUS current
            	DESCRIPTION
                	"The authentication free rule table."
            	::= { hwAAAMibObjects 63 }
             			
        userAuthenticationFreeRuleEntry OBJECT-TYPE
            SYNTAX UserAuthenticationFreeRuleEntry
            MAX-ACCESS not-accessible
            STATUS current
            DESCRIPTION
                "The authentication free rule entry."
            INDEX { userAuthenticationFreeRuleName }
            ::= { userAuthenticationFreeRuleTable 1 }

        UserAuthenticationFreeRuleEntry ::=
            SEQUENCE {   
                userAuthenticationFreeRuleName 
                    DisplayString,
                userAuthenticationFreeRuleACLNumber
                    Integer32,
                userAuthenticationFreeRuleIPv6ACLNumber
                	Integer32,
                userAuthenticationFreeRuleRowStatus         
                    RowStatus
            }
            
        userAuthenticationFreeRuleName OBJECT-TYPE
            SYNTAX DisplayString (SIZE (1..31))
            MAX-ACCESS read-only
            STATUS current
            DESCRIPTION
                "The authentication free rule name."
            ::= { userAuthenticationFreeRuleEntry 1 }
            
        userAuthenticationFreeRuleACLNumber OBJECT-TYPE
        	SYNTAX Integer32 (0|6000..6031)
            MAX-ACCESS read-create
            STATUS current
            DESCRIPTION
                "The ACL number."
            ::= { userAuthenticationFreeRuleEntry 2 } 
             
        userAuthenticationFreeRuleIPv6ACLNumber OBJECT-TYPE  
            SYNTAX Integer32 (0|3000..3031)
            MAX-ACCESS read-create
            STATUS current
            DESCRIPTION
                "The ACL number for ipv6."
            ::= { userAuthenticationFreeRuleEntry 3 }  
                        
        userAuthenticationFreeRuleRowStatus OBJECT-TYPE
            SYNTAX RowStatus
            MAX-ACCESS read-create
            STATUS current
            DESCRIPTION
                "The row administration status, only supporting add or delete."
            ::= { userAuthenticationFreeRuleEntry 4 } 
            
        
        hwDot1xAccessProfileTable OBJECT-TYPE
     	SYNTAX SEQUENCE OF HwDot1xAccessProfileEntry 
               	MAX-ACCESS not-accessible
            	STATUS current
            	DESCRIPTION
                	"The dot1x access profile table."
            	::= { hwAAAMibObjects 64 }
             			
        hwDot1xAccessProfileEntry OBJECT-TYPE
            SYNTAX HwDot1xAccessProfileEntry
            MAX-ACCESS not-accessible
            STATUS current
            DESCRIPTION
                "The dot1x access profile entry."
            INDEX { hwDot1xAccessProfileName }
            ::= { hwDot1xAccessProfileTable 1 }
            
        HwDot1xAccessProfileEntry ::=
            SEQUENCE {
            	hwDot1xAccessProfileName 
            	    DisplayString,
            	hwDot1xAccessProfileGuestAuthorServiceSchemeName
            	    DisplayString,
        	hwDot1xAccessProfileGuestAuthorUserGroupName         
        	    DisplayString,
        	hwDot1xAccessProfileGuestAuthorVLAN         
        	    Integer32,        
        	hwDot1xAccessProfileHandshakeSwitch
        	    TruthValue,
	hwDot1xAccessProfileHandShakePktType
	    INTEGER,
        	hwDot1xAccessProfileHandshakeInterval 
        	    Integer32,
        	hwDot1xAccessProfileIfEAPEnd               
        	    TruthValue,
        	hwDot1xAccessProfileEAPEndMethod         
        	    INTEGER,
	hwDot1xAccessProfileEAPNotifyPktEAPCode    
	    Integer32,
	hwDot1xAccessProfileEAPNotifyPktEAPType    
	    Integer32,
        	hwDot1xAccessProfileReAuthenEnable       
        	    TruthValue,
        	hwDot1xAccessProfileReauthenticationTimeout     
        	    Integer32,
        	hwDot1xAccessProfileClientTimeout     
        	    Integer32,
       	hwDot1xAccessProfileServerTimeout     
       	    Integer32,
        	hwDot1xAccessProfileTxPeriod     
        	    Integer32,
        	hwDot1xAccessProfileMaxRetryValue     
        	    Integer32,
        	hwDot1xAccessProfileSpeedLimitAuto       
        	    TruthValue, 
        	hwDot1xAccessProfileTriggerPktType
        	    INTEGER,
        	hwDot1xAccessProfileUnicastTrigger 
        	    TruthValue,
        	hwDot1xAccessProfileURL         
        	    DisplayString,
        	hwDot1xAccessProfileEthTrunkHandShakePeriod
        	    Integer32,
        	hwDot1xAccessProfileRowStatus         
        	    RowStatus,  
         	hwDot1xAccessProfileDot1xNoResponse       
        	    TruthValue

        	}
        
        hwDot1xAccessProfileName OBJECT-TYPE
            SYNTAX DisplayString (SIZE (1..31))
            MAX-ACCESS read-only
            STATUS current
            DESCRIPTION
                "The dot1x access profile name."
            ::= { hwDot1xAccessProfileEntry 1 }
            
        hwDot1xAccessProfileGuestAuthorServiceSchemeName OBJECT-TYPE
            SYNTAX DisplayString (SIZE (1..32))
            MAX-ACCESS read-create
            STATUS current
            DESCRIPTION
                "The guest service scheme name."
            ::= { hwDot1xAccessProfileEntry 2 }
             
        hwDot1xAccessProfileGuestAuthorUserGroupName OBJECT-TYPE
            SYNTAX DisplayString (SIZE (1..64))
            MAX-ACCESS read-create
            STATUS current
            DESCRIPTION
                "The guest user group name."
            ::= { hwDot1xAccessProfileEntry 3 }

        hwDot1xAccessProfileGuestAuthorVLAN OBJECT-TYPE
            SYNTAX Integer32 (0..4094)
            MAX-ACCESS read-create
            STATUS current
            DESCRIPTION
                "The guest VLAN."
            ::= { hwDot1xAccessProfileEntry 4 } 
        
        hwDot1xAccessProfileHandshakeSwitch OBJECT-TYPE
            SYNTAX TruthValue
            MAX-ACCESS read-create
            STATUS current
            DESCRIPTION
                "The handshake switch."
            ::= { hwDot1xAccessProfileEntry 5 }
            
        hwDot1xAccessProfileHandShakePktType OBJECT-TYPE
            SYNTAX INTEGER
            {
                default(1),
                srpsha1(20)
            }
            MAX-ACCESS read-create
            STATUS current
            DESCRIPTION
                "The handshake packet type."
            ::= { hwDot1xAccessProfileEntry 6 } 
            
        hwDot1xAccessProfileHandshakeInterval OBJECT-TYPE
            SYNTAX Integer32 (5..7200)
            MAX-ACCESS read-create
            STATUS current
            DESCRIPTION
                "The handshake period."
            ::= { hwDot1xAccessProfileEntry 7 }
            
        hwDot1xAccessProfileIfEAPEnd OBJECT-TYPE
            SYNTAX TruthValue
            MAX-ACCESS read-only
            STATUS current
            DESCRIPTION
                "The EAP end."
            ::= { hwDot1xAccessProfileEntry 8 }   
            
        hwDot1xAccessProfileEAPEndMethod OBJECT-TYPE
            SYNTAX INTEGER 
        	{
        		chap(1),
        		pap(2),
        		eap(3)
        	}
            MAX-ACCESS read-create
            STATUS current
            DESCRIPTION
                "The authentication method."
            ::= { hwDot1xAccessProfileEntry 9 }
             
        hwDot1xAccessProfileEAPNotifyPktEAPCode OBJECT-TYPE
            SYNTAX Integer32  (5..255)
            MAX-ACCESS read-create
            STATUS current
            DESCRIPTION
                "The EAP packet type."
            ::= { hwDot1xAccessProfileEntry 10 } 
            
        hwDot1xAccessProfileEAPNotifyPktEAPType OBJECT-TYPE
            SYNTAX Integer32  (1..255)
            MAX-ACCESS read-create
            STATUS current
            DESCRIPTION
                "The EAP packet data type."
            ::= { hwDot1xAccessProfileEntry 11 }
                          
        hwDot1xAccessProfileReAuthenEnable OBJECT-TYPE
            SYNTAX TruthValue
            MAX-ACCESS read-create
            STATUS current
            DESCRIPTION
                "Enable reauthenticate."
            ::= { hwDot1xAccessProfileEntry 12 }
            
        hwDot1xAccessProfileReauthenticationTimeout OBJECT-TYPE 
            SYNTAX Integer32  (1..65535)
            MAX-ACCESS read-create
            STATUS current
            DESCRIPTION
                "The reauthenticate time."
            ::= { hwDot1xAccessProfileEntry 13 }
            
        hwDot1xAccessProfileClientTimeout OBJECT-TYPE
            SYNTAX Integer32 (1..120)
            MAX-ACCESS read-create
            STATUS current
            DESCRIPTION
                "The client timeout."
            ::= { hwDot1xAccessProfileEntry 14 }
               
        hwDot1xAccessProfileServerTimeout OBJECT-TYPE
            SYNTAX Integer32 (1..120)
            MAX-ACCESS read-create
            STATUS current
            DESCRIPTION
                "The server timeout."
            ::= { hwDot1xAccessProfileEntry 15 } 
            
        hwDot1xAccessProfileTxPeriod OBJECT-TYPE 
            SYNTAX Integer32  (1..120)
            MAX-ACCESS read-create
            STATUS current
            DESCRIPTION
                "The tx period."
            ::= { hwDot1xAccessProfileEntry 16 }
            
        hwDot1xAccessProfileMaxRetryValue OBJECT-TYPE
            SYNTAX Integer32  (1..10)
            MAX-ACCESS read-create
            STATUS current
            DESCRIPTION
                "The max retry value."
            ::= { hwDot1xAccessProfileEntry 17 }
            
        hwDot1xAccessProfileSpeedLimitAuto OBJECT-TYPE
            SYNTAX TruthValue
            MAX-ACCESS read-create
            STATUS current
            DESCRIPTION
                "Enable speed limit automatically."
            ::= { hwDot1xAccessProfileEntry 18 } 
        
        hwDot1xAccessProfileTriggerPktType OBJECT-TYPE
            SYNTAX INTEGER
        	{
        		default(0),
        		arp(1),
        		dhcp(2)
        	}
            MAX-ACCESS read-create
            STATUS current
            DESCRIPTION
                "The max retry value."
            ::= { hwDot1xAccessProfileEntry 19 }
            
        hwDot1xAccessProfileUnicastTrigger OBJECT-TYPE
            SYNTAX TruthValue
            MAX-ACCESS read-create
            STATUS current
            DESCRIPTION
                "The unicast trigger switch."
            ::= { hwDot1xAccessProfileEntry 20 }
        
        hwDot1xAccessProfileURL OBJECT-TYPE
            SYNTAX DisplayString (SIZE(1..200))
            MAX-ACCESS read-create
            STATUS current
            DESCRIPTION
                "The url."
            ::= { hwDot1xAccessProfileEntry 21 }
        
        hwDot1xAccessProfileEthTrunkHandShakePeriod OBJECT-TYPE
            SYNTAX Integer32  (30..7200)
            MAX-ACCESS read-create
            STATUS current
            DESCRIPTION
                "The handshake period for Eth-Trunk port."
            ::= { hwDot1xAccessProfileEntry 22 }
        		         		          
        hwDot1xAccessProfileRowStatus OBJECT-TYPE
            SYNTAX RowStatus
            MAX-ACCESS read-create
            STATUS current
            DESCRIPTION
                "The row administration status, only supporting add or delete."
            ::= { hwDot1xAccessProfileEntry 23 }
                       
        hwDot1xAccessProfileDot1xNoResponse OBJECT-TYPE
            SYNTAX TruthValue
            MAX-ACCESS read-create
            STATUS current
            DESCRIPTION
                "Dot1x no-response authorize authen-server-down,enable is 1,disable is 2"
            ::= { hwDot1xAccessProfileEntry 24 }
   
        hwMACAuthenAccessProfileTable OBJECT-TYPE
     	SYNTAX SEQUENCE OF HwMACAuthenAccessProfileEntry 
               	MAX-ACCESS not-accessible
            	STATUS current
            	DESCRIPTION
                	"The MAC-authen access profile table."
            	::= { hwAAAMibObjects 65 }
             			
        hwMACAuthenAccessProfileEntry OBJECT-TYPE
            SYNTAX HwMACAuthenAccessProfileEntry
            MAX-ACCESS not-accessible
            STATUS current
            DESCRIPTION
                "The MAC-authen access profile entry."
            INDEX { hwMACAuthenAccessProfileName }
            ::= { hwMACAuthenAccessProfileTable 1 }
            
        HwMACAuthenAccessProfileEntry ::=
            SEQUENCE {  
            	hwMACAuthenAccessProfileName
            	    DisplayString,
        	hwMACAuthenAccessProfileReAuthenEnable       
       	    TruthValue,
        	hwMACAuthenAccessProfileReauthenticationTimeout     
        	     Integer32,
	hwMACAuthenAccessProfileServerTimeout     
	    Integer32,
        	hwMACAuthenAccessProfileUserNameFixedUserName     
        	    OCTET STRING,
	hwMACAuthenAccessProfileFixedPassword    
	    OCTET STRING,
	hwMACAuthenAccessProfileMACAddressFormat    
	    INTEGER,
	hwMACAuthenAccessProfileMACAddressPassword    
	    OCTET STRING,
	hwMACAuthenAccessProfileUserNameDHCPOption    
	    INTEGER,
	hwMACAuthenAccessProfileUserNameDHCPOSubOption    
	    INTEGER,
	hwMACAuthenAccessProfileTriggerPktType
	    Integer32,
	hwMACAuthenAccessProfileTriggerDHCPOptionType
	    INTEGER,
	hwMACAuthenAccessProfileDHCPRelaseOffline
	    TruthValue,
	hwMACAuthenAccessProfileDHCPRenewReAuthen
	    TruthValue,
	hwMACAuthenAccessProfilePermitAuthenMAC 
	    OCTET STRING,
	hwMACAuthenAccessProfilePermitAuthenMACMask
	    OCTET STRING,
        	hwMACAuthenAccessProfileRowStatus         
        	    RowStatus, 
        	hwMACAuthenProfileAuthMethod
        	    INTEGER
        	} 
        	
        hwMACAuthenAccessProfileName OBJECT-TYPE 
            SYNTAX DisplayString (SIZE (1..31))
            MAX-ACCESS read-only
            STATUS current
            DESCRIPTION
                "The MAC-authen access profile name."
            ::= { hwMACAuthenAccessProfileEntry 1 }  
                        
        hwMACAuthenAccessProfileReAuthenEnable OBJECT-TYPE
            SYNTAX TruthValue
            MAX-ACCESS read-create
            STATUS current
            DESCRIPTION
                "The reauthenticate switch."
            ::= { hwMACAuthenAccessProfileEntry 2 }
                      	
        hwMACAuthenAccessProfileReauthenticationTimeout OBJECT-TYPE
            SYNTAX Integer32  (1..65535)
            MAX-ACCESS read-create
            STATUS current
            DESCRIPTION
                "The reauthenticate period."
            ::= { hwMACAuthenAccessProfileEntry 3 } 
               
        hwMACAuthenAccessProfileServerTimeout OBJECT-TYPE
            SYNTAX Integer32  (1..120)
            MAX-ACCESS read-create
            STATUS current
            DESCRIPTION
                "The server timeout period."
            ::= { hwMACAuthenAccessProfileEntry 4 }
            
        hwMACAuthenAccessProfileUserNameFixedUserName OBJECT-TYPE
            SYNTAX OCTET STRING  (SIZE (1..64))
            MAX-ACCESS read-create
            STATUS current
            DESCRIPTION
                "The fixed username."
            ::= { hwMACAuthenAccessProfileEntry 5 }
            
        hwMACAuthenAccessProfileFixedPassword OBJECT-TYPE
            SYNTAX OCTET STRING  (SIZE (1..128))
            MAX-ACCESS read-create
            STATUS current
            DESCRIPTION
                "The fixed password."
            ::= { hwMACAuthenAccessProfileEntry 6 }
                
        hwMACAuthenAccessProfileMACAddressFormat OBJECT-TYPE
            SYNTAX INTEGER 
        	{
        		invalid(0),
        		macAddressWithoutHyphen(1),
        		macAddressWithHyphen(2),
        		fixed(3),
        		option(4),
        		macAddressWithHyphenNormal(5),
        		macAddressWithoutHyphenUpper(6),
        		macAddressWithHyphenUpper(7),
                                      macAddressWithHyphenNormalUpper(8),
                                      fixedUpper(9),
                                      macAddressWithHyphenColon(10),
                                      macAddressWithHyphenNormalColon(11),
                                      macAddressWithHyphenColonUpper(12),
                                      macAddressWithHyphenNormalColonUpper(13)


        	}
            MAX-ACCESS read-create
            STATUS current
            DESCRIPTION
                "The  MAC address format."
            ::= { hwMACAuthenAccessProfileEntry 7 } 
            
        hwMACAuthenAccessProfileMACAddressPassword OBJECT-TYPE
            SYNTAX OCTET STRING (SIZE (1..128))
            MAX-ACCESS read-create
            STATUS current
            DESCRIPTION
                "The MAC address password."
            ::= { hwMACAuthenAccessProfileEntry 8 }
              
        hwMACAuthenAccessProfileUserNameDHCPOption OBJECT-TYPE
            SYNTAX INTEGER
        	{
        	    default(0),
        	    dhcpoption(82)
        	}
            MAX-ACCESS read-create
            STATUS current
            DESCRIPTION
                "The DHCP option."
            ::= { hwMACAuthenAccessProfileEntry 9 }
              
        hwMACAuthenAccessProfileUserNameDHCPOSubOption OBJECT-TYPE
            SYNTAX INTEGER  
        	{
        		optionsubinvalid(0),
        		optionsubcircuitid(1),
        		optionremoteid(2)
        	}
            MAX-ACCESS read-create
            STATUS current
            DESCRIPTION
                "The DHCP suboption."
            ::= { hwMACAuthenAccessProfileEntry 10 }
            
        hwMACAuthenAccessProfileTriggerPktType OBJECT-TYPE
            SYNTAX Integer32 (1..255)
            MAX-ACCESS read-create
            STATUS current
            DESCRIPTION
                "The trigger packet type.
                0xFF all
                0x02 arp
                0x04 dhcp
                0x08 nd
                0x10 dhcpv6"
            ::= { hwMACAuthenAccessProfileEntry 11 }
            
        hwMACAuthenAccessProfileTriggerDHCPOptionType OBJECT-TYPE
            SYNTAX INTEGER
			{
                                                                                     default(0),
				optioncode(82)
			}
            MAX-ACCESS read-create
            STATUS current
            DESCRIPTION
                "The DHCP suboption."
            ::= { hwMACAuthenAccessProfileEntry 12 }
            
		hwMACAuthenAccessProfileDHCPRelaseOffline OBJECT-TYPE
			SYNTAX TruthValue
            MAX-ACCESS read-create
            STATUS current
            DESCRIPTION
                "The dhcp release offline switch ."
            ::= { hwMACAuthenAccessProfileEntry 13 } 
            
        hwMACAuthenAccessProfileDHCPRenewReAuthen OBJECT-TYPE
            SYNTAX TruthValue
            MAX-ACCESS read-create
            STATUS current
            DESCRIPTION
                "The dhcp renew reauthenticate switch."
            ::= { hwMACAuthenAccessProfileEntry 14 }
            
        hwMACAuthenAccessProfilePermitAuthenMAC OBJECT-TYPE
            SYNTAX OCTET STRING (SIZE (1..128))
            MAX-ACCESS read-create
            STATUS current
            DESCRIPTION
                "The permit mac address."
            ::= { hwMACAuthenAccessProfileEntry 15 }
            
        hwMACAuthenAccessProfilePermitAuthenMACMask OBJECT-TYPE
            SYNTAX OCTET STRING (SIZE (1..128))
            MAX-ACCESS read-create
            STATUS current
            DESCRIPTION
                "The mask of permit mac address."
            ::= { hwMACAuthenAccessProfileEntry 16 }

        hwMACAuthenAccessProfileRowStatus OBJECT-TYPE
        	SYNTAX RowStatus
            MAX-ACCESS read-create
            STATUS current
            DESCRIPTION
                "The row administration status, only supporting add or delete."
            ::= { hwMACAuthenAccessProfileEntry 17 } 
   
        hwMACAuthenProfileAuthMethod OBJECT-TYPE
            SYNTAX INTEGER
            {
                chap(1),
                pap(2)
            }
            MAX-ACCESS read-create
            STATUS current
            DESCRIPTION
                "The authentication method."
            ::= { hwMACAuthenAccessProfileEntry 18 }    
            
        hwPortalAccessProfileTable OBJECT-TYPE
     	SYNTAX SEQUENCE OF HwPortalAccessProfileEntry 
               	MAX-ACCESS not-accessible
            	STATUS current
            	DESCRIPTION
                	"The portal access profile table."
            	::= { hwAAAMibObjects 66 }
             			
        hwPortalAccessProfileEntry OBJECT-TYPE
            SYNTAX HwPortalAccessProfileEntry
            MAX-ACCESS not-accessible
            STATUS current
            DESCRIPTION
                "The portal access profile entry."
            INDEX { hwPortalAccessProfileName }
            ::= { hwPortalAccessProfileTable 1 }
            
        HwPortalAccessProfileEntry ::=
            SEQUENCE {     
            	                                                                hwPortalAccessProfileName         
            		                                               DisplayString,
				hwPortalAccessProfileDetectPeriod
				    Integer32,				
				hwPortalAccessProfilePortalServerDownServiceSchemeName    
				    OCTET STRING,
				hwPortalAccessProfilePortalServerDownUserGroupName     
					OCTET STRING,
				hwPortalAccessProfilePortalServerUpReAuthen     
					TruthValue,
				hwPortalAccessProfileAlarmUserLowNum    
					Integer32,
				hwPortalAccessProfileAlarmUserHighNum    
					Integer32,
				hwPortalAccessProfileAuthenNetWork    
					OCTET STRING,
				hwPortalAccessProfileAuthenNetWorkMask    
					OCTET STRING,
				hwPortalAccessProfilePortalServerName      
					DisplayString,
				hwPortalAccessProfilePortalAccessDirect      
					INTEGER,
				hwPortalAccessProfileLocalServerEnable       
					TruthValue,
                                                                                     hwPortalAccessProfileLocalServerAnonymous 
					TruthValue,
				hwPortalAccessProfileRowStatus         
					RowStatus,
			        hwPortalAccessProfilePortalBackupServerName      
					DisplayString,
                                                                 hwPortalAccessProfileLocalServerAnonymousUrl
                                                                                                OCTET STRING,
                                                                                hwPortalAccessProfileWebProxyEnable
                                                                                                      TruthValue,
                                                                                hwPortalAccessProfileWebProxyPort
                                                                                                       Integer32,
				hwPortalAccessProfileLocalServerAccessCode
					TruthValue	
			}
			
        hwPortalAccessProfileName OBJECT-TYPE
            SYNTAX DisplayString (SIZE (1..31))
            MAX-ACCESS read-only
            STATUS current
            DESCRIPTION
                "The portal access profile name."
            ::= { hwPortalAccessProfileEntry 1 }
            
		hwPortalAccessProfileDetectPeriod OBJECT-TYPE
			SYNTAX Integer32 (0|30..7200)
            MAX-ACCESS read-create
            STATUS current
            DESCRIPTION
                "The detect period."
            ::= { hwPortalAccessProfileEntry 2 }  
                        
		hwPortalAccessProfilePortalServerDownServiceSchemeName OBJECT-TYPE
			SYNTAX OCTET STRING (SIZE (0..32))
            MAX-ACCESS read-create
            STATUS current
            DESCRIPTION
                "The portal server down service scheme."
            ::= { hwPortalAccessProfileEntry 3 }
              
		hwPortalAccessProfilePortalServerDownUserGroupName OBJECT-TYPE
			SYNTAX OCTET STRING (SIZE (0..64))
            MAX-ACCESS read-create
            STATUS current
            DESCRIPTION
                "The portal server down user group."
            ::= { hwPortalAccessProfileEntry 4 } 
            
		hwPortalAccessProfilePortalServerUpReAuthen OBJECT-TYPE
			SYNTAX TruthValue
            MAX-ACCESS read-create
            STATUS current
            DESCRIPTION
                "The portal server up reauthenticate."
            ::= { hwPortalAccessProfileEntry 5 }
             
		hwPortalAccessProfileAlarmUserLowNum OBJECT-TYPE
			SYNTAX Integer32 (1..100)
            MAX-ACCESS read-create
            STATUS current
            DESCRIPTION
                "The minum alarm user number."
            ::= { hwPortalAccessProfileEntry 6 } 
             
		hwPortalAccessProfileAlarmUserHighNum OBJECT-TYPE
			SYNTAX Integer32 (1..100)
            MAX-ACCESS read-create
            STATUS current
            DESCRIPTION
                "The maxium alarm user number."
            ::= { hwPortalAccessProfileEntry 7 }
              
		hwPortalAccessProfileAuthenNetWork OBJECT-TYPE
			SYNTAX OCTET STRING (SIZE(1..1024))
            MAX-ACCESS read-create
            STATUS current
            DESCRIPTION
                "The ip address of  authentication network."
            ::= { hwPortalAccessProfileEntry 8 } 
            
		hwPortalAccessProfileAuthenNetWorkMask OBJECT-TYPE
			SYNTAX OCTET STRING (SIZE(1..1024))
            MAX-ACCESS read-create
            STATUS current
            DESCRIPTION
                "The mask of ip address of  authentication network."
            ::= { hwPortalAccessProfileEntry 9 }
             
            hwPortalAccessProfilePortalServerName OBJECT-TYPE
            SYNTAX DisplayString (SIZE(0..31))
            MAX-ACCESS read-create
            STATUS current
            DESCRIPTION
                "The portal server name."
            ::= { hwPortalAccessProfileEntry 10 }
              
            hwPortalAccessProfilePortalAccessDirect OBJECT-TYPE
			SYNTAX INTEGER
                                                               {
				invalid(0),
				direct(2),
				layer3(3)	
			}
            MAX-ACCESS read-create
            STATUS current
            DESCRIPTION
                "The type of portal authentication."
            ::= { hwPortalAccessProfileEntry 11 }

            hwPortalAccessProfileLocalServerEnable OBJECT-TYPE
			SYNTAX TruthValue
            MAX-ACCESS read-create
            STATUS current
            DESCRIPTION
                "The local portal server switch."
            ::= { hwPortalAccessProfileEntry 12 }

            hwPortalAccessProfileLocalServerAnonymous OBJECT-TYPE
			SYNTAX TruthValue
            MAX-ACCESS read-create
            STATUS current
            DESCRIPTION
                "The local portal server anonymous switch."
            ::= { hwPortalAccessProfileEntry 13 }
             
            hwPortalAccessProfileRowStatus OBJECT-TYPE
            SYNTAX RowStatus
            MAX-ACCESS read-create
            STATUS current
            DESCRIPTION
                "The row administration status, only supporting add or delete."
            ::= { hwPortalAccessProfileEntry 14 } 
        
	    hwPortalAccessProfilePortalBackupServerName OBJECT-TYPE
            SYNTAX DisplayString (SIZE(0..31))
            MAX-ACCESS read-create
            STATUS current
            DESCRIPTION
                "The portal backup server name."
            ::= { hwPortalAccessProfileEntry 15 }

	    hwPortalAccessProfileLocalServerAnonymousUrl OBJECT-TYPE
            SYNTAX OCTET STRING (SIZE(1..200))
            MAX-ACCESS read-create
            STATUS current
            DESCRIPTION
                "The portal local-server anonymouse url."
            ::= { hwPortalAccessProfileEntry 16 }

        hwPortalAccessProfileWebProxyEnable OBJECT-TYPE
			SYNTAX TruthValue
            MAX-ACCESS read-create
            STATUS current
            DESCRIPTION
                "The portal server web proxy."
            ::= { hwPortalAccessProfileEntry 17 }  
                        
        hwPortalAccessProfileWebProxyPort OBJECT-TYPE
			SYNTAX Integer32 (0..65535)
            MAX-ACCESS read-create
            STATUS current
            DESCRIPTION
                "The portal server web proxy port."
            ::= { hwPortalAccessProfileEntry 18 }
		
            hwPortalAccessProfileLocalServerAccessCode OBJECT-TYPE
            SYNTAX TruthValue
            MAX-ACCESS read-create
            STATUS current
            DESCRIPTION
                "The portal local server access code switch."
            ::= { hwPortalAccessProfileEntry 19 }

		--  ============== hwAAAInboundVPNAccessUserStatTable ============== 
        hwAAAInboundVPNAccessUserStatTable OBJECT-TYPE
            SYNTAX SEQUENCE OF HwAAAInboundVPNAccessUserStatEntry
            MAX-ACCESS not-accessible
            STATUS current
            DESCRIPTION
                "hwAAAInboundVPNAccessUserStatTable"
            ::= { hwAAAMibObjects 67 }     
            
        hwAAAInboundVPNAccessUserStatEntry OBJECT-TYPE
            SYNTAX HwAAAInboundVPNAccessUserStatEntry
            MAX-ACCESS not-accessible
            STATUS current
            DESCRIPTION
                "hwAAAInboundVPNAccessUserStatEntry"
            INDEX { hwAAAInboundVPNUserType, hwAAAInboundVPNName }
            ::= { hwAAAInboundVPNAccessUserStatTable 1 }
                                                 
        HwAAAInboundVPNAccessUserStatEntry ::=
            SEQUENCE {
                hwAAAInboundVPNUserType         INTEGER,
                hwAAAInboundVPNName             DisplayString,
                hwAAAInboundVPNAccessUserStat   Integer32
             }

        hwAAAInboundVPNUserType OBJECT-TYPE
            SYNTAX INTEGER
                {
                pppoe(1),
                pppoa(2),
                dhcp(3),
                lns(4),
                lac(5),
                ipv4(6),
                ipv6(7),
                dualStack(8),
                all(9)
                }
            MAX-ACCESS read-only
            STATUS current
            DESCRIPTION
                "user type
                1:pppoe
                2:pppoa
                3:dhcp
                4:lns
                5:lac
                6:ipv4
                7:ipv6
                8:dualStack
                9:all"
            ::= { hwAAAInboundVPNAccessUserStatEntry 1 }

                      
        hwAAAInboundVPNName OBJECT-TYPE
            SYNTAX DisplayString (SIZE (1..31))
            MAX-ACCESS read-only
            STATUS current
            DESCRIPTION
                "hwAAAInboundVPNName"
            ::= { hwAAAInboundVPNAccessUserStatEntry 2 }
                                                          
        hwAAAInboundVPNAccessUserStat OBJECT-TYPE
            SYNTAX Integer32 (0..2147483647)
            MAX-ACCESS read-only
            STATUS current
            DESCRIPTION
                "hwAAAInboundVPNAccessUserStat"
            ::= { hwAAAInboundVPNAccessUserStatEntry 3 }   

        --  ============== hwInterfaceAccessUserStatTable ==============                                                 
	    
        --  ============== FreeRule Extend Begin ==============
 		userAuthenticationFreeRuleExtTable OBJECT-TYPE
     			SYNTAX SEQUENCE OF UserAuthenticationFreeRuleExtEntry
            	MAX-ACCESS not-accessible
            	STATUS current
            	DESCRIPTION
                	"The authentication free rule extend table."
            	::= { hwAAAMibObjects 68 }
             			
        userAuthenticationFreeRuleExtEntry OBJECT-TYPE
            SYNTAX UserAuthenticationFreeRuleExtEntry
            MAX-ACCESS not-accessible
            STATUS current
            DESCRIPTION
                "The authentication free rule extend entry."
            INDEX { userAuthenticationFreeRuleName , userAuthenticationFreeRuleNumber }
            ::= { userAuthenticationFreeRuleExtTable 1 }

        UserAuthenticationFreeRuleExtEntry ::=
            SEQUENCE {   
            	userAuthenticationFreeRuleNumber
           			Integer32,
           		userAuthenticationFreeRuleSourceMode
           			Integer32,
           		userAuthenticationFreeRuleSourceVlan
           			Integer32,
           		userAuthenticationFreeRuleSourceInterface
           			OCTET STRING,
          		userAuthenticationFreeRuleSourceIP 			
            		IpAddress,
            	userAuthenticationFreeRuleSourceIPMask 
            		IpAddress,
            	userAuthenticationFreeRuleSourceMac
                    MacAddress,
                userAuthenticationFreeRuleDestinationMode
                    Integer32,
                userAuthenticationFreeRuleDestinationIP
                	IpAddress,
                userAuthenticationFreeRuleDestinationIPMask
                	IpAddress,
                userAuthenticationFreeRuleDestinationProtocol	
                	INTEGER,
                userAuthenticationFreeRuleDestinationPort
                	Integer32,
                userAuthenticationFreeRuleDestinationUserGroup		    
                    OCTET STRING,
                userAuthenticationFreeRuleExtRowStatus         
                    RowStatus
            }
                        
        userAuthenticationFreeRuleNumber OBJECT-TYPE  
        	SYNTAX Integer32 (0..129)
            MAX-ACCESS read-only
            STATUS current
            DESCRIPTION
                "The free rule id."
            ::= { userAuthenticationFreeRuleExtEntry 1 }
                       
        userAuthenticationFreeRuleSourceMode OBJECT-TYPE
        	SYNTAX Integer32 (0..3)
            MAX-ACCESS read-only
            STATUS current
            DESCRIPTION
                "The free rule source mode."
            ::= { userAuthenticationFreeRuleExtEntry 2 }      
            
        userAuthenticationFreeRuleSourceVlan OBJECT-TYPE
        	SYNTAX Integer32 (0..4094)
            MAX-ACCESS read-only
            STATUS current
            DESCRIPTION
                "The free rule source vlan."
            ::= { userAuthenticationFreeRuleExtEntry 3 }
              
        userAuthenticationFreeRuleSourceInterface OBJECT-TYPE
        	SYNTAX OCTET STRING (SIZE(1..63)) 
        	MAX-ACCESS read-only
            STATUS current
            DESCRIPTION
                "The free rule source interface."
            ::= { userAuthenticationFreeRuleExtEntry 4 } 
            
        userAuthenticationFreeRuleSourceIP OBJECT-TYPE
        	SYNTAX IpAddress 
        	MAX-ACCESS read-only
            STATUS current
            DESCRIPTION
                "The free rule source ip address."
            ::= { userAuthenticationFreeRuleExtEntry 5 }
             
        userAuthenticationFreeRuleSourceIPMask OBJECT-TYPE
        	SYNTAX IpAddress 
        	MAX-ACCESS read-only
            STATUS current
            DESCRIPTION
                "The mask of free rule source ip address."
            ::= { userAuthenticationFreeRuleExtEntry 6 }
               
        userAuthenticationFreeRuleSourceMac OBJECT-TYPE
            SYNTAX MacAddress 
        	MAX-ACCESS read-only
            STATUS current
            DESCRIPTION
                "The free rule source mac address."
            ::= { userAuthenticationFreeRuleExtEntry 7 }  
            
        userAuthenticationFreeRuleDestinationMode OBJECT-TYPE
        	SYNTAX Integer32 (0..3) 
        	MAX-ACCESS read-only
            STATUS current
            DESCRIPTION
                "The free rule destination mode."
            ::= { userAuthenticationFreeRuleExtEntry 8 }
                
        userAuthenticationFreeRuleDestinationIP OBJECT-TYPE
        	SYNTAX IpAddress 
        	MAX-ACCESS read-only
            STATUS current
            DESCRIPTION
                "The free rule destination ip address."
            ::= { userAuthenticationFreeRuleExtEntry 9 }
    
        userAuthenticationFreeRuleDestinationIPMask OBJECT-TYPE
        	SYNTAX IpAddress 
        	MAX-ACCESS read-only
            STATUS current
            DESCRIPTION
                "The mask of free rule destination ip address."
            ::= { userAuthenticationFreeRuleExtEntry 10 }
               
        userAuthenticationFreeRuleDestinationProtocol OBJECT-TYPE 
        	SYNTAX INTEGER
        	{
        		tcp(1),
        		udp(2),
        		none(3)
        	}
        	MAX-ACCESS read-only
            STATUS current
            DESCRIPTION
                "The free rule destination protocol."
            ::= { userAuthenticationFreeRuleExtEntry 11 } 
              
        userAuthenticationFreeRuleDestinationPort OBJECT-TYPE
        	SYNTAX Integer32 
        	MAX-ACCESS read-only
            STATUS current
            DESCRIPTION
                "The free rule destination port."
            ::= { userAuthenticationFreeRuleExtEntry 12 }
                
        userAuthenticationFreeRuleDestinationUserGroup OBJECT-TYPE
        	SYNTAX OCTET STRING (SIZE(1..64)) 
        	MAX-ACCESS read-only
            STATUS current
            DESCRIPTION
                "The free rule destination user group."
            ::= { userAuthenticationFreeRuleExtEntry 13 }
            
        userAuthenticationFreeRuleExtRowStatus OBJECT-TYPE
        	SYNTAX RowStatus
            MAX-ACCESS read-create
            STATUS current
            DESCRIPTION
                "The row administration status, only supporting add or delete."
            ::= { userAuthenticationFreeRuleExtEntry 14 } 
	    -- =============== FreeRule Extend End =================
                 
--===pwif begin===
       
        hwAAAPwifSlotConnectNumTable OBJECT-TYPE
            SYNTAX SEQUENCE OF HwAAAPwifSlotConnectNumEntry
            MAX-ACCESS not-accessible
            STATUS current 
            DESCRIPTION
                "This table is used to collect statistics about the number of user who go online from the subcard in the specified slot in the virtual access scenario."
            ::= { hwAAAMibObjects 69 }
        
            hwAAAPwifSlotConnectNumEntry OBJECT-TYPE
                  SYNTAX HwAAAPwifSlotConnectNumEntry
                  MAX-ACCESS not-accessible
                  STATUS current
                  DESCRIPTION
                            "Slot Query Online Number Entry
                            "
                        INDEX { hwAAAPwifSlotConnectNumSlot }
                        ::= { hwAAAPwifSlotConnectNumTable 1 }
        
                    HwAAAPwifSlotConnectNumEntry ::=
                        SEQUENCE { 
                            hwAAAPwifSlotConnectNumSlot
                                OCTET STRING,
                            hwAAAPwifSlotConnectNumOnlineNum
                                Integer32,
                            hwAAAPwifSlotConnectNumMaxOnlineNum
                                Integer32,
                            hwAAAPwifSlotConnectNumMaxOnlineAcctReadyNum
                                Integer32                  
                        }

                    hwAAAPwifSlotConnectNumSlot OBJECT-TYPE
                        SYNTAX OCTET STRING (SIZE (1..16))
                        MAX-ACCESS read-only
                        STATUS current
                        DESCRIPTION
                            "This object indicates the slot ID of the device.
"
                        ::= { hwAAAPwifSlotConnectNumEntry 1 }


                    hwAAAPwifSlotConnectNumOnlineNum OBJECT-TYPE
                        SYNTAX Integer32
                        MAX-ACCESS read-only
                        STATUS current
                        DESCRIPTION
                            "This object indicates the number of users who go online from the board.
"
                        ::= { hwAAAPwifSlotConnectNumEntry 2 }
                        
                    hwAAAPwifSlotConnectNumMaxOnlineNum OBJECT-TYPE
                        SYNTAX Integer32
                        MAX-ACCESS read-only
                        STATUS current
                        DESCRIPTION
                            "This object indicates the maximum number of users who go online from the board after the device is started.
"
                        ::= { hwAAAPwifSlotConnectNumEntry 3 }   
                    hwAAAPwifSlotConnectNumMaxOnlineAcctReadyNum OBJECT-TYPE
                       SYNTAX Integer32
                        MAX-ACCESS read-only
                        STATUS current
                        DESCRIPTION
                            "This object indicates the maximum number of users who go online from the board with correct accounting statistics after the device is started.
"
                        ::= { hwAAAPwifSlotConnectNumEntry 4 }                             
            
         hwAAAPwifSlotCardConnectNumTable OBJECT-TYPE
            SYNTAX SEQUENCE OF HwAAAPwifSlotCardConnectNumEntry
            MAX-ACCESS not-accessible
            STATUS current 
            DESCRIPTION
                "This table is used to collect statistics about the number of users who go online from the subcard in the specified slot in the virtual access scenario."
            ::= { hwAAAMibObjects 70 }
        
            hwAAAPwifSlotCardConnectNumEntry OBJECT-TYPE
                  SYNTAX HwAAAPwifSlotCardConnectNumEntry
                  MAX-ACCESS not-accessible
                  STATUS current
                  DESCRIPTION
                            "Slot Card Query Online Number Entry
                            "
                        INDEX { hwAAAPwifSlotCardConnectNumSlot, hwAAAPwifSlotCardConnectNumCard }
                        ::= { hwAAAPwifSlotCardConnectNumTable 1 }
        
                    HwAAAPwifSlotCardConnectNumEntry ::=
                        SEQUENCE { 
                            hwAAAPwifSlotCardConnectNumSlot
                                OCTET STRING,
                            hwAAAPwifSlotCardConnectNumCard
                                Integer32,                              
                            hwAAAPwifSlotCardConnectNumOnlineNum
                                Integer32,
                            hwAAAPwifSlotCardConnectNumIPv4OnlineNum
                                Integer32,                  
                            hwAAAPwifSlotCardConnectNumIPv6OnlineNum
                                Integer32,
                            hwAAAPwifSlotCardConnectNumDualOnlineNum
                                Integer32,
                            hwAAAPwifSlotCardConnectNumNoAuthNum
                                Integer32,
                            hwAAAPwifSlotCardConnectNumPPPAuthNum
                                Integer32,
                            hwAAAPwifSlotCardConnectNum8021xAuthNum
                                Integer32,
                            hwAAAPwifSlotCardConnectNumWebAuthNum
                                Integer32,
                            hwAAAPwifSlotCardConnectNumBindAuthNum
                                Integer32,
                            hwAAAPwifSlotCardConnectNumFastAuthNum
                                Integer32,
                            hwAAAPwifSlotCardConnectNumWlanAuthNum
                                Integer32,
                            hwAAAPwifSlotCardConnectNumAdminAuthNum
                                Integer32,
                            hwAAAPwifSlotCardConnectNumTunnelAuthNum
                                Integer32,
                            hwAAAPwifSlotCardConnectNumMIPAuthNum
                                Integer32
                                                                              
                        }

                    hwAAAPwifSlotCardConnectNumSlot OBJECT-TYPE
                        SYNTAX OCTET STRING (SIZE (1..16))
                        MAX-ACCESS read-only
                        STATUS current
                        DESCRIPTION
                            "This object indicates the slot ID of the device.
"
                        ::= { hwAAAPwifSlotCardConnectNumEntry 1 }
                    
                    hwAAAPwifSlotCardConnectNumCard OBJECT-TYPE
                        SYNTAX Integer32 
                        MAX-ACCESS read-only
                        STATUS current
                        DESCRIPTION
                            "This object indicates the subcard ID of the device.
"
                        ::= { hwAAAPwifSlotCardConnectNumEntry 2 }

                    hwAAAPwifSlotCardConnectNumOnlineNum OBJECT-TYPE
                        SYNTAX Integer32
                        MAX-ACCESS read-only
                        STATUS current
                        DESCRIPTION
                            "This object indicates the number of online users on the slot.
"
                        ::= { hwAAAPwifSlotCardConnectNumEntry 3 }    
                        
                    hwAAAPwifSlotCardConnectNumIPv4OnlineNum OBJECT-TYPE
                        SYNTAX Integer32
                        MAX-ACCESS read-only
                        STATUS current
                        DESCRIPTION
                            "This object indicates the number of online IPv4 users on the slot.
"
                        ::= { hwAAAPwifSlotCardConnectNumEntry 4 }    
                    
                    hwAAAPwifSlotCardConnectNumIPv6OnlineNum OBJECT-TYPE
                        SYNTAX Integer32
                        MAX-ACCESS read-only
                        STATUS current
                        DESCRIPTION
                            "This object indicates the number of online IPv6 users on the slot.
"
                        ::= { hwAAAPwifSlotCardConnectNumEntry 5 }    
                    
                    hwAAAPwifSlotCardConnectNumDualOnlineNum OBJECT-TYPE
                        SYNTAX Integer32
                        MAX-ACCESS read-only
                        STATUS current
                        DESCRIPTION
                            "This object indicates the number of online dual-stack users on the slot.
"
                        ::= { hwAAAPwifSlotCardConnectNumEntry 6 }    
                    
                    hwAAAPwifSlotCardConnectNumNoAuthNum OBJECT-TYPE
                        SYNTAX Integer32
                        MAX-ACCESS read-only
                        STATUS current
                        DESCRIPTION
                            "This object indicates the number of online users that are not authenticated on the slot.
"
                        ::= { hwAAAPwifSlotCardConnectNumEntry 7 }
                        
                    hwAAAPwifSlotCardConnectNumPPPAuthNum OBJECT-TYPE
                        SYNTAX Integer32
                        MAX-ACCESS read-only
                        STATUS current
                        DESCRIPTION
                            "This object indicates the number of online users on the slot who have passed PPP authentication.
"
                        ::= { hwAAAPwifSlotCardConnectNumEntry 8 }
                        
                    hwAAAPwifSlotCardConnectNum8021xAuthNum OBJECT-TYPE
                        SYNTAX Integer32
                        MAX-ACCESS read-only
                        STATUS current
                        DESCRIPTION
                            "This object indicates the number of online users on the slot who have passed 802.1x authentication.
"
                        ::= { hwAAAPwifSlotCardConnectNumEntry 9 }
                    
                    hwAAAPwifSlotCardConnectNumWebAuthNum OBJECT-TYPE
                        SYNTAX Integer32
                        MAX-ACCESS read-only
                        STATUS current
                        DESCRIPTION
                            "This object indicates the number of online users on the slot who have passed web authentication.
"
                        ::= { hwAAAPwifSlotCardConnectNumEntry 10 }
                    
                    hwAAAPwifSlotCardConnectNumBindAuthNum OBJECT-TYPE
                        SYNTAX Integer32
                        MAX-ACCESS read-only
                        STATUS current
                        DESCRIPTION
                            "This object indicates the number of online users on the slot who have passed binding authentication.
"
                        ::= { hwAAAPwifSlotCardConnectNumEntry 11 }
                    
                    hwAAAPwifSlotCardConnectNumFastAuthNum OBJECT-TYPE
                        SYNTAX Integer32
                        MAX-ACCESS read-only
                        STATUS current
                        DESCRIPTION
                            "This object indicates the number of online users on the slot who have passed fast authentication.
"
                        ::= { hwAAAPwifSlotCardConnectNumEntry 12 }    
                    
                    hwAAAPwifSlotCardConnectNumWlanAuthNum OBJECT-TYPE
                        SYNTAX Integer32
                        MAX-ACCESS read-only
                        STATUS current
                        DESCRIPTION
                            "This object indicates the number of online users on the slot who have passed WLAN authentication.
"
                        ::= { hwAAAPwifSlotCardConnectNumEntry 13 }    
                    
                    hwAAAPwifSlotCardConnectNumAdminAuthNum OBJECT-TYPE
                        SYNTAX Integer32
                        MAX-ACCESS read-only
                        STATUS current
                        DESCRIPTION
                            "This object indicates the number of online users on the slot who have passed administrator authentication.
"
                        ::= { hwAAAPwifSlotCardConnectNumEntry 14 }    
                    
                    hwAAAPwifSlotCardConnectNumTunnelAuthNum OBJECT-TYPE
                        SYNTAX Integer32
                        MAX-ACCESS read-only
                        STATUS current
                        DESCRIPTION
                            "This object indicates the number of online users on the slot who have passed tunnel authentication.
"
                        ::= { hwAAAPwifSlotCardConnectNumEntry 15 }    
                    
                    hwAAAPwifSlotCardConnectNumMIPAuthNum OBJECT-TYPE
                        SYNTAX Integer32
                        MAX-ACCESS read-only
                        STATUS current
                        DESCRIPTION
                            "This object indicates the number of online users on the slot who have passed MIP authentication.
"
                        ::= { hwAAAPwifSlotCardConnectNumEntry 16 }    
                                       
            
 hwAAAPwifSlotAccessUserStatTable OBJECT-TYPE
            SYNTAX SEQUENCE OF HwAAAPwifSlotAccessUserStatEntry
            MAX-ACCESS not-accessible
            STATUS current
            DESCRIPTION
                "This table is used to query the numbers of users of various types who go online from the board."
            ::= { hwAAAMibObjects 71 }     
            
        hwAAAPwifSlotAccessUserStatEntry OBJECT-TYPE
            SYNTAX HwAAAPwifSlotAccessUserStatEntry
            MAX-ACCESS not-accessible
            STATUS current
            DESCRIPTION
                "HwAAAPwifSlotAccessUserStatEntry"
            INDEX { hwUserType, hwAAAPwifSlotAccessUserStatSlot }
            ::= { hwAAAPwifSlotAccessUserStatTable 1 }
                                                 
        HwAAAPwifSlotAccessUserStatEntry ::=
            SEQUENCE {
                hwAAAPwifSlotAccessUserStatSlot                   OCTET STRING,
                hwAAAPwifSlotAccessUserStatUserStat               Integer32
             }
                      
        hwAAAPwifSlotAccessUserStatSlot OBJECT-TYPE
            SYNTAX OCTET STRING (SIZE (1..16))
            MAX-ACCESS read-only
            STATUS current
            DESCRIPTION
                "This object indicates the board number.
"
            ::= { hwAAAPwifSlotAccessUserStatEntry 1 }
                                                          
        hwAAAPwifSlotAccessUserStatUserStat OBJECT-TYPE
            SYNTAX Integer32 (0..2147483647)
            MAX-ACCESS read-only
            STATUS current
            DESCRIPTION
                "This object indicates the number of users of a specified type on the board.
"
            ::= { hwAAAPwifSlotAccessUserStatEntry 2 }

      hwAAAPwifAccessTable OBJECT-TYPE
            SYNTAX SEQUENCE OF HwAAAPwifAccessEntry
            MAX-ACCESS not-accessible
            STATUS current
            DESCRIPTION
                "The hwAccessTable is a function access table used to display user access information."
            ::= { hwAAAMibObjects 72 }

        hwAAAPwifAccessEntry OBJECT-TYPE
            SYNTAX HwAAAPwifAccessEntry
            MAX-ACCESS not-accessible
            STATUS current
            DESCRIPTION
                "access entry

                The access table is used to query the property of online users. The index item node is hwAccessIndex.
                Notice: Read operation is not allowed for all the items in this table.
                1. The index of hwAAAPwifAccessTable also uses hwAccessIndex, get operation only 
                    supports the standard get operation with hwAccessIndex as its index.
                2. To prevent too much interaction, get next operation does use the standard operation that uses hwAccessIndex as its index.
                "
            INDEX { hwAAAPwifAccessIndex }
            ::= { hwAAAPwifAccessTable 1 }

        HwAAAPwifAccessEntry ::=
            SEQUENCE {
                hwAAAPwifAccessIndex
                    Integer32,
                hwAAAPwifAccessUserName
                    DisplayString,
                hwAAAPwifAccessPortType
                    INTEGER,
                hwAAAPwifAccessPriority
                    Integer32,
                hwAAAPwifAccessSlotNo
                    OCTET STRING,
                hwAAAPwifAccessSubSlotNo
                    Integer32,
                hwAAAPwifAccessPortNo
                    Integer32,
                hwAAAPwifAccessVLANID
                    Integer32,
                hwAAAPwifAccessPVC
                    Integer32,
                hwAAAPwifAccessAuthenMethod
                    INTEGER,
                hwAAAPwifAccessAcctMethod
                    INTEGER,
                hwAAAPwifAccessIPAddress
                    IpAddress,                    
                hwAAAPwifAccessVRF
                    DisplayString,
                hwAAAPwifAccessMACAddress
                    MacAddress,
                hwAAAPwifAccessIfIdleCut
                    TruthValue,
                hwAAAPwifAccessIdleCutTime
                    Integer32,
                hwAAAPwifAccessIdleCutFlow
                    Integer32,
                hwAAAPwifAccessTimeLimit
                    Integer32,
                hwAAAPwifAccessTotalFlow64Limit
                    Counter64,
                hwAAAPwifAccessStartTime
                    DateAndTime,
                hwAAAPwifAccessCARIfUpActive
                    TruthValue,
                hwAAAPwifAccessCARIfDnActive
                    TruthValue,
                hwAAAPwifAccessUpFlow64
                    Counter64,
                hwAAAPwifAccessDnFlow64
                    Counter64,
                hwAAAPwifAccessUpPacket64
                    Counter64,
                hwAAAPwifAccessDnPacket64
                    Counter64,
                hwAAAPwifAccessCARUpCIR
                    Integer32,
                hwAAAPwifAccessCARUpPIR
                    Integer32,
                hwAAAPwifAccessCARUpCBS
                    Unsigned32,
                hwAAAPwifAccessCARUpPBS
                    Unsigned32,
                hwAAAPwifAccessCARDnCIR
                    Integer32,
                hwAAAPwifAccessCARDnPIR
                    Integer32,
                hwAAAPwifAccessCARDnCBS
                    Unsigned32,
                hwAAAPwifAccessCARDnPBS
                    Unsigned32,            
                hwAAAPwifAccessDownPriority
                    Integer32,    
--                hwAAAPwifAccessQinqVlanID
--                    Integer32,
--                hwAAAPwifAccessUserVlanID
--                    Integer32                    
                hwAAAPwifAccessQosProfile
                    DisplayString,
                hwAAAPwifAccessInterface
                    DisplayString,
                hwAAAPwifAccessIPv6IFID
                    Ipv6AddressIfIdentifier,
                hwAAAPwifAccessIPv6WanAddress
                    Ipv6Address,
                hwAAAPwifAccessIPv6WanPrefix
                    Ipv6AddressPrefix,
                hwAAAPwifAccessIPv6LanPrefix
                    Ipv6AddressPrefix,
                hwAAAPwifAccessIPv6LanPrefixLen
                    Integer32,
                hwAAAPwifAccessBasicIPType
                    DisplayString,
                hwAAAPwifAccessIPv6WaitDelay
                    Integer32,
                hwAAAPwifAccessIPv6ManagedAddressFlag
                    INTEGER,
                hwAAAPwifAccessIPv6CPIFIDAvailable
                    TruthValue,
                hwAAAPwifAccessIPv6OtherFlag
                    INTEGER,
                hwAAAPwifAccessIPv6CPAssignIFID
                    TruthValue,
                hwAAAPwifAccessLineID
                    DisplayString,
                hwAAAPwifAccessIPv6UpFlow64
                    Counter64,
                hwAAAPwifAccessIPv6DnFlow64
                    Counter64,
                hwAAAPwifAccessIPv6UpPacket64
                    Counter64,
                hwAAAPwifAccessIPv6DnPacket64
                    Counter64,               
                hwAAAPwifAccessDeviceName
                    DisplayString,
                hwAAAPwifAccessDeviceMACAddress
                    MacAddress,
                hwAAAPwifAccessDevicePortName
                    OCTET STRING,
                hwAAAPwifAccessAPID     
                    Unsigned32
             }

        hwAAAPwifAccessIndex OBJECT-TYPE
            SYNTAX Integer32 (0..2147483647)
            MAX-ACCESS read-only
            STATUS current
            DESCRIPTION
                "This object indicates the index of a user.
"
            ::= { hwAAAPwifAccessEntry 1 }

        hwAAAPwifAccessUserName OBJECT-TYPE
            SYNTAX DisplayString (SIZE (1..253))
            MAX-ACCESS read-only
            STATUS current
            DESCRIPTION
                "This object indicates the name of the user.
"
            ::= { hwAAAPwifAccessEntry 3 }

        hwAAAPwifAccessPortType OBJECT-TYPE
            SYNTAX INTEGER
                {
                all(1),
                ppp(2),
                vlan(3),
                vlanweb(4),
                vlanportal(5),
                vlan8021x(6),
                telnet(7),
                ftp(8),
                ssh(9),
                igmp(10)
                }
            MAX-ACCESS read-only
            STATUS current
            DESCRIPTION
                "This object indicates the port type of the user.
"
            ::= { hwAAAPwifAccessEntry 5 }

        hwAAAPwifAccessPriority OBJECT-TYPE
            SYNTAX Integer32 (0..15|255)
            MAX-ACCESS read-only
            STATUS current
            DESCRIPTION
                "This object indicates the access priority of the user.
"
            ::= { hwAAAPwifAccessEntry 6 } 
            
        hwAAAPwifAccessSlotNo OBJECT-TYPE
            SYNTAX OCTET STRING (SIZE (1..16))
            MAX-ACCESS read-only
            STATUS current
            DESCRIPTION
                "This object indicates the slot ID of the user."
            ::= { hwAAAPwifAccessEntry 8 }

        hwAAAPwifAccessSubSlotNo OBJECT-TYPE
            SYNTAX Integer32
            MAX-ACCESS read-only
            STATUS current
            DESCRIPTION
                "This object indicates the sub-slot ID of the user."
            ::= { hwAAAPwifAccessEntry 9 }

        hwAAAPwifAccessPortNo OBJECT-TYPE
            SYNTAX Integer32
            MAX-ACCESS read-only
            STATUS current
            DESCRIPTION
                "This object indicates the port number of the user.
"
            ::= { hwAAAPwifAccessEntry 10 }

        hwAAAPwifAccessVLANID OBJECT-TYPE
            SYNTAX Integer32 
            MAX-ACCESS read-only
            STATUS current
            DESCRIPTION
                "This object indicates the VLAN information of the user.
"
            ::= { hwAAAPwifAccessEntry 11 }

        hwAAAPwifAccessPVC OBJECT-TYPE
            SYNTAX Integer32
            MAX-ACCESS read-only
            STATUS current
            DESCRIPTION
                "This object indicates the VPI VCI information of the user.
"
            ::= { hwAAAPwifAccessEntry 12 }

        hwAAAPwifAccessAuthenMethod OBJECT-TYPE
            SYNTAX INTEGER
                {
                    local(1),
                    noauth(2),
                    radius(3),
                    localRadius(4),
                    radiusLocal(5),
                    radiusNoauth(6),
                    tacacs(7),
                    localTacacs(8),
                    tacacsLocal(9),
                    tacacsNone(10)         
                }
            MAX-ACCESS read-only
            STATUS current
            DESCRIPTION
                "This object indicates the authentication method of the user. The available options are local, noauth, radius, localRadius, radiusLocal, radiusNoauth, tacacs, localTacacs, tacacsLocal, and tacacsNone.
"
            ::= { hwAAAPwifAccessEntry 13 }

        hwAAAPwifAccessAcctMethod OBJECT-TYPE
            SYNTAX INTEGER
                {
                local(1),
                radius(2),               
                noacct(3),
                localradiusboth(4),
                hwtacacs(5),
                localhwtacacsboth(6)
                }
            MAX-ACCESS read-only
            STATUS current
            DESCRIPTION
                "This object indicates the accounting method of the user, The available options are local, radius, noacct, localradiusboth, hwtacacs, and localhwtacacsboth.
"
            ::= { hwAAAPwifAccessEntry 14 }

        hwAAAPwifAccessIPAddress OBJECT-TYPE
            SYNTAX IpAddress
            MAX-ACCESS read-only
            STATUS current
            DESCRIPTION
                "This object indicates the IP address of the user.
"
            ::= { hwAAAPwifAccessEntry 15 } 
            
      hwAAAPwifAccessVRF OBJECT-TYPE
            SYNTAX DisplayString (SIZE (1..31))
            MAX-ACCESS read-only
            STATUS current
            DESCRIPTION
                "This object indicates the VRF name of the user.
"
            ::= { hwAAAPwifAccessEntry 16 }

         hwAAAPwifAccessMACAddress OBJECT-TYPE
            SYNTAX MacAddress
            MAX-ACCESS read-only
            STATUS current
            DESCRIPTION
                "This object indicates the MAC address of the user.
"
            ::= { hwAAAPwifAccessEntry 17 }
        

        hwAAAPwifAccessIfIdleCut OBJECT-TYPE
            SYNTAX TruthValue
            MAX-ACCESS read-only
            STATUS current
            DESCRIPTION
                "This object indicates whether idle cut is used."
            ::= { hwAAAPwifAccessEntry 18 }

        hwAAAPwifAccessIdleCutTime OBJECT-TYPE
            SYNTAX Integer32
            MAX-ACCESS read-only
            STATUS current
            DESCRIPTION
                "This object indicates the idle cut interval.
"
            ::= { hwAAAPwifAccessEntry 19 }

        hwAAAPwifAccessIdleCutFlow OBJECT-TYPE
            SYNTAX Integer32
            MAX-ACCESS read-only
            STATUS current
            DESCRIPTION
                "This object indicates the idle cut traffic.
"
            ::= { hwAAAPwifAccessEntry 20 }

        hwAAAPwifAccessTimeLimit OBJECT-TYPE
            SYNTAX Integer32
            MAX-ACCESS read-only
            STATUS current
            DESCRIPTION
                "This object indicates the online duration limit of the user.
"
            ::= { hwAAAPwifAccessEntry 21 }

        hwAAAPwifAccessTotalFlow64Limit OBJECT-TYPE
            SYNTAX Counter64
            MAX-ACCESS read-only
            STATUS current
            DESCRIPTION
                "This object indicates the remaining traffic (64 bit) of the user.
"
            ::= { hwAAAPwifAccessEntry 22 }

        hwAAAPwifAccessStartTime OBJECT-TYPE
            SYNTAX DateAndTime
            MAX-ACCESS read-only
            STATUS current
            DESCRIPTION
                "This object indicates the access time of the user.
"
            ::= { hwAAAPwifAccessEntry 25 }

        hwAAAPwifAccessCARIfUpActive OBJECT-TYPE
            SYNTAX TruthValue
            MAX-ACCESS read-only
            STATUS current
            DESCRIPTION
                "This object indicates whether to implement upstream CAR.
"
            ::= { hwAAAPwifAccessEntry 27 }


        hwAAAPwifAccessCARIfDnActive OBJECT-TYPE
            SYNTAX TruthValue
            MAX-ACCESS read-only
            STATUS current
            DESCRIPTION
                "This object indicates whether to implement downstream CAR.
"
            ::= { hwAAAPwifAccessEntry 31 }

        hwAAAPwifAccessUpFlow64 OBJECT-TYPE
            SYNTAX Counter64
            MAX-ACCESS read-only
            STATUS current
            DESCRIPTION
                "This object indicates the number of bytes of upstream packets, in 64 bytes.
"
            ::= { hwAAAPwifAccessEntry 36 }

        hwAAAPwifAccessDnFlow64 OBJECT-TYPE
            SYNTAX Counter64
            MAX-ACCESS read-only
            STATUS current
            DESCRIPTION
                "This object indicates the number of bytes of downstream packets, in 64 bytes.
"
            ::= { hwAAAPwifAccessEntry 37 }

        hwAAAPwifAccessUpPacket64 OBJECT-TYPE
            SYNTAX Counter64
            MAX-ACCESS read-only
            STATUS current
            DESCRIPTION
                "This object indicates the number of upstream packets.
"
            ::= { hwAAAPwifAccessEntry 38 }

        hwAAAPwifAccessDnPacket64 OBJECT-TYPE
            SYNTAX Counter64
            MAX-ACCESS read-only
            STATUS current
            DESCRIPTION
                "This object indicates the number of downstream packets.
"
            ::= { hwAAAPwifAccessEntry 39 }

        hwAAAPwifAccessCARUpCIR OBJECT-TYPE
            SYNTAX Integer32 (16..10000000)
            MAX-ACCESS read-only
            STATUS current
            DESCRIPTION
                "This object indicates the average upstream traffic rate, in kbit/s.
"
            ::= { hwAAAPwifAccessEntry 45 }

        hwAAAPwifAccessCARUpPIR OBJECT-TYPE
            SYNTAX Integer32 (16..10000000)
            MAX-ACCESS read-only
            STATUS current
            DESCRIPTION
                "This object indicates the peak upstream traffic rate, in kbps.
"
            ::= { hwAAAPwifAccessEntry 46 }

         hwAAAPwifAccessCARUpCBS OBJECT-TYPE
            SYNTAX Unsigned32 (100..4294967295)
            MAX-ACCESS read-only
            STATUS current
            DESCRIPTION
                "This object indicates the upstream CBS, in bytes.
"
            ::= { hwAAAPwifAccessEntry 47 }

            
         hwAAAPwifAccessCARUpPBS OBJECT-TYPE
            SYNTAX Unsigned32 (0..4294967295)
            MAX-ACCESS read-only
            STATUS current
            DESCRIPTION
                "This object indicates the upstream PBS, in bytes.
"
            ::= { hwAAAPwifAccessEntry 48 }
            
          hwAAAPwifAccessCARDnCIR OBJECT-TYPE
            SYNTAX Integer32 (16..10000000)
            MAX-ACCESS read-only
            STATUS current
            DESCRIPTION
                "This object indicates the average downstream traffic rate, in kbps.
"
            ::= { hwAAAPwifAccessEntry 49 }

        hwAAAPwifAccessCARDnPIR OBJECT-TYPE
            SYNTAX Integer32 (16..10000000)
            MAX-ACCESS read-only
            STATUS current
            DESCRIPTION
                "This object indicates the peak downstream traffic rate, in kbps.
"
            ::= { hwAAAPwifAccessEntry 50 }

        hwAAAPwifAccessCARDnCBS OBJECT-TYPE
            SYNTAX Unsigned32 (100..4294967295)
            MAX-ACCESS read-only
            STATUS current
            DESCRIPTION
                "This object indicates the downstream CBS, in bytes.
"
            ::= { hwAAAPwifAccessEntry 51 }

            
       hwAAAPwifAccessCARDnPBS OBJECT-TYPE
            SYNTAX Unsigned32 (0..4294967295)
            MAX-ACCESS read-only
            STATUS current
            DESCRIPTION
                "This object indicates the downstream PBS, in bytes.
"
            ::= { hwAAAPwifAccessEntry 52 }

      hwAAAPwifAccessDownPriority OBJECT-TYPE
            SYNTAX Integer32 (0..15|255)
            MAX-ACCESS read-only
            STATUS current
            DESCRIPTION
                "This object indicates the downstream priority.
"
            ::= { hwAAAPwifAccessEntry 53 }

--        hwAAAPwifAccessQinqVlanID OBJECT-TYPE
--            SYNTAX Integer32 (0..4094)
--            MAX-ACCESS read-only
--            STATUS current
--            DESCRIPTION
--                "qinq vlan"
--            ::= { hwAAAPwifAccessEntry 54 }

--        hwAAAPwifAccessUserVlanID OBJECT-TYPE
--            SYNTAX Integer32 (0..4094)
--            MAX-ACCESS read-only
--            STATUS current
--            DESCRIPTION
--                "user VLAN"
--            ::= { hwAAAPwifAccessEntry 55 }

        hwAAAPwifAccessQosProfile OBJECT-TYPE
            SYNTAX DisplayString (SIZE (1..63))
            MAX-ACCESS read-create
            STATUS current
            DESCRIPTION
                "This object indicates the QoS profile in the virtual access scenario.
"
            ::= { hwAAAPwifAccessEntry 56 }

        hwAAAPwifAccessInterface OBJECT-TYPE
            SYNTAX DisplayString (SIZE (1..63))
            MAX-ACCESS read-only
            STATUS current
            DESCRIPTION
                "This object indicates the user access interface.
"
            ::= { hwAAAPwifAccessEntry 57 }

        hwAAAPwifAccessIPv6IFID OBJECT-TYPE
            SYNTAX Ipv6AddressIfIdentifier
            MAX-ACCESS read-only
            STATUS current
            DESCRIPTION
                "This object indicates the interface ID negotiated by IPv6CP for the PPPoE or L2TP user."
            ::= { hwAAAPwifAccessEntry 58 }

        hwAAAPwifAccessIPv6WanAddress OBJECT-TYPE
            SYNTAX Ipv6Address
            MAX-ACCESS read-only
            STATUS current
            DESCRIPTION
                "This object indicates the WAN interface address of the user."
            ::= { hwAAAPwifAccessEntry 59 }

        hwAAAPwifAccessIPv6WanPrefix OBJECT-TYPE
            SYNTAX Ipv6AddressPrefix
            MAX-ACCESS read-only
            STATUS current
            DESCRIPTION
                "This object indicates the WAN interface prefix of the user."
            ::= { hwAAAPwifAccessEntry 60 }

        hwAAAPwifAccessIPv6LanPrefix OBJECT-TYPE
            SYNTAX Ipv6AddressPrefix
            MAX-ACCESS read-only
            STATUS current
            DESCRIPTION
                "This object indicates the LAN interface address of the user.
"
            ::= { hwAAAPwifAccessEntry 61 }

        hwAAAPwifAccessIPv6LanPrefixLen OBJECT-TYPE
            SYNTAX Integer32 (0..128)
            MAX-ACCESS read-only
            STATUS current
            DESCRIPTION
                "This object indicates the LAN interface prefix of the user."
            ::= { hwAAAPwifAccessEntry 62 }

        hwAAAPwifAccessBasicIPType OBJECT-TYPE
            SYNTAX DisplayString (SIZE (1..3))
            MAX-ACCESS read-only
            STATUS current
            DESCRIPTION
                "This object indicates the IP address type by using which domain users can go online. The available options are UCHAR[0]-IPv4, UCHAR[1]-IPv6, and UCHAR[2]-IPv6-PD. Value 0 indicates that domain users do not use this IP address type for access. Value 1 indicates that domain users use this IP address type for access."
            ::= { hwAAAPwifAccessEntry 63 }

        hwAAAPwifAccessIPv6WaitDelay OBJECT-TYPE
            SYNTAX Integer32 (30..120)
            MAX-ACCESS read-only
            STATUS current
            DESCRIPTION
                "This object indicates the time used for waiting for DHCPv6 packets after IPv6 CP is performed."
            ::= { hwAAAPwifAccessEntry 64 }

        hwAAAPwifAccessIPv6ManagedAddressFlag OBJECT-TYPE
            SYNTAX INTEGER
            {
                ndra(1),
                dhcpv6(2),
                invalid(255)
            }
            MAX-ACCESS read-only
            STATUS current
            DESCRIPTION
                "This object indicates the IPv6 address allocation mode for PPPoE and L2TP users."
            ::= { hwAAAPwifAccessEntry 65 }

        hwAAAPwifAccessIPv6CPIFIDAvailable OBJECT-TYPE
            SYNTAX TruthValue
            MAX-ACCESS read-only
            STATUS current
            DESCRIPTION
                "This object indicates whether to use the interface ID negotiated by IPv6CP as the interface ID for allocating IP addresses when PPPoE and L2TP users use DHCPv6 to allocate IP addresses."
            ::= { hwAAAPwifAccessEntry 66 }

        hwAAAPwifAccessIPv6OtherFlag OBJECT-TYPE
            SYNTAX INTEGER
            {
                ndra(1),
                dhcpv6(2),
                invalid(255)
            }
            MAX-ACCESS read-only
            STATUS current
            DESCRIPTION
                "This object indicates the information allocation mode for PPPoE, L2TP, and IPoE users."
            ::= { hwAAAPwifAccessEntry 67 }

        hwAAAPwifAccessIPv6CPAssignIFID OBJECT-TYPE
            SYNTAX TruthValue
            MAX-ACCESS read-only
            STATUS current
            DESCRIPTION
                "This object indicates whether the interface ID of the user is available for IPv6CP negotiation."
            ::= { hwAAAPwifAccessEntry 68 }

        hwAAAPwifAccessLineID OBJECT-TYPE
            SYNTAX DisplayString (SIZE (0..255))
            MAX-ACCESS read-only
            STATUS current
            DESCRIPTION
                "This object indicates the access line ID."
            ::= { hwAAAPwifAccessEntry 69 }

        hwAAAPwifAccessIPv6UpFlow64 OBJECT-TYPE
            SYNTAX Counter64
            MAX-ACCESS read-only
            STATUS current
            DESCRIPTION
                "This object indicates the number of bytes of upstream IPv6 packets."
            ::= { hwAAAPwifAccessEntry 70 }

        hwAAAPwifAccessIPv6DnFlow64 OBJECT-TYPE
            SYNTAX Counter64
            MAX-ACCESS read-only
            STATUS current
            DESCRIPTION
                "This object indicates the number of bytes of downstream IPv6 packets."
            ::= { hwAAAPwifAccessEntry 71 }

        hwAAAPwifAccessIPv6UpPacket64 OBJECT-TYPE
            SYNTAX Counter64
            MAX-ACCESS read-only
            STATUS current
            DESCRIPTION
                "This object indicates the number of upstream IPv6 packets."
            ::= { hwAAAPwifAccessEntry 72 }

        hwAAAPwifAccessIPv6DnPacket64 OBJECT-TYPE
            SYNTAX Counter64
            MAX-ACCESS read-only
            STATUS current
            DESCRIPTION
                "This object indicates the number of downstream IPv6 packets."
            ::= { hwAAAPwifAccessEntry 73 }  
            
        hwAAAPwifAccessDeviceName OBJECT-TYPE
            SYNTAX DisplayString (SIZE (1..255))
            MAX-ACCESS read-only
            STATUS current
            DESCRIPTION
                "access device name"
            ::= { hwAAAPwifAccessEntry 74 }
            
        hwAAAPwifAccessDeviceMACAddress OBJECT-TYPE
            SYNTAX MacAddress
            MAX-ACCESS read-only
            STATUS current
            DESCRIPTION
                "Access device Mac address"
            ::= { hwAAAPwifAccessEntry 75 }
            
        hwAAAPwifAccessDevicePortName OBJECT-TYPE
            SYNTAX OCTET STRING
            MAX-ACCESS read-only
            STATUS current
            DESCRIPTION
                "Interface Name of Access device."
            ::= { hwAAAPwifAccessEntry 76 }
            
       hwAAAPwifAccessAPID OBJECT-TYPE
            SYNTAX Unsigned32 (0..4294836225)
            MAX-ACCESS read-only
            STATUS current
            DESCRIPTION
                "Access wiless device AP Id"
            ::= { hwAAAPwifAccessEntry 77 }
            
      --===pwif end===
     
      --===ReAuthenUser begin===

        hwReAuthenUserTable OBJECT IDENTIFIER ::= { hwAAAMibObjects 73 }
		
        hwReAuthenMacAddress OBJECT-TYPE
            SYNTAX MacAddress
            MAX-ACCESS read-write
            STATUS current
            DESCRIPTION
                 "User Mac Address"
            ::= { hwReAuthenUserTable 1 }
        
       --===ReAuthenUser end===     
       
  
        hwAccessUserNumberTable OBJECT IDENTIFIER ::= { hwAAAMibObjects 74 }

        hwAccessUserNumberEntry OBJECT IDENTIFIER ::= { hwAccessUserNumberTable 1 }
                              
                        
		             hwAccessUserNumberDot1x OBJECT-TYPE
		                SYNTAX Integer32 (0..65535)
		                MAX-ACCESS read-only
		                STATUS current
		                DESCRIPTION
		                    "
		                    This Dot1x access user number.
		                    "
		                ::= { hwAccessUserNumberEntry 1 } 
                        
		             hwAccessUserNumberMAC OBJECT-TYPE
		                SYNTAX Integer32 (0..65535)
		                MAX-ACCESS read-only
		                STATUS current
		                DESCRIPTION
		                    "
		                    This MAC access user number.
		                    "
		                ::= { hwAccessUserNumberEntry 2 } 

		             hwAccessUserNumberPortal OBJECT-TYPE
		                SYNTAX Integer32 (0..65535)
		                MAX-ACCESS read-only
		                STATUS current
		                DESCRIPTION
		                    "
		                    This Portal access user number.
		                    "
		                ::= { hwAccessUserNumberEntry 3 } 

		             hwAccessUserNumberPPP OBJECT-TYPE
		                SYNTAX Integer32 (0..65535)
		                MAX-ACCESS read-only
		                STATUS current
		                DESCRIPTION
		                    "
		                    This PPP access user number.
		                    "
		                ::= { hwAccessUserNumberEntry 4 } 

		             hwAccessUserNumberNone OBJECT-TYPE
		                SYNTAX Integer32 (0..65535)
		                MAX-ACCESS read-only
		                STATUS current
		                DESCRIPTION
		                    "
		                    This None access user number.
		                    "
		                ::= { hwAccessUserNumberEntry 5 } 

		             hwAccessUserNumberStatic OBJECT-TYPE
		                SYNTAX Integer32 (0..65535)
		                MAX-ACCESS read-only
		                STATUS current
		                DESCRIPTION
		                    "
		                    This Static access user number.
		                    "
		                ::= { hwAccessUserNumberEntry 6 } 
	     
		             hwAccessUserNumberAdmin OBJECT-TYPE
		                SYNTAX Integer32 (0..65535)
		                MAX-ACCESS read-only
		                STATUS current
		                DESCRIPTION
		                    "
		                    This Admin access user number.
		                    "
		                ::= { hwAccessUserNumberEntry 7 }				 
	
       
            hwAAAUserGroupUserStatTable OBJECT-TYPE
            SYNTAX SEQUENCE OF HwAAAUserGroupUserStatEntry
            MAX-ACCESS not-accessible
            STATUS current
            DESCRIPTION
                "The usergroup stat table."
            ::= { hwAAAMibObjects 75 }

            hwAAAUserGroupUserStatEntry OBJECT-TYPE
            SYNTAX HwAAAUserGroupUserStatEntry
            MAX-ACCESS not-accessible
            STATUS current
            DESCRIPTION
                "The usergroup stat table entry."
            INDEX { hwAAAUserGroupName }
            ::= { hwAAAUserGroupUserStatTable 1 }

            HwAAAUserGroupUserStatEntry ::=
            SEQUENCE {
                hwAAAUserGroupName
                    DisplayString, 
                hwAAAUserGroupTotalUsersNum
                    Unsigned32
                     }

            hwAAAUserGroupName OBJECT-TYPE
            SYNTAX DisplayString (SIZE (1..32))
            MAX-ACCESS read-only
            STATUS current
            DESCRIPTION
                "The usergroup name as stat index."
            ::= { hwAAAUserGroupUserStatEntry 1 }       
          
            hwAAAUserGroupTotalUsersNum OBJECT-TYPE
            SYNTAX Unsigned32 (0..4294967295)
            MAX-ACCESS read-only
            STATUS current
            DESCRIPTION
                "the number of a usergroup online users"
            ::= { hwAAAUserGroupUserStatEntry 2 }      
    
--  ============== hwCUAAAStatTable ==============
        hwCUAAAStatTable OBJECT-TYPE
            SYNTAX SEQUENCE OF HwCUAAAStatEntry
            MAX-ACCESS not-accessible
            STATUS current
            DESCRIPTION
                "BRAS user access statistics in CU separation scenarios."
            ::= { hwAAAMibObjects 76 }
            
        hwCUAAAStatEntry OBJECT-TYPE
            SYNTAX HwCUAAAStatEntry
            MAX-ACCESS not-accessible
            STATUS current
            DESCRIPTION
                "UP to the granularity of access to the number of online users, the number of bytes on the downlink, the maximum number of users."
            INDEX { hwCUUpId }
            ::= { hwCUAAAStatTable 1 }

            HwCUAAAStatEntry ::=
                SEQUENCE { 
                    hwCUUpId
                        Unsigned32,
                    hwCUTotalOnlineNum
                        Unsigned32,
                    hwCUTotalPPPoeOnlineNum
                        Unsigned32,
                    hwCUTotalPPPoaOnlineNum
                        Unsigned32,
                    hwCUTotalftpOnlineNum
                        Unsigned32,
                    hwCUTotalsshOnlineNum  
                        Unsigned32,
                    hwCUTotaltelnetOnlineNum
                        Unsigned32,
                    hwCUTotalVLANOnlineNum
                        Unsigned32,
                    hwCUHistoricMaxOnlineNum
                        Unsigned32,
                    hwCUResetHistoricMaxOnlineNum                        
                        Unsigned32,
                    hwCUResetOfflineReasonStatistic
                        Unsigned32,
                    hwCUResetOnlineFailReasonStatistic
                        Unsigned32,
                    hwCUMaxPPPoeOnlineNum
                        Unsigned32,
                    hwCUTotalPortalServerUserNum
                        Unsigned32,
                    hwCUMaxPortalServerUserNum     
                        Unsigned32,
                    hwCUTotalIPv4OnlineNum     
                        Unsigned32,
                    hwCUTotalIPv6OnlineNum 
                        Unsigned32,
                    hwCUTotalDualStackOnlineNum 
                        Unsigned32,
                    hwCUTotalIPv4FlowDnByte 
                        Counter64,
                    hwCUTotalIPv4FlowDnPkt 
                        Counter64,
                    hwCUTotalIPv4FlowUpByte
                        Counter64,
                    hwCUTotalIPv4FlowUpPkt     
                        Counter64,
                    hwCUTotalIPv6FlowDnByte     
                        Counter64,
                    hwCUTotalIPv6FlowDnPkt 
                        Counter64,
                    hwCUTotalIPv6FlowUpByte  
                        Counter64,
                    hwCUTotalIPv6FlowUpPkt 
                        Counter64,
                    hwCUHistoricMaxOnlineAcctReadyNum     
                        Unsigned32,
                    hwCUPubicLacUserNum      
                        Unsigned32,
                    hwCUHistoricMaxOnlineLocalNum      
                        Unsigned32,
                    hwCUHistoricMaxOnlineRemoteNum  
                        Unsigned32,
                    hwCUTotalLacOnlineNum   
                        Unsigned32,
                    hwCUTotalLnsOnlineNum  
                        Unsigned32,
                    hwCUTotalWlsOnlineNum     
                        Unsigned32,
                    hwCUTotalWrdOnlineNum      
                        Unsigned32,
                    hwCUDhcpUserOnlineFailCount      
                        Unsigned32,
                    hwCUTotalFamilyUserByUsernameOnlineNum  
                        Unsigned32,
                    hwCUDhcpUserOnlineV6FailCount   
                        Unsigned32,
                    hwCUHistoricMaxOnlineNumDate  
                        DisplayString,
                    hwCUTotalMasterOnlineNum
                        Unsigned32,
                    hwCUTotalSlaveOnlineNum
                        Unsigned32

                 }

            hwCUUpId OBJECT-TYPE
                SYNTAX Unsigned32 (0..4294967295)
                MAX-ACCESS read-only
                STATUS current
                DESCRIPTION
                    "UP identifier in CU separation scenarios."
                ::= { hwCUAAAStatEntry 1 }

            hwCUTotalOnlineNum OBJECT-TYPE
                SYNTAX Unsigned32 (0..4294967295)
                MAX-ACCESS read-only
                STATUS current
                DESCRIPTION
                    "Total number of access users on the UP."
                ::= { hwCUAAAStatEntry 2 }
                
            hwCUTotalPPPoeOnlineNum OBJECT-TYPE
                SYNTAX Unsigned32 (0..4294967295)
                MAX-ACCESS read-only
                STATUS current
                DESCRIPTION
                    "Total number of PPPoE users on the UP."
                ::= { hwCUAAAStatEntry 3 } 

            hwCUTotalPPPoaOnlineNum OBJECT-TYPE
                SYNTAX Unsigned32 (0..4294967295)
                MAX-ACCESS read-only
                STATUS current
                DESCRIPTION
                    "Total number of PPPoA users on the UP."
                ::= { hwCUAAAStatEntry 4 }   
                
            hwCUTotalftpOnlineNum OBJECT-TYPE
                SYNTAX Unsigned32 (0..4294967295)
                MAX-ACCESS read-only
                STATUS current
                DESCRIPTION
                    "Total number of FTP users on the UP."
                ::= { hwCUAAAStatEntry 5 } 

            hwCUTotalsshOnlineNum OBJECT-TYPE
                SYNTAX Unsigned32 (0..4294967295)
                MAX-ACCESS read-only
                STATUS current
                DESCRIPTION
                    "Total number of SSH users on the UP."
                ::= { hwCUAAAStatEntry 6 }  

            hwCUTotaltelnetOnlineNum OBJECT-TYPE
                SYNTAX Unsigned32 (0..4294967295)
                MAX-ACCESS read-only
                STATUS current
                DESCRIPTION
                    "Total number of Telnet users on the UP."
                ::= { hwCUAAAStatEntry 7 } 

            hwCUTotalVLANOnlineNum OBJECT-TYPE
                SYNTAX Unsigned32 (0..4294967295)
                MAX-ACCESS read-only
                STATUS current
                DESCRIPTION
                    "Total number of IPoE users on the UP."
                ::= { hwCUAAAStatEntry 8 }

            hwCUHistoricMaxOnlineNum OBJECT-TYPE
                SYNTAX Unsigned32 (0..4294967295)
                MAX-ACCESS read-only
                STATUS current
                DESCRIPTION
                    "Maximum number of users on the UP."
                ::= { hwCUAAAStatEntry 9 }

            hwCUResetHistoricMaxOnlineNum OBJECT-TYPE
                SYNTAX Unsigned32 (0..4294967295)
                MAX-ACCESS read-only
                STATUS current
                DESCRIPTION
                    "Reset the historical maximum number of users on the UP."
                ::= { hwCUAAAStatEntry 10 }   

            hwCUResetOfflineReasonStatistic OBJECT-TYPE
                SYNTAX Unsigned32 (0..4294967295)
                MAX-ACCESS read-only
                STATUS current
                DESCRIPTION
                    "Reset logout statistics about users on the UP."
                ::= { hwCUAAAStatEntry 11 } 

            hwCUResetOnlineFailReasonStatistic OBJECT-TYPE
                SYNTAX Unsigned32 (0..4294967295)
                MAX-ACCESS read-only
                STATUS current
                DESCRIPTION
                    "Reset logout failure statistics about users on the UP."
                ::= { hwCUAAAStatEntry 12 }     

            hwCUMaxPPPoeOnlineNum OBJECT-TYPE
                SYNTAX Unsigned32 (0..4294967295)
                MAX-ACCESS read-only
                STATUS current
                DESCRIPTION
                    "Maximum number of online PPPoE users on the UP."
                ::= { hwCUAAAStatEntry 13 }

            hwCUTotalPortalServerUserNum OBJECT-TYPE
                SYNTAX Unsigned32 (0..4294967295)
                MAX-ACCESS read-only
                STATUS current
                DESCRIPTION
                    "Number of online portal server users on the UP."
                ::= { hwCUAAAStatEntry 14 } 

            hwCUMaxPortalServerUserNum OBJECT-TYPE
                SYNTAX Unsigned32 (0..4294967295)
                MAX-ACCESS read-only
                STATUS current
                DESCRIPTION
                    "Maximum number of online portal server users on the UP."
                ::= { hwCUAAAStatEntry 15 } 

            hwCUTotalIPv4OnlineNum OBJECT-TYPE
                SYNTAX Unsigned32 (0..4294967295)
                MAX-ACCESS read-only
                STATUS current
                DESCRIPTION
                    "Number of online IPv4 users on the UP."
                ::= { hwCUAAAStatEntry 16 } 

            hwCUTotalIPv6OnlineNum OBJECT-TYPE
                SYNTAX Unsigned32 (0..4294967295)
                MAX-ACCESS read-only
                STATUS current
                DESCRIPTION
                    "Number of online IPv6 users on the UP."
                ::= { hwCUAAAStatEntry 17 }

            hwCUTotalDualStackOnlineNum OBJECT-TYPE
                SYNTAX Unsigned32 (0..4294967295)
                MAX-ACCESS read-only
                STATUS current
                DESCRIPTION
                    "Number of online IPv6 users on the UP."
                ::= { hwCUAAAStatEntry 18 } 

            hwCUTotalIPv4FlowDnByte OBJECT-TYPE
                SYNTAX Counter64
                MAX-ACCESS read-only
                STATUS current
                DESCRIPTION
                    "Number of downstream traffic bytes of IPv4 users on the UP."
                ::= { hwCUAAAStatEntry 19 }  

            hwCUTotalIPv4FlowDnPkt OBJECT-TYPE
                SYNTAX Counter64
                MAX-ACCESS read-only
                STATUS current
                DESCRIPTION
                    "Number of downstream packets of IPv4 users on the UP."
                ::= { hwCUAAAStatEntry 20 }
                
            hwCUTotalIPv4FlowUpByte OBJECT-TYPE
                SYNTAX Counter64
                MAX-ACCESS read-only
                STATUS current
                DESCRIPTION
                    "Number of upstream traffic bytes of IPv4 users on the UP."
                ::= { hwCUAAAStatEntry 21 }    

            hwCUTotalIPv4FlowUpPkt OBJECT-TYPE
                SYNTAX Counter64
                MAX-ACCESS read-only
                STATUS current
                DESCRIPTION
                    "Number of upstream packets of IPv4 users on the UP."
                ::= { hwCUAAAStatEntry 22 } 

            hwCUTotalIPv6FlowDnByte OBJECT-TYPE
                SYNTAX Counter64
                MAX-ACCESS read-only
                STATUS current
                DESCRIPTION
                    "Number of downstream traffic bytes of IPv6 users on the UP."
                ::= { hwCUAAAStatEntry 23 }

            hwCUTotalIPv6FlowDnPkt OBJECT-TYPE
                SYNTAX Counter64
                MAX-ACCESS read-only
                STATUS current
                DESCRIPTION
                    "Number of downstream packets of IPv6 users on the UP."
                ::= { hwCUAAAStatEntry 24 } 

            hwCUTotalIPv6FlowUpByte OBJECT-TYPE
                SYNTAX Counter64
                MAX-ACCESS read-only
                STATUS current
                DESCRIPTION
                    "Number of upstream traffic bytes of IPv6 users on the UP."
                ::= { hwCUAAAStatEntry 25 } 

            hwCUTotalIPv6FlowUpPkt OBJECT-TYPE
                SYNTAX Counter64
                MAX-ACCESS read-only
                STATUS current
                DESCRIPTION
                    "Number of upstream packets of IPv6 users on the UP."
                ::= { hwCUAAAStatEntry 26 }  

            hwCUHistoricMaxOnlineAcctReadyNum OBJECT-TYPE
                SYNTAX Unsigned32 (0..4294967295)
                MAX-ACCESS read-only
                STATUS current
                DESCRIPTION
                    "Historical maximum number of accounting-ready users on the UP."
                ::= { hwCUAAAStatEntry 27 } 

            hwCUPubicLacUserNum OBJECT-TYPE
                SYNTAX Unsigned32 (0..4294967295)
                MAX-ACCESS read-only
                STATUS current
                DESCRIPTION
                    "Number of LAC users on the UP."
                ::= { hwCUAAAStatEntry 28 } 

            hwCUHistoricMaxOnlineLocalNum OBJECT-TYPE
                SYNTAX Unsigned32 (0..4294967295)
                MAX-ACCESS read-only
                STATUS current
                DESCRIPTION
                    "Historical maximum number of local users on the UP."
                ::= { hwCUAAAStatEntry 29 }  

            hwCUHistoricMaxOnlineRemoteNum OBJECT-TYPE
                SYNTAX Unsigned32 (0..4294967295)
                MAX-ACCESS read-only
                STATUS current
                DESCRIPTION
                    "Historical maximum number of remote users on the UP."
                ::= { hwCUAAAStatEntry 30 } 

            hwCUTotalLacOnlineNum OBJECT-TYPE
                SYNTAX Unsigned32 (0..4294967295)
                MAX-ACCESS read-only
                STATUS current
                DESCRIPTION
                    "Number of LAC users on the UP."
                ::= { hwCUAAAStatEntry 31 } 

            hwCUTotalLnsOnlineNum OBJECT-TYPE
                SYNTAX Unsigned32 (0..4294967295)
                MAX-ACCESS read-only
                STATUS current
                DESCRIPTION
                    "Number of LNS users on the UP."
                ::= { hwCUAAAStatEntry 32 }      

            hwCUTotalWlsOnlineNum OBJECT-TYPE
                SYNTAX Unsigned32 (0..4294967295)
                MAX-ACCESS read-only
                STATUS current
                DESCRIPTION
                    "Number of WLS users on the UP."
                ::= { hwCUAAAStatEntry 33 }  

            hwCUTotalWrdOnlineNum OBJECT-TYPE
                SYNTAX Unsigned32 (0..4294967295)
                MAX-ACCESS read-only
                STATUS current
                DESCRIPTION
                    "Number of WRD users on the UP."
                ::= { hwCUAAAStatEntry 34 }    

            hwCUDhcpUserOnlineFailCount OBJECT-TYPE
                SYNTAX Unsigned32 (0..4294967295)
                MAX-ACCESS read-only
                STATUS current
                DESCRIPTION
                    "Number of users with DHCP login failures on the UP."
                ::= { hwCUAAAStatEntry 35 } 

            hwCUTotalFamilyUserByUsernameOnlineNum OBJECT-TYPE
                SYNTAX Unsigned32 (0..4294967295)
                MAX-ACCESS read-only
                STATUS current
                DESCRIPTION
                    "Number of family users on the UP."
                ::= { hwCUAAAStatEntry 36 }    

            hwCUDhcpUserOnlineV6FailCount OBJECT-TYPE
                SYNTAX Unsigned32 (0..4294967295)
                MAX-ACCESS read-only
                STATUS current
                DESCRIPTION
                    "Number of users with DHCPv6 login failures on the UP."
                ::= { hwCUAAAStatEntry 37 }  
                
            hwCUHistoricMaxOnlineNumDate OBJECT-TYPE
                SYNTAX DisplayString (SIZE(1..32))
                MAX-ACCESS read-only
                STATUS current
                DESCRIPTION
                    "Date and time when the number of access users reaches the maximum number."
                ::= { hwCUAAAStatEntry 38 }
                
            hwCUTotalMasterOnlineNum OBJECT-TYPE
                SYNTAX Unsigned32 (0..4294967295)
                MAX-ACCESS read-only
                STATUS current
                DESCRIPTION
                    "Number of users on the master UP in hot backup scenarios."
                ::= { hwCUAAAStatEntry 39 } 

            hwCUTotalSlaveOnlineNum OBJECT-TYPE
                SYNTAX Unsigned32 (0..4294967295)
                MAX-ACCESS read-only
                STATUS current
                DESCRIPTION
                    "Number of users on the backup UP in hot backup scenarios."
                ::= { hwCUAAAStatEntry 40 }                 
    --======       
	   hwBRASLicenseTable OBJECT-TYPE
            SYNTAX SEQUENCE OF HwBRASLicenseEntry
            MAX-ACCESS not-accessible
            STATUS current
            DESCRIPTION
                "BRAS access user license list. "
            ::= { hwAAAMibObjects 77 }
        
        hwBRASLicenseEntry OBJECT-TYPE
            SYNTAX HwBRASLicenseEntry
            MAX-ACCESS not-accessible
            STATUS current
            DESCRIPTION
                "BRAS access user usage, including the license resource name, number of users, and license resource usage."
            INDEX { hwBrasLicenseResource }
            ::= { hwBRASLicenseTable 1 }
        
        HwBRASLicenseEntry ::=
            SEQUENCE { 
                hwBrasLicenseResource   DisplayString, 
                hwBrasLicenseTotal    Unsigned32, 
                hwBrasLicenseUsed    Unsigned32, 
                hwBrasLicenseRatio    Unsigned32
                                             
                }
    
            hwBrasLicenseResource OBJECT-TYPE
            SYNTAX DisplayString (SIZE (1..64))
            MAX-ACCESS read-only
            STATUS current
            DESCRIPTION
                "License resource name."
            ::= { hwBRASLicenseEntry 1 }
    
        hwBrasLicenseTotal OBJECT-TYPE
            SYNTAX Unsigned32 (0..4294967295)
            MAX-ACCESS read-only
            STATUS current
            DESCRIPTION
                "Total number of license resources."
            ::= { hwBRASLicenseEntry 2 }         

    
        hwBrasLicenseUsed OBJECT-TYPE
            SYNTAX Unsigned32 (0..4294967295)
            MAX-ACCESS read-only
            STATUS current
            DESCRIPTION
                "Number of in-use license resources. "
            ::= { hwBRASLicenseEntry 3 }
    
        hwBrasLicenseRatio OBJECT-TYPE
            SYNTAX Unsigned32 (0..4294967295) 
            MAX-ACCESS read-only
            STATUS current
            DESCRIPTION
                "License resource usage."
            ::= { hwBRASLicenseEntry 4 }

        hwAAAAccessTable OBJECT-TYPE
            SYNTAX SEQUENCE OF HwAAAAccessEntry
             MAX-ACCESS not-accessible
            STATUS current
            DESCRIPTION 
	    "Description."
            ::= { hwAAAMibObjects 78 }
		

	hwAAAAccessEntry OBJECT-TYPE
	    SYNTAX HwAAAAccessEntry
	    MAX-ACCESS not-accessible
	    STATUS current
	    DESCRIPTION
	    "Description."
	    INDEX { hwAAAAccessIndex }
	    ::= { hwAAAAccessTable 1 }
		
	HwAAAAccessEntry ::=
	    SEQUENCE { 
                hwAAAAccessIndex
                    Integer32,
                hwAAAAccessUserName
                    DisplayString,
                hwAAAAccessPortType
                    INTEGER,
                hwAAAAccessPriority
                    Integer32,
                hwAAAAccessSlotNo
                    Integer32,
                hwAAAAccessSubSlotNo
                    Integer32,
                hwAAAAccessPortNo
                    Integer32,
                hwAAAAccessVLANID
                    Integer32,
                hwAAAAccessPVC
                    Integer32,
                hwAAAAccessAuthenMethod
                    INTEGER,
                hwAAAAccessAcctMethod
                    INTEGER,
                hwAAAAccessIPAddress
                    IpAddress,                    
                hwAAAAccessVRF
                    DisplayString,
                hwAAAAccessMACAddress
                    MacAddress,
                hwAAAAccessIfIdleCut
                    TruthValue,
                hwAAAAccessIdleCutTime
                    Unsigned32,
                hwAAAAccessIdleCutFlow
                    Integer32,
                hwAAAAccessTimeLimit
                    Unsigned32,
                hwAAAAccessTotalFlow64LimitHigh
                    Unsigned32,
                hwAAAAccessTotalFlow64LimitLow
                    Unsigned32,
                hwAAAAccessStartTime
                    DateAndTime,
                hwAAAAccessCARIfUpActive
                    TruthValue,
                hwAAAAccessCARIfDnActive
                    TruthValue,
                hwAAAAccessUpFlow64
                    Counter64,
                hwAAAAccessDnFlow64
                    Counter64,
                hwAAAAccessUpPacket64
                    Counter64,
                hwAAAAccessDnPacket64
                    Counter64,
                hwAAAAccessCARUpCIR
                    Unsigned32,
                hwAAAAccessCARUpPIR
                    Unsigned32,
                hwAAAAccessCARUpCBS
                    Unsigned32,
                hwAAAAccessCARUpPBS
                    Unsigned32,
                hwAAAAccessCARDnCIR
                    Unsigned32,
                hwAAAAccessCARDnPIR
                    Unsigned32,
                hwAAAAccessCARDnCBS
                    Unsigned32,
                hwAAAAccessCARDnPBS
                    Unsigned32,            
                hwAAAAccessDownPriority
                    Integer32,                     
                hwAAAAccessQosProfile
                    DisplayString,
                hwAAAAccessInterface
                    DisplayString,
                hwAAAAccessIPv6IFID
                    Ipv6AddressIfIdentifier,
                hwAAAAccessIPv6WanAddress
                    Ipv6Address,
                hwAAAAccessIPv6WanPrefix
                    Ipv6AddressPrefix,
                hwAAAAccessIPv6LanPrefix
                    Ipv6AddressPrefix,
                hwAAAAccessIPv6LanPrefixLen
                    Integer32,
                hwAAAAccessBasicIPType
                    DisplayString,
                hwAAAAccessIPv6WaitDelay
                    Integer32,
                hwAAAAccessIPv6ManagedAddressFlag
                    INTEGER,
                hwAAAAccessIPv6CPIFIDAvailable
                    TruthValue,
                hwAAAAccessIPv6OtherFlag
                    INTEGER,
                hwAAAAccessIPv6CPAssignIFID
                    TruthValue,
                hwAAAAccessLineID
                    DisplayString,
                hwAAAAccessIPv6UpFlow64
                    Counter64,
                hwAAAAccessIPv6DnFlow64
                    Counter64,
                hwAAAAccessIPv6UpPacket64
                    Counter64,
                hwAAAAccessIPv6DnPacket64
                    Counter64,               
                hwAAAAccessDeviceName
                    DisplayString,
                hwAAAAccessDeviceMACAddress
                    MacAddress,
                hwAAAAccessDevicePortName
                    OCTET STRING,
                hwAAAAccessAPID     
                    Unsigned32
                
	     }
        hwAAAAccessIndex OBJECT-TYPE
            SYNTAX Integer32 (0..2147483647)
            MAX-ACCESS read-only
            STATUS current
            DESCRIPTION
                "unqualified index"
            ::= { hwAAAAccessEntry 1 }

        hwAAAAccessUserName OBJECT-TYPE
            SYNTAX DisplayString (SIZE (1..253))
            MAX-ACCESS read-only
            STATUS current
            DESCRIPTION
                "access user name"
            ::= { hwAAAAccessEntry 3 }

        hwAAAAccessPortType OBJECT-TYPE
            SYNTAX INTEGER
                {
                all(1),
                ppp(2),
                vlan(3),
                vlanweb(4),
                vlanportal(5),
                vlan8021x(6),
                telnet(7),
                ftp(8),
                ssh(9),
                igmp(10)
                }
            MAX-ACCESS read-only
            STATUS current
            DESCRIPTION
                "access port type
                1:all
                2:PPP
                3:VLAN
                4:WEB of VLAN
                5:Portal of VLAN
                6:802.1X
                7:telnet
                8:ftp
                9:SSH
                10:igmp"
            ::= { hwAAAAccessEntry 5 }

        hwAAAAccessPriority OBJECT-TYPE
            SYNTAX Integer32 (0..15|255)
            MAX-ACCESS read-only
            STATUS current
            DESCRIPTION
                "access up priority"
            ::= { hwAAAAccessEntry 6 } 
            
        hwAAAAccessSlotNo OBJECT-TYPE
            SYNTAX Integer32
            MAX-ACCESS read-only
            STATUS current
            DESCRIPTION
                "slot No."
            ::= { hwAAAAccessEntry 8 }

        hwAAAAccessSubSlotNo OBJECT-TYPE
            SYNTAX Integer32
            MAX-ACCESS read-only
            STATUS current
            DESCRIPTION
                "subslot No."
            ::= { hwAAAAccessEntry 9 }

        hwAAAAccessPortNo OBJECT-TYPE
            SYNTAX Integer32
            MAX-ACCESS read-only
            STATUS current
            DESCRIPTION
                "port No."
            ::= { hwAAAAccessEntry 10 }

        hwAAAAccessVLANID OBJECT-TYPE
            SYNTAX Integer32 
            MAX-ACCESS read-only
            STATUS current
            DESCRIPTION
                "VLAN id"
            ::= { hwAAAAccessEntry 11 }

        hwAAAAccessPVC OBJECT-TYPE
            SYNTAX Integer32
            MAX-ACCESS read-only
            STATUS current
            DESCRIPTION
                "VPI VPC"
            ::= { hwAAAAccessEntry 12 }

        hwAAAAccessAuthenMethod OBJECT-TYPE
            SYNTAX INTEGER
                {
                    local(1),
                    noauth(2),
                    radius(3),
                    localRadius(4),
                    radiusLocal(5),
                    radiusNoauth(6),
                    tacacs(7),
                    localTacacs(8),
                    tacacsLocal(9),
                    tacacsNone(10)         
                }
            MAX-ACCESS read-only
            STATUS current
            DESCRIPTION
                "authentication method"
            ::= { hwAAAAccessEntry 13 }

        hwAAAAccessAcctMethod OBJECT-TYPE
            SYNTAX INTEGER
                {
                local(1),
                radius(2),               
                noacct(3),
                localradiusboth(4),
                hwtacacs(5),
                localhwtacacsboth(6)
                }
            MAX-ACCESS read-only
            STATUS current
            DESCRIPTION
                "account method"
            ::= { hwAAAAccessEntry 14 }

        hwAAAAccessIPAddress OBJECT-TYPE
            SYNTAX IpAddress
            MAX-ACCESS read-only
            STATUS current
            DESCRIPTION
                "IP address"
            ::= { hwAAAAccessEntry 15 } 
            
        hwAAAAccessVRF OBJECT-TYPE
            SYNTAX DisplayString (SIZE (1..31))
            MAX-ACCESS read-only
            STATUS current
            DESCRIPTION
                "VRF name"
            ::= { hwAAAAccessEntry 16 }

         hwAAAAccessMACAddress OBJECT-TYPE
            SYNTAX MacAddress
            MAX-ACCESS read-only
            STATUS current
            DESCRIPTION
                "Mac address"
            ::= { hwAAAAccessEntry 17 }
        

        hwAAAAccessIfIdleCut OBJECT-TYPE
            SYNTAX TruthValue
            MAX-ACCESS read-only
            STATUS current
            DESCRIPTION
                "if idle cut"
            ::= { hwAAAAccessEntry 18 }

        hwAAAAccessIdleCutTime OBJECT-TYPE
            SYNTAX Unsigned32
            MAX-ACCESS read-only
            STATUS current
            DESCRIPTION
                "idle cut time"
            ::= { hwAAAAccessEntry 19 }

        hwAAAAccessIdleCutFlow OBJECT-TYPE
            SYNTAX Integer32
            MAX-ACCESS read-only
            STATUS current
            DESCRIPTION
                "idle cut flow"
            ::= { hwAAAAccessEntry 20 }

        hwAAAAccessTimeLimit OBJECT-TYPE
            SYNTAX Unsigned32
            MAX-ACCESS read-only
            STATUS current
            DESCRIPTION
                "session time"
            ::= { hwAAAAccessEntry 21 }

        hwAAAAccessTotalFlow64LimitHigh OBJECT-TYPE
            SYNTAX Unsigned32
            MAX-ACCESS read-only
            STATUS current
            DESCRIPTION
                "remain flow(32bit)"
            ::= { hwAAAAccessEntry 22 }
        
        hwAAAAccessTotalFlow64LimitLow OBJECT-TYPE
            SYNTAX Unsigned32
            MAX-ACCESS read-only
            STATUS current
            DESCRIPTION
                "remain flow(32bit)"
            ::= { hwAAAAccessEntry 23 }
	
        hwAAAAccessStartTime OBJECT-TYPE
            SYNTAX DateAndTime
            MAX-ACCESS read-only
            STATUS current
            DESCRIPTION
                "start time"
            ::= { hwAAAAccessEntry 25 }

        hwAAAAccessCARIfUpActive OBJECT-TYPE
            SYNTAX TruthValue
            MAX-ACCESS read-only
            STATUS current
            DESCRIPTION
                "up car control"
            ::= { hwAAAAccessEntry 27 }


        hwAAAAccessCARIfDnActive OBJECT-TYPE
            SYNTAX TruthValue
            MAX-ACCESS read-only
            STATUS current
            DESCRIPTION
                "down car control"
            ::= { hwAAAAccessEntry 31 }

        hwAAAAccessUpFlow64 OBJECT-TYPE
            SYNTAX Counter64
            MAX-ACCESS read-only
            STATUS current
            DESCRIPTION
                "up flow(64Byte)"
            ::= { hwAAAAccessEntry 36 }

        hwAAAAccessDnFlow64 OBJECT-TYPE
            SYNTAX Counter64
            MAX-ACCESS read-only
            STATUS current
            DESCRIPTION
                "down flow(64Byte)"
            ::= { hwAAAAccessEntry 37 }

        hwAAAAccessUpPacket64 OBJECT-TYPE
            SYNTAX Counter64
            MAX-ACCESS read-only
            STATUS current
            DESCRIPTION
                "up packet"
            ::= { hwAAAAccessEntry 38 }
        
        hwAAAAccessDnPacket64 OBJECT-TYPE
            SYNTAX Counter64
            MAX-ACCESS read-only
            STATUS current
            DESCRIPTION
                "down packet"
            ::= { hwAAAAccessEntry 39 }

        hwAAAAccessCARUpCIR OBJECT-TYPE
            SYNTAX Unsigned32 (0..10000000)
            MAX-ACCESS read-only
            STATUS current
            DESCRIPTION
                "up committed information rate(kbit/s)"
            ::= { hwAAAAccessEntry 45 }

        hwAAAAccessCARUpPIR OBJECT-TYPE
            SYNTAX Unsigned32 (0..10000000)
            MAX-ACCESS read-only
            STATUS current
            DESCRIPTION
                "up peak information rate(kbit/s)"
            ::= { hwAAAAccessEntry 46 }

         hwAAAAccessCARUpCBS OBJECT-TYPE
            SYNTAX Unsigned32 (0..4294967295)
            MAX-ACCESS read-only
            STATUS current
            DESCRIPTION
                "up committed burst size(byte)"
            ::= { hwAAAAccessEntry 47 }

            
         hwAAAAccessCARUpPBS OBJECT-TYPE
            SYNTAX Unsigned32 (0..4294967295)
            MAX-ACCESS read-only
            STATUS current
            DESCRIPTION
                "up peak burst size(byte)"
            ::= { hwAAAAccessEntry 48 }
            
          hwAAAAccessCARDnCIR OBJECT-TYPE
            SYNTAX Unsigned32 (0..10000000)
            MAX-ACCESS read-only
            STATUS current
            DESCRIPTION
                "down committed information rate(kbit/s)"
            ::= { hwAAAAccessEntry 49 }

        hwAAAAccessCARDnPIR OBJECT-TYPE
            SYNTAX Unsigned32 (0..10000000)
            MAX-ACCESS read-only
            STATUS current
            DESCRIPTION
                "down peak information rate(kbit/s)"
            ::= { hwAAAAccessEntry 50 }

        hwAAAAccessCARDnCBS OBJECT-TYPE
            SYNTAX Unsigned32 (0..4294967295)
            MAX-ACCESS read-only
            STATUS current
            DESCRIPTION
                "down committed burst size(byte)"
            ::= { hwAAAAccessEntry 51 }

            
       hwAAAAccessCARDnPBS OBJECT-TYPE
            SYNTAX Unsigned32 (0..4294967295)
            MAX-ACCESS read-only
            STATUS current
            DESCRIPTION
                "down peak burst size(byte)"
            ::= { hwAAAAccessEntry 52 }

      hwAAAAccessDownPriority OBJECT-TYPE
            SYNTAX Integer32 (0..15|255)
            MAX-ACCESS read-only
            STATUS current
            DESCRIPTION
                "access down priority"
            ::= { hwAAAAccessEntry 53 }

--        hwAAAAccessQinqVlanID OBJECT-TYPE
--            SYNTAX Integer32 (0..4094)
--            MAX-ACCESS read-only
--            STATUS current
--            DESCRIPTION
--                "qinq vlan"
--            ::= { hwAAAAccessEntry 54 }

--        hwAAAAccessUserVlanID OBJECT-TYPE
--            SYNTAX Integer32 (0..4094)
--            MAX-ACCESS read-only
--            STATUS current
--            DESCRIPTION
--                "user VLAN"
--            ::= { hwAAAAccessEntry 55 }

        hwAAAAccessQosProfile OBJECT-TYPE
            SYNTAX DisplayString (SIZE (1..63))
            MAX-ACCESS read-create
            STATUS current
            DESCRIPTION
                "QOS profile"
            ::= { hwAAAAccessEntry 56 }

        hwAAAAccessInterface OBJECT-TYPE
            SYNTAX DisplayString (SIZE (1..63))
            MAX-ACCESS read-only
            STATUS current
            DESCRIPTION
                "user access interface"
            ::= { hwAAAAccessEntry 57 }
        hwAAAAccessIPv6IFID OBJECT-TYPE
            SYNTAX Ipv6AddressIfIdentifier
            MAX-ACCESS read-only
            STATUS current
            DESCRIPTION
                "The user's interface ID when IPv6CP negotiation."
            ::= { hwAAAAccessEntry 58 }

        hwAAAAccessIPv6WanAddress OBJECT-TYPE
            SYNTAX Ipv6Address
            MAX-ACCESS read-only
            STATUS current
            DESCRIPTION
                "The user's WAN address."
            ::= { hwAAAAccessEntry 59 }

        hwAAAAccessIPv6WanPrefix OBJECT-TYPE
            SYNTAX Ipv6AddressPrefix
            MAX-ACCESS read-only
            STATUS current
            DESCRIPTION
                "The user's WAN prefix."
            ::= { hwAAAAccessEntry 60 }
        hwAAAAccessIPv6LanPrefix OBJECT-TYPE
            SYNTAX Ipv6AddressPrefix
            MAX-ACCESS read-only
            STATUS current
            DESCRIPTION
                "The user's LAN prefix."
            ::= { hwAAAAccessEntry 61 }

        hwAAAAccessIPv6LanPrefixLen OBJECT-TYPE
            SYNTAX Integer32 (0..128)
            MAX-ACCESS read-only
            STATUS current
            DESCRIPTION
                "The user's LAN prefix length."
            ::= { hwAAAAccessEntry 62 }

        hwAAAAccessBasicIPType OBJECT-TYPE
            SYNTAX DisplayString (SIZE (1..3))
            MAX-ACCESS read-only
            STATUS current
            DESCRIPTION
                "The basic service type. UCHAR[0]-IPv4, UCHAR[1]-IPv6, UCHAR[2]-IPv6-PD. '0'-without such basic service, '1'-with such basic service."
            ::= { hwAAAAccessEntry 63 }

        hwAAAAccessIPv6WaitDelay OBJECT-TYPE
            SYNTAX Integer32 (0|30..120)
            MAX-ACCESS read-only
            STATUS current
            DESCRIPTION
                "The time of waiting for DHCPv6 packet after IPv6CP negotiation."
            ::= { hwAAAAccessEntry 64 }
        hwAAAAccessIPv6ManagedAddressFlag OBJECT-TYPE
            SYNTAX INTEGER
            {
                ndra(1),
                dhcpv6(2),
                invalid(255)
            }
            MAX-ACCESS read-only
            STATUS current
            DESCRIPTION
                "The address configuration method for PPP and L2TP user."
            ::= { hwAAAAccessEntry 65 }

        hwAAAAccessIPv6CPIFIDAvailable OBJECT-TYPE
            SYNTAX TruthValue
            MAX-ACCESS read-only
            STATUS current
            DESCRIPTION
                "The flag indicating whether PPP and L2TP user will use the interface-id of ipv6cp negotiation in DHCPv6 address allocation."
            ::= { hwAAAAccessEntry 66 }

        hwAAAAccessIPv6OtherFlag OBJECT-TYPE
            SYNTAX INTEGER
            {
                ndra(1),
                dhcpv6(2),
                invalid(255)
            }
            MAX-ACCESS read-only
            STATUS current
            DESCRIPTION
                "The method PPP and L2TP user get configuration parameters."
            ::= { hwAAAAccessEntry 67 }
        hwAAAAccessIPv6CPAssignIFID OBJECT-TYPE
            SYNTAX TruthValue
            MAX-ACCESS read-only
            STATUS current
            DESCRIPTION
                "The flag indicating whether to accept user's interface-id when ipv6cp negotiation."
            ::= { hwAAAAccessEntry 68 }

        hwAAAAccessLineID OBJECT-TYPE
            SYNTAX DisplayString (SIZE (0..255))
            MAX-ACCESS read-only
            STATUS current
            DESCRIPTION
                "The access-line-id information."
            ::= { hwAAAAccessEntry 69 }

        hwAAAAccessIPv6UpFlow64 OBJECT-TYPE
            SYNTAX Counter64
            MAX-ACCESS read-only
            STATUS current
            DESCRIPTION
                "The user's up flow."
            ::= { hwAAAAccessEntry 70 }
        hwAAAAccessIPv6DnFlow64 OBJECT-TYPE
            SYNTAX Counter64
            MAX-ACCESS read-only
            STATUS current
            DESCRIPTION
                "The user's down flow."
            ::= { hwAAAAccessEntry 71 }

        hwAAAAccessIPv6UpPacket64 OBJECT-TYPE
            SYNTAX Counter64
            MAX-ACCESS read-only
            STATUS current
            DESCRIPTION
                "The user's up flow packet."
            ::= { hwAAAAccessEntry 72 }

        hwAAAAccessIPv6DnPacket64 OBJECT-TYPE
            SYNTAX Counter64
            MAX-ACCESS read-only
            STATUS current
            DESCRIPTION
                "The user's down flow packet."
            ::= { hwAAAAccessEntry 73 }  
           
        hwAAAAccessDeviceName OBJECT-TYPE
            SYNTAX DisplayString (SIZE (1..255))
            MAX-ACCESS read-only
            STATUS current
            DESCRIPTION
                "access device name"
            ::= { hwAAAAccessEntry 74 }
            
        hwAAAAccessDeviceMACAddress OBJECT-TYPE
            SYNTAX MacAddress
            MAX-ACCESS read-only
            STATUS current
            DESCRIPTION
                "Access device Mac address"
            ::= { hwAAAAccessEntry 75 }
            
        hwAAAAccessDevicePortName OBJECT-TYPE
            SYNTAX OCTET STRING
            MAX-ACCESS read-only
            STATUS current
            DESCRIPTION
                "Interface Name of Access device."
            ::= { hwAAAAccessEntry 76 }
       hwAAAAccessAPID OBJECT-TYPE
            SYNTAX Unsigned32 (0..4294836225)
            MAX-ACCESS read-only
            STATUS current
            DESCRIPTION
                "Access wiless device AP Id"
            ::= { hwAAAAccessEntry 77 }

        hwLocalEapServerTable OBJECT-TYPE
            SYNTAX SEQUENCE OF HwLocalEapServerEntry
            MAX-ACCESS not-accessible
            STATUS current
            DESCRIPTION
                "Description."
            ::= { hwAAAMibObjects 79 }

        hwLocalEapServerEntry OBJECT-TYPE
            SYNTAX HwLocalEapServerEntry
            MAX-ACCESS not-accessible
            STATUS current
            DESCRIPTION
            "Description."
            INDEX { hwEapSvrTemplateName }
            ::= { hwLocalEapServerTable 1 }

        HwLocalEapServerEntry ::=
            SEQUENCE { 
                hwEapSvrTemplateName
                    DisplayString,
                hwEapAuthenMethod
                    DisplayString,
                hwEapAuthenPhaseOneFlag
                    INTEGER,
                hwEapAuthenLocalCertFormat
                    INTEGER,
                hwEapAuthenLocalCertFileName
                    DisplayString,
                hwEapAuthenCaCertFormat
                    INTEGER,
                hwEapAuthenCaCertFileName
                    DisplayString,
                hwEapAuthenPrivateKeyFormat
                    INTEGER,
                hwEapAuthenPrivateKeyFileName
                    DisplayString,
                hwEapAuthenPrivateKeyFilePsw
                    DisplayString,
                hwLocalEapServerRowStatus
                    RowStatus
            }

        hwEapSvrTemplateName OBJECT-TYPE
            SYNTAX DisplayString (SIZE (1..31))
            MAX-ACCESS read-create
            STATUS current
            DESCRIPTION
                "Description."
            ::= { hwLocalEapServerEntry 1 }

        hwEapAuthenMethod OBJECT-TYPE
            SYNTAX DisplayString (SIZE (1..31))
            MAX-ACCESS read-create
            STATUS current
            DESCRIPTION
                "Description."
            ::= { hwLocalEapServerEntry 2 }

        hwEapAuthenPhaseOneFlag OBJECT-TYPE
            SYNTAX INTEGER
                {
                enable(1),
                disable(2)
                }
            MAX-ACCESS read-create
            STATUS current
            DESCRIPTION
                "Description."
            DEFVAL { disable }
            ::= { hwLocalEapServerEntry 3 }

        hwEapAuthenLocalCertFormat OBJECT-TYPE
            SYNTAX INTEGER
                {
                pem(1),
                der(2)
                }
            MAX-ACCESS read-create
            STATUS current
            DESCRIPTION
                "Description."
            ::= { hwLocalEapServerEntry 4 }

        hwEapAuthenLocalCertFileName OBJECT-TYPE
            SYNTAX DisplayString (SIZE (1..63))
            MAX-ACCESS read-create
            STATUS current
            DESCRIPTION
                "Description."
            ::= { hwLocalEapServerEntry 5 }

        hwEapAuthenCaCertFormat OBJECT-TYPE
            SYNTAX INTEGER { pem(1) }
            MAX-ACCESS read-create
            STATUS current
            DESCRIPTION
                "Description."
            ::= { hwLocalEapServerEntry 6 }

        hwEapAuthenCaCertFileName OBJECT-TYPE
            SYNTAX DisplayString (SIZE (1..63))
            MAX-ACCESS read-create
            STATUS current
            DESCRIPTION
                "Description."
            ::= { hwLocalEapServerEntry 7 }

        hwEapAuthenPrivateKeyFormat OBJECT-TYPE
            SYNTAX INTEGER
                {
                pem(1),
                der(2),
                pkcs12(3)
                }
            MAX-ACCESS read-create
            STATUS current
            DESCRIPTION
                "Description."
            ::= { hwLocalEapServerEntry 8 }

        hwEapAuthenPrivateKeyFileName OBJECT-TYPE
            SYNTAX DisplayString (SIZE (1..63))
            MAX-ACCESS read-create
            STATUS current
            DESCRIPTION
                "Description."
            ::= { hwLocalEapServerEntry 9 }

        hwEapAuthenPrivateKeyFilePsw OBJECT-TYPE
            SYNTAX DisplayString
            MAX-ACCESS read-only
            STATUS current
            DESCRIPTION
                "Description."
            ::= { hwLocalEapServerEntry 10 }

        hwLocalEapServerRowStatus OBJECT-TYPE
            SYNTAX RowStatus
            MAX-ACCESS read-create
            STATUS current
            DESCRIPTION
                "Description."
            ::= { hwLocalEapServerEntry 11 }

        hwLocalEapServerSetting OBJECT IDENTIFIER ::= { hwAAAMibObjects 80 }

        hwEapSvrTemplateNameEnabled OBJECT-TYPE
            SYNTAX DisplayString (SIZE (0..31))
            MAX-ACCESS read-create
            STATUS current
            DESCRIPTION
                "Description."
            ::= { hwLocalEapServerSetting 1 }

        hwAAACuDomainStatTable OBJECT-TYPE
            SYNTAX SEQUENCE OF HwAAACuDomainStatEntry
            MAX-ACCESS not-accessible
            STATUS current
            DESCRIPTION
                "Number of users in the UP granularity by domain."
            ::= { hwAAAMibObjects 81 }

        hwAAACuDomainStatEntry OBJECT-TYPE
            SYNTAX HwAAACuDomainStatEntry
            MAX-ACCESS not-accessible
            STATUS current
            DESCRIPTION
                "Number of users in the UP granularity by domain."
            INDEX { hwCUUpId, hwDomainName }
            ::= { hwAAACuDomainStatTable 1 }

        HwAAACuDomainStatEntry ::=
            SEQUENCE {
                hwAAACuDomainTotalOnlineNum
                    Unsigned32,
                hwAAACuDomainIPv4OnlineNum
                    Unsigned32,
                hwAAACuDomainIPv6OnlineNum
                    Unsigned32,
                hwAAACuDomainDualOnlineNum
                    Unsigned32
            }

        hwAAACuDomainTotalOnlineNum OBJECT-TYPE
            SYNTAX Unsigned32 (0..4294967295)
            MAX-ACCESS read-only
            STATUS current
            DESCRIPTION
                "Total number of access users in a domain on the UP."
            ::= { hwAAACuDomainStatEntry 1 }

        hwAAACuDomainIPv4OnlineNum OBJECT-TYPE
            SYNTAX Unsigned32 (0..4294967295)
            MAX-ACCESS read-only
            STATUS current
            DESCRIPTION
                "Total number of ipv4 access users in a domain on the UP."
            ::= { hwAAACuDomainStatEntry 2 }

        hwAAACuDomainIPv6OnlineNum OBJECT-TYPE
            SYNTAX Unsigned32 (0..4294967295)
            MAX-ACCESS read-only
            STATUS current
            DESCRIPTION
                "Total number of ipv6 access users in a domain on the UP."
            ::= { hwAAACuDomainStatEntry 3 }

        hwAAACuDomainDualOnlineNum OBJECT-TYPE
            SYNTAX Unsigned32 (0..4294967295)
            MAX-ACCESS read-only
            STATUS current
            DESCRIPTION
                "Total number of dual-stack access users in a domain on the UP."
            ::= { hwAAACuDomainStatEntry 4 }

        hwAAACuUserTypeStatTable OBJECT-TYPE
            SYNTAX SEQUENCE OF HwAAACuUserTypeStatEntry
            MAX-ACCESS not-accessible
            STATUS current
            DESCRIPTION
                "Number of users in the UP granularity by domain."
            ::= { hwAAAMibObjects 82 }

        hwAAACuUserTypeStatEntry OBJECT-TYPE
            SYNTAX HwAAACuUserTypeStatEntry
            MAX-ACCESS not-accessible
            STATUS current
            DESCRIPTION
                "Number of users in the UP granularity by user type."
            INDEX { hwCUUpId, hwAAACuUserType }
            ::= { hwAAACuUserTypeStatTable 1 }

        HwAAACuUserTypeStatEntry ::=
            SEQUENCE { 
                hwAAACuUserType
                    INTEGER,
                hwAAACuUserTypeTotalOnlineNum
                    Unsigned32,
                hwAAACuUserTypeIPv4OnlineNum
                    Unsigned32,
                hwAAACuUserTypeIPv6OnlineNum
                    Unsigned32,
                hwAAACuUserTypeDualOnlineNum
                    Unsigned32
            }

        hwAAACuUserType OBJECT-TYPE
            SYNTAX INTEGER
                {
                ppp(0),
                l2tp(1),
                ip(2)
                }
            MAX-ACCESS read-only
            STATUS current
            DESCRIPTION
                "This object indicates a user type. The available options are ppp(0), l2tp(1), ip(2)."
            ::= { hwAAACuUserTypeStatEntry 1 }

        hwAAACuUserTypeTotalOnlineNum OBJECT-TYPE
            SYNTAX Unsigned32 (0..4294967295)
            MAX-ACCESS read-only
            STATUS current
            DESCRIPTION
                "Total number of access users in a user type on the UP."
            ::= { hwAAACuUserTypeStatEntry 2 }

        hwAAACuUserTypeIPv4OnlineNum OBJECT-TYPE
            SYNTAX Unsigned32 (0..4294967295)
            MAX-ACCESS read-only
            STATUS current
            DESCRIPTION
                "Total number of ipv4 access users in a user type on the UP."
            ::= { hwAAACuUserTypeStatEntry 3 }

        hwAAACuUserTypeIPv6OnlineNum OBJECT-TYPE
            SYNTAX Unsigned32 (0..4294967295)
            MAX-ACCESS read-only
            STATUS current
            DESCRIPTION
                "Total number of ipv6 access users in a user type on the UP."
            ::= { hwAAACuUserTypeStatEntry 4 }

        hwAAACuUserTypeDualOnlineNum OBJECT-TYPE
            SYNTAX Unsigned32 (0..4294967295)
            MAX-ACCESS read-only
            STATUS current
            DESCRIPTION
                "Total number of dual-stack access users in a user type on the UP."
            ::= { hwAAACuUserTypeStatEntry 5 }

        hwAAADomainIPV6PoolTable OBJECT-TYPE
            SYNTAX SEQUENCE OF HwAAADomainIPV6PoolEntry
            MAX-ACCESS not-accessible
            STATUS current
            DESCRIPTION
                "The IPV6 pool of domain table."
            ::= { hwAAAMibObjects 83 }

        hwAAADomainIPV6PoolEntry OBJECT-TYPE
            SYNTAX HwAAADomainIPV6PoolEntry
            MAX-ACCESS not-accessible
            STATUS current
            DESCRIPTION
                "The IPV6 pool of domain entry."
            INDEX { hwDomainName,hwAAADomainIPV6PoolName }
            ::= { hwAAADomainIPV6PoolTable 1 }

       HwAAADomainIPV6PoolEntry ::=
            SEQUENCE {
                hwAAADomainIPV6PoolName OCTET STRING,
                hwAAADomainIPV6PoolIndex Unsigned32 ,
                hwAAADomainIPV6PoolConstantIndex Unsigned32 ,
                hwAAADomainIPV6PoolPosition Unsigned32 
            }

        hwAAADomainIPV6PoolName OBJECT-TYPE
            SYNTAX OCTET STRING(SIZE (1..32))
            MAX-ACCESS read-only
            STATUS current
            DESCRIPTION
                "The IPV6 pool name."
            ::= { hwAAADomainIPV6PoolEntry 1 }

        hwAAADomainIPV6PoolIndex OBJECT-TYPE
            SYNTAX Unsigned32 
            MAX-ACCESS read-only
            STATUS current
            DESCRIPTION
                "The IPV6 pool index."
            ::= { hwAAADomainIPV6PoolEntry 2 }

        hwAAADomainIPV6PoolConstantIndex OBJECT-TYPE
            SYNTAX Unsigned32 
            MAX-ACCESS read-only
            STATUS current
            DESCRIPTION
                "The IPV6 pool constant index."
            ::= { hwAAADomainIPV6PoolEntry 3 }

        hwAAADomainIPV6PoolPosition OBJECT-TYPE
            SYNTAX Unsigned32(1..4096)
            MAX-ACCESS read-only
            STATUS current
            DESCRIPTION
                "The IPV6 pool position in domain."
            ::= { hwAAADomainIPV6PoolEntry 4 }

          hwPevlanStatTable OBJECT-TYPE
            SYNTAX SEQUENCE OF HwPevlanStatEntry
            MAX-ACCESS not-accessible
            STATUS current
            DESCRIPTION
                "The BRAS user access statistics with pevlan specified."
            ::= { hwAAAMibObjects 84 }

        hwPevlanStatEntry OBJECT-TYPE
            SYNTAX HwPevlanStatEntry
            MAX-ACCESS not-accessible
            STATUS current
            DESCRIPTION
                "The BRAS user access statistics with pevlan specified."
            INDEX { hwPevlanId }
            ::= { hwPevlanStatTable 1 }

       HwPevlanStatEntry ::=
            SEQUENCE {
                hwPevlanId Unsigned32,
                hwNormalUserNum Unsigned32 ,
                hwRuiLocalUserNum Unsigned32 ,
                hwRuiRemoteUserNum Unsigned32 ,
                hwRadiusAuthenUserNum Unsigned32,
                hwRadiusProxyAuthenUserNum Unsigned32 ,
                hwNoAuthenUserNum Unsigned32 ,
                hwLocalAuthenUserNum Unsigned32 ,
                hwTotalUserNum Unsigned32 
            }

        hwPevlanId OBJECT-TYPE
            SYNTAX Unsigned32 (0..4094)
            MAX-ACCESS read-only
            STATUS current
            DESCRIPTION
                "The pevlan Id. The value 0 indicates that the BRAS user access packet does not carry the VLAN information."
            ::= { hwPevlanStatEntry 1 }

        hwNormalUserNum OBJECT-TYPE
            SYNTAX Unsigned32 
            MAX-ACCESS read-only
            STATUS current
            DESCRIPTION
                "Specifies the number of normal BRAS users with pevlan specified."
            ::= { hwPevlanStatEntry 2 }

        hwRuiLocalUserNum OBJECT-TYPE
            SYNTAX Unsigned32 
            MAX-ACCESS read-only
            STATUS current
            DESCRIPTION
                "Specifies the number of rui local BRAS users with pevlan specified."
            ::= { hwPevlanStatEntry 3 }

        hwRuiRemoteUserNum OBJECT-TYPE
            SYNTAX Unsigned32
            MAX-ACCESS read-only
            STATUS current
            DESCRIPTION
                "Specifies the number of rui remote BRAS users with pevlan specified."
            ::= { hwPevlanStatEntry 4 }

        hwRadiusAuthenUserNum OBJECT-TYPE
            SYNTAX Unsigned32
            MAX-ACCESS read-only
            STATUS current
            DESCRIPTION
                "Specifies the number of RADIUS authenticated BRAS users with pevlan specified."
            ::= { hwPevlanStatEntry 5 }

        hwRadiusProxyAuthenUserNum OBJECT-TYPE
            SYNTAX Unsigned32 
            MAX-ACCESS read-only
            STATUS current
            DESCRIPTION
                "Specifies the number of BRAS users passing RADIUS proxy authentication with pevlan specified. "
            ::= { hwPevlanStatEntry 6 }

        hwNoAuthenUserNum OBJECT-TYPE
            SYNTAX Unsigned32 
            MAX-ACCESS read-only
            STATUS current
            DESCRIPTION
                "Specifies the number of unauthenticated BRAS users with pevlan specified."
            ::= { hwPevlanStatEntry 7 }

        hwLocalAuthenUserNum OBJECT-TYPE
            SYNTAX Unsigned32
            MAX-ACCESS read-only
            STATUS current
            DESCRIPTION
                "Specifies the number of BRAS users passing local authentication with pevlan specified."
            ::= { hwPevlanStatEntry 8 }

        hwTotalUserNum OBJECT-TYPE
            SYNTAX Unsigned32
            MAX-ACCESS read-only
            STATUS current
            DESCRIPTION
                "Specifies the number of total BRAS users with pevlan specified."
            ::= { hwPevlanStatEntry 9 }
 --======                          
           
            --  ============== conformance information ==============
        hwAaaConformance OBJECT IDENTIFIER ::= { hwAaa 5 }
        
        
        hwAaaCompliances OBJECT IDENTIFIER ::= { hwAaaConformance 1 }
        hwAaaCompliance MODULE-COMPLIANCE
               STATUS      current
               DESCRIPTION
                   "The compliance statement for systems supporting 
                this module."

               MODULE      -- this module
               MANDATORY-GROUPS    { hwAuthenSchemeGroup, hwAcctSchemeGroup, hwDomainGroup,
                                  hwDomainExtGroup, hwDomainStatGroup, hwAuthorSchemeGroup,
                                  hwLocalUserGroup, hwLocalUserExtGroup, hwAaaSettingGroup,
                                  hwAaaStatGroup, hwAccessGroup, hwAccessExtGroup,
                                  hwAcctSchemeExtGroup, hwBillPoolGroup, hwBillTFTPGroup,
                                  hwUclGrpGroup, hwIpAccessGroup, hwCutAccessUserGroup,
                                  hwAaaUserPppGroup, hwAaaUserWebandFastGroup, hwAaaUserDot1XGroup,
                                  hwAaaUserBindGroup, hwRecordSchemeGroup, hwMACAccessGroup,
                                  hwSlotConnectNumGroup, hwOfflineReasonStatGroup, hwMulticastListGroup,
                                  hwMulticastProfileGroup, hwMulticastProfileExtGroup, hwAaaTrapOidGroup,
                                  hwAaaTrapsNotificationsGroup, hwLamTrapsNotificationsGroup,hwObsoleteGroup,
                                  hwServiceSchemeGroup, hwDhcpOpt121RouteGroup, hwAccessDelayPerSlotGroup, hwVpnAccessUserStatGroup,
                                  hwInterfaceAccessUserStatGroup,hwDomainAccessUserStatGroup,hwSlotAccessUserStatGroup,hwReAuthenUserGroup,hwReauthorizeGroup,  
                                  hwUserLogGroup,hwGlobalDhcpOpt64SepAndSegGroup,hwGlobalDhcpServerAckGroup, hwWlanInterfaceGroup, hwAuthorCmdGroup,hwAAARateGroup,
                                  hwLocalUserPwPolicyAdminGroup    , hwLocalUserPwPolicyAccGroup

}  
                                               
              ::= { hwAaaCompliances 1 }
                                   
                --  ============== groups ==============  
        hwAaaObjectGroups OBJECT IDENTIFIER ::= { hwAaaConformance 2 } 
                                 
        hwAuthenSchemeGroup OBJECT-GROUP
            OBJECTS { hwAuthenSchemeName, hwAuthenMethod, hwAuthenRowStatus,
                    hwAuthenFailPolicy, hwAuthenFailDomain, hwAuthenMethodNew,
                    hwAuthenTypeAdminChap, hwServerNoRespAcct, hwServerNoRespAuthor}
            STATUS current       
            DESCRIPTION          
                "The authentication scheme configuration."
            ::= { hwAaaObjectGroups 1 }


        hwAcctSchemeGroup OBJECT-GROUP
            OBJECTS { hwAcctSchemeName, hwAccMethod, hwAcctStartFail,
                      hwAcctOnlineFail, hwAccRealTimeInter, hwAcctRowStatus, hwAcctRealTimeIntervalUnit }
            STATUS current
            DESCRIPTION 
                "The account scheme configuration."
            ::= { hwAaaObjectGroups 2 }
             
        hwDomainGroup OBJECT-GROUP
            OBJECTS { hwDomainName, hwDomainAuthenSchemeName, hwDomainAcctSchemeName,
                      hwDomainRadiusGroupName, hwDomainAccessLimitNum, hwDomainIfSrcRoute,
                      hwDomainNextHopIP, hwDomainIdleCutTime, hwDomainIdleCutFlow,
                      hwDomainRowStatus, hwDomainType,hwDomainServiceSchemeName,hwDomainIdleCutType,
                      hwDomainForcePushUrl, hwDomainForcePushUrlTemplate, hwStateBlockFirstTimeRangeName,
                      hwStateBlockSecondTimeRangeName, hwStateBlockThirdTimeRangeName,hwStateBlockForthTimeRangeName,hwDomainFlowStatistic,hwDomainAcctCopyRdsServerName }
            STATUS current
            DESCRIPTION 
                "The domain group configuration."
            ::= { hwAaaObjectGroups 3 } 
            
        hwDomainExtGroup OBJECT-GROUP
            OBJECTS { hwDomainPPPURL, hwIfDomainActive, hwPriority,
                      hwWebServerURL, hwIPPoolOneName, hwIPPoolTwoName,
                      hwIPPoolThreeName, hwTwoLevelAcctRadiusGroupName, hwVPDNGroupIndex,
                      hwUclIndex, hwIfPPPoeURL, hwUclGroupName,
                      hwVpdnGroupName, hwDomainVrf, hwDomainGre,
                      hwDomainRenewIPTag, hwPortalURL, hwPortalServerIP,
                      hwRedirectTimesLimit, hwDot1xTemplate, hwWebServerIP,
                      hwWebServerMode, hwPoolWarningThreshold, hwTacGroupName,
                      hwServicePolicyName, hwCopsGroupSSGType, hwDomainAuthorSchemeName, hwNtvUserProfileName,
                      hwDomainQoSProfile, hwDomainZone,
                      hwIfL2tpRadiusForce, hwDownPriority, hwPPPForceAuthtype,
                      hwDnsIPAddress, hwAdminUserPriority, hwShapingTemplate,
                      hwDomainDPIPolicyName, hwCopsGroupSIGType, hwCopsGroupCIPNType,
                      hwPCReduceCir, hwValAcctType, hwValRadiusServer,
                      hwValCopsServer, hwPCReducePir, hwDomainInboundL2tpQoSProfile,
                      hwDomainOutboundL2tpQoSProfile, hwIfMulticastForward, hwMulticastVirtualSchedulRezCir,
                      hwMulticastVirtualSchedulRezPir, hwMaxMulticastListNum, hwMultiProfile,
                      hwDomainServiceType, hwWebServerUrlParameter, hwWebServerRedirectKeyMscgName, hwPoratalServerUrlParameter, hwPoratalServerFirstUrlKeyName,
                      hwPoratalServerFirstUrlKeyDefaultName,hwDnsSecondIPAddress, hwDomainIgmpEnable,
                      hwIPv6PoolName, hwIPv6PrefixshareFlag, hwUserBasicServiceIPType, hwPriDnsIPv6Address, hwSecDnsIPv6Address,
                      hwDualStackAccountingType, hwIPv6PoolWarningThreshold, hwIPv6CPWaitDHCPv6Delay, hwIPv6ManagedAddressFlag,
                      hwIPv6CPIFIDAvailable, hwIPv6OtherFlag,hwIPv6CPAssignIFID, hwMultiIPv6ProfileName,
                      hwWebServerURLSlave, hwWebServerIPSlave, hwBindAuthWebIP, hwBindAuthWebVrf, hwBindAuthWebIPSlave, hwBindAuthWebVrfSlave, hwExtVpdnGroupName,
                      hwDomainUserGroupName, hwAFTRName, hwDomainDhcpOpt64SepAndSeg, hwDomainDhcpServerAck  }
            STATUS current
            DESCRIPTION 
                "The domain extent table group configuration."
            ::= { hwAaaObjectGroups 4 }
            
        hwDomainStatGroup OBJECT-GROUP
            OBJECTS { hwDomainAccessedNum, hwDomainOnlineNum, hwDomainOnlinePPPUser,
                      hwDomainFlowDnByte, hwDomainFlowDnPkt, hwDomainFlowUpByte,
                      hwDomainFlowUpPkt, hwDomainIPTotalNum, hwDomainIPUsedNum,
                      hwDomainIPConflictNum, hwDomainIPExcludeNum, hwDomainIPIdleNum,hwDomainIPUsedPercent,hwDomainPPPoENum,
                      hwDomainIPv6AddressTotalNum, hwDomainIPv6AddressUsedNum, hwDomainIPv6AddressFreeNum,
                      hwDomainIPv6AddressConflictNum, hwDomainIPv6AddressExcludeNum, hwDomainIPv6AddressUsedPercent,
                      hwDomainNDRAPrefixTotalNum, hwDomainNDRAPrefixUsedNum, hwDomainNDRAPrefixFreeNum,
                      hwDomainNDRAPrefixConflictNum, hwDomainNDRAPrefixExcludeNum, hwDomainNDRAPrefixUsedPercent,
                      hwDomainPDPrefixTotalNum, hwDomainPDPrefixUsedNum, hwDomainPDPrefixFreeNum,
                      hwDomainPDPrefixConflictNum, hwDomainPDPrefixExcludeNum, hwDomainPDPrefixUsedPercent, 
                      hwDomainIPv6FlowDnByte, hwDomainIPv6FlowDnPkt, hwDomainIPv6FlowUpByte, hwDomainIPv6FlowUpPkt }
            STATUS current
            DESCRIPTION 
                "The domain statistics group configuration."
            ::= { hwAaaObjectGroups 5 }

        hwAuthorSchemeGroup OBJECT-GROUP
            OBJECTS { hwAuthorSchemeName, hwAuthorMethod, hwAuthorRowStatus }
            STATUS current
            DESCRIPTION 
                "The authorization scheme group configuration."
            ::= { hwAaaObjectGroups 6 }

        hwLocalUserGroup OBJECT-GROUP
            OBJECTS { hwLocalUserName, hwLocalUserPassword, hwLocalUserAccessType,
                      hwLocalUserPriority, hwftpdirction, hwQosProfileName,
                      hwLocalUserRowStatus, hwLocalUserIpAddress, hwLocalUserVpnInstance, hwLocalUserAccessLimitNum,
                      hwLocalUserPasswordLifetimeMin, hwLocalUserPasswordLifetimeMax, hwLocalUserIfAllowWeakPassword }
            STATUS current
            DESCRIPTION 
                "The local user group configuration."
            ::= { hwAaaObjectGroups 7 }

        hwLocalUserExtGroup OBJECT-GROUP
            OBJECTS { hwLocalUserState, hwLocalUserNoCallBackVerify, hwLocalUserCallBackDialStr, hwLocalUserBlockFailTimes,
                      hwLocalUserBlockInterval, hwLocalUserUserGroup, hwLocalUserDeviceType, hwLocalUserExpireDate, 
                      hwLocalUserIdleTimeoutSecond, hwLocalUserTimeRange, hwLocalUserIsExpired, hwLocalUserExpireHour,
					  hwLocalUserRole}
            STATUS current
            DESCRIPTION 
                "The local user extent group configuration." 
            ::= { hwAaaObjectGroups 8 }

        hwAaaSettingGroup OBJECT-GROUP
            OBJECTS { hwRoamChar, hwGlobalControl, hwSystemRecord,
                      hwOutboundRecord, hwCmdRecord, hwPPPUserOfflineStandardize,
                      hwDomainNameParseDirection, hwDomainNameLocation, hwAccessSpeedNumber,
                      hwAccessSpeedPeriod, hwRealmNameChar, hwRealmParseDirection,
                      hwIPOXpassword, hwAccessDelayTransitionStep,
                      hwAccessDelayTime, hwAccessDelayMinTime, hwParsePriority,
                      hwRealmNameLocation, hwIPOXUsernameOption82, hwIPOXUsernameIP,
                      hwIPOXUsernameSysname, hwIPOXUsernameMAC,hwDefaultUserName, hwNasSerial,
                      hwAAAPasswordRepeatNumber, hwAAAPasswordRemindDay, 
                      hwOnlineUserNumLowerLimitThreshold, hwOnlineUserNumUpperLimitThreshold, hwOnlineUserNumLowerLimitCpThreshold, hwOnlineUserNumLowerLimitCpInstanceId, hwOnlineUserNumUpperLimitCpThreshold, hwOnlineUserNumUpperLimitCpInstanceId,
                      hwIPOXpasswordKeyType, hwReauthorizeEnable, hwDomainNameDelimiter,
                      hwDomainNameSecurityDelimiter, hwGlobalAuthEventAuthFailResponseFail,hwGlobalAuthEventAuthFailVlan,
                      hwGlobalAuthEventAuthenServerDownResponseFail,hwGlobalAuthEventAuthenServerDownVlan,
                      hwGlobalAuthEventClientNoResponseVlan,hwGlobalAuthEventPreAuthVlan,hwGlobalAuthEventAuthFailUserGroup,
                      hwGlobalAuthEventAuthenServerDownUserGroup,hwGlobalAuthEventClientNoResponseUserGroup,
                      hwGlobalAuthEventPreAuthUserGroup,hwTriggerLoose,hwOfflineSpeedNumber, hwAuthorModifyMode, 
                      hwLocalRetryInterval, hwLocalRetryTime, hwLocalBlockTime, hwRemoteRetryInterval, hwRemoteRetryTime, 
                      hwRemoteBlockTime, hwBlockDisable, hwTotalAuthReqNumPortal, hwTotalAuthReqNumMac, hwTotalAuthReqNumDot1x, hwChgPswVertifyFlag, hwLamPswComplexityCheckMethod,
                      hwRemoteAccessRetryInterval, hwRemoteAccessRetryTime, hwRemoteAccessBlockTime, hwRemoteAdminRetryInterval, hwRemoteAdminRetryTime, hwRemoteAdminBlockTime, hwPassChangeOfflineEnable}
            STATUS current
            DESCRIPTION 
                "The AAA setting group configuration."
            ::= { hwAaaObjectGroups 9 }

        hwAaaStatGroup OBJECT-GROUP
            OBJECTS { hwTotalOnlineNum, hwTotalPPPoeOnlineNum, hwTotalPPPoAOnlineNum,
                      hwTotalftpOnlineNum, hwTotalsshOnlineNum, hwTotaltelnetOnlineNum,
                      hwTotalVLANOnlineNum, hwHistoricMaxOnlineNum, hwResetHistoricMaxOnlineNum,
                      hwResetOfflineReasonStatistic, hwResetOnlineFailReasonStatistic,
                      hwMaxPPPoeOnlineNum, hwTotalPortalServerUserNum, hwMaxPortalServerUserNum,
                      hwTotalIPv4OnlineNum, hwTotalIPv6OnlineNum, hwTotalDualStackOnlineNum,
                      hwTotalIPv4FlowDnByte, hwTotalIPv4FlowDnPkt, hwTotalIPv4FlowUpByte,
                      hwTotalIPv4FlowUpPkt, hwTotalIPv6FlowDnByte, hwTotalIPv6FlowDnPkt, 
                      hwTotalIPv6FlowUpByte, hwTotalIPv6FlowUpPkt, hwHistoricMaxOnlineAcctReadyNum,
                      hwPubicLacUserNum, hwHistoricMaxOnlineLocalNum, hwHistoricMaxOnlineRemoteNum,
                      hwTotalLacOnlineNum,hwTotalLnsOnlineNum,hwTotalWlsOnlineNum,hwTotalWrdOnlineNum, hwDhcpUserOnlineFailCount,
					  hwTotalFamilyUserByUsernameOnlineNum, hwDhcpUserOnlineV6FailCount ,hwHistoricMaxOnlineNumDate}                   
            STATUS current
            DESCRIPTION                                          
                "The AAA statistics group configuration."
            ::= { hwAaaObjectGroups 10 }

        hwAccessGroup OBJECT-GROUP
            OBJECTS { hwAccessIndex, hwAccessUserName, hwAccessPortType,
                      hwAccessPriority, hwAccessSlotNo, hwAccessSubSlotNo,
                      hwAccessPortNo, hwAccessVLANID, hwAccessPVC,
                      hwAccessAuthenMethod, hwAccessAcctMethod, hwAccessIPAddress,
                      hwAccessVRF, hwAccessMACAddress, hwAccessIfIdleCut,
                      hwAccessIdleCutTime, hwAccessIdleCutFlow, hwAccessTimeLimit, 
                      hwAccessTotalFlow64Limit, hwAccessStartTime, hwAccessCARIfUpActive,
                      hwAccessCARIfDnActive, hwAccessUpFlow64, hwAccessDnFlow64, 
                      hwAccessUpPacket64, hwAccessDnPacket64, hwAccessCARUpCIR,
                      hwAccessCARUpPIR, hwAccessCARUpCBS, hwAccessCARUpPBS,
                      hwAccessCARDnCIR, hwAccessCARDnPIR, hwAccessCARDnCBS,
                      hwAccessCARDnPBS, hwAccessDownPriority, hwAccessQosProfile, hwAccessInterface,
                      hwAccessIPv6IFID, hwAccessIPv6WanAddress, hwAccessIPv6WanPrefix, hwAccessIPv6LanPrefix,
                      hwAccessIPv6LanPrefixLen, hwAccessBasicIPType, hwAccessIPv6WaitDelay, hwAccessIPv6ManagedAddressFlag,
                      hwAccessIPv6CPIFIDAvailable, hwAccessIPv6OtherFlag, hwAccessIPv6CPAssignIFID, hwAccessLineID,
                      hwAccessIPv6UpFlow64, hwAccessIPv6DnFlow64, hwAccessIPv6UpPacket64, hwAccessIPv6DnPacket64,
                      hwAccessDeviceName,hwAccessDeviceMACAddress,hwAccessDevicePortName,hwAccessAPID, hwAccessQinQVLANID,
					  hwAccessOption82CircuitID, hwAccessOption82RemoteID, hwAccessSessionTimeout, hwAccessISPVLAN, hwAccessISPInterface }
            STATUS current
            DESCRIPTION 
                "The access group configuration."
            ::= { hwAaaObjectGroups 11 }

        hwAccessExtGroup OBJECT-GROUP
            OBJECTS { hwAccessUCLGroup, hwAuthenticationState,
                      hwAuthorizationState, hwAccountingState, hwAccessDomainName,
                      hwIdleTimeLength, hwAcctSessionID, hwAccessStartAcctTime,
                      hwAccessNormalServerGroup, hwAccessDomainAcctCopySeverGroup, hwAccessPVlanAcctCopyServerGroup,
                      hwAccessCurAuthenPlace, hwAccessActionFlag, hwAccessAuthtype, hwAccessType, hwAccessOnlineTime,
                      hwAccessGateway, hwAccessSSID, hwAccessAPMAC, hwAccessDomain, hwAccessCurAccountingPlace,
                      hwAccessCurAuthorPlace, hwAccessUserGroup, hwAccessResourceInsufficientInbound, hwAccessResourceInsufficientOutbound,
                      hwAccessAuthorizetype, hwAccessBakeState}
              STATUS current
             DESCRIPTION 
                "The access extent group configuration."
            ::= { hwAaaObjectGroups 12 }

        hwAcctSchemeExtGroup OBJECT-GROUP
            OBJECTS { hwIfRealtimeAcct, hwRealtimeFailMaxnum, hwStartFailOnlineIfSendInterim }
            STATUS current
            DESCRIPTION 
                "The account scheme extent group configuration."
            ::= { hwAaaObjectGroups 13 }

        hwBillPoolGroup OBJECT-GROUP
            OBJECTS { hwBillsPoolVolume, hwBillsPoolNum, hwBillsPoolAlarmThreshold,    
                      hwBillsPoolBackupMode, hwBillsPoolBackupInterval, hwBillsPoolBackupNow,    
                      hwBillsPoolReset  }
            STATUS current
            DESCRIPTION 
                "The bill pool group configuration."
            ::= { hwAaaObjectGroups 14 }

        hwBillTFTPGroup OBJECT-GROUP
            OBJECTS { hwBillsTFTPSrvIP, hwBillsTFTPMainFileName  }
            STATUS current
            DESCRIPTION 
                "The bill tftp group configuration."
            ::= { hwAaaObjectGroups 15 }

        hwUclGrpGroup OBJECT-GROUP
            OBJECTS { hwUclGrpName, hwUclGrpRowStatus  }
            STATUS current
            DESCRIPTION 
                "The user group configuration."
            ::= { hwAaaObjectGroups 16 }

        hwIpAccessGroup OBJECT-GROUP
            OBJECTS { hwIPAccessIPaddress, hwIPAccessCID, hwIPAccessVRF  }
            STATUS current
            DESCRIPTION 
                "The IP access group configuration."
            ::= { hwAaaObjectGroups 17 }

        hwCutAccessUserGroup OBJECT-GROUP
            OBJECTS { hwCutStartUserID, hwCutEndUserID, hwCutIPaddress,
                      hwCutMacAddres, hwCutUserName, hwCutUserAttri,
                      hwCutDomain, hwCutIPPoolName, hwCutIfIndex,
                      hwCutVlanID, hwCutVPI, hwCutVCI,
                      hwCutVRF, hwCutAccessInterface, hwCutUserSSID, hwCutAccessSlot, hwCutUserGroup }
            STATUS current
            DESCRIPTION 
                "The cut access user scheme group configuration."
            ::= { hwAaaObjectGroups 18 }
    
        hwAaaUserPppGroup OBJECT-GROUP
            OBJECTS { hwTotalConnectNum, hwTotalSuccessNum, hwTotalLCPFailNum,
                      hwTotalAuthenFailNum, hwTotalNCPFailNum, hwTotalIPAllocFailNum,
                      hwTotalOtherPPPFailNum, hwTotalPPPFailNum  }
            STATUS current
            DESCRIPTION 
                "The AAA user ppp group configuration."
            ::= { hwAaaObjectGroups 19 }

        hwAaaUserWebandFastGroup OBJECT-GROUP
            OBJECTS { hwTotalWebConnectNum, hwTotalSuccessWebConnectNum  }
            STATUS current
            DESCRIPTION 
                "The AAA user web and fast group configuration."
            ::= { hwAaaObjectGroups 20 }

        hwAaaUserDot1XGroup OBJECT-GROUP
            OBJECTS { hwTotalDot1XConnectNum, hwTotalSuccessDot1XConnectNum  }
            STATUS current
            DESCRIPTION 
                "The AAA user dot1x group configuration."
            ::= { hwAaaObjectGroups 21 }

        hwAaaUserBindGroup OBJECT-GROUP
            OBJECTS { hwTotalBindConnectNum, hwTotalSuccessBindConnectNum  }
            STATUS current
            DESCRIPTION 
                "The AAA user bind group configuration."
            ::= { hwAaaObjectGroups 22 }

        hwRecordSchemeGroup OBJECT-GROUP
            OBJECTS { hwRecordSchemeName, hwRecordTacGroupName, hwRecordRowStatus  }
            STATUS current
            DESCRIPTION 
                "The record scheme group configuration."
            ::= { hwAaaObjectGroups 23 }

        hwMACAccessGroup OBJECT-GROUP
            OBJECTS { hwMACAccessMACAddress, hwMACAccessCID  }
            STATUS current
            DESCRIPTION 
                "The MAC access group configuration."
            ::= { hwAaaObjectGroups 24 }

        hwSlotConnectNumGroup OBJECT-GROUP
            OBJECTS { hwSlotConnectNumSlot, hwSlotConnectNumOnlineNum, hwSlotConnectNumMaxOnlineNum, 
                      hwSlotConnectNumMaxOnlineAcctReadyNum, hwSlotConnectNumIPv4OnlineNum, hwSlotConnectNumIPv6OnlineNum, 
                      hwSlotConnectNumDualOnlineNum, hwSlotConnectNumMaxOnlineNumDate, hwSlotConnectNumMaxOnlineAcctRNumDate  }
            STATUS current
            DESCRIPTION 
                "The slot connect number group configuration."
            ::= { hwAaaObjectGroups 25 }

        hwOfflineReasonStatGroup OBJECT-GROUP
            OBJECTS { hwOfflineReason, hwOfflineReasonStatistic, hwOnlineFailReasonStatistic  }
            STATUS current
            DESCRIPTION 
                "The offline reason statistics group configuration."
            ::= { hwAaaObjectGroups 26 }

        hwMulticastListGroup OBJECT-GROUP
            OBJECTS { hwMulticastListIndex, hwMulticastListName, hwMulticastListSourceIp,
                      hwMulticastListSourceIpMask, hwMulticastListGroupIp, hwMulticastListGroupIpMask,
                      hwMulticastListVpnInstance,hwMulticastListRowStatus  }
            STATUS current
            DESCRIPTION 
                "The multicast list group configuration."
            ::= { hwAaaObjectGroups 27 }

        hwMulticastProfileGroup OBJECT-GROUP
            OBJECTS { hwMulticastProfileIndex, hwMulticastProfileName, hwMulticastProfileRowStatus  }
            STATUS current
            DESCRIPTION 
                "The multicast profile group configuration."
            ::= { hwAaaObjectGroups 28 }

        hwMulticastProfileExtGroup OBJECT-GROUP
            OBJECTS { hwMulticastListBindName, hwMulticastProfileExtRowStatus  }
            STATUS current
            DESCRIPTION 
                "The multicast profile extent group configuration."
            ::= { hwAaaObjectGroups 29 }

        hwAaaTrapOidGroup OBJECT-GROUP
            OBJECTS { hwDomainIndex, hwHdFreeamount, hwHdWarningThreshold,
                      hwUserSlot, hwUserSlotMaxNumThreshold, hwOnlineUserNumThreshold,
                      hwPolicyRoute,hwPolicyRouteThreshold,hwRbsDownReason,hwRbpOldState,
                      hwRbpChangeName,hwMaxUserThresholdType,hwRbpNewState,hwRbsName,
                      hwRbpChangeReason,hwRemoteDownloadAclUsedValue,hwRemoteDownloadAclThresholdValue}
            STATUS current
            DESCRIPTION 
                "The AAA trap old group configuration."
            ::= { hwAaaObjectGroups 30 }

        hwAaaTrapsNotificationsGroup NOTIFICATION-GROUP
            NOTIFICATIONS { hwUserIPAllocAlarm, hwUserIPv6AddressAllocAlarm, hwUserNDRAPrefixAllocAlarm, hwUserDelegationPrefixAllocAlarm, 
                            hwUserSlotMaxNum, hwOnlineUserNumAlarm, hwSetUserQosProfileFail, hwUserMaxNum, hwRbpStateChange, hwRbsDown, hwRbsUp, hwUserIPAllocAlarmResume, 
                            hwUserIPv6AddressAllocAlarmResume, hwUserNDRAPrefixAllocAlarmResume, hwUserDelegationPrefixAllocAlarmResume,
                            hwUserNameIndexAllocAlarm, hwUserNameIndexAllocAlarmResume,
                            hwCUUserNameIndexAllocAlarm, hwCUUserNameIndexAllocAlarmResume,
                            hwOnlineUserNumUpperLimitAlarm, hwOnlineUserNumUpperLimitResume, hwOnlineUserNumLowerLimitAlarm,
                            hwOnlineUserNumLowerLimitResume, hwIPLowerlimitWarningAlarm, hwIPLowerlimitWarningResume,
                            hwIPv6AddressLowerlimitWarningAlarm, hwIPv6AddressLowerlimitWarningResume, hwIPv6NDRAPrefixLowerlimitWarningAlarm,
                            hwIPv6NDRAPrefixLowerlimitWarningResume, hwIPv6PDPrefixLowerlimitWarningAlarm,hwIPv6PDPrefixLowerlimitWarningResume,hwPolicyRouteSlotMaxNum,
                            hwRemoteDownloadAclThresholdAlarm,hwRemoteDownloadAclThresholdResume,
                            hwAdminLoginFailed, hwAdminLoginFailedClear, hwUserGroupThresholdAlarm, hwUserGroupThresholdResume,hwEDSGLicenseExpireAlarm,hwEDSGLicenseExpireResume,
                            hwAAAAccessUserResourceOrCpuAlarm, hwAAAAccessUserResourceOrCpuResume,hwCUIPLowerlimitAlarm,
                            hwCUIPLowerlimitWarningResume,hwCUIPv6AddressLowerlimitAlarm,hwCUIPv6AddressLowerlimitResume,hwCUIPv6NDRAPrefixLowerlimitAlarm,
                            hwCUIPv6NDRAPrefixLowerlimitResume,hwCUIPv6PDPrefixLowerlimitAlarm,hwCUIPv6PDPrefixLowerlimitResume,hwCUUserDelegationPrefixAllocAlarm,
                            hwCUUserDelegationPrefixAllocAlarmResume,hwCUUserIPAllocAlarm,hwCUUserIPAllocAlarmResume,hwCUUserIPv6AddressAllocAlarm,
                            hwCUUserIPv6AddressAllocAlarmResume,hwCUUserNDRAPrefixAllocAlarm,hwCUUserNDRAPrefixAllocAlarmResume}
            STATUS current
            DESCRIPTION 
                "The AAA traps."
            ::= { hwAaaObjectGroups 31 }

        hwLamTrapsNotificationsGroup NOTIFICATION-GROUP
            NOTIFICATIONS { hwHarddiskoverflow, hwHarddiskReachThreshold, hwHarddiskOK,
                            hwCachetoFTPFail, hwHDtoFTPFail, hwAAAUserPwdWillExpire, hwAAAUserPwdExpired }
            STATUS current
            DESCRIPTION 
                "The lam traps."
            ::= { hwAaaObjectGroups 32 }
            
        hwObsoleteGroup OBJECT-GROUP
            OBJECTS { hwNtvUserProfileName }
            STATUS obsolete
            DESCRIPTION 
                "The obsolete group configuration."
            ::= { hwAaaObjectGroups 33 } 
        
        hwServiceSchemeGroup OBJECT-GROUP
        OBJECTS {hwServiceSchemeNextHopIp, hwServiceSchemeUserPriority,
                     hwServiceSchemeIdleCutTime, hwServiceSchemeIdleCutFlow, 
                     hwServiceSchemeDnsFirst, hwServiceSchemeDnsSecond, 
                     hwSrvSchemeAdminUserPriority,  hwSrvSchemeIpPoolOneName,
                     hwSrvSchemeIpPoolTwoName, hwSrvSchemeIpPoolThreeName, 
                     hwServiceSchemeRowStatus,hwServiceSchemeIdleCutType,
                     hwServiceSchemeIdleCutFlowValue,hwServiceSchemeRedirectACL,hwServiceSchemePriority, hwServiceSchemeRedirectIPv6ACL }
       STATUS current
       DESCRIPTION 
            "The service scheme group configuration."
          ::= { hwAaaObjectGroups 34 }
      
       hwDhcpOpt121RouteGroup OBJECT-GROUP
       OBJECTS {hwDhcpOpt121RouteDestIp,  hwDhcpOpt121RouteMask, 
                hwDhcpOpt121RouteNextHop, hwDhcpOpt121RouteRowStatus }
       STATUS current
       DESCRIPTION 
            "The dhcp option121 route group configuration."
          ::= { hwAaaObjectGroups 35 }
       --  ============== begin : added by w00127306 for V6R3C01 ==============    
       hwAccessDelayPerSlotGroup OBJECT-GROUP
        OBJECTS {hwAccessDelayPerSlotSlot, hwAccessDelayPerSlotTransitionStep,
                     hwAccessDelayPerSlotMaxTime, hwAccessDelayPerSlotMinTime, 
                     hwAccessDelayPerSlotRowStatus}
       STATUS current
       DESCRIPTION 
            "The access delay per slot group configuration."
          ::= { hwAaaObjectGroups 36 }
      
       hwVpnAccessUserStatGroup OBJECT-GROUP
       OBJECTS {hwUserType, hwVpnAccessUserStatVpnName, 
                hwVpnAccessUserStatUserStat }
       STATUS current
       DESCRIPTION 
            "The vpn access user stat configuration."
          ::= { hwAaaObjectGroups 37 }   
          
       hwInterfaceAccessUserStatGroup OBJECT-GROUP
       OBJECTS {hwInterfaceAccessUserStatInterfaceIndex,  hwInterfaceAccessUserStatUserStat }
       STATUS current
       DESCRIPTION 
            "The interface access user stat configuration."
          ::= { hwAaaObjectGroups 38 }  
          
       hwDomainAccessUserStatGroup OBJECT-GROUP
       OBJECTS {hwDomainAccessUserStatUserStat }
       STATUS current
       DESCRIPTION 
            "The domain access user stat configuration."
          ::= { hwAaaObjectGroups 39 }    
          
       hwSlotAccessUserStatGroup OBJECT-GROUP
       OBJECTS {hwSlotAccessUserStatSlot, hwSlotAccessUserStatUserStat }
       STATUS current
       DESCRIPTION 
            "The slot access user stat configuration."
          ::= { hwAaaObjectGroups 40 }                          
       --  ============== end : added by w00127306 for V6R3C01 ============== 
       
       hwDomainIncludePoolGroup OBJECT-GROUP
       OBJECTS {hwDomainIncludeIPPoolGroupName, hwDomainIncludeIPPoolGroupRowStates }
       STATUS current
       DESCRIPTION 
            "Configure a pool group in the specified domain."
          ::= { hwAaaObjectGroups 45 }  
       
       hwDomainIPPoolMoveTo OBJECT-GROUP
       OBJECTS {hwDomainIncludeIPPoolName, hwDomainIncludeIPPoolMoveto }
       STATUS current
       DESCRIPTION 
            "Change the priority of pool group in the specified domain."
          ::= { hwAaaObjectGroups 46 }


       
       hwUserLogGroup OBJECT-GROUP
       OBJECTS {hwUserLogAccess, hwUserLogIPAddress,hwUserLogPort,
                hwUserLogVersion,hwShowUserLogStatistic,hwResetUserLogStatistic}
       STATUS current
       DESCRIPTION 
            "The user log configuration"
          ::= { hwAaaObjectGroups 47 }

       hwGlobalDhcpOpt64SepAndSegGroup OBJECT-GROUP
       OBJECTS {hwGlobalDhcpOpt64SepAndSeg}
       STATUS current
       DESCRIPTION 
            "The global option64 parse separator configuration"
          ::= { hwAaaObjectGroups 48 }
       
       hwGlobalDhcpServerAckGroup OBJECT-GROUP
       OBJECTS {hwGlobalDhcpServerAck}
       STATUS current
       DESCRIPTION 
            "The global whether to deal dhcp server's ack packet configuration"
          ::= { hwAaaObjectGroups 49 }
             
       hwReauthorizeGroup OBJECT-GROUP
       OBJECTS {hwReauthorizeUsername, hwReauthorizeUsergroup }
       STATUS current
       DESCRIPTION 
            "Change user's user-group by username."
          ::= { hwAaaObjectGroups 50 }

       hwWlanInterfaceGroup OBJECT-GROUP
       OBJECTS {hwWlanInterfaceIndex, hwWlanInterfaceName, hwWlanInterfaceDomainNameDelimiter, hwWlanInterfaceDomainNameSecurityDelimiter,
                hwWlanInterfaceDomainNameParseDirection, hwWlanInterfaceDomainNameLocation }
       STATUS current
       DESCRIPTION 
            "The domain configuration in interface."
          ::= { hwAaaObjectGroups 56 }
          
       hwAuthorCmdGroup OBJECT-GROUP
       OBJECTS {hwAuthorCmdLevel, hwAuthorCmdMode, hwAuthorCmdRowStatus }
       STATUS current
       DESCRIPTION 
            "The authorization-cmd configuration."
          ::= { hwAaaObjectGroups 57 }
            
       hwAAARateGroup OBJECT-GROUP
       OBJECTS {hwAAARateDirection, hwAAARateType, hwAAARateRealPeak,  hwAAARateRealAverage,hwAAARateRealUsedCount, hwAAARateRealPercent}
       STATUS current
       DESCRIPTION 
            "Tariff package information statistics."
          ::= { hwAaaObjectGroups 58 }    
                        
     hwLocalUserPwPolicyAdminGroup OBJECT-GROUP
       OBJECTS {hwAdminEnable,hwAdminExpire, hwAdminPwHistroyRecordNum,  hwAdminAlertBefore,hwAdminAlertOrginal}
       STATUS current
       DESCRIPTION 
            "Administrator password policy."
          ::= { hwAaaObjectGroups 59 }        
                     
         hwLocalUserPwPolicyAccGroup OBJECT-GROUP
       OBJECTS {hwAccEnable, hwAccPwHistroyRecordNum}
       STATUS current
       DESCRIPTION 
            "Access-user password policy."
          ::= { hwAaaObjectGroups 60 }  
  hwAAADomainIPPoolGroup OBJECT-GROUP
       OBJECTS {hwAAADomainIPPoolName, hwAAADomainIPPoolIndex, hwAAADomainIPPoolConstantIndex,hwAAADomainIPPoolPosition, hwAAADomainIPPoolRowStatus}
       STATUS current
       DESCRIPTION 
            "The IP pool of domain."
          ::= { hwAaaObjectGroups 61 }
  userAuthenProfileGroup OBJECT-GROUP
  		OBJECTS {userAuthenProfileName, userAuthenProfileDot1xAccessProfileName, userAuthenProfileMacAuthenAccessProfileName,
  					userAuthenProfilePortalAccessProfileName, userAuthenProfileSingleAccess, userAuthenProfilePreAuthenServiceSchemeName,
  					userAuthenProfilePreAuthenUserGroupName, userAuthenProfilePreAuthenVLAN, userAuthenProfileAuthenFailAuthorServiceSchemeName,
  					userAuthenProfileAuthenFailAuthorUserGroupName, userAuthenProfileAuthenFailAuthorVLAN, userAuthenProfileAuthenServerDownServiceSchemeName,
  					userAuthenProfileAuthenServerDownUserGroupName, userAuthenProfileAuthenServerDownVLAN, userAuthenProfileAuthenServerDownResponseSuccess, userAuthenProfileAuthenServerUpReauthen,
  					userAuthenProfileMacAuthenFirst, userAuthenProfileMACBypass, userAuthenProfileDot1xForceDomain, userAuthenProfileMACAuthenForceDomain,
  					userAuthenProfilePortalForceDomain, userAuthenProfileDot1xDefaultDomain, userAuthenProfileMACAuthenDefaultDomain, userAuthenProfilePortalDefaultDomain, userAuthenProfileSecurityNameDelimiter,
  					userAuthenProfilePreAuthenReAuthenTimer, userAuthenProfileAuthenFailReAuthenTimer, userAuthenProfilePreAuthenAgingTime, userAuthenProfileAuthenFailAgingTime,
  					userAuthenProfileFreeRuleName, userAuthenProfileAuthenSchemeName, userAuthenProfileAuthorSchemeName, userAuthenProfileAcctSchemeName,
  					userAuthenProfileServiceSchemeName,userAuthenProfileUserGroupName, userAuthenProfileRadiusServerName, userAuthenProfileHwtacacsServerName, userAuthenProfileAuthenticationMode,
  					userAuthenProfileMaxUser, userAuthenProfileAuthenFailAuthorResponseSuccess, userAuthenProfileArpDetect, userAuthenProfileArpDetectTimer, userAuthenProfileRowStatus}
  		STATUS current
  		DESCRIPTION
  			"The authentication profile." 
  			::= { hwAaaObjectGroups 62 } 
  userAuthenticationFreeRuleGroup OBJECT-GROUP 
  		OBJECTS {userAuthenticationFreeRuleName, userAuthenticationFreeRuleACLNumber, userAuthenticationFreeRuleIPv6ACLNumber, userAuthenticationFreeRuleNumber,
  					userAuthenticationFreeRuleSourceMode, userAuthenticationFreeRuleSourceVlan, userAuthenticationFreeRuleSourceInterface, userAuthenticationFreeRuleSourceIP,
  					userAuthenticationFreeRuleSourceIPMask, userAuthenticationFreeRuleSourceMac, userAuthenticationFreeRuleDestinationMode, userAuthenticationFreeRuleDestinationIP,
  					userAuthenticationFreeRuleDestinationIPMask, userAuthenticationFreeRuleDestinationProtocol, userAuthenticationFreeRuleDestinationPort,
  					userAuthenticationFreeRuleDestinationUserGroup, userAuthenticationFreeRuleRowStatus}  
  		STATUS current
  		DESCRIPTION
  			"The authentication free rule." 
  			::= { hwAaaObjectGroups 63 }
  hwDot1xAccessProfileGroup OBJECT-GROUP
  		OBJECTS {hwDot1xAccessProfileName, hwDot1xAccessProfileGuestAuthorServiceSchemeName, hwDot1xAccessProfileGuestAuthorUserGroupName, hwDot1xAccessProfileGuestAuthorVLAN,
  					hwDot1xAccessProfileHandshakeSwitch, hwDot1xAccessProfileHandShakePktType, hwDot1xAccessProfileHandshakeInterval, hwDot1xAccessProfileIfEAPEnd,
  					hwDot1xAccessProfileEAPEndMethod, hwDot1xAccessProfileEAPNotifyPktEAPCode, hwDot1xAccessProfileEAPNotifyPktEAPType, hwDot1xAccessProfileReAuthenEnable,
  					hwDot1xAccessProfileReauthenticationTimeout, hwDot1xAccessProfileClientTimeout, hwDot1xAccessProfileServerTimeout, hwDot1xAccessProfileTxPeriod,
  					hwDot1xAccessProfileMaxRetryValue, hwDot1xAccessProfileSpeedLimitAuto, hwDot1xAccessProfileTriggerPktType, hwDot1xAccessProfileUnicastTrigger,
  					hwDot1xAccessProfileURL, hwDot1xAccessProfileEthTrunkHandShakePeriod, hwDot1xAccessProfileRowStatus,hwDot1xAccessProfileDot1xNoResponse}  
  		STATUS current
  		DESCRIPTION
  			"The dot1x access profile." 
  			::= { hwAaaObjectGroups 64 } 
  hwMACAuthenAccessProfileGroup OBJECT-GROUP
  		OBJECTS {hwMACAuthenAccessProfileName, hwMACAuthenAccessProfileReAuthenEnable, hwMACAuthenAccessProfileReauthenticationTimeout, hwMACAuthenAccessProfileServerTimeout,
  					hwMACAuthenAccessProfileUserNameFixedUserName, hwMACAuthenAccessProfileFixedPassword, hwMACAuthenAccessProfileMACAddressFormat, hwMACAuthenAccessProfileMACAddressPassword,
  					hwMACAuthenAccessProfileUserNameDHCPOption, hwMACAuthenAccessProfileUserNameDHCPOSubOption, hwMACAuthenAccessProfileTriggerPktType, hwMACAuthenAccessProfileTriggerDHCPOptionType,
  					hwMACAuthenAccessProfileDHCPRelaseOffline, hwMACAuthenAccessProfileDHCPRenewReAuthen, hwMACAuthenAccessProfilePermitAuthenMAC, hwMACAuthenAccessProfilePermitAuthenMACMask,
  					hwMACAuthenAccessProfileRowStatus}
  		STATUS current
  		DESCRIPTION
  			"The mac-authen access profile." 
  			::= { hwAaaObjectGroups 65 } 
  hwPortalAccessProfileGroup OBJECT-GROUP  
  		OBJECTS {hwPortalAccessProfileName, hwPortalAccessProfileDetectPeriod, hwPortalAccessProfilePortalServerDownServiceSchemeName, hwPortalAccessProfilePortalServerDownUserGroupName,
  					hwPortalAccessProfilePortalServerUpReAuthen, hwPortalAccessProfileAlarmUserLowNum, hwPortalAccessProfileAlarmUserHighNum, hwPortalAccessProfileAuthenNetWork,
  					hwPortalAccessProfileAuthenNetWorkMask, hwPortalAccessProfilePortalServerName, hwPortalAccessProfilePortalAccessDirect, hwPortalAccessProfileLocalServerEnable,
  					hwPortalAccessProfileRowStatus, hwPortalAccessProfilePortalBackupServerName, hwPortalAccessProfileLocalServerAnonymousUrl} 
  		STATUS current
  		DESCRIPTION
  			"The portal access profile." 
  			::= { hwAaaObjectGroups 66 }    

  hwReAuthenUserGroup OBJECT-GROUP
		OBJECTS { hwReAuthenMacAddress }
		STATUS current
		DESCRIPTION 
			"ReAuthen User"
			::= { hwAaaObjectGroups 67 }            
			
  hwAccessUserNumberGroup OBJECT-GROUP  
  		OBJECTS {hwAccessUserNumberDot1x,hwAccessUserNumberMAC,hwAccessUserNumberPortal,hwAccessUserNumberPPP,
  		hwAccessUserNumberNone,hwAccessUserNumberStatic,hwAccessUserNumberAdmin} 
  		STATUS current
  		DESCRIPTION
  			"The access users profile." 
  			::= { hwAaaObjectGroups 68 }  
 
       --  ============== conformance information define end ==============  

    
    END
