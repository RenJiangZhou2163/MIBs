--
-- HUAWEI-SECURITY-CAR-MIB.mib
-- MIB generated by MG-SOFT Visual MIB Builder Version 4.0 Build 347
-- Friday, February 13, 2015 at 16:22:33
--

--  
-- =============================================================================
-- Copyright (C) 2018 by HUAWEI TECHNOLOGIES. All rights reserved.
--  
-- Description:  
-- Reference: Huawei Enterprise MIB
-- Version: V1.03
-- History: 
--        V1.00 The initial version created by Zuoyi 90006056. 
-- =============================================================================

	HUAWEI-SECURITY-CAR-MIB DEFINITIONS ::= BEGIN
 
		IMPORTS
			private			
				FROM RFC1155-SMI			
			OBJECT-GROUP, MODULE-COMPLIANCE, NOTIFICATION-GROUP			
				FROM SNMPv2-CONF			
			IpAddress, Integer32, Gauge32, OBJECT-TYPE, MODULE-IDENTITY, 
			NOTIFICATION-TYPE			
				FROM SNMPv2-SMI;
	
	
		-- 1.3.6.1.4.1.2011.6.122.63
		hwSecCAR MODULE-IDENTITY 
			LAST-UPDATED "201809252000Z"
			ORGANIZATION 
				"Huawei Technologies Co.,Ltd."
			CONTACT-INFO 
				"Huawei Industrial Base Bantian, Longgang Shenzhen 518129 People's Republic of China Website: http://www.huawei.com Email: support@huawei.com
				"
			DESCRIPTION 
				"V1.00
				The CAR mib is for Eudemon and USG product series."
            REVISION "201809252000Z"
			DESCRIPTION 
				"modify for hardware car table trap at 201809252000Z"
			REVISION "201704102100Z"
			DESCRIPTION 
				"modify for monitor table trap at 2201704102100Z"
			REVISION "201509282100Z"
			DESCRIPTION 
				"modify for ipcar detail trap at 201509282100Z"
			REVISION "201305141900Z"		-- May 14, 2013 at 19:00 GMT
			DESCRIPTION 
				"modify for v5r1 at 201305141900Z"
                                                        			::= { hwSecurity 63 }

		
	
--
-- Node definitions
--
	
--  1.3.6.1.4.1.2011.6.122.63
-- May 14, 2013 at 19:00 GMT
-- May 14, 2013 at 19:00 GMT
-- 
-- Node definitions
-- 
-- 1.3.6.1.4.1
		-- 1.3.6.1.4.1
		enterprises OBJECT IDENTIFIER ::= { private 1 }

		
--    1.3.6.1.4.1.2011.6.122.62
-- March 08, 2013 at 19:00 GMT
-- ===============================================
-- Node definitions
-- ===============================================
-- 1.3.6.1.4.1.2011
		-- 1.3.6.1.4.1.2011
		huawei OBJECT IDENTIFIER ::= { enterprises 2011 }

		
--  1.3.6.1.4.1.2011.6
		-- 1.3.6.1.4.1.2011.6
		huaweiUtility OBJECT IDENTIFIER ::= { huawei 6 }

		
--  1.3.6.1.4.1.2011.6.122
		-- 1.3.6.1.4.1.2011.6.122
		hwSecurity OBJECT IDENTIFIER ::= { huaweiUtility 122 }

		
--  1.3.6.1.4.1.2011.6.122.63.1
		-- 1.3.6.1.4.1.2011.6.122.63.1
		hwSecCARTraps OBJECT IDENTIFIER ::= { hwSecCAR 1 }

		
--  1.3.6.1.4.1.2011.6.122.63.1.1
		-- 1.3.6.1.4.1.2011.6.122.63.1.1
		hwSecGroupCARTrafficOverThreshold NOTIFICATION-TYPE
			STATUS current
			DESCRIPTION 
				"The user login failed."
			::= { hwSecCARTraps 1 }

		
--  1.3.6.1.4.1.2011.6.122.63.1.2
		-- 1.3.6.1.4.1.2011.6.122.63.1.2
		hwSecGroupCARTrafficBelowThreshold NOTIFICATION-TYPE
			STATUS current
			DESCRIPTION 
				"Description."
			::= { hwSecCARTraps 2 }

		
--  1.3.6.1.4.1.2011.6.122.63.1.3
		-- 1.3.6.1.4.1.2011.6.122.63.1.3
		hwSecGroupCARSessionOverThreshold NOTIFICATION-TYPE
			STATUS current
			DESCRIPTION 
				"Description."
			::= { hwSecCARTraps 3 }

		
--  1.3.6.1.4.1.2011.6.122.63.1.4
		-- 1.3.6.1.4.1.2011.6.122.63.1.4
		hwSecGroupCARSessionBelowThreshold NOTIFICATION-TYPE
			STATUS current
			DESCRIPTION 
				"Description."
			::= { hwSecCARTraps 4 }

		
--  1.3.6.1.4.1.2011.6.122.63.1.5
		-- 1.3.6.1.4.1.2011.6.122.63.1.5
		hwSecGroupCARSessRateOverThreshold NOTIFICATION-TYPE
			STATUS current
			DESCRIPTION 
				"Description."
			::= { hwSecCARTraps 5 }

		
--  1.3.6.1.4.1.2011.6.122.63.1.6
		-- 1.3.6.1.4.1.2011.6.122.63.1.6
		hwSecGroupCARSessRateBelowThreshold NOTIFICATION-TYPE
			STATUS current
			DESCRIPTION 
				"Description."
			::= { hwSecCARTraps 6 }

		
--  1.3.6.1.4.1.2011.6.122.63.1.7
		-- 1.3.6.1.4.1.2011.6.122.63.1.7
		hwSecIPCARTrafficOverThreshold NOTIFICATION-TYPE
			OBJECTS { hwSecCARVsysName, hwSecCARIPAddress, hwSecCARZoneName, hwSecCARPeak, hwSecCARPolicyName, 
				hwSecCARClassName, hwSecCARThread }
			STATUS current
			DESCRIPTION 
				"Description."
			::= { hwSecCARTraps 7 }

		
--  1.3.6.1.4.1.2011.6.122.63.1.8
		-- 1.3.6.1.4.1.2011.6.122.63.1.8
		hwSecIPCARTrafficBelowThreshold NOTIFICATION-TYPE
			OBJECTS { hwSecCARVsysName, hwSecCARIPAddress, hwSecCARZoneName, hwSecCARPeak, hwSecCARPolicyName, 
				hwSecCARClassName, hwSecCARThread }
			STATUS current
			DESCRIPTION 
				"Description."
			::= { hwSecCARTraps 8 }

		
--  1.3.6.1.4.1.2011.6.122.63.1.9
		-- 1.3.6.1.4.1.2011.6.122.63.1.9
		hwSecIPCARSessionOverThreshold NOTIFICATION-TYPE
			STATUS current
			DESCRIPTION 
				"Description."
			::= { hwSecCARTraps 9 }

		
--  1.3.6.1.4.1.2011.6.122.63.1.10
		-- 1.3.6.1.4.1.2011.6.122.63.1.10
		hwSecIPCARSessionBelowThreshold NOTIFICATION-TYPE
			STATUS current
			DESCRIPTION 
				"Description."
			::= { hwSecCARTraps 10 }

		
--  1.3.6.1.4.1.2011.6.122.63.1.11
		-- 1.3.6.1.4.1.2011.6.122.63.1.11
		hwSecIPCARSessRateOverThreshold NOTIFICATION-TYPE
			STATUS current
			DESCRIPTION 
				"Description."
			::= { hwSecCARTraps 11 }

		
--  1.3.6.1.4.1.2011.6.122.63.1.12
		-- 1.3.6.1.4.1.2011.6.122.63.1.12
		hwSecIPCARSessRateBelowThreshold NOTIFICATION-TYPE
			STATUS current
			DESCRIPTION 
				"Description."
			::= { hwSecCARTraps 12 }

--  1.3.6.1.4.1.2011.6.122.63.1.13
		-- 1.3.6.1.4.1.2011.6.122.63.1.13
		hwSecCarMonitorTableOverThreshold NOTIFICATION-TYPE
			OBJECTS { hwSecCarTrapSlot, hwSecCarTrapCPU, hwSecCarMonitorTableCount, hwSecCarMonitorTableThreshold }
			STATUS current
			DESCRIPTION 
				"Description."
			::= { hwSecCARTraps 13 }
			
--  1.3.6.1.4.1.2011.6.122.63.1.14
		-- 1.3.6.1.4.1.2011.6.122.63.1.14
		hwSecCarMonitorTableBelowThreshold NOTIFICATION-TYPE
			OBJECTS { hwSecCarTrapSlot, hwSecCarTrapCPU, hwSecCarMonitorTableCount, hwSecCarMonitorTableThreshold }
			STATUS current
			DESCRIPTION 
				"Description."
			::= { hwSecCARTraps 14 }
		
--  1.3.6.1.4.1.2011.6.122.63.1.15
		-- 1.3.6.1.4.1.2011.6.122.63.1.15
		hwSecHardwareCarTableOverThreshold NOTIFICATION-TYPE
			OBJECTS { hwSecCarTrapSlot, hwSecCarTrapCPU, hwSecHardwareCarTableTrapCount, hwSecHardwareCarTableTrapThreshold }
			STATUS current
			DESCRIPTION 
				"Description."
			::= { hwSecCARTraps 15 }
			
--  1.3.6.1.4.1.2011.6.122.63.1.16
		-- 1.3.6.1.4.1.2011.6.122.63.1.16
		hwSecHardwareCarTableBelowThreshold NOTIFICATION-TYPE
			OBJECTS { hwSecCarTrapSlot, hwSecCarTrapCPU, hwSecHardwareCarTableTrapCount, hwSecHardwareCarTableTrapThreshold }
			STATUS current
			DESCRIPTION 
				"Description."
			::= { hwSecCARTraps 16 }

--  1.3.6.1.4.1.2011.6.122.63.1.17
		-- 1.3.6.1.4.1.2011.6.122.63.1.17
		hwSecHardwareStatTableOverThreshold NOTIFICATION-TYPE
			OBJECTS { hwSecCarTrapSlot, hwSecCarTrapCPU, hwSecHardwareStatTableTrapCount, hwSecHardwareStatTableTrapThreshold }
			STATUS current
			DESCRIPTION 
				"Description."
			::= { hwSecCARTraps 17 }

--  1.3.6.1.4.1.2011.6.122.63.1.18
		-- 1.3.6.1.4.1.2011.6.122.63.1.18
		hwSecHardwareStatTableBelowThreshold NOTIFICATION-TYPE
			OBJECTS { hwSecCarTrapSlot, hwSecCarTrapCPU, hwSecHardwareStatTableTrapCount, hwSecHardwareStatTableTrapThreshold }
			STATUS current
			DESCRIPTION 
				"Description."
			::= { hwSecCARTraps 18 }

--  1.3.6.1.4.1.2011.6.122.63.1.19
		-- 1.3.6.1.4.1.2011.6.122.63.1.19
		hwSecHardwareCarProfileTableOverThreshold NOTIFICATION-TYPE
			OBJECTS { hwSecCarTrapSlot, hwSecCarTrapCPU, hwSecHardwareCarProfileTableTrapCount, hwSecHardwareCarProfileTableTrapThreshold }
			STATUS current
			DESCRIPTION 
				"Description."
			::= { hwSecCARTraps 19 }

--  1.3.6.1.4.1.2011.6.122.63.1.20
		-- 1.3.6.1.4.1.2011.6.122.63.1.20
		hwSecHardwareCarProfileTableBelowThreshold NOTIFICATION-TYPE
			OBJECTS { hwSecCarTrapSlot, hwSecCarTrapCPU, hwSecHardwareCarProfileTableTrapCount, hwSecHardwareCarProfileTableTrapThreshold }
			STATUS current
			DESCRIPTION 
				"Description."
			::= { hwSecCARTraps 20 }

--  1.3.6.1.4.1.2011.6.122.63.2
		-- 1.3.6.1.4.1.2011.6.122.63.2
		hwSecCARTrapsObjects OBJECT IDENTIFIER ::= { hwSecCAR 2 }

		
--  1.3.6.1.4.1.2011.6.122.63.2.1
		-- 1.3.6.1.4.1.2011.6.122.63.2.1
		hwSecCARVsysName OBJECT-TYPE
			SYNTAX OCTET STRING
			MAX-ACCESS accessible-for-notify
			STATUS current
			DESCRIPTION
				"Description."
			::= { hwSecCARTrapsObjects 1 }

		
--  1.3.6.1.4.1.2011.6.122.63.2.2
		-- 1.3.6.1.4.1.2011.6.122.63.2.2
		hwSecCARIPAddress OBJECT-TYPE
			SYNTAX IpAddress
			MAX-ACCESS accessible-for-notify
			STATUS current
			DESCRIPTION
				"Description."
			::= { hwSecCARTrapsObjects 2 }

		
--  1.3.6.1.4.1.2011.6.122.63.2.3
		-- 1.3.6.1.4.1.2011.6.122.63.2.3
		hwSecCARZoneName OBJECT-TYPE
			SYNTAX OCTET STRING
			MAX-ACCESS accessible-for-notify
			STATUS current
			DESCRIPTION
				"Description."
			::= { hwSecCARTrapsObjects 3 }

		
--  1.3.6.1.4.1.2011.6.122.63.2.4
		-- 1.3.6.1.4.1.2011.6.122.63.2.4
		hwSecCARPolicyName OBJECT-TYPE
			SYNTAX OCTET STRING
			MAX-ACCESS accessible-for-notify
			STATUS current
			DESCRIPTION
				"Description."
			::= { hwSecCARTrapsObjects 4 }

		
--  1.3.6.1.4.1.2011.6.122.63.2.5
		-- 1.3.6.1.4.1.2011.6.122.63.2.5
		hwSecCARClassName OBJECT-TYPE
			SYNTAX OCTET STRING
			MAX-ACCESS accessible-for-notify
			STATUS current
			DESCRIPTION
				"Description."
			::= { hwSecCARTrapsObjects 5 }

		
--  1.3.6.1.4.1.2011.6.122.63.2.6
		-- 1.3.6.1.4.1.2011.6.122.63.2.6
		hwSecCARPeak OBJECT-TYPE
			SYNTAX Gauge32
			MAX-ACCESS accessible-for-notify
			STATUS current
			DESCRIPTION
				"Description."
			::= { hwSecCARTrapsObjects 6 }

		
--  1.3.6.1.4.1.2011.6.122.63.2.7
		-- 1.3.6.1.4.1.2011.6.122.63.2.7
		hwSecCARThread OBJECT-TYPE
			SYNTAX Integer32
			MAX-ACCESS accessible-for-notify
			STATUS current
			DESCRIPTION
				"Description."
			::= { hwSecCARTrapsObjects 7 }
 --  1.3.6.1.4.1.2011.6.122.63.2.8
		-- 1.3.6.1.4.1.2011.6.122.63.2.8
		hwSecCarTrapSlot OBJECT-TYPE
			SYNTAX Integer32
			MAX-ACCESS accessible-for-notify
			STATUS current
			DESCRIPTION
				"Description."
			::= { hwSecCARTrapsObjects 8 }   
			
 --  1.3.6.1.4.1.2011.6.122.63.2.9
		-- 1.3.6.1.4.1.2011.6.122.63.2.9
		hwSecCarTrapCPU OBJECT-TYPE
			SYNTAX Integer32
			MAX-ACCESS accessible-for-notify
			STATUS current
			DESCRIPTION
				"Description."
			::= { hwSecCARTrapsObjects 9 }

 --  1.3.6.1.4.1.2011.6.122.63.2.10
		-- 1.3.6.1.4.1.2011.6.122.63.2.10
		hwSecCarMonitorTableCount OBJECT-TYPE
			SYNTAX Integer32
			MAX-ACCESS accessible-for-notify
			STATUS current
			DESCRIPTION
				"Description."
			::= { hwSecCARTrapsObjects 10 }   
			
 --  1.3.6.1.4.1.2011.6.122.63.2.11
		-- 1.3.6.1.4.1.2011.6.122.63.2.11
		hwSecCarMonitorTableThreshold OBJECT-TYPE
			SYNTAX Integer32
			MAX-ACCESS accessible-for-notify
			STATUS current
			DESCRIPTION
				"Description."
			::= { hwSecCARTrapsObjects 11 }
		
 --  1.3.6.1.4.1.2011.6.122.63.2.12
		-- 1.3.6.1.4.1.2011.6.122.63.2.12
		hwSecHardwareCarTableTrapCount OBJECT-TYPE
			SYNTAX Integer32
			MAX-ACCESS accessible-for-notify
			STATUS current
			DESCRIPTION
				"Description."
			::= { hwSecCARTrapsObjects 12 }
		
 --  1.3.6.1.4.1.2011.6.122.63.2.13
		-- 1.3.6.1.4.1.2011.6.122.63.2.13
		hwSecHardwareCarTableTrapThreshold OBJECT-TYPE
			SYNTAX Integer32
			MAX-ACCESS accessible-for-notify
			STATUS current
			DESCRIPTION
				"Description."
			::= { hwSecCARTrapsObjects 13 }

 --  1.3.6.1.4.1.2011.6.122.63.2.14
		-- 1.3.6.1.4.1.2011.6.122.63.2.14
		hwSecHardwareStatTableTrapCount OBJECT-TYPE
			SYNTAX Integer32
			MAX-ACCESS accessible-for-notify
			STATUS current
			DESCRIPTION
				"Description."
			::= { hwSecCARTrapsObjects 14 }

 --  1.3.6.1.4.1.2011.6.122.63.2.15
		-- 1.3.6.1.4.1.2011.6.122.63.2.15
		hwSecHardwareStatTableTrapThreshold OBJECT-TYPE
			SYNTAX Integer32
			MAX-ACCESS accessible-for-notify
			STATUS current
			DESCRIPTION
				"Description."
			::= { hwSecCARTrapsObjects 15 }

 --  1.3.6.1.4.1.2011.6.122.63.2.16
		-- 1.3.6.1.4.1.2011.6.122.63.2.16
		hwSecHardwareCarProfileTableTrapCount OBJECT-TYPE
			SYNTAX Integer32
			MAX-ACCESS accessible-for-notify
			STATUS current
			DESCRIPTION
				"Description."
			::= { hwSecCARTrapsObjects 16 }

 --  1.3.6.1.4.1.2011.6.122.63.2.17
		-- 1.3.6.1.4.1.2011.6.122.63.2.17
		hwSecHardwareCarProfileTableTrapThreshold OBJECT-TYPE
			SYNTAX Integer32
			MAX-ACCESS accessible-for-notify
			STATUS current
			DESCRIPTION
				"Description."
			::= { hwSecCARTrapsObjects 17 }

--  1.3.6.1.4.1.2011.6.122.63.4
		-- 1.3.6.1.4.1.2011.6.122.63.4
		hwSecCARConformance OBJECT IDENTIFIER ::= { hwSecCAR 4 }

		
--  1.3.6.1.4.1.2011.6.122.63.4.1
		-- 1.3.6.1.4.1.2011.6.122.63.4.1
		hwSecCARCompliances OBJECT IDENTIFIER ::= { hwSecCARConformance 1 }

		
--  this module
-- 1.3.6.1.4.1.2011.6.122.63.4.1.1
-- this module
		-- 1.3.6.1.4.1.2011.6.122.63.4.1.1
		hwSecCARCompliance MODULE-COMPLIANCE
			STATUS current
			DESCRIPTION 
				"Description."
			MODULE -- this module
				MANDATORY-GROUPS { hwSecCARTrapObjectsGroup, hwSecCARTrapGroup }
			::= { hwSecCARCompliances 1 }

		
--  1.3.6.1.4.1.2011.6.122.63.4.2
		-- 1.3.6.1.4.1.2011.6.122.63.4.2
		hwSecCARGroups OBJECT IDENTIFIER ::= { hwSecCARConformance 2 }

		
--  1.3.6.1.4.1.2011.6.122.63.4.2.1
		-- 1.3.6.1.4.1.2011.6.122.63.4.2.1
		hwSecCARTrapObjectsGroup OBJECT-GROUP
			OBJECTS { hwSecCARVsysName, hwSecCARPolicyName, hwSecCARClassName, hwSecCARThread, hwSecCARIPAddress, 
				hwSecCARZoneName, hwSecCARPeak }
			STATUS current
			DESCRIPTION 
				"Description."
			::= { hwSecCARGroups 1 }

		
--  1.3.6.1.4.1.2011.6.122.63.4.2.2
		-- 1.3.6.1.4.1.2011.6.122.63.4.2.2
		hwSecCARTrapGroup NOTIFICATION-GROUP
			NOTIFICATIONS { hwSecGroupCARTrafficOverThreshold, hwSecGroupCARSessionBelowThreshold, hwSecIPCARTrafficBelowThreshold, hwSecIPCARSessionOverThreshold, hwSecIPCARSessionBelowThreshold, 
				hwSecIPCARSessRateOverThreshold, hwSecGroupCARTrafficBelowThreshold, hwSecGroupCARSessionOverThreshold, hwSecGroupCARSessRateOverThreshold, hwSecGroupCARSessRateBelowThreshold, 
				hwSecIPCARTrafficOverThreshold, hwSecIPCARSessRateBelowThreshold }
			STATUS current
			DESCRIPTION 
				"Description."
			::= { hwSecCARGroups 2 }

		
	
	END

--
-- HUAWEI-SECURITY-CAR-MIB.mib
--
