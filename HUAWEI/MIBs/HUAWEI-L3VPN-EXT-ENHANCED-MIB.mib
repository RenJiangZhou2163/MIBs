--  ==================================================================
-- Copyright (C) 2009 by  HUAWEI TECHNOLOGIES. All rights reserved.
-- 
-- Description: HUAWEI L3VPN Statistics Management MIB
-- Reference:
-- Version:     V1.0
-- History:
--              V1.0 guoyuanchang 61066, 2010-08-17, publish
-- ==================================================================
    HUAWEI-L3VPN-EXT-ENHANCED-MIB DEFINITIONS ::= BEGIN
 
        IMPORTS
            hwDatacomm          
                FROM HUAWEI-MIB         
            OBJECT-GROUP, MODULE-COMPLIANCE, NOTIFICATION-GROUP         
                FROM SNMPv2-CONF            
            IpAddress,TimeTicks,Integer32,Gauge32, Unsigned32,Counter32,Counter64, OBJECT-TYPE, 
            MODULE-IDENTITY, NOTIFICATION-TYPE          
                FROM SNMPv2-SMI         
            DisplayString, TimeStamp, RowStatus, DateAndTime         
                FROM SNMPv2-TC 
            EnabledStatus
                FROM  P-BRIDGE-MIB
            InterfaceIndex          
                FROM IF-MIB  ;
                
                
                
        hwL3vpn MODULE-IDENTITY 
            LAST-UPDATED "200902171659Z"        -- Feb 13, 2009 at 16:59 GMT
            ORGANIZATION 
                "Huawei Technologies Co.,Ltd."
            CONTACT-INFO 
                "Huawei Industrial Base
                  Bantian, Longgang
                   Shenzhen 518129
                   People's Republic of China
                   Website: http://www.huawei.com
                   Email: support@huawei.com
                 "
            DESCRIPTION
                "The HUAWEI-L3VPN-EXT-ENHANCED-MIB contains objects to statistic L3VPN's traffic."
            ::= { hwDatacomm 150 }
                
                
                
--
-- Node definitions
--

        hwL3vpnEnhancedStatMibObjects OBJECT IDENTIFIER ::= { hwL3vpn 3 }               



     
-- The L3VPN Statistic Table
-- 
        hwL3vpnEnhancedStatisticsTable OBJECT-TYPE
            SYNTAX SEQUENCE OF HwL3vpnEnhancedStatisticsEntry
            MAX-ACCESS not-accessible
            STATUS current
            DESCRIPTION
                "This table contains the L3VPN's Traffic Statistic."
            ::= { hwL3vpnEnhancedStatMibObjects 1 }
        
        hwL3vpnEnhancedStatisticsEntry OBJECT-TYPE
            SYNTAX HwL3vpnEnhancedStatisticsEntry
            MAX-ACCESS not-accessible
            STATUS current
            DESCRIPTION
                "Provides the information of the L3VPN's Traffic Statistic."
            INDEX { hwL3vpnVrfName }
            ::= { hwL3vpnEnhancedStatisticsTable 1 }
        
        HwL3vpnEnhancedStatisticsEntry ::=
            SEQUENCE {
                hwL3vpnVrfName           
                    DisplayString, 
                hwL3vpnStatEnable
                    EnabledStatus,                
                hwL3vpnStatInTrafficRate
                    Gauge32,
                hwL3vpnStatOutTrafficRate
                    Gauge32,
                hwL3vpnStatInPacketsRate
                    Gauge32,
                hwL3vpnStatOutPacketsRate
                    Gauge32,
                hwL3vpnStatInBytes
                    Counter64,
                hwL3vpnStatOutBytes
                    Counter64,
                hwL3vpnStatInPackets
                    Counter64,
                hwL3vpnStatOutPackets
                    Counter64,
                hwL3vpnStatInUnicastPackets
                    Counter64,
                hwL3vpnStatOutUnicastPackets
                    Counter64,
                hwL3vpnStatInMulticastPackets
                    Counter64,
                hwL3vpnStatOutMulticastPackets
                    Counter64,
                hwL3vpnStatInBroadcastPackets
                    Counter64,
                hwL3vpnStatOutBroadcastPackets
                    Counter64,
                hwL3vpnStatResetTime
                    DateAndTime,
                hwL3vpnStatResetStatistic
                    INTEGER 
             }
        
            hwL3vpnVrfName OBJECT-TYPE
            SYNTAX DisplayString (SIZE (1..31))
            MAX-ACCESS not-accessible
            STATUS current
            DESCRIPTION
                "This object indicates the VRF's name."
            ::= { hwL3vpnEnhancedStatisticsEntry 1 }  
            
            hwL3vpnStatEnable OBJECT-TYPE
            SYNTAX EnabledStatus
            MAX-ACCESS read-write
            STATUS current
            DESCRIPTION
                "This object indicates the enable sign of L3VPN's traffic statistics."
            DEFVAL { disable }
            ::= { hwL3vpnEnhancedStatisticsEntry 2 }
 

        hwL3vpnStatInTrafficRate OBJECT-TYPE
            SYNTAX Gauge32
            MAX-ACCESS read-only
            STATUS current
            DESCRIPTION
                "Average bytes of the traffic received per second."
            ::= { hwL3vpnEnhancedStatisticsEntry 3 }
        
        hwL3vpnStatOutTrafficRate OBJECT-TYPE
            SYNTAX Gauge32
            MAX-ACCESS read-only
            STATUS current
            DESCRIPTION
                "Average bytes of the traffic transmitted out per second ."
            ::= { hwL3vpnEnhancedStatisticsEntry 4 }
        
        hwL3vpnStatInPacketsRate OBJECT-TYPE
            SYNTAX Gauge32
            MAX-ACCESS read-only
            STATUS current
            DESCRIPTION
                "Average packets of the traffic received per second."
            ::= { hwL3vpnEnhancedStatisticsEntry 5 }
        
        hwL3vpnStatOutPacketsRate OBJECT-TYPE
            SYNTAX Gauge32
            MAX-ACCESS read-only
            STATUS current
            DESCRIPTION
                "Average packets of the traffic transmitted out per second."
            ::= { hwL3vpnEnhancedStatisticsEntry 6 } 
            
        hwL3vpnStatInBytes OBJECT-TYPE
            SYNTAX Counter64
            MAX-ACCESS read-only
            STATUS current
            DESCRIPTION
                "The total number of bytes received."
            ::= { hwL3vpnEnhancedStatisticsEntry 7 }
            
        hwL3vpnStatOutBytes OBJECT-TYPE
            SYNTAX Counter64
            MAX-ACCESS read-only
            STATUS current
            DESCRIPTION
                "The total number of bytes transmitted out."
            ::= { hwL3vpnEnhancedStatisticsEntry 8 }
            
        hwL3vpnStatInPackets OBJECT-TYPE
            SYNTAX Counter64
            MAX-ACCESS read-only
            STATUS current
            DESCRIPTION
                "The total number of Packets received."
            ::= { hwL3vpnEnhancedStatisticsEntry 9 }
            
        hwL3vpnStatOutPackets OBJECT-TYPE
            SYNTAX Counter64
            MAX-ACCESS read-only
            STATUS current
            DESCRIPTION
                "The total number of Packets transmitted out."
            ::= { hwL3vpnEnhancedStatisticsEntry 10 } 
            
        hwL3vpnStatInUnicastPackets OBJECT-TYPE
            SYNTAX Counter64
            MAX-ACCESS read-only
            STATUS current
            DESCRIPTION
                "The total number of unicast Packets received."
            ::= { hwL3vpnEnhancedStatisticsEntry 11 }
            
        hwL3vpnStatOutUnicastPackets OBJECT-TYPE
            SYNTAX Counter64
            MAX-ACCESS read-only
            STATUS current
            DESCRIPTION
                "The total number of unicast Packets transmitted out."
            ::= { hwL3vpnEnhancedStatisticsEntry 12 } 
            
        hwL3vpnStatInMulticastPackets OBJECT-TYPE
            SYNTAX Counter64
            MAX-ACCESS read-only
            STATUS current
            DESCRIPTION
                "The total number of multicast Packets received."
            ::= { hwL3vpnEnhancedStatisticsEntry 13 }
            
        hwL3vpnStatOutMulticastPackets OBJECT-TYPE
            SYNTAX Counter64
            MAX-ACCESS read-only
            STATUS current
            DESCRIPTION
                "The total number of multicast Packets transmitted out."
            ::= { hwL3vpnEnhancedStatisticsEntry 14 }   
            
        hwL3vpnStatInBroadcastPackets OBJECT-TYPE
            SYNTAX Counter64
            MAX-ACCESS read-only
            STATUS current
            DESCRIPTION
                "The total number of broadcast Packets received."
            ::= { hwL3vpnEnhancedStatisticsEntry 15 } 
            
        hwL3vpnStatOutBroadcastPackets OBJECT-TYPE
            SYNTAX Counter64
            MAX-ACCESS read-only
            STATUS current
            DESCRIPTION
                "The total number of broadcast Packets transmitted out."
            ::= { hwL3vpnEnhancedStatisticsEntry 16 }
            
        hwL3vpnStatResetTime OBJECT-TYPE
            SYNTAX DateAndTime
            MAX-ACCESS read-only
            STATUS current
            DESCRIPTION
                "Last time of clean out."
            ::= { hwL3vpnEnhancedStatisticsEntry 17 } 
             
       hwL3vpnStatResetStatistic OBJECT-TYPE
            SYNTAX INTEGER
            {
                resetStatistic(1)                           
            }
            MAX-ACCESS read-write
            STATUS current
            DESCRIPTION
                "Reset traffic statistics of the vpn instance."
            ::= { hwL3vpnEnhancedStatisticsEntry 18 }
            
-- The L3VPN Qos Statistic Table
-- 
        hwL3vpnEnhancedQosStatisticsTable OBJECT-TYPE
            SYNTAX SEQUENCE OF HwL3vpnEnhancedQosStatisticsEntry
            MAX-ACCESS not-accessible
            STATUS current
            DESCRIPTION
                "This table contains the L3VPN's Qos traffic statistics."
            ::= { hwL3vpnEnhancedStatMibObjects 2 }
        
        hwL3vpnEnhancedQosStatisticsEntry OBJECT-TYPE
            SYNTAX HwL3vpnEnhancedQosStatisticsEntry
            MAX-ACCESS not-accessible
            STATUS current
            DESCRIPTION
                "Provides the information of the L3VPN's Qos traffic statistics."
            INDEX { hwL3vpnQosStatVrfIName, hwL3vpnQosStatQueueID }
            ::= { hwL3vpnEnhancedQosStatisticsTable 1 }
        
        HwL3vpnEnhancedQosStatisticsEntry ::=
            SEQUENCE {
                hwL3vpnQosStatVrfIName           
                    DisplayString,     
                hwL3vpnQosStatQueueID
                    INTEGER,
                hwL3vpnQosStatPassPackets
                    Counter64,
                hwL3vpnQosStatPassBytes
                    Counter64,
                hwL3vpnQosStatDiscardPackets
                    Counter64,
                hwL3vpnQosStatDiscardBytes
                    Counter64,
                hwL3vpnQosStatPassPacketsRate
                    Counter64,
                hwL3vpnQosStatPassBytesRate
                    Counter64,
                hwL3vpnQosStatDiscardPacketsRate
                    Counter64,
                hwL3vpnQosStatDiscardBytesRate
                    Counter64
            } 
            
        hwL3vpnQosStatVrfIName OBJECT-TYPE
            SYNTAX DisplayString (SIZE (1..31))
            MAX-ACCESS not-accessible
            STATUS current
            DESCRIPTION
                "This object indicates the VRF's name."
            ::= { hwL3vpnEnhancedQosStatisticsEntry 1 }  
            
        hwL3vpnQosStatQueueID OBJECT-TYPE
            SYNTAX INTEGER
                {
                be(1),
                af1(2),
                af2(3),
                af3(4),
                af4(5),
                ef(6),
                cs6(7),
                cs7(8)
                }
            MAX-ACCESS not-accessible
            STATUS current
            DESCRIPTION
                "This object indicates the queue's ID. The value must be 
                be,af1,af2,af3,af4,ef,cs6,cs7."
            ::= { hwL3vpnEnhancedQosStatisticsEntry 2 }
        
        
        hwL3vpnQosStatPassPackets OBJECT-TYPE
            SYNTAX Counter64
            MAX-ACCESS read-only
            STATUS current
            DESCRIPTION
                "Number of total passed packets, based on the vpn instance."
            ::= { hwL3vpnEnhancedQosStatisticsEntry 3 }


        hwL3vpnQosStatPassBytes OBJECT-TYPE
            SYNTAX Counter64
            MAX-ACCESS read-only
            STATUS current
            DESCRIPTION
                "Number of total passed bytes, based on the vpn instance."
            ::= { hwL3vpnEnhancedQosStatisticsEntry 4 }


        hwL3vpnQosStatDiscardPackets OBJECT-TYPE
            SYNTAX Counter64
            MAX-ACCESS read-only
            STATUS current
            DESCRIPTION
                "Number of total discarded packets, based on the vpn instance."
            ::= { hwL3vpnEnhancedQosStatisticsEntry 5 }


        hwL3vpnQosStatDiscardBytes OBJECT-TYPE
            SYNTAX Counter64
            MAX-ACCESS read-only
            STATUS current
            DESCRIPTION
                "Number of total discarded bytes, based on the vpn instance."
            ::= { hwL3vpnEnhancedQosStatisticsEntry 6 }


        hwL3vpnQosStatPassPacketsRate OBJECT-TYPE
            SYNTAX Counter64
            MAX-ACCESS read-only
            STATUS current
            DESCRIPTION
                "Rate of passed packets for the past 30 seconds, based on the vpn instance. Unit: pps"
            ::= { hwL3vpnEnhancedQosStatisticsEntry 7 }


        hwL3vpnQosStatPassBytesRate OBJECT-TYPE
            SYNTAX Counter64
            MAX-ACCESS read-only
            STATUS current
            DESCRIPTION
                "Rate of passed bytes for the past 30 seconds, based on the vpn instance. Unit: bps"
            ::= { hwL3vpnEnhancedQosStatisticsEntry 8 }


        hwL3vpnQosStatDiscardPacketsRate OBJECT-TYPE
            SYNTAX Counter64
            MAX-ACCESS read-only
            STATUS current
            DESCRIPTION
                "Rate of discarded packets for the past 30 seconds, based on the vpn instance. Unit: pps"
            ::= { hwL3vpnEnhancedQosStatisticsEntry 9 }


        hwL3vpnQosStatDiscardBytesRate OBJECT-TYPE
            SYNTAX Counter64
            MAX-ACCESS read-only
            STATUS current
            DESCRIPTION
                "Rate of discarded bytes for the past 30 seconds, based on the vpn instance. Unit: bps"
            ::= { hwL3vpnEnhancedQosStatisticsEntry 10 }


-- The L3VPN Peer Statistic Table
-- 
        hwL3vpnEnhancedPeerStatisticsTable OBJECT-TYPE
            SYNTAX SEQUENCE OF HwL3vpnEnhancedPeerStatisticsEntry
            MAX-ACCESS not-accessible
            STATUS current
            DESCRIPTION
                "This table contains the L3VPN's Traffic Statistic."
            ::= { hwL3vpnEnhancedStatMibObjects 3 }
        
        hwL3vpnEnhancedPeerStatisticsEntry OBJECT-TYPE
            SYNTAX HwL3vpnEnhancedPeerStatisticsEntry
            MAX-ACCESS not-accessible
            STATUS current
            DESCRIPTION
                "Provides the information of the L3VPN Peer's Traffic Statistic."
            INDEX { hwL3vpnPeerVrfName, hwL3vpnPeerStatPeerAddress }
            ::= { hwL3vpnEnhancedPeerStatisticsTable 1 }
        
        HwL3vpnEnhancedPeerStatisticsEntry ::=
            SEQUENCE {
                hwL3vpnPeerVrfName           
                    DisplayString,
                hwL3vpnPeerStatPeerAddress           
                    IpAddress,     
                hwL3vpnPeerStatEnable
                    EnabledStatus,
                hwL3vpnPeerStatResetStatistic
                    INTEGER,      
                hwL3vpnPeerStatResetTime
                    DateAndTime,                                     
                hwL3vpnPeerStatQosPacketsRate
                    Counter64,
                hwL3vpnPeerStatQosBytesRate 
                    Counter64,    
                hwL3vpnPeerStatQosPackets
                    Counter64,
                hwL3vpnPeerStatQosBytes
                    Counter64                    
             }
        
        hwL3vpnPeerVrfName OBJECT-TYPE
            SYNTAX DisplayString (SIZE (1..31))
            MAX-ACCESS not-accessible
            STATUS current
            DESCRIPTION
                "This object indicates the VRF's name."
            ::= { hwL3vpnEnhancedPeerStatisticsEntry 1 } 
        
        hwL3vpnPeerStatPeerAddress OBJECT-TYPE
            SYNTAX IpAddress
            MAX-ACCESS not-accessible
            STATUS current
            DESCRIPTION
                "The peer IP address of L3vpn instance."
            ::= { hwL3vpnEnhancedPeerStatisticsEntry 2 }
                
        hwL3vpnPeerStatEnable OBJECT-TYPE
            SYNTAX EnabledStatus
            MAX-ACCESS read-write
            STATUS current
            DESCRIPTION
                "This object indicates the enable sign of L3VPN peer's traffic statistics."
            DEFVAL { disable }
            ::= { hwL3vpnEnhancedPeerStatisticsEntry 3 }
                         
        hwL3vpnPeerStatResetStatistic OBJECT-TYPE
            SYNTAX INTEGER
            {
                resetStatistic(1)                           
            }

            MAX-ACCESS read-write
            STATUS current
            DESCRIPTION
                "Reset traffic statistics for peer of the L3vpn instance."
            ::= { hwL3vpnEnhancedPeerStatisticsEntry 4 } 
                        
        hwL3vpnPeerStatResetTime OBJECT-TYPE
            SYNTAX DateAndTime
            MAX-ACCESS read-only
            STATUS current
            DESCRIPTION
                "Last time of clean out."
            ::= { hwL3vpnEnhancedPeerStatisticsEntry 5 }
        
        hwL3vpnPeerStatQosPacketsRate OBJECT-TYPE  
            SYNTAX Counter64
            MAX-ACCESS read-only
            STATUS current
            DESCRIPTION
                "Average packets of the traffic transmitted out per second."
            ::= { hwL3vpnEnhancedPeerStatisticsEntry 6 }
        
        hwL3vpnPeerStatQosBytesRate OBJECT-TYPE
            SYNTAX Counter64
            MAX-ACCESS read-only
            STATUS current
            DESCRIPTION
                "Average bytes of the traffic transmitted out per second ."
            ::= { hwL3vpnEnhancedPeerStatisticsEntry 7 }
        
        hwL3vpnPeerStatQosPackets OBJECT-TYPE
            SYNTAX Counter64
            MAX-ACCESS read-only
            STATUS current
            DESCRIPTION
                "The total number of Packets transmitted out."
            ::= { hwL3vpnEnhancedPeerStatisticsEntry 8 }       
                             
        hwL3vpnPeerStatQosBytes OBJECT-TYPE
            SYNTAX Counter64
            MAX-ACCESS read-only
            STATUS current
            DESCRIPTION
                "The total number of bytes transmitted out."
            ::= { hwL3vpnEnhancedPeerStatisticsEntry 9 }
            
                            
-- The L3VPN Peer Qos Statistic Table
-- 
        hwL3vpnEnhancedPeerQosStatisticsTable OBJECT-TYPE
            SYNTAX SEQUENCE OF HwL3vpnEnhancedPeerQosStatisticsEntry
            MAX-ACCESS not-accessible
            STATUS current
            DESCRIPTION
                "This table contains the L3vpn Peer's Qos traffic statistics."
            ::= { hwL3vpnEnhancedStatMibObjects 4 }
        
        hwL3vpnEnhancedPeerQosStatisticsEntry OBJECT-TYPE
            SYNTAX HwL3vpnEnhancedPeerQosStatisticsEntry
            MAX-ACCESS not-accessible
            STATUS current
            DESCRIPTION
                "Provides the information of the L3VPN Peer's Qos traffic statistics."
            INDEX { hwL3vpnPeerQosStatVrfName, hwL3vpnPeerQosStatPeerAddress, hwL3vpnPeerQosStatQueueID }
            ::= { hwL3vpnEnhancedPeerQosStatisticsTable 1 }
        
        HwL3vpnEnhancedPeerQosStatisticsEntry ::=
            SEQUENCE {
                hwL3vpnPeerQosStatVrfName           
                    DisplayString,
                hwL3vpnPeerQosStatPeerAddress           
                    IpAddress,         
                hwL3vpnPeerQosStatQueueID
                    INTEGER,
                hwL3vpnPeerQosStatPassPackets
                    Counter64,
                hwL3vpnPeerQosStatPassBytes
                    Counter64,
                hwL3vpnPeerQosStatDiscardPackets
                    Counter64,
                hwL3vpnPeerQosStatDiscardBytes
                    Counter64,
                hwL3vpnPeerQosStatPassPacketsRate
                    Counter64,
                hwL3vpnPeerQosStatPassBytesRate
                    Counter64,
                hwL3vpnPeerQosStatDiscardPacketsRate
                    Counter64,
                hwL3vpnPeerQosStatDiscardBytesRate
                    Counter64
            } 
            
        hwL3vpnPeerQosStatVrfName OBJECT-TYPE
            SYNTAX DisplayString (SIZE (1..31))
            MAX-ACCESS not-accessible
            STATUS current
            DESCRIPTION
                "This object indicates the VRF's name."
            ::= { hwL3vpnEnhancedPeerQosStatisticsEntry 1 }  
        
        hwL3vpnPeerQosStatPeerAddress OBJECT-TYPE
            SYNTAX IpAddress
            MAX-ACCESS not-accessible
            STATUS current
            DESCRIPTION
                "The peer IP address of L3vpn instance."
            ::= { hwL3vpnEnhancedPeerQosStatisticsEntry 2 }    
        
        hwL3vpnPeerQosStatQueueID OBJECT-TYPE
            SYNTAX INTEGER
                {
                be(1),
                af1(2),
                af2(3),
                af3(4),
                af4(5),
                ef(6),
                cs6(7),
                cs7(8)
                }
            MAX-ACCESS not-accessible
            STATUS current
            DESCRIPTION
                "This object indicates the queue's ID. The value must be 
                be,af1,af2,af3,af4,ef,cs6,cs7."
            ::= { hwL3vpnEnhancedPeerQosStatisticsEntry 3 }
        
        
        hwL3vpnPeerQosStatPassPackets OBJECT-TYPE
            SYNTAX Counter64
            MAX-ACCESS read-only
            STATUS current
            DESCRIPTION
                "Number of total passed packets, based on peer of the vpn instance."
            ::= { hwL3vpnEnhancedPeerQosStatisticsEntry 4 }


        hwL3vpnPeerQosStatPassBytes OBJECT-TYPE
            SYNTAX Counter64
            MAX-ACCESS read-only
            STATUS current
            DESCRIPTION
                "Number of total passed bytes, based on peer of the vpn instance."
            ::= { hwL3vpnEnhancedPeerQosStatisticsEntry 5 }


        hwL3vpnPeerQosStatDiscardPackets OBJECT-TYPE
            SYNTAX Counter64
            MAX-ACCESS read-only
            STATUS current
            DESCRIPTION
                "Number of total discarded packets, based on peer of the vpn instance."
            ::= { hwL3vpnEnhancedPeerQosStatisticsEntry 6 }


        hwL3vpnPeerQosStatDiscardBytes OBJECT-TYPE
            SYNTAX Counter64
            MAX-ACCESS read-only
            STATUS current
            DESCRIPTION
                "Number of total discarded bytes, based on peer of the vpn instance."
            ::= { hwL3vpnEnhancedPeerQosStatisticsEntry 7 }


        hwL3vpnPeerQosStatPassPacketsRate OBJECT-TYPE
            SYNTAX Counter64
            MAX-ACCESS read-only
            STATUS current
            DESCRIPTION
                "Rate of passed packets for the past 30 seconds, based on peer of the vpn instance. Unit: pps"
            ::= { hwL3vpnEnhancedPeerQosStatisticsEntry 8 }


        hwL3vpnPeerQosStatPassBytesRate OBJECT-TYPE
            SYNTAX Counter64
            MAX-ACCESS read-only
            STATUS current
            DESCRIPTION
                "Rate of passed bytes for the past 30 seconds, based on peer of the vpn instance. Unit: bps"
            ::= { hwL3vpnEnhancedPeerQosStatisticsEntry 9 }


        hwL3vpnPeerQosStatDiscardPacketsRate OBJECT-TYPE
            SYNTAX Counter64
            MAX-ACCESS read-only
            STATUS current
            DESCRIPTION
                "Rate of discarded packets for the past 30 seconds, based on peer of the vpn instance. Unit: pps"
            ::= { hwL3vpnEnhancedPeerQosStatisticsEntry 10 }


        hwL3vpnPeerQosStatDiscardBytesRate OBJECT-TYPE
            SYNTAX Counter64
            MAX-ACCESS read-only
            STATUS current
            DESCRIPTION
                "Rate of discarded bytes for the past 30 seconds, based on peer of the vpn instance. Unit: bps"
            ::= { hwL3vpnEnhancedPeerQosStatisticsEntry 11 }

-- Conformance            
            
        hwL3vpnEnhancedConformance OBJECT IDENTIFIER ::= { hwL3vpn 4 }

-- group 
       
        hwL3vpnEnhancedGroups OBJECT IDENTIFIER ::= { hwL3vpnEnhancedConformance 1 }

-- L3vpn Enhanced Statistics Group        
        hwL3vpnEnhancedStatisticsGroup OBJECT-GROUP
            OBJECTS {hwL3vpnStatEnable,hwL3vpnStatInTrafficRate, hwL3vpnStatOutTrafficRate, hwL3vpnStatInPacketsRate, hwL3vpnStatOutPacketsRate, hwL3vpnStatInBytes, 
                hwL3vpnStatOutBytes, hwL3vpnStatInPackets, hwL3vpnStatOutPackets, hwL3vpnStatInUnicastPackets, hwL3vpnStatOutUnicastPackets, 
                hwL3vpnStatInMulticastPackets, hwL3vpnStatOutMulticastPackets, hwL3vpnStatInBroadcastPackets, hwL3vpnStatOutBroadcastPackets, 
                hwL3vpnStatResetTime, hwL3vpnStatResetStatistic}
            STATUS current
            DESCRIPTION 
                "The L3vpn Enhanced Statistics Group."
            ::= { hwL3vpnEnhancedGroups 1 }                                          

-- L3vpn Enhanced Qos Statistics Group            
        hwL3vpnEnhancedQosStatisticsGroup OBJECT-GROUP
            OBJECTS {hwL3vpnQosStatPassPackets, hwL3vpnQosStatPassBytes, hwL3vpnQosStatDiscardPackets, hwL3vpnQosStatDiscardBytes, 
                hwL3vpnQosStatPassPacketsRate, hwL3vpnQosStatPassBytesRate, 
                hwL3vpnQosStatDiscardPacketsRate, hwL3vpnQosStatDiscardBytesRate }
            STATUS current
            DESCRIPTION 
                "The L3vpn Enhanced Qos Statistics Group."
            ::= { hwL3vpnEnhancedGroups 2 }

-- L3vpn Enhanced Peer Statistics Group        
        hwL3vpnEnhancedPeerStatisticsGroup OBJECT-GROUP
            OBJECTS {hwL3vpnPeerStatEnable,hwL3vpnPeerStatResetStatistic, hwL3vpnPeerStatResetTime,
                hwL3vpnPeerStatQosPacketsRate, hwL3vpnPeerStatQosBytesRate, 
                hwL3vpnPeerStatQosPackets, hwL3vpnPeerStatQosBytes}
            STATUS current
            DESCRIPTION 
                "The L3vpn Enhanced Statistics Group."
            ::= { hwL3vpnEnhancedGroups 3 }

-- L3vpn Enhanced Peer Qos Statistics Group            
        hwL3vpnEnhancedPeerQosStatisticsGroup OBJECT-GROUP
            OBJECTS {hwL3vpnPeerQosStatPassPackets, hwL3vpnPeerQosStatPassBytes, hwL3vpnPeerQosStatDiscardPackets, hwL3vpnPeerQosStatDiscardBytes, 
                hwL3vpnPeerQosStatPassPacketsRate, hwL3vpnPeerQosStatPassBytesRate, 
                hwL3vpnPeerQosStatDiscardPacketsRate, hwL3vpnPeerQosStatDiscardBytesRate }
            STATUS current
            DESCRIPTION 
                "The L3vpn Enhanced Qos Statistics Group."
            ::= { hwL3vpnEnhancedGroups 4 }            
-- Compliance        
        hwL3vpnEnhancedCompliances OBJECT IDENTIFIER ::= {hwL3vpnEnhancedConformance 2}            
        
        hwL3vpnEnhancedCompliance MODULE-COMPLIANCE
            STATUS current
            DESCRIPTION 
                "The compliance statement for HUAWEI-L3VPN-EXT-ENHANCED-MIB."
            MODULE -- this module
                MANDATORY-GROUPS { hwL3vpnEnhancedStatisticsGroup}
            ::= { hwL3vpnEnhancedCompliances 1 }            
    END
