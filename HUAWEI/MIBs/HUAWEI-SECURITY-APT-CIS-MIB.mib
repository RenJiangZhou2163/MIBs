-- ===================================================================
-- Copyright (C) 2016 by HUAWEI TECHNOLOGIES. All rights reserved.
-- Description: 
-- Reference:
-- Version: V1.01
-- ===================================================================


         HUAWEI-SECURITY-APT-CIS-MIB DEFINITIONS ::= BEGIN
 
        IMPORTS
	    enterprises			
		FROM RFC1155-SMI
            OBJECT-GROUP            
                FROM SNMPv2-CONF            
            Gauge32, NOTIFICATION-TYPE, Integer32, Counter64, OBJECT-TYPE, MODULE-IDENTITY            
                FROM SNMPv2-SMI            
            TruthValue            
                FROM SNMPv2-TC;
    
    -- 1.3.6.1.4.1.2011.6.122.47 
    hwSecAptCisMibObjects MODULE-IDENTITY
       LAST-UPDATED "201611020000Z" 
       ORGANIZATION "Huawei Technologies Co.,Ltd."
       CONTACT-INFO 
                   "Huawei Industrial Base
                    Bantian, Longgang
                    Shenzhen 518129
                    People's Republic of China
                    Website: http://www.huawei.com
                    Email: support@huawei.com
                   "
       DESCRIPTION
           "The MIB module is for entities implementing the access node
            side of the Access Node Control Protocol (ANCP).

            Copyright (C) The IETF Trust (2008).  The initial version of
            this MIB module was published in RFC yyyy; for full legal
            notices see the RFC itself."
-- RFC Ed.: replace yyyy with actual RFC number & remove this note
       
       --  Revision history

       REVISION    "201611020000Z"
       DESCRIPTION "V1.00, initial version."
       REVISION    "201612130000Z"
       DESCRIPTION "V1.01, initial version."

       
-- RFC Ed.: replace yyyy with actual RFC number & remove this note
       ::= { hwSecurity 78 }
-- The value xxx to be assigned by IANA.
    

--
-- Node definitions
--                       
 	-- 1.3.6.1.4.1.2011
	huawei OBJECT IDENTIFIER ::= { enterprises 2011 }
        
        -- 1.3.6.1.4.1.2011.6
        huaweiUtility OBJECT IDENTIFIER ::= { huawei 6 }
        
        -- 1.3.6.1.4.1.2011.6.122
        hwSecurity OBJECT IDENTIFIER ::= { huaweiUtility 122 }          
        
        -- 1.3.6.1.4.1.2011.6.122.78
        -- hwSecAptCisMibObjects OBJECT IDENTIFIER ::= { hwSecurity 78 }
   
       	-- 1.3.6.1.4.1.2011.6.122.78.1                          
    	hwSecAptCisTrapsObjests OBJECT IDENTIFIER ::= { hwSecAptCisMibObjects 1 } 
    	        	
             -- 1.3.6.1.4.1.2011.6.122.78.1.1	//threshold number     
    	hwSecAptCisThresholdNum OBJECT-TYPE
        	SYNTAX Gauge32 (0..100)        	
        	MAX-ACCESS accessible-for-notify
        	STATUS current
        	DESCRIPTION
            		"threshold of AptCis log."
        	::= { hwSecAptCisTrapsObjests 1 }


       -- 1.3.6.1.4.1.2011.6.122.78.1.2 	//threat number     
    	hwSecAptCisThreatLogNum OBJECT-TYPE
        	SYNTAX Gauge32 (0..10000)        	
        	MAX-ACCESS accessible-for-notify
        	STATUS current
        	DESCRIPTION
            		"threat number of AptCis log."
        	::= { hwSecAptCisTrapsObjests 2 }    
        		        	     
	
        -- 1.3.6.1.4.1.2011.6.122.78.1.3	//slot 		
       	hwSecAptCisTrapSlot OBJECT-TYPE
        	SYNTAX Gauge32 (1..16)
        	MAX-ACCESS accessible-for-notify
        	STATUS current
        	DESCRIPTION
            		"The firewall slot number."
        	::= { hwSecAptCisTrapsObjests 3 }     
        
        -- 1.3.6.1.4.1.2011.6.122.78.1.4	//cpu        
    	hwSecAptCisTrapCPU OBJECT-TYPE
        	SYNTAX Gauge32 (0..3) 
        	MAX-ACCESS accessible-for-notify
       	 	STATUS current
        	DESCRIPTION
            		"The firewall CPU number."
        	::= { hwSecAptCisTrapsObjests 4 }                 
        
   	
        -- 1.3.6.1.4.1.2011.6.122.78.2                          
    	hwSecAptCisTraps OBJECT IDENTIFIER ::= { hwSecAptCisMibObjects 2 }   	 
         
        -- 1.3.6.1.4.1.2011.6.122.78.2.1        		                                
        hwSecAptCisThreatLogOverThreshold NOTIFICATION-TYPE
		OBJECTS { 			  
			  hwSecAptCisThresholdNum,
                                                         hwSecAptCisThreatLogNum, 
			  hwSecAptCisTrapSlot,
			  hwSecAptCisTrapCPU  
		        }
		STATUS     current
		DESCRIPTION
		    "The Threat Logs Exceeds Threshold."
		::= { hwSecAptCisTraps 1 }   
		  
		-- 1.3.6.1.4.1.2011.6.122.78.2.2 
		hwSecAptCisThreatLogOverThresholdRecover NOTIFICATION-TYPE
		OBJECTS { 
			  hwSecAptCisThresholdNum,
                                                         hwSecAptCisThreatLogNum,
			  hwSecAptCisTrapSlot,
			  hwSecAptCisTrapCPU  
		        }
		STATUS     current
		DESCRIPTION
		    "The Threat Logs Descends Threshold."
		::= { hwSecAptCisTraps 2 }

	         
    END

--
-- HUAWEI-SECURITY-APT-CIS-MIB.mib
--
