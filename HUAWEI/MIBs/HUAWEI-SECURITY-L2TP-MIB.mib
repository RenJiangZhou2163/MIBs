--
-- HUAWEI-SECURITY-L2TP-MIB.mib
-- MIB generated by MG-SOFT Visual MIB Builder Version 4.0 Build 341
-- Wednesday, May 15, 2013 at 11:47:10
--

--   =============================================================================
-- Copyright (C) 2017 by HUAWEI TECHNOLOGIES. All rights reserved.
--    
-- Description:  
-- Reference: Huawei Enterprise MIB
-- Version: V1.02
-- History: 
--          V1.00 The initial version created by Zuoyi 90006056. 
-- =============================================================================


	HUAWEI-SECURITY-L2T-MIB DEFINITIONS ::= BEGIN
 
		IMPORTS
			enterprises			
				FROM RFC1155-SMI			
			OBJECT-GROUP			
				FROM SNMPv2-CONF			
			IpAddress, Unsigned32, Integer32, OBJECT-TYPE, MODULE-IDENTITY, NOTIFICATION-TYPE			
				FROM SNMPv2-SMI
			MODULE-COMPLIANCE, OBJECT-GROUP, NOTIFICATION-GROUP
                                FROM SNMPv2-CONF  			
			TruthValue, RowStatus, DateAndTime, TimeInterval, TEXTUAL-CONVENTION			
				FROM SNMPv2-TC;
	
	
		hwL2tMibObjects MODULE-IDENTITY 
                LAST-UPDATED "201702222049Z"                -- Feb 22, 2017 at 22:51 GMT
			ORGANIZATION 
				"Huawei Technologies Co.,Ltd."
        CONTACT-INFO 
                   "Huawei Industrial Base
                    Bantian, Longgang
                    Shenzhen 518129
                    People's Republic of China
                    Website: http://www.huawei.com
                    Email: support@huawei.com
                   "

            DESCRIPTION 
                "
                V1.00
                The HUAWEI-SECURITY-L2TP-MIB contains objects to manage the firewall l2t module.
                "
             REVISION  "201702222049Z"

            DESCRIPTION "Delete  hwl2tUsersReachCPUMax and hwl2tUsersBelowCPUThreshold in hwl2tTrap at 2017-2-22."

            REVISION  "201702041120Z"

            DESCRIPTION "Add hwl2tSlot and hwl2tCPU in l2tTrapObject and hwl2tUsersReachMax and hwl2tUsersReachCPUMax in hwl2tTrap at 2017-02-04."

            REVISION  "201412261558Z"

            DESCRIPTION "The HUAWEI-SECURITY-L2TP-MIB contains objects to manage the firewall l2t module."

			::= { hwSecurity 2 }


--
-- Node definitions
--
                -- 1.3.6.1.4.1.2011
                huawei OBJECT IDENTIFIER ::= { enterprises 2011 }
        
                -- 1.3.6.1.4.1.2011.6
                huaweiUtility OBJECT IDENTIFIER ::= { huawei 6 }
        
                -- 1.3.6.1.4.1.2011.6.122
                hwSecurity OBJECT IDENTIFIER ::= { huaweiUtility 122 }
                
 	
		-- 1.3.6.1.4.1.2011.5.25.8.1.1
		hwl2tEnableFlag OBJECT-TYPE
			SYNTAX TruthValue
			MAX-ACCESS read-write
			STATUS current
			DESCRIPTION
				"
				the tunnul function switch.
				1: true(on)
				2: false(off)
				"
			DEFVAL { false }
			::= { hwL2tMibObjects 1 }		
			
         
--L2TP Group Configure Table
                        
                hwl2tGroupConfigTable OBJECT-TYPE
                        SYNTAX SEQUENCE OF Hwl2tGroupConfigEntry
                        MAX-ACCESS not-accessible
                        STATUS current
                        DESCRIPTION
                                "l2t group configure."
                        ::= { hwL2tMibObjects 2 }
                
                hwl2tGroupConfigEntry OBJECT-TYPE
                        SYNTAX Hwl2tGroupConfigEntry
                        MAX-ACCESS not-accessible
                        STATUS current
                        DESCRIPTION
                                "."
                        INDEX { hwl2tGroupindex }
                        ::= { hwl2tGroupConfigTable 1 }
                
                Hwl2tGroupConfigEntry ::=
                        SEQUENCE { 
                                hwl2tGroupindex
                                        Integer32,
                                hwl2tGroupName
                                        OCTET STRING,
                                hwl2tTunnelNumber
                                        Integer32,
                                hwl2tGroupFlag
                                        Integer32,
                                hwl2tGroupAuthentication
                                        TruthValue,
                                hwl2tGroupPassWord
                                        OCTET STRING,   
                                hwl2tGroupAvpHidden
                                        TruthValue,
                                hwl2tGroupTunnelName
                                        OCTET STRING,
                                hwl2tGroupRemoteName
                                        OCTET STRING,
                                hwl2tGroupRetransmit
                                        Integer32,
                                hwl2tGroupTimeout
                                        TimeInterval,
                                hwl2tGroupTimer
                                        TimeInterval,
                                hwl2tGroupLnsIP1
                                        IpAddress,
                                hwl2tGroupLnsIP2
                                        IpAddress,
                                hwl2tGroupLnsIP3
                                        IpAddress,
                                hwl2tGroupLnsIP4
                                        IpAddress,
                                hwl2tGroupLnsIP5
                                        IpAddress,        
                                hwl2tGroupForceChap
                                        TruthValue,
                                hwl2tGroupForceLcp                
                                        TruthValue,
                                hwl2tGroupVt
                                        Integer32,
                                hwl2tGroupRowStatus
                                        RowStatus
                         }

                hwl2tGroupindex OBJECT-TYPE
                        SYNTAX Integer32(1..1000)
                        MAX-ACCESS not-accessible
                        STATUS current
                        DESCRIPTION
                                "Number of l2t-group."
                        ::= { hwl2tGroupConfigEntry 1 }
                
                hwl2tGroupName OBJECT-TYPE
                        SYNTAX OCTET STRING (SIZE(1..32))
                        MAX-ACCESS read-write
                        STATUS current
                        DESCRIPTION
                                "l2t group name."
                        ::= { hwl2tGroupConfigEntry 2 }
                                
                hwl2tTunnelNumber OBJECT-TYPE
                        SYNTAX Integer32(0..320000)
                        MAX-ACCESS read-only
                        STATUS current
                        DESCRIPTION
                                "l2t tunnel number"
                        ::= { hwl2tGroupConfigEntry 3 }        
                        
                hwl2tGroupFlag OBJECT-TYPE
                        SYNTAX Integer32(0..2)
                        MAX-ACCESS read-only
                        STATUS current
                        DESCRIPTION
                                "l2t group type identifier lac/lns."
                        DEFVAL { 0 }
                        ::= { hwl2tGroupConfigEntry 4 }
                
                hwl2tGroupAuthentication OBJECT-TYPE
                        SYNTAX TruthValue
                        MAX-ACCESS read-write
                        STATUS current
                        DESCRIPTION
                                "Whether the tunnel enable authentication."
                        DEFVAL { true }
                        ::= { hwl2tGroupConfigEntry 5 }
                        
                hwl2tGroupPassWord OBJECT-TYPE
                        SYNTAX OCTET STRING (SIZE(0..16))
                        MAX-ACCESS read-write
                        STATUS current
                        DESCRIPTION
                                "l2t group authentication password."
                        ::= { hwl2tGroupConfigEntry 6 }
                
                hwl2tGroupAvpHidden OBJECT-TYPE
                        SYNTAX TruthValue
                        MAX-ACCESS read-write
                        STATUS current
                        DESCRIPTION
                                "Whether the Avp hide."
                        DEFVAL { false }
                        ::= { hwl2tGroupConfigEntry 7 }
                
                hwl2tGroupTunnelName OBJECT-TYPE
                        SYNTAX OCTET STRING (SIZE(0..30))
                        MAX-ACCESS read-write
                        STATUS current
                        DESCRIPTION
                                "l2t local tunnel name."
                        ::= { hwl2tGroupConfigEntry 8 }
                        
                hwl2tGroupRemoteName OBJECT-TYPE
                        SYNTAX OCTET STRING (SIZE(0..30))
                        MAX-ACCESS read-write
                        STATUS current
                        DESCRIPTION
                                "l2t group peer's name."
                        ::= { hwl2tGroupConfigEntry 9 }

                hwl2tGroupRetransmit OBJECT-TYPE
                        SYNTAX Integer32(1..10)
                        MAX-ACCESS read-write
                        STATUS current
                        DESCRIPTION
                                "Retransmit of l2t control packet."
                        ::= { hwl2tGroupConfigEntry 10 }

                hwl2tGroupTimeout OBJECT-TYPE
                        SYNTAX TimeInterval
                        MAX-ACCESS read-write
                        STATUS current
                        DESCRIPTION
                                "
                                Timeout of l2t control packet."
                        ::= { hwl2tGroupConfigEntry 11 }

                hwl2tGroupTimer OBJECT-TYPE
                        SYNTAX TimeInterval
                        MAX-ACCESS read-write
                        STATUS current
                        DESCRIPTION
                                "
                                Hand shake timeout of l2t group."
                        ::= { hwl2tGroupConfigEntry 12 }
 
                hwl2tGroupLnsIP1 OBJECT-TYPE
                        SYNTAX IpAddress
                        MAX-ACCESS read-write
                        STATUS current
                        DESCRIPTION
                                "Lns ip address1."
                        ::= { hwl2tGroupConfigEntry 13 }
 
                hwl2tGroupLnsIP2 OBJECT-TYPE
                        SYNTAX IpAddress
                        MAX-ACCESS read-write
                        STATUS current
                        DESCRIPTION
                                "Lns ip address2."
                        ::= { hwl2tGroupConfigEntry 14 }
 
                hwl2tGroupLnsIP3 OBJECT-TYPE
                        SYNTAX IpAddress
                        MAX-ACCESS read-write
                        STATUS current
                        DESCRIPTION
                                "Lns ip address3."
                        ::= { hwl2tGroupConfigEntry 15 }
 
                hwl2tGroupLnsIP4 OBJECT-TYPE
                        SYNTAX IpAddress
                        MAX-ACCESS read-write
                        STATUS current
                        DESCRIPTION
                                "Lns ip address4."
                        ::= { hwl2tGroupConfigEntry 16 }
 
                hwl2tGroupLnsIP5 OBJECT-TYPE
                        SYNTAX IpAddress
                        MAX-ACCESS read-write
                        STATUS current
                        DESCRIPTION
                                "Lns ip address5."
                        ::= { hwl2tGroupConfigEntry 17 }       
                
                hwl2tGroupForceChap OBJECT-TYPE
                        SYNTAX TruthValue
                        MAX-ACCESS read-write
                        STATUS current
                        DESCRIPTION
                                "Whether force chap."
                        ::= { hwl2tGroupConfigEntry 18 }       
                        
                hwl2tGroupForceLcp OBJECT-TYPE
                        SYNTAX TruthValue
                        MAX-ACCESS read-write
                        STATUS current
                        DESCRIPTION
                                "Whether force lcp renegotiate."
                        ::= { hwl2tGroupConfigEntry 19 }
                        
                hwl2tGroupVt OBJECT-TYPE
                        SYNTAX Integer32(0..1023|65535)
                        MAX-ACCESS read-write
                        STATUS current
                        DESCRIPTION
                                "Virtual template number."
                        ::= { hwl2tGroupConfigEntry 20 }
                        
                hwl2tGroupRowStatus OBJECT-TYPE
                        SYNTAX RowStatus
                        MAX-ACCESS read-write
                        STATUS current
                        DESCRIPTION
                                "The group row status. "                      
                        ::= { hwl2tGroupConfigEntry 21}
                        
                        
-- l2t Tunnel Configure Table
                hwl2tTunnelTable OBJECT-TYPE
                        SYNTAX SEQUENCE OF Hwl2tTunnelEntry 
                        MAX-ACCESS not-accessible
                        STATUS current
                        DESCRIPTION
                                "This table specifies the monitoring attributes for
                                 Huawei l2t tunnel."
                        ::= { hwL2tMibObjects 3 }
                
                hwl2tTunnelEntry OBJECT-TYPE
                        SYNTAX Hwl2tTunnelEntry 
                        MAX-ACCESS not-accessible
                        STATUS current
                        DESCRIPTION
                                "Each entry in the hwl2tTunnelTable holds a set of monitoring
                                 parameters associated with an instance of l2t tunnel."
                        INDEX { hwl2tTunnelIndex}
                        ::= { hwl2tTunnelTable 1 }
                
                Hwl2tTunnelEntry ::=
                        SEQUENCE { 
                                hwl2tTunnelIndex
                                        Integer32,                                
                                hwl2tTunnelLocalID                
                                        Integer32,
                                hwl2tTunnelRemoteID
                                        Integer32,
                                hwl2tTunnelRemoteName
                                        OCTET STRING,
                                hwl2tTunnelRemoteIP
                                        IpAddress,
                                hwl2tTunnelRemotePort
                                        Integer32,
                                hwl2tTunnelSessionNum
                                        Integer32,
                                hwl2tLnsGroupRowStatus
                                        RowStatus                                                                                                                                                       
                         }

                hwl2tTunnelIndex OBJECT-TYPE
                        SYNTAX Integer32
                        MAX-ACCESS not-accessible
                        STATUS current
                        DESCRIPTION
                                "A unique value for l2t tunnel table.  Its value ranges
                                 between 0 and 65535 and may not be contigous."
                        ::= { hwl2tTunnelEntry 1 }
                        
                hwl2tTunnelLocalID OBJECT-TYPE
                        SYNTAX Integer32 (1..65535)
                        MAX-ACCESS read-only
                        STATUS current
                        DESCRIPTION
                                "l2t tunnel local's id."
                        ::= { hwl2tTunnelEntry 2 }
                
                hwl2tTunnelRemoteID OBJECT-TYPE
                        SYNTAX Integer32 (1..65535)
                        MAX-ACCESS read-only
                        STATUS current
                        DESCRIPTION
                                "l2t tunnel peer's id."      
                        ::= { hwl2tTunnelEntry 3 }
                        
                hwl2tTunnelRemoteName OBJECT-TYPE
                        SYNTAX OCTET STRING
                        MAX-ACCESS read-only
                        STATUS current
                        DESCRIPTION
                                "l2t tunnel peer's name."       
                        ::= { hwl2tTunnelEntry 4 }
                        
                hwl2tTunnelRemoteIP OBJECT-TYPE
                        SYNTAX IpAddress
                        MAX-ACCESS read-only
                        STATUS current
                        DESCRIPTION
                                "l2t tunnel peer's IP address."    
                        ::= { hwl2tTunnelEntry 5 }
                        
                hwl2tTunnelRemotePort OBJECT-TYPE
                        SYNTAX Integer32 (1..65535)
                        MAX-ACCESS read-only
                        STATUS current
                        DESCRIPTION
                                "l2t tunnel peer's port number."        
                        ::= { hwl2tTunnelEntry 6 }
                        
                hwl2tTunnelSessionNum OBJECT-TYPE
                        SYNTAX Integer32 (0..65535)
                        MAX-ACCESS read-only
                        STATUS current
                        DESCRIPTION
                                "Number of l2t tunnel's sessions"          
                        ::= { hwl2tTunnelEntry 7 }
                        
                hwl2tLnsGroupRowStatus OBJECT-TYPE
                        SYNTAX RowStatus
                        MAX-ACCESS read-write
                        STATUS current
                        DESCRIPTION
                                "The tunnel row status."                               
                        ::= { hwl2tTunnelEntry 8}
                        
                        
--l2t Session Table
 
                hwl2tSessionTable OBJECT-TYPE
                        SYNTAX SEQUENCE OF Hwl2tSessionEntry
                        MAX-ACCESS not-accessible
                        STATUS current
                        DESCRIPTION
                                "This table specifies the monitoring attributes for
                                 Huawei l2t session."
                        ::= { hwL2tMibObjects 4 }
                
                hwl2tSessionEntry OBJECT-TYPE
                        SYNTAX Hwl2tSessionEntry
                        MAX-ACCESS not-accessible
                        STATUS current
                        DESCRIPTION
                                "Each entry in the hwl2tSessionTable holds a set of monitoring
                                 parameters associated with an instance of l2t session."
                        INDEX { hwl2tSessionIndex }
                        ::= { hwl2tSessionTable 1 }
                
                Hwl2tSessionEntry ::=
                        SEQUENCE { 
                                hwl2tSessionIndex
                                        Integer32,
                                hwl2tSessionTunnelID
                                	Integer32,
                                hwl2tSessionLocalSID
                                        Integer32,
                                hwl2tSessionRemoteSID
                                        Integer32,
                                hwl2tSessionUserName
                                        OCTET STRING,
                                hwl2tSessionState
                                        INTEGER,
                                hwl2tSessionCallType
                                        INTEGER,
                                hwl2tSessionSerialNumber
                                        Unsigned32                                                                                                                                                      
                         }

                   hwl2tSessionIndex OBJECT-TYPE
                           SYNTAX          Integer32
                           MAX-ACCESS      not-accessible
                           STATUS          current
                           DESCRIPTION
                              "This object identifies the session's associated
                               l2t tunnel ifIndex value."
                           ::= { hwl2tSessionEntry 1 }
                           
                   hwl2tSessionTunnelID OBJECT-TYPE
                   	   SYNTAX          Integer32  (0..65535)
                           MAX-ACCESS      read-only
                           STATUS          current
                           DESCRIPTION
                              "This object contains the local assigned tunnel
                               identifier for this session. "
                           ::= { hwl2tSessionEntry 2 }
                
                   hwl2tSessionLocalSID OBJECT-TYPE
                           SYNTAX          Integer32 (1..65535)
                           MAX-ACCESS      read-only
                           STATUS          current
                           DESCRIPTION
                              "This object contains the local assigned session
                               identifier for this session."
                           ::= { hwl2tSessionEntry 3 }
                
                   hwl2tSessionRemoteSID OBJECT-TYPE
                           SYNTAX          Integer32  (0..65535)
                           MAX-ACCESS      read-only
                           STATUS          current
                           DESCRIPTION
                              "This object contains the remote assigned session
                               identifier for this session. When a session is
                               starting this value may be zero until the remote
                               tunnel endpoint has responded."
                           ::= { hwl2tSessionEntry 4 }
                
                   hwl2tSessionUserName OBJECT-TYPE
                           SYNTAX          OCTET STRING
                           MAX-ACCESS      read-only
                           STATUS          current
                           DESCRIPTION
                              "This object identifies the peer session name on
                               this interface. This is typically the login name
                               of the remote user. If the user name is unknown to
                               the local tunnel peer then this object will contain
                               a null string."
                           ::= { hwl2tSessionEntry 5 }
                            
               
                   hwl2tSessionState   OBJECT-TYPE
                           SYNTAX          INTEGER {
                                               sessionIdle(1),
                                               sessionConnecting(2),
                                               sessionEstablished(3),
                                               sessionDisconnecting(4)
                                           }
                           MAX-ACCESS      read-only
                           STATUS          current
                           DESCRIPTION
                              "This object contains the current state of the
                               session."
                           ::= { hwl2tSessionEntry 6 }
                
                   hwl2tSessionCallType OBJECT-TYPE
                           SYNTAX          INTEGER {
                                               lacIncoming(1),
                                               lnsIncoming(2),
                                               lacOutgoing(3),
                                               lnsOutgoing(4)
                                           }
                           MAX-ACCESS      read-only
                           STATUS          current
                           DESCRIPTION
                              "This object indicates the type of call and the
                               role this tunnel peer is providing for this
                               session. For example, lacIncoming(1) indicates
                               that this tunnel peer is acting as a LAC and
                               generated a Incoming-Call-Request to the tunnel
                               peer (the LNS). Note that tunnel peers can be
                               both LAC and LNS simultaneously."
                           ::= { hwl2tSessionEntry 7 }
                
                   hwl2tSessionSerialNumber OBJECT-TYPE
                           SYNTAX          Unsigned32
                           MAX-ACCESS      read-only
                           STATUS          current
                           DESCRIPTION
                              "This object contains the serial number that has
                               been assigned to this  session."
                           ::= { hwl2tSessionEntry 8 }
                        
-- ===============================================
-- l2tTrapObject.
-- ===============================================
 
 		hwl2tTrapObject OBJECT IDENTIFIER ::= { hwL2tMibObjects 7 }
	        	        
	    	hwl2tTunnelindex OBJECT-TYPE
			SYNTAX Integer32 (1..65535)
			MAX-ACCESS accessible-for-notify
			STATUS current
			DESCRIPTION
				"The l2t tunnel index."
			::= { hwl2tTrapObject 1 }
	        
	    	hwl2tSessionindex OBJECT-TYPE
			SYNTAX Integer32 (1..2147483647)
			MAX-ACCESS accessible-for-notify
			STATUS current
			DESCRIPTION
				"The l2t session index."
			::= { hwl2tTrapObject 2 }
	        
	    	hwl2tTunnelRemoteAddr OBJECT-TYPE
			SYNTAX IpAddress
			MAX-ACCESS accessible-for-notify
			STATUS current
			DESCRIPTION
				"The l2t peer's address."
			::= { hwl2tTrapObject 3 }

	    	hwl2tTunnelUserName OBJECT-TYPE
			SYNTAX OCTET STRING
			MAX-ACCESS accessible-for-notify
			STATUS current
			DESCRIPTION
				"The l2t peer's name."
			::= { hwl2tTrapObject 4 }
			
		hwl2tTunnelStartTime OBJECT-TYPE
			SYNTAX DateAndTime
			MAX-ACCESS accessible-for-notify
			STATUS current
			DESCRIPTION
				"The l2t peer's online time."
			::= { hwl2tTrapObject 5 }
			
		hwl2tRemoteName OBJECT-TYPE
			SYNTAX OCTET STRING
			MAX-ACCESS accessible-for-notify
			STATUS current
			DESCRIPTION
				"remote tunnel name"
			::= { hwl2tTrapObject 6 }
			
		hwl2tTunnelGroupIndex OBJECT-TYPE
			SYNTAX Integer32 (1..1000)
			MAX-ACCESS accessible-for-notify
			STATUS current
			DESCRIPTION
				"The l2t group index."
			::= { hwl2tTrapObject 7 }

                                         hwl2tSlot OBJECT-TYPE
			SYNTAX Integer32 (1..16)
			MAX-ACCESS accessible-for-notify
			STATUS current
			DESCRIPTION
				"The slot number."
			::= { hwl2tTrapObject 8 }
		
		hwl2tCPU OBJECT-TYPE
			SYNTAX Integer32 (0..3)
			MAX-ACCESS accessible-for-notify
			STATUS current
			DESCRIPTION
				"The CPU number."
			::= { hwl2tTrapObject 9 }
                        
-- ===============================================
-- definition of traps.      
-- ===============================================

                hwl2tTrap OBJECT IDENTIFIER ::= { hwL2tMibObjects 8 }
                hwl2tNotifications OBJECT IDENTIFIER ::= { hwl2tTrap 1 }
                                
                hwl2tSessionStart NOTIFICATION-TYPE
                OBJECTS { 
                          hwl2tTunnelindex,                    
                          hwl2tSessionindex,
                          hwl2tTunnelRemoteAddr,
                          hwl2tTunnelUserName,
                          hwl2tTunnelStartTime,
                          hwl2tRemoteName,
                          hwl2tTunnelGroupIndex
                        }
                STATUS     current
                DESCRIPTION
                               "This notification is generated when an l2t 
                                Tunnel is created."
                ::= { hwl2tNotifications 1 }
                
                hwl2tSessionStop NOTIFICATION-TYPE
                OBJECTS {
                          hwl2tTunnelindex,                    
                          hwl2tSessionindex,
                          hwl2tTunnelRemoteAddr,
                          hwl2tTunnelUserName,
                          hwl2tTunnelStartTime,
                          hwl2tRemoteName,
                          hwl2tTunnelGroupIndex
                        }
                STATUS     current
                DESCRIPTION
                               "This notification is generated when an l2t
                                Tunnel is deleted."
                ::= { hwl2tNotifications 2 }
                
                hwl2tUsersReachMax NOTIFICATION-TYPE
                OBJECTS {
                                     hwl2tSlot,
                                     hwl2tCPU
                	              }
                STATUS     current
                DESCRIPTION
                               "This notification is generated when number of online
                                L2TP users reach the upper limit."
                ::= { hwl2tNotifications 3 }
                
                hwl2tUsersBelowThreshold NOTIFICATION-TYPE
                OBJECTS {
                	                hwl2tSlot,
                                     hwl2tCPU
                	              }
                STATUS     current
                DESCRIPTION
                               "This notification is generated when number of online
                                L2TP users is lower than threshold value."
                ::= { hwl2tNotifications 4 }

-- ===============================================
-- Conformance Information             
-- ===============================================

		hwl2tMibConformance OBJECT IDENTIFIER ::= { hwL2tMibObjects 10 }
		
		hwl2tMibCompliances OBJECT IDENTIFIER ::= { hwl2tMibConformance 1 }
		
		hwl2tMibGroups OBJECT IDENTIFIER ::= { hwl2tMibConformance 2 }
		
		
-- ===============================================
-- Compliance Statements             
-- ===============================================	
	
        hwl2tMibCompliance MODULE-COMPLIANCE
			 STATUS current
			 DESCRIPTION 
				" "
			 MODULE -- this module
			 MANDATORY-GROUPS 
				{ 
					hwl2tGroupConfigTableGroup,
					hwl2tTunnelTableGroup,
					hwl2tSessionTableGroup,
					hwl2tTrapObjectGroup,
					hwl2tTrapGroup
				}
			::= { hwl2tMibCompliances 1 }
		     
		hwl2tGroupConfigTableGroup OBJECT-GROUP
			OBJECTS { 
                                	hwl2tTunnelNumber,
                                	hwl2tGroupName,
                                	hwl2tGroupFlag,
                                	hwl2tGroupAuthentication,
                                	hwl2tGroupPassWord,   
                                	hwl2tGroupAvpHidden,
                                	hwl2tGroupTunnelName,
                                	hwl2tGroupRemoteName,
                                	hwl2tGroupRetransmit,
                                	hwl2tGroupTimeout,
                                	hwl2tGroupTimer,
                                	hwl2tGroupLnsIP1,
                                	hwl2tGroupLnsIP2,
                                	hwl2tGroupLnsIP3,
                                	hwl2tGroupLnsIP4,
                                	hwl2tGroupLnsIP5,      
                                	hwl2tGroupForceChap,
                                	hwl2tGroupForceLcp,
                                	hwl2tGroupVt,
                                	hwl2tGroupRowStatus						
				}
			STATUS current
			DESCRIPTION 
				"l2t group configure."
			::= { hwl2tMibGroups 2 }			     
        
        	hwl2tTunnelTableGroup OBJECT-GROUP
			OBJECTS {                                
                                	hwl2tTunnelLocalID,
                                	hwl2tTunnelRemoteID,
                                	hwl2tTunnelRemoteName,
                                	hwl2tTunnelRemoteIP,
                                	hwl2tTunnelRemotePort,
                                	hwl2tTunnelSessionNum,
                                	hwl2tLnsGroupRowStatus      						
				}
			STATUS current
			DESCRIPTION 
				"This table specifies the monitoring attributes for
                                 Huawei l2t tunnel."
			::= { hwl2tMibGroups 3 }
			
		hwl2tSessionTableGroup OBJECT-GROUP
			OBJECTS {                       
                                	hwl2tSessionTunnelID,
                                	hwl2tSessionLocalSID,
                                	hwl2tSessionRemoteSID,
                                	hwl2tSessionUserName,
                                	hwl2tSessionState,
                                	hwl2tSessionCallType,
                                	hwl2tSessionSerialNumber        						
				}
			STATUS current
			DESCRIPTION 
				"This table specifies the monitoring attributes for
                                 Huawei l2t session."
			::= { hwl2tMibGroups 4 }
			
		hwl2tTrapObjectGroup OBJECT-GROUP
			OBJECTS {                               
                                	hwl2tTunnelindex,
                                	hwl2tSessionindex,
                                	hwl2tTunnelRemoteAddr,
                                	hwl2tTunnelUserName,
                                	hwl2tTunnelStartTime,
                                	hwl2tRemoteName,
                                	hwl2tTunnelGroupIndex,
                                           hwl2tSlot,
                                	hwl2tCPU       						
				}
			STATUS current
			DESCRIPTION 
				"l2t trap objects."
			::= { hwl2tMibGroups 5 }
			
		hwl2tTrapGroup NOTIFICATION-GROUP
			NOTIFICATIONS {                               
                                	hwl2tSessionStart,
                                	hwl2tSessionStop,
                                           hwl2tUsersReachMax,
                                           hwl2tUsersBelowThreshold						
				}
			STATUS current
			DESCRIPTION 
				"l2t traps."
			::= { hwl2tMibGroups 6 }
			
        END

--
-- HUAWEI-SECURITY-l2t-MIB
--
