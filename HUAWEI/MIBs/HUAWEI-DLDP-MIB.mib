--
-- HUAWEI-DLDP-MIB.mib
-- MIB generated by MG-SOFT Visual MIB Builder Version 3.0 Build 253
-- Tuesday, September 23, 2014 at 09:06:22
--

--   =================================================================
-- Copyright (C) 2018 by  HUAWEI TECHNOLOGIES. All rights reserved
-- 
-- Description: HUAWEI DLDP MIB, this mib will maintain information of DLDP 
--              protocol for datacomm product.  
-- Reference:
-- Version:     V2.03
-- History:
--  
--  V2.00 2008-07-15 initial version
-- =================================================================

	HUAWEI-DLDP-MIB DEFINITIONS ::= BEGIN
 
		IMPORTS
			hwDatacomm			
				FROM HUAWEI-MIB			
			InterfaceIndex			
				FROM IF-MIB			
			EnabledStatus			
				FROM P-BRIDGE-MIB			
			OBJECT-GROUP, MODULE-COMPLIANCE, NOTIFICATION-GROUP			
				FROM SNMPv2-CONF			
			Integer32, Counter32, OBJECT-TYPE, MODULE-IDENTITY, NOTIFICATION-TYPE			
				FROM SNMPv2-SMI			
			TruthValue, RowStatus, MacAddress, TEXTUAL-CONVENTION			
				FROM SNMPv2-TC;
	
	
--  Revision history
		hwDldpMIB MODULE-IDENTITY 
			LAST-UPDATED "201809180001Z"  	-- Sept 18, 2018 at 00:00 GMT
			ORGANIZATION 
				"Huawei Technologies Co.,Ltd."
			CONTACT-INFO 
				"Huawei Industrial Base
				Bantian, Longgang
				Shenzhen 518129
				People's Republic of China
				Website: http://www.huawei.com
				Email: support@huawei.com
				"
			DESCRIPTION 
				"This file is a DLDP-MIB. It provides the functions such as
				globally enabling or disabling the DLDP protocol, enabling the global
				alarm, clearing statistics on ports and configuring work mode."
                                                          REVISION "201809180001Z"		-- Sept 18, 2018 at 00:00 GMT
			DESCRIPTION
				"V2.02, Modify node hwDldpUnidirectionalShutdown,hwDldpWorkMode,hwDldpAuthenMode."
			REVISION "201410210000Z"		-- October 21, 2014 at 00:00 GMT
			DESCRIPTION
				"V2.02, hhhhhh."
                                                          REVISION "201311300000Z"		-- November 30, 2013 at 00:00 GMT
			DESCRIPTION
				"V2.00, initial version."
			REVISION "200807151430Z"		-- July 15, 2008 at 14:30 GMT
			DESCRIPTION
				"V2.01, added hwDldpIfTable, hwDldpIfNeighbourTable and hwDldpIfStatisticsTable."
			::= { hwDatacomm 173 }
		
	
--
-- Textual conventions
--
	
--  Textual Convention
		PortIndex ::= TEXTUAL-CONVENTION
			STATUS current
			DESCRIPTION 
				"Each port is uniquely identified by a port number. The port number ranges from 0
				to 575."
			SYNTAX Integer32 (0..575)
			
	
--
-- Node definitions
--
	
--  ============================================================================
-- Node definitions
-- ============================================================================ 
		-- 1.3.6.1.4.1.2011.5.25.173.1
		hwDldpObjects OBJECT IDENTIFIER ::= { hwDldpMIB 1 }
		
--  ============================================================================
-- 
-- ======================= Objects definitions=================================
-- 
-- ============================================================================  
		-- 1.3.6.1.4.1.2011.5.25.173.1.1
		hwDldpConfiguration OBJECT IDENTIFIER ::= { hwDldpObjects 1 }
		
		-- 1.3.6.1.4.1.2011.5.25.173.1.1.1
		hwDldpEnable OBJECT-TYPE
			SYNTAX EnabledStatus
			MAX-ACCESS read-write
			STATUS current
			DESCRIPTION
				"Globally enable or disable the DLDP configuration. If the hwDldpEnable 
				is 1, DLDP is enabled. If the hwDldpEnable is 2, DLDP is disabled. 
				By default, DLDP is disabled."
			DEFVAL { 2 }
			::= { hwDldpConfiguration 1 }
		
		-- 1.3.6.1.4.1.2011.5.25.173.1.1.2
		hwDldpUnidirectionalShutdown OBJECT-TYPE
			SYNTAX INTEGER
				{
				auto(1),
				manual(2)
				}
			MAX-ACCESS read-write
			STATUS current
			DESCRIPTION
				"When the device discovers a one-way link, the shutdown mode of port. The modes include
				auto and manual. By default, DLDP is auto."
			DEFVAL { auto }
			::= { hwDldpConfiguration 2 }
		
		-- 1.3.6.1.4.1.2011.5.25.173.1.1.3
		hwDldpWorkMode OBJECT-TYPE
			SYNTAX INTEGER
				{
				normal(1),
				enhance(2)
				}
			MAX-ACCESS read-write
			STATUS current
			DESCRIPTION
				"It configures the work mode of the DLDP protocol, including normal and enhanced mode.
				By default, the mode is enhanced."
			DEFVAL { enhance }
			::= { hwDldpConfiguration 3 }
		
		-- 1.3.6.1.4.1.2011.5.25.173.1.1.4
		hwDldpAdvertInterval OBJECT-TYPE
			SYNTAX Integer32 (1..100)
			MAX-ACCESS read-write
			STATUS current
			DESCRIPTION
				"Global interval for sending advertisement packets for the DLDP configuration.
				By default, the interval is 5s."
			DEFVAL { 5 }
			::= { hwDldpConfiguration 4 }
		
		-- 1.3.6.1.4.1.2011.5.25.173.1.1.5
		hwDelayDownTimer OBJECT-TYPE
			SYNTAX Integer32 (1..5)
			MAX-ACCESS read-write
			STATUS current
			DESCRIPTION
				"Global timeout of DelayDown timer. The value rangs from 1s to 5s,
				By default, the time is 1s."
			DEFVAL { 1 }
			::= { hwDldpConfiguration 5 }
		
		-- 1.3.6.1.4.1.2011.5.25.173.1.1.6
		hwDldpAuthenMode OBJECT-TYPE
			SYNTAX INTEGER
				{
				none(1),
				md5(2),
				simple(3),
				sha(4)
				}
			MAX-ACCESS read-write
			STATUS current
			DESCRIPTION
				"Global authentication mode of the DLDP configuration. It has three authentication
				modes, including none, md5, simple, and sha. By default the authentication mode
				is none."
			DEFVAL { none }
			::= { hwDldpConfiguration 6 }
		
		-- 1.3.6.1.4.1.2011.5.25.173.1.1.7
		hwDldpMd5Password OBJECT-TYPE
			SYNTAX OCTET STRING (SIZE (1..24))
			MAX-ACCESS read-write
			STATUS current
			DESCRIPTION
				"Global md5 password for authentication when authentication is md5."
			::= { hwDldpConfiguration 7 }
		
		-- 1.3.6.1.4.1.2011.5.25.173.1.1.8
		hwDldpSimplePassword OBJECT-TYPE
			SYNTAX OCTET STRING (SIZE (1..16))
			MAX-ACCESS read-write
			STATUS current
			DESCRIPTION
				"Global simple password for authentication when authentication is simple."
			::= { hwDldpConfiguration 8 }
		
		-- 1.3.6.1.4.1.2011.5.25.173.1.1.9
		hwDldpPortTable OBJECT-TYPE
			SYNTAX SEQUENCE OF HwDldpPortEntry
			MAX-ACCESS not-accessible
			STATUS current
			DESCRIPTION
				"DLDP port configuration table."
			::= { hwDldpConfiguration 9 }
		
		-- 1.3.6.1.4.1.2011.5.25.173.1.1.9.1
		hwDldpPortEntry OBJECT-TYPE
			SYNTAX HwDldpPortEntry
			MAX-ACCESS not-accessible
			STATUS current
			DESCRIPTION
				"Entries of the DLDP port configuration table."
			INDEX { hwDldpPortIndex }
			::= { hwDldpPortTable 1 }
		
		HwDldpPortEntry ::=
			SEQUENCE { 
				hwDldpPortIndex
					PortIndex,
				hwDldpPortStateReset
					TruthValue,
				hwDldpPortState
					INTEGER,
				hwDldpPortLinkState
					INTEGER,
				hwDldpResetStatistics
					TruthValue,
				hwDldpRowStatus
					RowStatus
			 }

		-- 1.3.6.1.4.1.2011.5.25.173.1.1.9.1.1
		hwDldpPortIndex OBJECT-TYPE
			SYNTAX PortIndex
			MAX-ACCESS not-accessible
			STATUS current
			DESCRIPTION
				"It describes enabled DLDP port index. Each port is uniquely identified by a port number. It ranges from 0
				to 575."
			::= { hwDldpPortEntry 1 }
		
		-- 1.3.6.1.4.1.2011.5.25.173.1.1.9.1.2
		hwDldpPortStateReset OBJECT-TYPE
			SYNTAX TruthValue
			MAX-ACCESS read-create
			STATUS current
			DESCRIPTION
				"It describes the DLDP status of the reset port."
			DEFVAL { false }
			::= { hwDldpPortEntry 2 }
		
		-- 1.3.6.1.4.1.2011.5.25.173.1.1.9.1.3
		hwDldpPortState OBJECT-TYPE
			SYNTAX INTEGER
				{
				initial(1),
				inactive(2),
				active(3),
				advertisement(4),
				probe(5),
				disable(6),
				delayDown(7),
				loop(8)
				}
			MAX-ACCESS read-only
			STATUS current
			DESCRIPTION
				"Port state has eight states, including initial, inactive, active,
				advertisement, probe, disable, delayDown, and loop."
			::= { hwDldpPortEntry 3 }
		
		-- 1.3.6.1.4.1.2011.5.25.173.1.1.9.1.4
		hwDldpPortLinkState OBJECT-TYPE
			SYNTAX INTEGER
				{
				up(1),
				down(2)
				}
			MAX-ACCESS read-only
			STATUS current
			DESCRIPTION
				"Port state has two modes, including up and down."
			::= { hwDldpPortEntry 4 }
		
		-- 1.3.6.1.4.1.2011.5.25.173.1.1.9.1.5
		hwDldpResetStatistics OBJECT-TYPE
			SYNTAX TruthValue
			MAX-ACCESS read-create
			STATUS current
			DESCRIPTION
				"It clears the statistics of packets received and sent on the current 
				port."
			::= { hwDldpPortEntry 5 }
		
		-- 1.3.6.1.4.1.2011.5.25.173.1.1.9.1.6
		hwDldpRowStatus OBJECT-TYPE
			SYNTAX RowStatus
			MAX-ACCESS read-create
			STATUS current
			DESCRIPTION
				" Operation of CreateAndGo can be
				used to create a new instance, and operation of Destroy be 
				used to destroy an existent index. But these operations 
				will not take effect if they are not activated by running the
				command of activating or setting mib node of hwDldpEnable."
			::= { hwDldpPortEntry 6 }
		
		-- 1.3.6.1.4.1.2011.5.25.173.1.1.10
		hwDldpNeighbourTable OBJECT-TYPE
			SYNTAX SEQUENCE OF HwDldpNeighbourEntry
			MAX-ACCESS not-accessible
			STATUS current
			DESCRIPTION
				"DLDP Neighbour configuration table."
			::= { hwDldpConfiguration 10 }
		
		-- 1.3.6.1.4.1.2011.5.25.173.1.1.10.1
		hwDldpNeighbourEntry OBJECT-TYPE
			SYNTAX HwDldpNeighbourEntry
			MAX-ACCESS not-accessible
			STATUS current
			DESCRIPTION
				"Entries of the DLDP Neighbour configuration table."
			INDEX { hwDldpPortIndex, hwDldpNeighbourMacAddr, hwDldpNeighbourPortIndex }
			::= { hwDldpNeighbourTable 1 }
		
		HwDldpNeighbourEntry ::=
			SEQUENCE { 
				hwDldpNeighbourMacAddr
					MacAddress,
				hwDldpNeighbourPortIndex
					Integer32,
				hwDldpNeighbourPortName
					OCTET STRING,
				hwDldpNeighbourState
					INTEGER,
				hwDldpNeighbourAgeTime
					Integer32
			 }

		-- 1.3.6.1.4.1.2011.5.25.173.1.1.10.1.1
		hwDldpNeighbourMacAddr OBJECT-TYPE
			SYNTAX MacAddress
			MAX-ACCESS not-accessible
			STATUS current
			DESCRIPTION
				"When the activated port detects a neighbor, it can record the neighbor information, including
				MAC address of neighbor. The port may detect multiple neighbors."
			::= { hwDldpNeighbourEntry 1 }
		
		-- 1.3.6.1.4.1.2011.5.25.173.1.1.10.1.2
		hwDldpNeighbourPortIndex OBJECT-TYPE
			SYNTAX Integer32 (0..65535)
			MAX-ACCESS not-accessible
			STATUS current
			DESCRIPTION
				"When the activated port detects a neighbor, it can record the port index of the neighbour."
			::= { hwDldpNeighbourEntry 2 }
		
		-- 1.3.6.1.4.1.2011.5.25.173.1.1.10.1.3
		hwDldpNeighbourPortName OBJECT-TYPE
			SYNTAX OCTET STRING (SIZE (0..255))
			MAX-ACCESS read-only
			STATUS current
			DESCRIPTION
				"When the activated port detects a neighbor, it can record the port name of the neighbour."
			::= { hwDldpNeighbourEntry 3 }
		
		-- 1.3.6.1.4.1.2011.5.25.173.1.1.10.1.4
		hwDldpNeighbourState OBJECT-TYPE
			SYNTAX INTEGER
				{
				unknown(1),
				oneWay(2),
				twoWay(3)
				}
			MAX-ACCESS read-only
			STATUS current
			DESCRIPTION
				"When the activated port detects a neighbor, it can record the state of the neighbour, and its value includes unknown, one way, and two way."
			::= { hwDldpNeighbourEntry 4 }
		
		-- 1.3.6.1.4.1.2011.5.25.173.1.1.10.1.5
		hwDldpNeighbourAgeTime OBJECT-TYPE
			SYNTAX Integer32 (3..300)
			MAX-ACCESS read-only
			STATUS current
			DESCRIPTION
				"When the activated port detects a neighbor, it can record the aging time of the neighbor. The aging time
				is three times the interval for sending advertisement packets."
			DEFVAL { 15 }
			::= { hwDldpNeighbourEntry 5 }
		
		-- 1.3.6.1.4.1.2011.5.25.173.1.1.11
		hwDldpIfTable OBJECT-TYPE
			SYNTAX SEQUENCE OF HwDldpIfEntry
			MAX-ACCESS not-accessible
			STATUS current
			DESCRIPTION
				"DLDP interface configuration table."
			::= { hwDldpConfiguration 11 }
		
		-- 1.3.6.1.4.1.2011.5.25.173.1.1.11.1
		hwDldpIfEntry OBJECT-TYPE
			SYNTAX HwDldpIfEntry
			MAX-ACCESS not-accessible
			STATUS current
			DESCRIPTION
				"Entries of the DLDP interface configuration table."
			INDEX { hwDldpIfIndex }
			::= { hwDldpIfTable 1 }
		
		HwDldpIfEntry ::=
			SEQUENCE { 
				hwDldpIfIndex
					InterfaceIndex,
				hwDldpIfStateReset
					TruthValue,
				hwDldpIfState
					INTEGER,
				hwDldpIfLinkState
					INTEGER,
				hwDldpIfResetStatistics
					TruthValue,
				hwDldpIfRowStatus
					RowStatus
			 }

		-- 1.3.6.1.4.1.2011.5.25.173.1.1.11.1.1
		hwDldpIfIndex OBJECT-TYPE
			SYNTAX InterfaceIndex
			MAX-ACCESS not-accessible
			STATUS current
			DESCRIPTION
				"It describes enabled DLDP interface index. Each port is uniquely identified by a port number. It ranges from 0
				to 62535."
			::= { hwDldpIfEntry 1 }
		
		-- 1.3.6.1.4.1.2011.5.25.173.1.1.11.1.2
		hwDldpIfStateReset OBJECT-TYPE
			SYNTAX TruthValue
			MAX-ACCESS read-create
			STATUS current
			DESCRIPTION
				"It describes the DLDP status of the reset port."
			DEFVAL { false }
			::= { hwDldpIfEntry 2 }
		
		-- 1.3.6.1.4.1.2011.5.25.173.1.1.11.1.3
		hwDldpIfState OBJECT-TYPE
			SYNTAX INTEGER
				{
				initial(1),
				inactive(2),
				active(3),
				advertisement(4),
				probe(5),
				disable(6),
				delayDown(7),
				loop(8)
				}
			MAX-ACCESS read-only
			STATUS current
			DESCRIPTION
				"Port state has eight states, including initial, inactive, active,
				advertisement, probe, disable, delayDown, and loop."
			::= { hwDldpIfEntry 3 }
		
		-- 1.3.6.1.4.1.2011.5.25.173.1.1.11.1.4
		hwDldpIfLinkState OBJECT-TYPE
			SYNTAX INTEGER
				{
				up(1),
				down(2)
				}
			MAX-ACCESS read-only
			STATUS current
			DESCRIPTION
				"Port state has two modes, including up and down."
			::= { hwDldpIfEntry 4 }
		
		-- 1.3.6.1.4.1.2011.5.25.173.1.1.11.1.5
		hwDldpIfResetStatistics OBJECT-TYPE
			SYNTAX TruthValue
			MAX-ACCESS read-create
			STATUS current
			DESCRIPTION
				"It clears the statistics of packets received and sent on the current 
				port."
			::= { hwDldpIfEntry 5 }
		
		-- 1.3.6.1.4.1.2011.5.25.173.1.1.11.1.6
		hwDldpIfRowStatus OBJECT-TYPE
			SYNTAX RowStatus
			MAX-ACCESS read-create
			STATUS current
			DESCRIPTION
				" Operation of CreateAndGo can be
				used to create a new instance, and operation of Destroy be 
				used to destroy an existent index. But these operations 
				will not take effect if they are not activated by running the
				command of activating or setting mib node of hwDldpEnable."
			::= { hwDldpIfEntry 6 }
		
		-- 1.3.6.1.4.1.2011.5.25.173.1.1.12
		hwDldpIfNeighbourTable OBJECT-TYPE
			SYNTAX SEQUENCE OF HwDldpIfNeighbourEntry
			MAX-ACCESS not-accessible
			STATUS current
			DESCRIPTION
				"DLDP Neighbour configuration table."
			::= { hwDldpConfiguration 12 }
		
		-- 1.3.6.1.4.1.2011.5.25.173.1.1.12.1
		hwDldpIfNeighbourEntry OBJECT-TYPE
			SYNTAX HwDldpIfNeighbourEntry
			MAX-ACCESS not-accessible
			STATUS current
			DESCRIPTION
				"Entries of the DLDP Neighbour configuration table."
			INDEX { hwDldpIfIndex, hwDldpIfNeighbourMacAddr, hwDldpIfNeighbourIfIndex }
			::= { hwDldpIfNeighbourTable 1 }
		
		HwDldpIfNeighbourEntry ::=
			SEQUENCE { 
				hwDldpIfNeighbourMacAddr
					MacAddress,
				hwDldpIfNeighbourIfIndex
					Integer32,
				hwDldpIfNeighbourPortName
					OCTET STRING,
				hwDldpIfNeighbourState
					INTEGER,
				hwDldpIfNeighbourAgeTime
					Integer32
			 }

		-- 1.3.6.1.4.1.2011.5.25.173.1.1.12.1.1
		hwDldpIfNeighbourMacAddr OBJECT-TYPE
			SYNTAX MacAddress
			MAX-ACCESS not-accessible
			STATUS current
			DESCRIPTION
				"When the activated port detects a neighbor, it can record the neighbor information, including
				MAC address of neighbor. The port may detect multiple neighbors."
			::= { hwDldpIfNeighbourEntry 1 }
		
		-- 1.3.6.1.4.1.2011.5.25.173.1.1.12.1.2
		hwDldpIfNeighbourIfIndex OBJECT-TYPE
			SYNTAX Integer32 (0..65535)
			MAX-ACCESS not-accessible
			STATUS current
			DESCRIPTION
				"When the activated port detects a neighbor, it can record the port index of the neighbour."
			::= { hwDldpIfNeighbourEntry 2 }
		
		-- 1.3.6.1.4.1.2011.5.25.173.1.1.12.1.3
		hwDldpIfNeighbourPortName OBJECT-TYPE
			SYNTAX OCTET STRING (SIZE (0..255))
			MAX-ACCESS read-only
			STATUS current
			DESCRIPTION
				"When the activated port detects a neighbor, it can record the port name of the neighbour."
			::= { hwDldpIfNeighbourEntry 3 }
		
		-- 1.3.6.1.4.1.2011.5.25.173.1.1.12.1.4
		hwDldpIfNeighbourState OBJECT-TYPE
			SYNTAX INTEGER
				{
				unknown(1),
				oneWay(2),
				twoWay(3)
				}
			MAX-ACCESS read-only
			STATUS current
			DESCRIPTION
				"When the activated port detects a neighbor, it can record the state of the neighbour, and its value includes unknown, one way, and two way."
			::= { hwDldpIfNeighbourEntry 4 }
		
		-- 1.3.6.1.4.1.2011.5.25.173.1.1.12.1.5
		hwDldpIfNeighbourAgeTime OBJECT-TYPE
			SYNTAX Integer32 (3..300)
			MAX-ACCESS read-only
			STATUS current
			DESCRIPTION
				"When the activated port detects a neighbor, it can record the aging time of the neighbor. The aging time
				is three times the interval for sending advertisement packets."
			DEFVAL { 15 }
			::= { hwDldpIfNeighbourEntry 5 }
		
		-- 1.3.6.1.4.1.2011.5.25.173.1.1.13
		hwDldpShaPassword OBJECT-TYPE
			SYNTAX OCTET STRING (SIZE (1..16))
			MAX-ACCESS read-write
			STATUS current
			DESCRIPTION
				"Global sha password for authentication when authentication is sha."
			::= { hwDldpConfiguration 13 }
		
		-- 1.3.6.1.4.1.2011.5.25.173.1.2
		hwDldpStatistics OBJECT IDENTIFIER ::= { hwDldpObjects 2 }
		
		-- 1.3.6.1.4.1.2011.5.25.173.1.2.1
		hwDldpPortStatisticsTable OBJECT-TYPE
			SYNTAX SEQUENCE OF HwDldpPortStatisticsEntry
			MAX-ACCESS not-accessible
			STATUS current
			DESCRIPTION
				"DLDP port statics configuration table."
			::= { hwDldpStatistics 1 }
		
		-- 1.3.6.1.4.1.2011.5.25.173.1.2.1.1
		hwDldpPortStatisticsEntry OBJECT-TYPE
			SYNTAX HwDldpPortStatisticsEntry
			MAX-ACCESS not-accessible
			STATUS current
			DESCRIPTION
				"Entries of the table of the packets sent or received on the DLDP port."
			INDEX { hwDldpPortIndex }
			::= { hwDldpPortStatisticsTable 1 }
		
		HwDldpPortStatisticsEntry ::=
			SEQUENCE { 
				hwDldpPortStatisticsTx
					Counter32,
				hwDldpPortStatisticsRxTotal
					Counter32,
				hwDldpPortStatisticsRxError
					Counter32,
				hwDldpPortStatisticsRxLoop
					Counter32,
				hwDldpPortStatisticsRxValid
					Counter32,
				hwDldpPortStatisticsRxAuthenFail
					Counter32
			 }

		-- 1.3.6.1.4.1.2011.5.25.173.1.2.1.1.1
		hwDldpPortStatisticsTx OBJECT-TYPE
			SYNTAX Counter32
			MAX-ACCESS read-only
			STATUS current
			DESCRIPTION
				"It describes the number of packets sent on the activated port."
			::= { hwDldpPortStatisticsEntry 1 }
		
		-- 1.3.6.1.4.1.2011.5.25.173.1.2.1.1.2
		hwDldpPortStatisticsRxTotal OBJECT-TYPE
			SYNTAX Counter32
			MAX-ACCESS read-only
			STATUS current
			DESCRIPTION
				"It describes the number of packets received on the activated port."
			::= { hwDldpPortStatisticsEntry 2 }
		
		-- 1.3.6.1.4.1.2011.5.25.173.1.2.1.1.3
		hwDldpPortStatisticsRxError OBJECT-TYPE
			SYNTAX Counter32
			MAX-ACCESS read-only
			STATUS current
			DESCRIPTION
				"It describes the number of error packets received on the activated port."
			::= { hwDldpPortStatisticsEntry 3 }
		
		-- 1.3.6.1.4.1.2011.5.25.173.1.2.1.1.4
		hwDldpPortStatisticsRxLoop OBJECT-TYPE
			SYNTAX Counter32
			MAX-ACCESS read-only
			STATUS current
			DESCRIPTION
				"It describes the number of loop packets received on the activated port."
			::= { hwDldpPortStatisticsEntry 4 }
		
		-- 1.3.6.1.4.1.2011.5.25.173.1.2.1.1.5
		hwDldpPortStatisticsRxValid OBJECT-TYPE
			SYNTAX Counter32
			MAX-ACCESS read-only
			STATUS current
			DESCRIPTION
				"It describes the number of valid packets received on the activated port."
			::= { hwDldpPortStatisticsEntry 5 }
		
		-- 1.3.6.1.4.1.2011.5.25.173.1.2.1.1.6
		hwDldpPortStatisticsRxAuthenFail OBJECT-TYPE
			SYNTAX Counter32
			MAX-ACCESS read-only
			STATUS current
			DESCRIPTION
				"It describes the number of authentication failure packets received on the activated port."
			::= { hwDldpPortStatisticsEntry 6 }
		
		-- 1.3.6.1.4.1.2011.5.25.173.1.2.2
		hwDldpIfStatisticsTable OBJECT-TYPE
			SYNTAX SEQUENCE OF HwDldpIfStatisticsEntry
			MAX-ACCESS not-accessible
			STATUS current
			DESCRIPTION
				"DLDP port statics configuration table."
			::= { hwDldpStatistics 2 }
		
		-- 1.3.6.1.4.1.2011.5.25.173.1.2.2.1
		hwDldpIfStatisticsEntry OBJECT-TYPE
			SYNTAX HwDldpIfStatisticsEntry
			MAX-ACCESS not-accessible
			STATUS current
			DESCRIPTION
				"Entries of the table of the packets sent or received on the DLDP port."
			INDEX { hwDldpIfIndex }
			::= { hwDldpIfStatisticsTable 1 }
		
		HwDldpIfStatisticsEntry ::=
			SEQUENCE { 
				hwDldpIfStatisticsTx
					Counter32,
				hwDldpIfStatisticsRxTotal
					Counter32,
				hwDldpIfStatisticsRxError
					Counter32,
				hwDldpIfStatisticsRxLoop
					Counter32,
				hwDldpIfStatisticsRxValid
					Counter32,
				hwDldpIfStatisticsRxAuthenFail
					Counter32
			 }

		-- 1.3.6.1.4.1.2011.5.25.173.1.2.2.1.1
		hwDldpIfStatisticsTx OBJECT-TYPE
			SYNTAX Counter32
			MAX-ACCESS read-only
			STATUS current
			DESCRIPTION
				"It describes the number of packets sent on the activated port."
			::= { hwDldpIfStatisticsEntry 1 }
		
		-- 1.3.6.1.4.1.2011.5.25.173.1.2.2.1.2
		hwDldpIfStatisticsRxTotal OBJECT-TYPE
			SYNTAX Counter32
			MAX-ACCESS read-only
			STATUS current
			DESCRIPTION
				"It describes the number of packets received on the activated port."
			::= { hwDldpIfStatisticsEntry 2 }
		
		-- 1.3.6.1.4.1.2011.5.25.173.1.2.2.1.3
		hwDldpIfStatisticsRxError OBJECT-TYPE
			SYNTAX Counter32
			MAX-ACCESS read-only
			STATUS current
			DESCRIPTION
				"It describes the number of error packets received on the activated port."
			::= { hwDldpIfStatisticsEntry 3 }
		
		-- 1.3.6.1.4.1.2011.5.25.173.1.2.2.1.4
		hwDldpIfStatisticsRxLoop OBJECT-TYPE
			SYNTAX Counter32
			MAX-ACCESS read-only
			STATUS current
			DESCRIPTION
				"It describes the number of loop packets received on the activated port."
			::= { hwDldpIfStatisticsEntry 4 }
		
		-- 1.3.6.1.4.1.2011.5.25.173.1.2.2.1.5
		hwDldpIfStatisticsRxValid OBJECT-TYPE
			SYNTAX Counter32
			MAX-ACCESS read-only
			STATUS current
			DESCRIPTION
				"It describes the number of valid packets received on the activated port."
			::= { hwDldpIfStatisticsEntry 5 }
		
		-- 1.3.6.1.4.1.2011.5.25.173.1.2.2.1.6
		hwDldpIfStatisticsRxAuthenFail OBJECT-TYPE
			SYNTAX Counter32
			MAX-ACCESS read-only
			STATUS current
			DESCRIPTION
				"It describes the number of authentication failure packets received on the activated port."
			::= { hwDldpIfStatisticsEntry 6 }
		
		-- 1.3.6.1.4.1.2011.5.25.173.2
		hwDldpPortTrapObjects OBJECT IDENTIFIER ::= { hwDldpMIB 2 }
		
		-- 1.3.6.1.4.1.2011.5.25.173.2.1
		hwDldpTrapInterfaceIndex OBJECT-TYPE
			SYNTAX InterfaceIndex
			MAX-ACCESS accessible-for-notify
			STATUS current
			DESCRIPTION
				"It describes the interface index of the activated port that detected one way or found that two way is resumed."
			::= { hwDldpPortTrapObjects 1 }
		
		-- 1.3.6.1.4.1.2011.5.25.173.2.2
		hwDldpTrapIfName OBJECT-TYPE
			SYNTAX OCTET STRING (SIZE (0..64))
			MAX-ACCESS accessible-for-notify
			STATUS current
			DESCRIPTION
				"It describes the interface name of the activated port that detected one way or found that two way is resumed."
			::= { hwDldpPortTrapObjects 2 }
		
		-- 1.3.6.1.4.1.2011.5.25.173.2.3
		hwDldpTrapFaultReason OBJECT-TYPE
			SYNTAX OCTET STRING (SIZE (0..64))
			MAX-ACCESS accessible-for-notify
			STATUS current
			DESCRIPTION
				"It describes the reason interface fault."
			::= { hwDldpPortTrapObjects 3 }
		
		-- 1.3.6.1.4.1.2011.5.25.173.3
		hwDldpTraps OBJECT IDENTIFIER ::= { hwDldpMIB 3 }
		
-- -Notifycation        
		-- 1.3.6.1.4.1.2011.5.25.173.3.1
		hwDldpUnidirectionalLink NOTIFICATION-TYPE
			OBJECTS { hwDldpTrapInterfaceIndex, hwDldpTrapIfName, hwDldpTrapFaultReason }
			STATUS current
			DESCRIPTION 
				"Notify the NMS that the DLDP detected one way. The hwDldpTrapInterfaceIndex node is the interface index."
			::= { hwDldpTraps 1 }
		
		-- 1.3.6.1.4.1.2011.5.25.173.3.2
		hwDldpLinkResume NOTIFICATION-TYPE
			OBJECTS { hwDldpTrapInterfaceIndex, hwDldpTrapIfName }
			STATUS current
			DESCRIPTION 
				"Notify the NMS that the DLDP detected that unidirectional link was resumed. The hwDldpTrapInterfaceIndex node is interface index."
			::= { hwDldpTraps 2 }
		
		-- 1.3.6.1.4.1.2011.5.25.173.3.3
		hwDldpLoopDetect NOTIFICATION-TYPE
			OBJECTS { hwDldpTrapInterfaceIndex, hwDldpTrapIfName }
			STATUS current
			DESCRIPTION 
				"Notify the NMS that the DLDP detected Loop State. The hwDldpTrapInterfaceIndex node is the interface index."
			::= { hwDldpTraps 3 }
		
		-- 1.3.6.1.4.1.2011.5.25.173.3.4
		hwDldpLoopResume NOTIFICATION-TYPE
			OBJECTS { hwDldpTrapInterfaceIndex, hwDldpTrapIfName }
			STATUS current
			DESCRIPTION 
				"Notify the NMS that the DLDP detected Loop State was resumed. The hwDldpTrapInterfaceIndex node is interface index."
			::= { hwDldpTraps 4 }
		
		-- 1.3.6.1.4.1.2011.5.25.173.4
		hwDldpConformance OBJECT IDENTIFIER ::= { hwDldpMIB 4 }
		
--  ***********************************************************
-- 
-- HAUWEIDLDPMIBCONFORMANCE
-- 
-- ***********************************************************
-- 
		-- 1.3.6.1.4.1.2011.5.25.173.4.1
		hwDldpCompliances OBJECT IDENTIFIER ::= { hwDldpConformance 1 }
		
--  compliance statements
-- this module
		-- 1.3.6.1.4.1.2011.5.25.173.4.1.1
		hwDldpCompliance MODULE-COMPLIANCE
			STATUS current
			DESCRIPTION 
				"The compliance statement for SNMP entities which implement
				the HUAWEI-DLDP-MIB."
			MODULE -- this module
				MANDATORY-GROUPS { hwDldpConfigGroup, hwDldpStatisticsGroup, hwDldpPortGroup, hwDldpPortTrapGroup, hwDldpTrapGroup
					 }
			::= { hwDldpCompliances 1 }
		
		-- 1.3.6.1.4.1.2011.5.25.173.4.2
		hwDldpGroups OBJECT IDENTIFIER ::= { hwDldpConformance 2 }
		
--  MIB groupings
		-- 1.3.6.1.4.1.2011.5.25.173.4.2.1
		hwDldpConfigGroup OBJECT-GROUP
			OBJECTS { hwDldpEnable, hwDldpUnidirectionalShutdown, hwDldpWorkMode, hwDldpAdvertInterval, hwDelayDownTimer, 
				hwDldpAuthenMode, hwDldpMd5Password, hwDldpSimplePassword, hwDldpShaPassword }
			STATUS current
			DESCRIPTION 
				"The collection of objects which are used to configure the
				DLDP implementation behavior.
				This group is mandatory for agents which implement the DLDP."
			::= { hwDldpGroups 1 }
		
		-- 1.3.6.1.4.1.2011.5.25.173.4.2.2
		hwDldpStatisticsGroup OBJECT-GROUP
			OBJECTS { hwDldpPortStatisticsTx, hwDldpPortStatisticsRxTotal, hwDldpPortStatisticsRxError, hwDldpPortStatisticsRxLoop, hwDldpPortStatisticsRxValid, 
				hwDldpPortStatisticsRxAuthenFail, hwDldpIfStatisticsTx, hwDldpIfStatisticsRxTotal, hwDldpIfStatisticsRxError, hwDldpIfStatisticsRxLoop, 
				hwDldpIfStatisticsRxValid, hwDldpIfStatisticsRxAuthenFail }
			STATUS current
			DESCRIPTION 
				"The collection of objects which are used to represent DLDP
				statistics.
				This group is mandatory for agents which implement the DLDP
				and have the capability of receiving and transmitting DLDP frames."
			::= { hwDldpGroups 2 }
		
		-- 1.3.6.1.4.1.2011.5.25.173.4.2.3
		hwDldpPortGroup OBJECT-GROUP
			OBJECTS { hwDldpPortStateReset, hwDldpPortState, hwDldpPortLinkState, hwDldpResetStatistics, hwDldpRowStatus, 
				hwDldpNeighbourPortName, hwDldpNeighbourState, hwDldpNeighbourAgeTime, hwDldpIfStateReset, hwDldpIfState, 
				hwDldpIfLinkState, hwDldpIfResetStatistics, hwDldpIfRowStatus, hwDldpIfNeighbourPortName, hwDldpIfNeighbourState, 
				hwDldpIfNeighbourAgeTime }
			STATUS current
			DESCRIPTION 
				"The collection of objects indicates the information of port."
			::= { hwDldpGroups 3 }
		
		-- 1.3.6.1.4.1.2011.5.25.173.4.2.4
		hwDldpPortTrapGroup OBJECT-GROUP
			OBJECTS { hwDldpTrapInterfaceIndex, hwDldpTrapIfName }
			STATUS current
			DESCRIPTION 
				"The collection of objects indicates that the activated port index detected one way or found that two way is resumed."
			::= { hwDldpGroups 4 }
		
		-- 1.3.6.1.4.1.2011.5.25.173.4.2.5
		hwDldpTrapGroup NOTIFICATION-GROUP
			NOTIFICATIONS { hwDldpUnidirectionalLink, hwDldpLinkResume, hwDldpLoopDetect, hwDldpLoopResume }
			STATUS current
			DESCRIPTION 
				"The collection of notifications used to indicate that the HUAWEI-DLDP-MIB
				data is consistent and indicate the general status information.
				This group is mandatory for agents which implement the DLDP
				and have the capability of receiving DLDP frames."
			::= { hwDldpGroups 5 }
		
	
	END

--
-- HUAWEI-DLDP-MIB.mib
--
