--  =================================================================
-- Copyright (C) 2018 by  HUAWEI TECHNOLOGIES. All rights reserved
-- 
-- Description:
-- Reference:
-- Version: V1.02
-- History: V1.00
-- 2014-04-09,initial version
-- =================================================================

    HUAWEI-SECURITY-SESSION-STAT-MIB DEFINITIONS ::= BEGIN
 
        IMPORTS
	   	IpAddress, Integer32, Counter32, Gauge32, Counter64, OBJECT-TYPE, MODULE-IDENTITY
			FROM SNMPv2-SMI 
		MODULE-COMPLIANCE, OBJECT-GROUP, NOTIFICATION-GROUP          
		            FROM SNMPv2-CONF
    		enterprises			
		            FROM RFC1155-SMI;     
    
        hwSecSessStatMIB MODULE-IDENTITY 
            LAST-UPDATED "201801311147Z"		-- June 31, 2018 at 11:00 GMT
			ORGANIZATION 
				"Huawei Technologies Co.,Ltd."
			CONTACT-INFO
				"Huawei Industrial Base
            	 Bantian, Longgang
                 Shenzhen 518129
                 People's Republic of China
                 Website: http://www.huawei.com
                 Email: support@huawei.com"
			DESCRIPTION 
				"
                V1.00
                The HUAWEI-SECURITY-SESSION-STAT-MIB contains objects to manage the security statistics for firewall product.
                "
			--  Revision history          
                                                                               REVISION    "201801311147Z"
					DESCRIPTION "V1.00, Add nodes(hwSecCurrIpv6SessNum, hwSecConIpv6SessNum)."
                                                                                    REVISION    "201606162147Z"
					DESCRIPTION "V1.01, Add nodes(hwSecCurrSessThresholdRatio, hwSecConSessThresholdRatio,hwSecCurrSessNumUsage,hwSecConSessNumUsage )   ." 	                   
				REVISION    "201601181147Z"
					DESCRIPTION "V1.00, completed the first draft."	
                                                                              
                ::= { hwSecurity 69 }
--
-- Node definitions
--                       
 	-- 1.3.6.1.4.1.2011
	huawei OBJECT IDENTIFIER ::= { enterprises 2011 }
        
        -- 1.3.6.1.4.1.2011.6
        huaweiUtility OBJECT IDENTIFIER ::= { huawei 6 }
        
        -- 1.3.6.1.4.1.2011.6.122
        hwSecurity OBJECT IDENTIFIER ::= { huaweiUtility 122 }          
        
        -- 1.3.6.1.4.1.2011.6.122.69.1
        hwSecSessStatTable OBJECT IDENTIFIER ::= { hwSecSessStatMIB 1 }  
              
        -- 1.3.6.1.4.1.2011.6.122.69.1.1
        hwSecSessStatEntry OBJECT IDENTIFIER ::= { hwSecSessStatTable 1 }        
         
        -- 1.3.6.1.4.1.2011.6.122.69.1.1.1
        hwSecCurrSessThreshold OBJECT-TYPE
            SYNTAX Integer32
            MAX-ACCESS read-only
            STATUS current
            DESCRIPTION
                "
                threshold for concurrent sessions
                "
            ::= { hwSecSessStatEntry 1 }
        
        -- 1.3.6.1.4.1.2011.6.122.69.1.1.2
        hwSecCurrSessNum OBJECT-TYPE
            SYNTAX Integer32
            MAX-ACCESS read-only    
            STATUS current
            DESCRIPTION
                "
                number of concurrent sessions
                "
            ::= { hwSecSessStatEntry 2 }
        
        -- 1.3.6.1.4.1.2011.6.122.69.1.1.3
        hwSecConSessThreshold OBJECT-TYPE
            SYNTAX Integer32
            MAX-ACCESS read-only
            STATUS current
            DESCRIPTION
                "
                threshold for new sessions
                "
            ::= { hwSecSessStatEntry 3 } 
            
        -- 1.3.6.1.4.1.2011.6.122.69.1.1.4
        hwSecConSessNum OBJECT-TYPE
            SYNTAX Integer32
            MAX-ACCESS read-only
            STATUS current
            DESCRIPTION
                "
                number of new sessions
                "
            ::= { hwSecSessStatEntry 4 }

         -- 1.3.6.1.4.1.2011.6.122.69.1.1.5
        hwSecCurrSessThresholdRatio OBJECT-TYPE
            SYNTAX Integer32
            MAX-ACCESS read-only
            STATUS current
            DESCRIPTION
                "
                threshold ratio for concurrent sessions 
                "
            ::= { hwSecSessStatEntry 5 }
        
        -- 1.3.6.1.4.1.2011.6.122.69.1.1.6
        hwSecConSessThresholdRatio OBJECT-TYPE
            SYNTAX Integer32
            MAX-ACCESS read-only    
            STATUS current
            DESCRIPTION
                "
                threshold ratio of new sessions
                "
            ::= { hwSecSessStatEntry 6 }
        
        -- 1.3.6.1.4.1.2011.6.122.69.1.1.7
        hwSecCurrSessNumUsage OBJECT-TYPE
            SYNTAX Integer32
            MAX-ACCESS read-only
            STATUS current
            DESCRIPTION
                "
                usage for current sessions
                "
            ::= { hwSecSessStatEntry 7 } 
            
        -- 1.3.6.1.4.1.2011.6.122.69.1.1.8
        hwSecConSessNumUsage OBJECT-TYPE
            SYNTAX Integer32
            MAX-ACCESS read-only
            STATUS current
            DESCRIPTION
                "
                usage  of new sessions
                "
            ::= { hwSecSessStatEntry 8 }
        
        -- 1.3.6.1.4.1.2011.6.122.69.1.1.9
        hwSecCurrIpv6SessNum OBJECT-TYPE
            SYNTAX Counter64
            MAX-ACCESS read-only    
            STATUS current
            DESCRIPTION
                "
                number of concurrent IPv6 sessions
                "
            ::= { hwSecSessStatEntry 9 }
		
         -- 1.3.6.1.4.1.2011.6.122.69.1.1.10
        hwSecConIpv6SessNum OBJECT-TYPE
            SYNTAX Counter64
            MAX-ACCESS read-only
            STATUS current
            DESCRIPTION
                "
                number of new IPv6 sessions
                "
            ::= { hwSecSessStatEntry 10 }

    END

--
-- HUAWEI-SECURITY-SESSION-STAT-MIB
--
