RC-MPLS-TE-MIB DEFINITIONS ::= BEGIN

IMPORTS
    OBJECT-TYPE, MODULE-IDENTITY, Unsigned32, IpAddress  
            FROM SNMPv2-SMI
    MacAddress, DisplayString, RowStatus
            FROM SNMPv2-TC   
    rc 
            FROM RC-SMI;  

rcMplsTeMIB MODULE-IDENTITY
 			    LAST-UPDATED
				"201212110000Z"
				ORGANIZATION
				""
				CONTACT-INFO
				" "
				DESCRIPTION
				""
				REVISION
				"201212110000Z" 
				DESCRIPTION
				""
                ::= { rc 1}	  
 
   -- traps
   rcMplsTeNotifications 			  OBJECT IDENTIFIER ::= { rcMplsTeMIB 0 }
   -- conformance
   rcMplsTeConformance                OBJECT IDENTIFIER ::= { rcMplsTeMIB 9 }
     
--*************************************************************************
--  rcMplsTeNotifications
--*************************************************************************  
   rcMplsLspUp NOTIFICATION-TYPE
      OBJECTS     {
         rcMplsTunnelOperStatus
      }
      STATUS      current
      DESCRIPTION
           "This notification is generated when a
		    MplsTunnelOperStatus object for one of the
			LSPs is about to leave the down state
			and transition into up state."
      ::= { rcMplsTeNotifications 1 }

   rcMplsLspDown NOTIFICATION-TYPE
      OBJECTS     {
         rcMplsTunnelOperStatus
      }
      STATUS      current
      DESCRIPTION
           "This notification is generated when a
			MplsTunnelOperStatus object for one of the
			LSPs is about to leave the up state
			and transition into down state."
      ::= { rcMplsTeNotifications 2 }

    rcMplsTeGroups
        OBJECT IDENTIFIER ::= { rcMplsTeConformance 1 }
   
--*************************************************************************
--  rcMplsTETunnelCfgTable
--*************************************************************************   
	rcMplsTETunnelCfgTable OBJECT-TYPE
		SYNTAX      SEQUENCE OF RcMplsTETunnelCfgEntry
		MAX-ACCESS  not-accessible
		STATUS      current
		DESCRIPTION
				""
		::= { rcMplsTeMIB 1 }
 
   rcMplsTETunnelCfgEntry  OBJECT-TYPE
      SYNTAX        RcMplsTETunnelCfgEntry
      MAX-ACCESS    not-accessible
      STATUS        current
      DESCRIPTION
           "An entry in this table represents an MPLS tunnel.
			An entry can be created by a network administrator
			or by an SNMP agent as instructed by an MPLS
			signalling protocol. Whenever a new entry is
			created with mplsTETunnelIsIf set to true(1), then a
			corresponding entry is created in ifTable as well
			(see RFC 2863). The ifType of this entry is
		    mplsTETunnel(150).A tunnel entry needs to be 
			uniquely identified across a MPLS network. 
			Indices mplsTETunnelIndex and mplsTETunnelInstance 
			uniquely identify a tunnel on the LSR originating 
			the tunnel. To uniquely identify a tunnel across 
			an MPLS network requires index mplsTETunnelIngressLSRId.
			The last index mplsTETunnelEgressLSRId is useful in 
			identifying all instances of a tunnel that terminate 
			on the same egress LSR."
      INDEX {
         rcMplsTETunnelCfgTunnelID
      }
      ::= { rcMplsTETunnelCfgTable 1 }

    RcMplsTETunnelCfgEntry ::= SEQUENCE {
         rcMplsTETunnelCfgTunnelID           Unsigned32,
         rcMplsTETunnelCfgEgressLSRId        IpAddress,
         rcMplsTETunnelCfgSetupPrio          Integer32,
         rcMplsTETunnelCfgHoldingPrio        Integer32,
         rcMplsTETunnelCfgRecordRoute        INTEGER,
         rcMplsTETunnelCfgBandwidth          Unsigned32,
         rcMplsTETunnelCfgExplicitPathName   DisplayString,
		 rcMplsTETunnelCfgExplicitPathID     Unsigned32,
		 rcMplsTETunnelCfgHSB                INTEGER,
		 rcMplsTETunnelCfgHSBExplicitPathName  DisplayString,
		 rcMplsTETunnelCfgHSBExplicitPathID  Unsigned32,
		 rcMplsTunnelOperStatus              INTEGER,
		 rcMplsTETunnelCfgRowSta             RowStatus

      }

	rcMplsTETunnelCfgTunnelID OBJECT-TYPE
      SYNTAX        Unsigned32(1..4000)
      MAX-ACCESS    not-accessible
      STATUS        current
      DESCRIPTION
           "Uniquely identifies a set of tunnel instances
			between a pair of ingress and egress LSRs.
			Managers should obtain new values for row
			creation in this table by reading
			mplsTETunnelIndexNext. When
			the MPLS signalling protocol is rsvp(2) this value
		    SHOULD be equal to the value signaled in the
			Tunnel Id of the Session object. "
      ::= { rcMplsTETunnelCfgEntry 1 }
	 
	rcMplsTETunnelCfgEgressLSRId OBJECT-TYPE
      SYNTAX        IpAddress
      MAX-ACCESS    read-create
      STATUS        current
      DESCRIPTION
           "Identity of the egress LSR associated with this
			tunnel instance. "
      ::= { rcMplsTETunnelCfgEntry 2 }

	rcMplsTETunnelCfgSetupPrio OBJECT-TYPE
      SYNTAX        Integer32(0..7)
      MAX-ACCESS    read-create
      STATUS        current
      DESCRIPTION
           "Indicates the setup priority of this tunnel. "
      ::= { rcMplsTETunnelCfgEntry 3 }

	rcMplsTETunnelCfgHoldingPrio OBJECT-TYPE
      SYNTAX        Integer32(0..7)
      MAX-ACCESS    read-create
      STATUS        current
      DESCRIPTION
           "Indicates the holding priority for this tunnel. "
      ::= { rcMplsTETunnelCfgEntry 4 }	  

	rcMplsTETunnelCfgRecordRoute OBJECT-TYPE
      SYNTAX        INTEGER { false(0), true(1) }
      MAX-ACCESS    read-create
      STATUS        current
      DESCRIPTION
           "If this object is true, then it enables the RecordRoute. "
      ::= { rcMplsTETunnelCfgEntry 5 }		  

	rcMplsTETunnelCfgBandwidth OBJECT-TYPE
      SYNTAX        Unsigned32
      MAX-ACCESS    read-create
      STATUS        current
      DESCRIPTION
           "The bandwidth of this tunnel. "
      ::= { rcMplsTETunnelCfgEntry 6 }		

	rcMplsTETunnelCfgExplicitPathName OBJECT-TYPE
      SYNTAX        DisplayString(SIZE(0..129))
      MAX-ACCESS    read-create
      STATUS        current
      DESCRIPTION
           "The explicit path name of the tunnel master lsp used. "
      ::= { rcMplsTETunnelCfgEntry 7 }	
	
	rcMplsTETunnelCfgExplicitPathID OBJECT-TYPE
      SYNTAX        Unsigned32(1..65535)
      MAX-ACCESS    read-create
      STATUS        current
      DESCRIPTION
           "The explicit path id of the tunnel master lsp used."
      ::= { rcMplsTETunnelCfgEntry 8 }		
	  
	rcMplsTETunnelCfgHSB OBJECT-TYPE
      SYNTAX        INTEGER {false(0),true(1)}
      MAX-ACCESS    read-create
      STATUS        current
      DESCRIPTION
           "If this object is true, then it enables the hot standby."
      ::= { rcMplsTETunnelCfgEntry 9 }	
	  
	rcMplsTETunnelCfgHSBExplicitPathName OBJECT-TYPE
      SYNTAX        DisplayString(SIZE(0..129))
      MAX-ACCESS    read-create
      STATUS        current
      DESCRIPTION
           "The explicit path name of the tunnel hot standby lsp used."
      ::= { rcMplsTETunnelCfgEntry 10 }	
	  
	rcMplsTETunnelCfgHSBExplicitPathID OBJECT-TYPE
      SYNTAX        Unsigned32(1..65535)
      MAX-ACCESS    read-create
      STATUS        current
      DESCRIPTION
           "The explicit path id of the tunnel hot standby lsp used."
      ::= { rcMplsTETunnelCfgEntry 11 }	
	  
	rcMplsTETunnelCfgRowSta OBJECT-TYPE
      SYNTAX        RowStatus
      MAX-ACCESS    read-create
      STATUS        current
      DESCRIPTION
           "This variable is used to create, modify, and/or
			delete a row in this table."
      ::= { rcMplsTETunnelCfgEntry 12 }	

    rcMplsTunnelOperStatus OBJECT-TYPE
        SYNTAX      INTEGER {
            -- ready to pass packets
            up(1),
            down(2),
            -- in some test mode
            testing(3),
            -- status cannot be determined
            unknown(4),
            dormant(5),
            -- some component is missing
            notPresent(6),
            -- down due to the state of
            -- lower layer interfaces
            lowerLayerDown(7)
            }
        MAX-ACCESS     read-only
        STATUS          current
        DESCRIPTION
            "Indicates the actual operational status of this
            tunnel, which is typically but not limited to, a
            function of the state of individual segments of
            this tunnel."
        ::= { rcMplsTETunnelCfgEntry 13 }	  
	  
--*************************************************************************
--  rcMplsTEPathOptCfgTable
--*************************************************************************   
	rcMplsTEPathOptCfgTable OBJECT-TYPE
		SYNTAX      SEQUENCE OF RcMplsTEPathOptCfgEntry
		MAX-ACCESS  not-accessible
		STATUS      current
		DESCRIPTION
				""
		::= { rcMplsTeMIB 2 }
 
   rcMplsTEPathOptCfgEntry  OBJECT-TYPE
      SYNTAX        RcMplsTEPathOptCfgEntry
      MAX-ACCESS    not-accessible
      STATUS        current
      DESCRIPTION
           " "
      INDEX {
         rcMplsTEPathOptCfgTunnelID,
		 rcMplsTEPathOptCfgNumber
      }
      ::= { rcMplsTEPathOptCfgTable 1 }

    RcMplsTEPathOptCfgEntry ::= SEQUENCE {
         rcMplsTEPathOptCfgTunnelID           Unsigned32,
         rcMplsTEPathOptCfgNumber        	  Unsigned32,
         rcMplsTEPathOptCfgPathType           INTEGER,
         rcMplsTEPathOptCfgExpPathName        DisplayString,
         rcMplsTEPathOptCfgExpPathID          Unsigned32,
         rcMplsTEPathOptCfgRowSta          	  RowStatus

      }
	  
	rcMplsTEPathOptCfgTunnelID OBJECT-TYPE
      SYNTAX        Unsigned32(1..4000)
      MAX-ACCESS    not-accessible
      STATUS        current
      DESCRIPTION
           "The index of path option which equals to tunnel id."
      ::= { rcMplsTEPathOptCfgEntry 1 }	

	rcMplsTEPathOptCfgNumber OBJECT-TYPE
      SYNTAX        Unsigned32(1)
      MAX-ACCESS    not-accessible
      STATUS        current
      DESCRIPTION
           "Secondary index whitch identifies the configure value of path option ."
      ::= { rcMplsTEPathOptCfgEntry 2 }	
	  
	rcMplsTEPathOptCfgPathType OBJECT-TYPE
      SYNTAX        INTEGER {dynamic(1),explicitId(2),explicitName(3)}
      MAX-ACCESS    read-create
      STATUS        current
      DESCRIPTION
           "If this value is dynamic ,indicates that user only specify the source and destination of
			the path and the CSPF will calculate the remainder of the path. If this value is 
			explicitId or explicitName, the user specify the entire path for the tunnel . This path may contain
			strict or loose hops. Each hop along a specific path SHOULD have this object set to the same value."
      ::= { rcMplsTEPathOptCfgEntry 3 }	

	rcMplsTEPathOptCfgExpPathName OBJECT-TYPE
      SYNTAX       DisplayString(SIZE(1..129))
      MAX-ACCESS    read-create
      STATUS        current
      DESCRIPTION
           "The name of Path Option.If the type of Path Option is dynamic,then this value is '1';
			if the type is explicitId or explicitName,then this value is a number or a string."
      ::= { rcMplsTEPathOptCfgEntry 4 }		 

	rcMplsTEPathOptCfgExpPathID OBJECT-TYPE
      SYNTAX       Unsigned32(1..65536)
      MAX-ACCESS   read-create
      STATUS        current
      DESCRIPTION
           "The name of Path Option.If the type of Path Option is dynamic,then this value is '1';
			if the type is explicitId or explicitName,then this value is a number or a string."
      ::= { rcMplsTEPathOptCfgEntry 5 }	

	rcMplsTEPathOptCfgRowSta OBJECT-TYPE
      SYNTAX       RowStatus
      MAX-ACCESS   read-create
      STATUS        current
      DESCRIPTION
           "This variable is used to create, modify, and/or
			delete a row in this table. "
      ::= { rcMplsTEPathOptCfgEntry 6 }		
	  
	  
--*************************************************************************
--  rcMplsTEExplicitPathNameCfgTable
--*************************************************************************   
	rcMplsTEExplicitPathNameCfgTable OBJECT-TYPE
		SYNTAX      SEQUENCE OF RcMplsTEExplicitPathNameCfgEntry
		MAX-ACCESS  not-accessible
		STATUS      current
		DESCRIPTION
				"Explicit-path table is user configured,the user should specify the
				 entire path for the tunnel to take. This path may contain strict or 
				 loose hops. Each hop along a specific path SHOULD have this object 
				 set to the same value."
		::= { rcMplsTeMIB 3 }
 
   rcMplsTEExplicitPathNameCfgEntry  OBJECT-TYPE
      SYNTAX        RcMplsTEExplicitPathNameCfgEntry
      MAX-ACCESS    not-accessible
      STATUS        current
      DESCRIPTION
           "Explicit-path table entry. "
      INDEX {
         rcMplsTEExplicitPathNameCfgName
      }
      ::= { rcMplsTEExplicitPathNameCfgTable 1 }

    RcMplsTEExplicitPathNameCfgEntry ::= SEQUENCE {
         rcMplsTEExplicitPathNameCfgName           DisplayString,
         rcMplsTEExplicitPathNameCfgRowSta         RowStatus

      }
	  
	rcMplsTEExplicitPathNameCfgName OBJECT-TYPE
      SYNTAX        DisplayString(SIZE(1..129))
      MAX-ACCESS    not-accessible
      STATUS        current
      DESCRIPTION
           "The index of Explicit-path table.The explicit name is a string."
      ::= { rcMplsTEExplicitPathNameCfgEntry 1 }	

	rcMplsTEExplicitPathNameCfgRowSta OBJECT-TYPE
      SYNTAX       RowStatus
      MAX-ACCESS   read-create
      STATUS        current
      DESCRIPTION
           "This variable is used to create, modify, and/or
			delete a row in this table. "
      ::= { rcMplsTEExplicitPathNameCfgEntry 2 }		

--*************************************************************************
--  rcMplsTEExplicitPathIDCfgTable
--*************************************************************************   
	rcMplsTEExplicitPathIDCfgTable OBJECT-TYPE
		SYNTAX      SEQUENCE OF RcMplsTEExplicitPathIDCfgEntry
		MAX-ACCESS  not-accessible
		STATUS      current
		DESCRIPTION
				"Explicit-path table is user configured,the user should specify the
				 entire path for the tunnel to take. This path may contain strict or 
				loose hops. Each hop along a specific path SHOULD have this object 
				set to the same value."
		::= { rcMplsTeMIB 4 }
 
   rcMplsTEExplicitPathIDCfgEntry  OBJECT-TYPE
      SYNTAX        RcMplsTEExplicitPathIDCfgEntry
      MAX-ACCESS    not-accessible
      STATUS        current
      DESCRIPTION
           "Explicit-path table entry. "
      INDEX {
         rcMplsTEExplicitPathIDCfgIdentifer
      }
      ::= { rcMplsTEExplicitPathIDCfgTable 1 }

    RcMplsTEExplicitPathIDCfgEntry ::= SEQUENCE {
         rcMplsTEExplicitPathIDCfgIdentifer      Unsigned32,
         rcMplsTEExplicitPathIDCfgRowSta         RowStatus

      }
	  
	rcMplsTEExplicitPathIDCfgIdentifer OBJECT-TYPE
      SYNTAX        Unsigned32(1..65535)
      MAX-ACCESS    not-accessible
      STATUS        current
      DESCRIPTION
           "The index of Explicit-path table.The explicitId is a number."
      ::= { rcMplsTEExplicitPathIDCfgEntry 1 }	

	rcMplsTEExplicitPathIDCfgRowSta OBJECT-TYPE
      SYNTAX       RowStatus
      MAX-ACCESS   read-create
      STATUS        current
      DESCRIPTION
           "This variable is used to create, modify, and/or
			delete a row in this table. "
      ::= { rcMplsTEExplicitPathIDCfgEntry 2 }		

--*************************************************************************
--  rcMplsTEExplicitRouteNameCfgTable
--*************************************************************************   
	rcMplsTEExplicitRouteNameCfgTable OBJECT-TYPE
		SYNTAX      SEQUENCE OF RcMplsTEExplicitRouteNameCfgEntry
		MAX-ACCESS  not-accessible
		STATUS      current
		DESCRIPTION
				""
		::= { rcMplsTeMIB 5 }
 
   rcMplsTEExplicitRouteNameCfgEntry  OBJECT-TYPE
      SYNTAX        RcMplsTEExplicitRouteNameCfgEntry
      MAX-ACCESS    not-accessible
      STATUS        current
      DESCRIPTION
           " "
      INDEX {
         rcMplsTEExplicitRouteNameCfgName,
		 rcMplsTEExplicitRouteNameCfgIndex
      }
      ::= { rcMplsTEExplicitRouteNameCfgTable 1 }

    RcMplsTEExplicitRouteNameCfgEntry ::= SEQUENCE {
         rcMplsTEExplicitRouteNameCfgName          DisplayString,
		 rcMplsTEExplicitRouteNameCfgIndex         Unsigned32,
		 rcMplsTEExplicitRouteNameCfgNextIP        IpAddress,
		 rcMplsTEExplicitRouteNameCfgHopType       INTEGER,
		 rcMplsTEExplicitRouteNameCfgHopAttribute  INTEGER,		 
         rcMplsTEExplicitRouteNameCfgRowSta        RowStatus

      }
	  
	rcMplsTEExplicitRouteNameCfgName OBJECT-TYPE
      SYNTAX        DisplayString(SIZE(1..129))
      MAX-ACCESS    not-accessible
      STATUS        current
      DESCRIPTION
           "The primary index of Explicit-path route table.The explicit name is a string."
      ::= { rcMplsTEExplicitRouteNameCfgEntry 1 }	

	rcMplsTEExplicitRouteNameCfgIndex OBJECT-TYPE
      SYNTAX       Unsigned32(1..96)
      MAX-ACCESS   not-accessible
      STATUS       current
      DESCRIPTION
           "Secondary index of Explicit-path route table.IP addr index. "
      ::= { rcMplsTEExplicitRouteNameCfgEntry 2 }		  
	
	rcMplsTEExplicitRouteNameCfgNextIP OBJECT-TYPE
      SYNTAX       IpAddress
      MAX-ACCESS   read-create
      STATUS       current
      DESCRIPTION
           "Identify the next hop IP address,This field is a displayable string in the
			format of 'XXX.XXX.XXX.XXX,' repeated.Example:1.1.1.1,1.1.1.2."
      ::= { rcMplsTEExplicitRouteNameCfgEntry 3 }	
	  
	rcMplsTEExplicitRouteNameCfgHopType OBJECT-TYPE
      SYNTAX       INTEGER{include(1),exclude(2)}
      MAX-ACCESS   read-create
      STATUS       current
      DESCRIPTION
           "The hop type. "
      ::= { rcMplsTEExplicitRouteNameCfgEntry 4 }		 

	rcMplsTEExplicitRouteNameCfgHopAttribute OBJECT-TYPE
      SYNTAX       INTEGER{strict(1),loose(2),interface(3),routerid(4)}
      MAX-ACCESS   read-create
      STATUS       current
      DESCRIPTION
           "The hop router attribute. "
      ::= { rcMplsTEExplicitRouteNameCfgEntry 5 }			

	rcMplsTEExplicitRouteNameCfgRowSta OBJECT-TYPE
      SYNTAX       RowStatus
      MAX-ACCESS   read-create
      STATUS       current
      DESCRIPTION
           "This variable is used to create, modify, and/or
			delete a row in this table."
      ::= { rcMplsTEExplicitRouteNameCfgEntry 6 }	
	  
--*************************************************************************
--  rcMplsTEExplicitRouteIDCfgTable
--*************************************************************************   
	rcMplsTEExplicitRouteIDCfgTable OBJECT-TYPE
		SYNTAX      SEQUENCE OF RcMplsTEExplicitRouteIDCfgEntry
		MAX-ACCESS  not-accessible
		STATUS      current
		DESCRIPTION
				""
		::= { rcMplsTeMIB 6 }
 
   rcMplsTEExplicitRouteIDCfgEntry  OBJECT-TYPE
      SYNTAX        RcMplsTEExplicitRouteIDCfgEntry
      MAX-ACCESS    not-accessible
      STATUS        current
      DESCRIPTION
           " "
      INDEX {
         rcMplsTEExplicitRouteIDCfgIdentifer,
		 rcMplsTEExplicitRouteIDCfgIndex
      }
      ::= { rcMplsTEExplicitRouteIDCfgTable 1 }

    RcMplsTEExplicitRouteIDCfgEntry ::= SEQUENCE {
         rcMplsTEExplicitRouteIDCfgIdentifer       Unsigned32,
		 rcMplsTEExplicitRouteIDCfgIndex           Unsigned32,
		 rcMplsTEExplicitRouteIDCfgNextIP          IpAddress,
		 rcMplsTEExplicitRouteIDCfgHopType         INTEGER,
		 rcMplsTEExplicitRouteIDCfgHopAttribute    INTEGER,		 
         rcMplsTEExplicitRouteIDCfgRowSta          RowStatus

      }
	  
	rcMplsTEExplicitRouteIDCfgIdentifer OBJECT-TYPE
      SYNTAX        Unsigned32(1..65535)
      MAX-ACCESS    not-accessible
      STATUS        current
      DESCRIPTION
           "The primary index of Explicit-path route table.The explicitId is a number."
      ::= { rcMplsTEExplicitRouteIDCfgEntry 1 }	

	rcMplsTEExplicitRouteIDCfgIndex OBJECT-TYPE
      SYNTAX       Unsigned32(1..96)
      MAX-ACCESS   not-accessible
      STATUS       current
      DESCRIPTION
           "Secondary index of Explicit-path route table.IP addr index. "
      ::= { rcMplsTEExplicitRouteIDCfgEntry 2 }		  
	
	rcMplsTEExplicitRouteIDCfgNextIP OBJECT-TYPE
      SYNTAX       IpAddress
      MAX-ACCESS   read-create
      STATUS       current
      DESCRIPTION
           "Identify the next hop IP address,This field is a displayable string in the
			format of 'XXX.XXX.XXX.XXX,' repeated.Example:1.1.1.1,1.1.1.2."
      ::= { rcMplsTEExplicitRouteIDCfgEntry 3 }	
	  
	rcMplsTEExplicitRouteIDCfgHopType OBJECT-TYPE
      SYNTAX       INTEGER{include(1),exclude(2)}
      MAX-ACCESS   read-create
      STATUS       current
      DESCRIPTION
           "The hop type. "
      ::= { rcMplsTEExplicitRouteIDCfgEntry 4 }		 

	rcMplsTEExplicitRouteIDCfgHopAttribute OBJECT-TYPE
      SYNTAX       INTEGER{strict(1),loose(2),interface(3),routerid(4)}
      MAX-ACCESS   read-create
      STATUS       current
      DESCRIPTION
           "The hop router attribute. "
      ::= { rcMplsTEExplicitRouteIDCfgEntry 5 }			

	rcMplsTEExplicitRouteIDCfgRowSta OBJECT-TYPE
      SYNTAX       RowStatus
      MAX-ACCESS   read-create
      STATUS       current
      DESCRIPTION
           "This variable is used to create, modify, and/or
			delete a row in this table."
      ::= { rcMplsTEExplicitRouteIDCfgEntry 6 }	

--*************************************************************************
--  rcMplsTEHotStandbyCfgTable
--*************************************************************************   
	rcMplsTEHotStandbyCfgTable OBJECT-TYPE
		SYNTAX      SEQUENCE OF RcMplsTEHotStandbyCfgEntry
		MAX-ACCESS  not-accessible
		STATUS      current
		DESCRIPTION
				""
		::= { rcMplsTeMIB 7 }
 
   rcMplsTEHotStandbyCfgEntry  OBJECT-TYPE
      SYNTAX        RcMplsTEHotStandbyCfgEntry
      MAX-ACCESS    not-accessible
      STATUS        current
      DESCRIPTION
           " "
      INDEX {
         rcMplsTEHotStandbyCfgTunnelID,
		 rcMplsTEHotStandbyCfgProtOptNo
      }
      ::= { rcMplsTEHotStandbyCfgTable 1 }

    RcMplsTEHotStandbyCfgEntry ::= SEQUENCE {
         rcMplsTEHotStandbyCfgTunnelID       	Unsigned32,
		 rcMplsTEHotStandbyCfgProtOptNo         Unsigned32,
		 rcMplsTEHotStandbyCfgPathType          INTEGER,
		 rcMplsTEHotStandbyCfgExpPathName       DisplayString,
		 rcMplsTEHotStandbyCfgExpPathID    		Unsigned32,		 
         rcMplsTEHotStandbyCfgRowSta          	RowStatus

      }
	  
	rcMplsTEHotStandbyCfgTunnelID OBJECT-TYPE
      SYNTAX        Unsigned32(1..4000)
      MAX-ACCESS    not-accessible
      STATUS        current
      DESCRIPTION
           "The primary index of path option which equals to tunnel id."
      ::= { rcMplsTEHotStandbyCfgEntry 1 }	

	rcMplsTEHotStandbyCfgProtOptNo OBJECT-TYPE
      SYNTAX       Unsigned32(1)
      MAX-ACCESS   not-accessible
      STATUS       current
      DESCRIPTION
           "The secondary index which identifies the configure value of protected path option.Its value always is 1. "
      ::= { rcMplsTEHotStandbyCfgEntry 2 }		  
	
	rcMplsTEHotStandbyCfgPathType OBJECT-TYPE
      SYNTAX       INTEGER {dynamic(1),explicitId(2),explicitName(3)}
      MAX-ACCESS   read-create
      STATUS       current
      DESCRIPTION
           "If this value is dynamic ,indicates that user only specify the source and destination of
			the path and the CSPF will calculate the remainder of the path. If this value is 
			explicitId or explicitName, the user specify the entire path for the tunnel . This path may contain
			strict or loose hops. Each hop along a specific path SHOULD have this object set to the same value. "
      ::= { rcMplsTEHotStandbyCfgEntry 3 }	
	  
	rcMplsTEHotStandbyCfgExpPathName OBJECT-TYPE
      SYNTAX       DisplayString(SIZE(1..129))
      MAX-ACCESS   read-create
      STATUS       current
      DESCRIPTION
           "The name of explicit path for protecting the master path. "
      ::= { rcMplsTEHotStandbyCfgEntry 4 }		 

	rcMplsTEHotStandbyCfgExpPathID OBJECT-TYPE
      SYNTAX       Unsigned32(1..65535)
      MAX-ACCESS   read-create
      STATUS       current
      DESCRIPTION
           "The ID of explicit path for protecting the master path. "
      ::= { rcMplsTEHotStandbyCfgEntry 5 }			

	rcMplsTEHotStandbyCfgRowSta OBJECT-TYPE
      SYNTAX       RowStatus
      MAX-ACCESS   read-create
      STATUS       current
      DESCRIPTION
           "This variable is used to create, modify, and/or
			delete a row in this table."
      ::= { rcMplsTEHotStandbyCfgEntry 6 }	
	  
--*************************************************************************
--  rcMplsTETunnelGroupCfgTable
--*************************************************************************   
	rcMplsTETunnelGroupCfgTable OBJECT-TYPE
		SYNTAX      SEQUENCE OF RcMplsTETunnelGroupCfgEntry
		MAX-ACCESS  not-accessible
		STATUS      current
		DESCRIPTION
				""
		::= { rcMplsTeMIB 8 }
 
   rcMplsTETunnelGroupCfgEntry  OBJECT-TYPE
      SYNTAX        RcMplsTETunnelGroupCfgEntry
      MAX-ACCESS    not-accessible
      STATUS        current
      DESCRIPTION
           " "
      INDEX {
         rcMplsTETunnelGroupCfgPrimaryTunnelID
      }
      ::= { rcMplsTETunnelGroupCfgTable 1 }

    RcMplsTETunnelGroupCfgEntry ::= SEQUENCE {
         rcMplsTETunnelGroupCfgPrimaryTunnelID           Unsigned32,
		 rcMplsTETunnelGroupCfgSecondaryTunnelID         Unsigned32,
         rcMplsTETunnelGroupCfgRowSta         			 RowStatus

      }
	  
	rcMplsTETunnelGroupCfgPrimaryTunnelID OBJECT-TYPE
      SYNTAX        Unsigned32(1..4000)
      MAX-ACCESS    not-accessible
      STATUS        current
      DESCRIPTION
           "The index of tunnel group table which equals to primary tunnel id."
      ::= { rcMplsTETunnelGroupCfgEntry 1 }	

	rcMplsTETunnelGroupCfgSecondaryTunnelID OBJECT-TYPE
      SYNTAX        Unsigned32(1..4000)
      MAX-ACCESS    read-create
      STATUS        current
      DESCRIPTION
           "The secondary tunnel ID."
      ::= { rcMplsTETunnelGroupCfgEntry 2 }		  

	rcMplsTETunnelGroupCfgRowSta OBJECT-TYPE
      SYNTAX       RowStatus
      MAX-ACCESS   read-create
      STATUS       current
      DESCRIPTION
           "This variable is used to create, modify, and/or
			delete a row in this table. "
      ::= { rcMplsTETunnelGroupCfgEntry 3 }

    rcMplsTeNotificationGroup NOTIFICATION-GROUP
        NOTIFICATIONS {
			rcMplsLspUp,
			rcMplsLspDown
            }
        STATUS  current
        DESCRIPTION
            "Set of notifications implemented in this module.
            None is mandatory."
        ::= { rcMplsTeGroups 8 }	  
	  
END
