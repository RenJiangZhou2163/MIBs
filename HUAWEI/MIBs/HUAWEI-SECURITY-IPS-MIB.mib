--
-- HUAWEI-SECURITY-IPS-MIB.mib
-- MIB generated by MG-SOFT Visual MIB Builder Version 6.0  Build 88
-- Wednesday, April 27, 2016 at 10:12:44
--

--  HUAWEI-SECURITY-IPS-MIB3.mib
-- MIB generated by MG-SOFT Visual MIB Builder Version 6.0  Build 88
-- Wednesday, December 02, 2015 at 12:07:39
-- 
--   =================================================================
-- Copyright (C) 2016 by  HUAWEI TECHNOLOGIES. All rights reserved
-- 
-- Description:
-- Reference:
-- Version: V1.01
-- History:
-- 2011-01-12,<contents>
-- =================================================================

	HUAWEI-SECURITY-IPS-MIB DEFINITIONS ::= BEGIN
 
		IMPORTS
			enterprises			
				FROM RFC1155-SMI			
			OBJECT-GROUP, MODULE-COMPLIANCE, NOTIFICATION-GROUP			
				FROM SNMPv2-CONF			
			Integer32, OBJECT-TYPE, MODULE-IDENTITY, NOTIFICATION-TYPE			
				FROM SNMPv2-SMI;
	
	
		-- 1.3.6.1.4.1.2011.6.122.43
		hwSecIPS MODULE-IDENTITY 
			LAST-UPDATED "201612200900Z"		-- December 20, 2016 at 09:00 GMT
			ORGANIZATION 
				"Huawei Technologies Co.,Ltd."
			CONTACT-INFO 
				"
				Huawei Industrial Base Bantian, Longgang Shenzhen 518129 People's Republic of China Website: http://www.huawei.com Email: support@huawei.com
				"  
            
                        DESCRIPTION 
				"
				V1.01  Add IPS card Pulled Out Event Alert.
				"
                        REVISION "201612200900Z"		-- December 20, 2016 at 09:00 GMT   
		    			
			DESCRIPTION 
				"
				V1.00
				The HUAWEI-SECSTAT-MIB contains objects to manage the security statistics for firewall product.
				"
			REVISION "201604260900Z"		-- April 26, 2016 at 09:00 GMT
			DESCRIPTION 
				"1.00"
			::= { hwSecurity 43 }

		
	
--
-- Node definitions
--
	
--  1.3.6.1.4.1.2011.6.122.43
-- April 10, 2003 at 09:00 GMT
-- 
-- Node definitions
-- 
--  Node definitions
-- 
-- 1.3.6.1.4.1.2011
-- 1.3.6.1.4.1.2011
		-- 1.3.6.1.4.1.2011
		huawei OBJECT IDENTIFIER ::= { enterprises 2011 }

		
--   1.3.6.1.4.1.2011.6
-- 1.3.6.1.4.1.2011.6
		-- 1.3.6.1.4.1.2011.6
		huaweiUtility OBJECT IDENTIFIER ::= { huawei 6 }

		
--   1.3.6.1.4.1.2011.6.122
-- 1.3.6.1.4.1.2011.6.122
		-- 1.3.6.1.4.1.2011.6.122
		hwSecurity OBJECT IDENTIFIER ::= { huaweiUtility 122 }

		
--   1.3.6.1.4.1.2011.6.122.43
-- hwSecIPS OBJECT IDENTIFIER ::= { hwSecurity 43 }
-- 1.3.6.1.4.1.2011.6.122.43.1
-- 1.3.6.1.4.1.2011.6.122.43.1
		-- 1.3.6.1.4.1.2011.6.122.43.1
		hwSecIpsTraps OBJECT IDENTIFIER ::= { hwSecIPS 1 }

		
--   1.3.6.1.4.1.2011.6.122.43.1.1
-- 1.3.6.1.4.1.2011.6.122.43.1.1
		-- 1.3.6.1.4.1.2011.6.122.43.1.1
		hwSecIpsObjests OBJECT IDENTIFIER ::= { hwSecIpsTraps 1 }

		
--   1.3.6.1.4.1.2011.6.122.43.1.1.1
-- 1.3.6.1.4.1.2011.6.122.43.1.1.3
		-- 1.3.6.1.4.1.2011.6.122.43.1.1.3
		hwSecIpsDetectObjects OBJECT IDENTIFIER ::= { hwSecIpsObjests 3 }

		
--   1.3.6.1.4.1.2011.6.122.43.1.1.3.2
-- 1.3.6.1.4.1.2011.6.122.43.1.1.3.2
		-- 1.3.6.1.4.1.2011.6.122.43.1.1.3.2
		hwSecIpsDetectSrcIp OBJECT-TYPE
			SYNTAX OCTET STRING (SIZE (0..255))
			MAX-ACCESS accessible-for-notify
			STATUS current
			DESCRIPTION
				"
				source IP address
				"
			::= { hwSecIpsDetectObjects 2 }

		
--   1.3.6.1.4.1.2011.6.122.43.1.1.3.3
-- 1.3.6.1.4.1.2011.6.122.43.1.1.3.3
		-- 1.3.6.1.4.1.2011.6.122.43.1.1.3.3
		hwSecIpsDetectDstIp OBJECT-TYPE
			SYNTAX OCTET STRING (SIZE (0..255))
			MAX-ACCESS accessible-for-notify
			STATUS current
			DESCRIPTION
				"
				destination IP address
				"
			::= { hwSecIpsDetectObjects 3 }

		
--   1.3.6.1.4.1.2011.6.122.43.1.1.3.4
-- 1.3.6.1.4.1.2011.6.122.43.1.1.3.4
		-- 1.3.6.1.4.1.2011.6.122.43.1.1.3.4
		hwSecIpsDetectSrcPort OBJECT-TYPE
			SYNTAX Integer32 (0..65535)
			MAX-ACCESS accessible-for-notify
			STATUS current
			DESCRIPTION
				"
				source port
				"
			::= { hwSecIpsDetectObjects 4 }

		
--   1.3.6.1.4.1.2011.6.122.43.1.1.3.5
-- 1.3.6.1.4.1.2011.6.122.43.1.1.3.5
		-- 1.3.6.1.4.1.2011.6.122.43.1.1.3.5
		hwSecIpsDetectDstPort OBJECT-TYPE
			SYNTAX Integer32 (0..65535)
			MAX-ACCESS accessible-for-notify
			STATUS current
			DESCRIPTION
				"
				destination port
				"
			::= { hwSecIpsDetectObjects 5 }

		
--   1.3.6.1.4.1.2011.6.122.43.1.1.3.8
-- 1.3.6.1.4.1.2011.6.122.43.1.1.3.8
		-- 1.3.6.1.4.1.2011.6.122.43.1.1.3.8
		hwSecIpsDetectProtoType OBJECT-TYPE
			SYNTAX OCTET STRING (SIZE (0..255))
			MAX-ACCESS accessible-for-notify
			STATUS current
			DESCRIPTION
				"
				protocol name (type)
				"
			::= { hwSecIpsDetectObjects 8 }

		
--   1.3.6.1.4.1.2011.6.122.43.1.1.3.10
-- 1.3.6.1.4.1.2011.6.122.43.1.1.3.10
		-- 1.3.6.1.4.1.2011.6.122.43.1.1.3.10
		hwSecIpsDetectSignatureName OBJECT-TYPE
			SYNTAX OCTET STRING (SIZE (0..255))
			MAX-ACCESS accessible-for-notify
			STATUS current
			DESCRIPTION
				"
				signature name
				"
			::= { hwSecIpsDetectObjects 10 }

		
--  1.3.6.1.4.1.2011.6.122.43.1.1.3.18
		-- 1.3.6.1.4.1.2011.6.122.43.1.1.3.18
		hwSecIpsDetectTime OBJECT-TYPE
			SYNTAX OCTET STRING (SIZE (1..64))
			MAX-ACCESS accessible-for-notify
			STATUS current
			DESCRIPTION
				"ips detect time."
			::= { hwSecIpsDetectObjects 18 }

		
--   ===============================================
-- definition of traps.      
-- ===============================================
-- 1.3.6.1.4.1.2011.6.122.43.1.2    
-- 1.3.6.1.4.1.2011.6.122.43.1.2
		-- 1.3.6.1.4.1.2011.6.122.43.1.2
		hwSecIpsAlert OBJECT IDENTIFIER ::= { hwSecIpsTraps 2 }

		
--  1.3.6.1.4.1.2011.6.122.43.1.2.8
		-- 1.3.6.1.4.1.2011.6.122.43.1.2.8
		hwSecIpsThreatAlert NOTIFICATION-TYPE
			OBJECTS { hwSecIpsDetectSrcIp, hwSecIpsDetectDstIp, hwSecIpsDetectSrcPort, hwSecIpsDetectDstPort, hwSecIpsDetectProtoType, 
				hwSecIpsDetectSignatureName, hwSecIpsDetectTime }
			STATUS current
			DESCRIPTION 
				"Description."
			::= { hwSecIpsAlert 8 }

		
--  conformance
-- 1.3.6.1.4.1.2011.6.122.43.2
		-- 1.3.6.1.4.1.2011.6.122.43.2
		hwIPSConformance OBJECT IDENTIFIER ::= { hwSecIPS 2 }

		
--  1.3.6.1.4.1.2011.6.122.43.2.1
		-- 1.3.6.1.4.1.2011.6.122.43.2.1
		hwIPSCompliances OBJECT IDENTIFIER ::= { hwIPSConformance 1 }

		
--   this module
-- 1.3.6.1.4.1.2011.6.122.43.2.1.1
-- this module
		-- 1.3.6.1.4.1.2011.6.122.43.2.1.1
		hwIPSCompliance MODULE-COMPLIANCE
			STATUS current
			DESCRIPTION 
				"Compliance statement for agents that provide full support for 
				hwBaseTrapMIB."
			MODULE -- this module
				MANDATORY-GROUPS { hwIPSObjectGroup, hwIPSTrapGroup }
			::= { hwIPSCompliances 1 }

		
--  1.3.6.1.4.1.2011.6.122.43.2.2
		-- 1.3.6.1.4.1.2011.6.122.43.2.2
		hwIPSTrapGroups OBJECT IDENTIFIER ::= { hwIPSConformance 2 }

		
--  1.3.6.1.4.1.2011.6.122.43.2.2.1
		-- 1.3.6.1.4.1.2011.6.122.43.2.2.1
		hwIPSObjectGroup OBJECT-GROUP
			OBJECTS { hwSecIpsDetectSrcIp, hwSecIpsDetectDstIp, hwSecIpsDetectSrcPort, hwSecIpsDetectDstPort, hwSecIpsDetectProtoType, 
				hwSecIpsDetectSignatureName, hwSecIpsDetectTime }
			STATUS current
			DESCRIPTION 
				"Group for ips trap objects."
			::= { hwIPSTrapGroups 1 }

		
--  1.3.6.1.4.1.2011.6.122.43.2.2.2
		-- 1.3.6.1.4.1.2011.6.122.43.2.2.2
		hwIPSTrapGroup NOTIFICATION-GROUP
			NOTIFICATIONS { hwSecIpsThreatAlert }
			STATUS current
			DESCRIPTION 
				"Group for all ips traps."
			::= { hwIPSTrapGroups 2 }        
			
		
--   1.3.6.1.4.1.2011.6.122.43
-- 1.3.6.1.4.1.2011.6.122.43.3
		-- 1.3.6.1.4.1.2011.6.122.43.3
		hwIpsCardEventTraps OBJECT IDENTIFIER ::= { hwSecIPS 3 }
		
--   1.3.6.1.4.1.2011.6.122.43.3.1
-- 1.3.6.1.4.1.2011.6.122.43.3.1
		-- 1.3.6.1.4.1.2011.6.122.43.3.1
		hwIpsCardEventObjects OBJECT IDENTIFIER ::= { hwIpsCardEventTraps 1 }
				
--   1.3.6.1.4.1.2011.6.122.43.3.1.1
-- 1.3.6.1.4.1.2011.6.122.43.3.1.1
		-- 1.3.6.1.4.1.2011.6.122.43.3.1.1
		hwIpsCardSlot OBJECT-TYPE
			SYNTAX Integer32 (0..65535)
			MAX-ACCESS accessible-for-notify
			STATUS current
			DESCRIPTION
				"
				slot number
				"
			::= { hwIpsCardEventObjects 1 }

		
--   1.3.6.1.4.1.2011.6.122.43.3.1.2
-- 1.3.6.1.4.1.2011.6.122.43.3.1.2
		-- 1.3.6.1.4.1.2011.6.122.43.3.1.2
		hwIpsCardCpu OBJECT-TYPE
			SYNTAX Integer32 (0..65535)
			MAX-ACCESS accessible-for-notify
			STATUS current
			DESCRIPTION
				"
				cpu number
				"
			::= { hwIpsCardEventObjects 2 }

		
--   ===============================================
-- definition of traps.      
-- ===============================================
-- 1.3.6.1.4.1.2011.6.122.43.3.2    
-- 1.3.6.1.4.1.2011.6.122.43.3.2
		-- 1.3.6.1.4.1.2011.6.122.43.3.2
		hwIpsCardEventAlert OBJECT IDENTIFIER ::= { hwIpsCardEventTraps 2 }

		
--  1.3.6.1.4.1.2011.6.122.43.3.2.1
		-- 1.3.6.1.4.1.2011.6.122.43.3.2.1
		hwIpsCardPullOutAlert NOTIFICATION-TYPE
			OBJECTS { hwIpsCardSlot, hwIpsCardCpu }
			STATUS current
			DESCRIPTION 
				"ips card pull out alert."
			::= { hwIpsCardEventAlert 1 }
		
	
	END

--
-- HUAWEI-SECURITY-IPS-MIB.mib
--
