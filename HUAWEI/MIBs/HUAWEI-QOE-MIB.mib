--  =====================================================================================
-- Copyright (C) 2019 by  HUAWEI TECHNOLOGIES. All rights reserved.
-- 
-- Description: HUAWEI-QOE-MIB is defined to manage the V8 router QOE features.
--              QOE related SNMP operation and traps shall be defined in this MIB.
--              HUAWEI-MQE-MIB manages V5 QOE features and will not be extended any more.
--              HUAWEI-QOE-MIB and HUAWEI-MQE-MIB do not conflict.                    
-- Reference:
-- Version: V1.07
-- History:
--         v1.00 created by g00385748 2017-09-07
-- =====================================================================================
	HUAWEI-QOE-MIB DEFINITIONS ::= BEGIN
 
		IMPORTS
			hwDatacomm			
				FROM HUAWEI-MIB			
			OBJECT-GROUP, MODULE-COMPLIANCE, NOTIFICATION-GROUP			
				FROM SNMPv2-CONF			
			IpAddress, Integer32, Unsigned32, Gauge32, OBJECT-TYPE, MODULE-IDENTITY, NOTIFICATION-TYPE			
				FROM SNMPv2-SMI;

		-- 1.3.6.1.4.1.2011.5.25.349
		hwQoeMIB MODULE-IDENTITY 
			LAST-UPDATED "201908312130Z"		
			ORGANIZATION 
				"Huawei Technologies Co.,Ltd."
			CONTACT-INFO 
				"Huawei Industrial Base
				Bantian, Longgang
				Shenzhen 518129
				People's Republic of China
				Website: http://www.huawei.com
				Email: support@huawei.com
				"
			DESCRIPTION 
				"Modify 201908312130Z."
		                       REVISION 
				"201908312130Z"
			DESCRIPTION 
				"Modify 201811122130Z."
		                       REVISION 
				"201811122130Z"
			DESCRIPTION 
				"Modify 201806301040Z."
		                       REVISION 
				"201806301040Z"
			DESCRIPTION 
				"Modify 201805031040Z."
		                       REVISION 
				"201805031040Z"
			DESCRIPTION 
				"Modify 201803261153Z."
		                       REVISION 
				"201803261153Z"
			DESCRIPTION 
				"Modify 201709212021Z."
		                       REVISION 
				"201709212021Z"
			DESCRIPTION 
				"The QOE MIB module is defined to manage the QOE features."

			REVISION 
				"201709192021Z"
			DESCRIPTION 
				"The QOE MIB module is defined to manage the QOE features."
			REVISION 
				"201709072021Z"
            DESCRIPTION  
                "V1.00, Inital version."
			::= { hwDatacomm 349 }
	
	
--
-- Node definitions
--

		-- 1.3.6.1.4.1.2011.5.25.349.1
		hwQoeObjects OBJECT IDENTIFIER ::= { hwQoeMIB 1 }
		-- 1.3.6.1.4.1.2011.5.25.349.1.1
		hwQoeScalar OBJECT IDENTIFIER ::= { hwQoeObjects 1 }

		--- EMDI Scalars
		-- 1.3.6.1.4.1.2011.5.25.349.1.1.1
		hwEmdiScalar OBJECT IDENTIFIER ::= { hwQoeScalar 1 }

		-- 1.3.6.1.4.1.2011.5.25.349.1.1.1.1
		hwEmdiChannelName OBJECT-TYPE
			SYNTAX OCTET STRING (SIZE (0..32))
			MAX-ACCESS read-only
			STATUS current
			DESCRIPTION
				"The hwEmdiChannelName is the name of the monitored multicast channel. It uniquely identify the channel."
			::= { hwEmdiScalar 1 }			

		-- 1.3.6.1.4.1.2011.5.25.349.1.1.1.2			
		hwEmdiChannelSourceAddress OBJECT-TYPE
			SYNTAX IpAddress
			MAX-ACCESS read-only
			STATUS current
			DESCRIPTION
				"The hwEmdiChannelSourceAddress is the source address of the monitored multicast channel. It is an IPv4 address."
			::= { hwEmdiScalar 2 }		

		-- 1.3.6.1.4.1.2011.5.25.349.1.1.1.3
		hwEmdiChannelGroupAddress OBJECT-TYPE
			SYNTAX IpAddress
			MAX-ACCESS read-only
			STATUS current
			DESCRIPTION
				"The hwEmdiChannelGroupAddress is the group address of the monitored multicast channel. It is an IPv4 address, ranged from 224.0.0.0 to 239.255.255.255. 
				Note that the 224.0.0.0 to 224.0.0.255 is reserved and can not be used for a multicast channel."
			::= { hwEmdiScalar 3 }


		-- 1.3.6.1.4.1.2011.5.25.349.1.1.1.4			
		hwEmdiRtpLrThreshold OBJECT-TYPE
			SYNTAX Integer32 (1..5000)
			MAX-ACCESS read-only
			STATUS current
			DESCRIPTION
				"The hwEmdiRtpLrThreshold is a threshold value. If the RTP-LR of a multicast channel exceeds the threshold in some continuous monitor period,
				the TRAP hwEmdiRtpLrOverThreshold will be triggered.If the RTP-LR of a multicast channel is lower than the threshold in some continuous monitor period,
				the TRAP hwEmdiRtpLrOverThresholdResume will be triggered."
			::= { hwEmdiScalar 4 }

		-- 1.3.6.1.4.1.2011.5.25.349.1.1.1.5			
		hwEmdiRtpLrValue OBJECT-TYPE
			SYNTAX Integer32 (1..5000)
			MAX-ACCESS read-only
			STATUS current
			DESCRIPTION
				"The hwEmdiRtpLrValue is the RTP-LR of a multicast channel. RTP-LR stands for the packet loss rate of a RTP over UDP multicast channel."
			::= { hwEmdiScalar 5}					

		-- 1.3.6.1.4.1.2011.5.25.349.1.1.1.6			
		hwEmdiRtpSerThreshold OBJECT-TYPE
			SYNTAX Integer32 (1..5000)
			MAX-ACCESS read-only
			STATUS current
			DESCRIPTION
				"The hwEmdiRtpSerThreshold is a threshold value. If the RTP-SER of a multicast channel exceeds the threshold in some continuous monitor period,
				the TRAP hwEmdiRtpSerOverThreshold will be triggered.If the RTP-SER of a multicast channel is lower than the threshold in some continuous monitor period,
				the TRAP hwEmdiRtpSerOverThresholdResume will be triggered."
			::= { hwEmdiScalar 6 }

		-- 1.3.6.1.4.1.2011.5.25.349.1.1.1.7			
		hwEmdiRtpSerValue OBJECT-TYPE
			SYNTAX Integer32 (1..5000)
			MAX-ACCESS read-only
			STATUS current
			DESCRIPTION
				"The hwEmdiRtpSerValue is the RTP-SER of a multicast channel. RTP-SER stands for the packet sequence error of a RTP over UDP multicast channel."
			::= { hwEmdiScalar 7 }				
		
		-- 1.3.6.1.4.1.2011.5.25.349.1.1.1.8			
		hwEmdiChannelSlot OBJECT-TYPE
			SYNTAX OCTET STRING (SIZE (0..64))
			MAX-ACCESS read-only
			STATUS current
			DESCRIPTION
				"The hwEmdiChannelSlot is the slotId of a LPU on which multicast packet loss is detected."
			::= { hwEmdiScalar 8 }	

		hwEmdiChannelInterface OBJECT-TYPE
			SYNTAX OCTET STRING (SIZE (0..32))
			MAX-ACCESS read-only
			STATUS current
			DESCRIPTION
				"The hwEmdiChannelInterface is the Interface of a LPU on which IPTV packet loss is detected."
			::= { hwEmdiScalar 9 }	


			
		-- 1.3.6.1.4.1.2011.5.25.349.2
		hwQoeNotifications OBJECT IDENTIFIER ::= { hwQoeMIB 2 }
		-- 1.3.6.1.4.1.2011.5.25.349.2.1
		hwEmdiNotifications OBJECT IDENTIFIER ::= { hwQoeNotifications 1 }

		-- 1.3.6.1.4.1.2011.5.25.349.2.1.1
		hwEmdiRtpLrOverThreshold NOTIFICATION-TYPE
			OBJECTS { hwEmdiChannelName, hwEmdiChannelSourceAddress, hwEmdiChannelGroupAddress, hwEmdiRtpLrThreshold, hwEmdiRtpLrValue }
			STATUS current
			DESCRIPTION 
				"This trap indicates that RTP-LR of a multicast channel exceeds the threshold in some continuous monitor period."
			::= { hwEmdiNotifications 1 }		

		-- 1.3.6.1.4.1.2011.5.25.349.2.1.2
		hwEmdiRtpLrOverThresholdResume NOTIFICATION-TYPE
			OBJECTS { hwEmdiChannelName, hwEmdiChannelSourceAddress, hwEmdiChannelGroupAddress, hwEmdiRtpLrThreshold, hwEmdiRtpLrValue }
			STATUS current
			DESCRIPTION 
				"This trap indicates that RTP-LR of a multicast channel is lower than the threshold in some continuous monitor period."
			::= { hwEmdiNotifications 2 }	

		-- 1.3.6.1.4.1.2011.5.25.349.2.1.3
		hwEmdiRtpSerOverThreshold NOTIFICATION-TYPE
			OBJECTS { hwEmdiChannelName, hwEmdiChannelSourceAddress, hwEmdiChannelGroupAddress, hwEmdiRtpSerThreshold, hwEmdiRtpSerValue }
			STATUS current
			DESCRIPTION 
				"This trap indicates that RTP-SER of a multicast channel exceeds the threshold in some continuous monitor period."
			::= { hwEmdiNotifications 3 }		

		-- 1.3.6.1.4.1.2011.5.25.349.2.1.4
		hwEmdiRtpSerOverThresholdResume NOTIFICATION-TYPE
			OBJECTS { hwEmdiChannelName, hwEmdiChannelSourceAddress, hwEmdiChannelGroupAddress, hwEmdiRtpSerThreshold, hwEmdiRtpSerValue }
			STATUS current
			DESCRIPTION 
				"This trap indicates that RTP-SER of a multicast channel is lower than the threshold in some continuous monitor period."
			::= { hwEmdiNotifications 4 }	

		-- 1.3.6.1.4.1.2011.5.25.349.2.1.7
		hwEmdiRtpLrOverThresholdSlot NOTIFICATION-TYPE
			OBJECTS { hwEmdiChannelSlot }
			STATUS current
			DESCRIPTION 
				"The packet loss rate of a multicast channel exceeded the alarm threshold in three of five detection periods."
			::= { hwEmdiNotifications 7 }	
			
		-- 1.3.6.1.4.1.2011.5.25.349.2.1.8
		hwEmdiRtpLrOverThresholdSlotResume NOTIFICATION-TYPE
			OBJECTS { hwEmdiChannelSlot }
			STATUS current
			DESCRIPTION 
				"The packet loss rate of a multicast channel belowed the alarm threshold in fifteen detection periods."
			::= { hwEmdiNotifications 8 }

		-- 1.3.6.1.4.1.2011.5.25.349.2.1.9
		hwEmdiOutRtpLrOverThreshold NOTIFICATION-TYPE
			OBJECTS { hwEmdiChannelName, hwEmdiChannelSourceAddress, hwEmdiChannelGroupAddress, hwEmdiRtpLrThreshold, hwEmdiRtpLrValue, hwEmdiChannelSlot, hwEmdiChannelInterface }
			STATUS current
			DESCRIPTION 
				"This trap indicates that outbound RTP-LR of a multicast channel exceeds the threshold in some continuous monitor period."
			::= { hwEmdiNotifications 9 }		

		-- 1.3.6.1.4.1.2011.5.25.349.2.1.10
		hwEmdiOutRtpLrOverThresholdResume NOTIFICATION-TYPE
			OBJECTS { hwEmdiChannelName, hwEmdiChannelSourceAddress, hwEmdiChannelGroupAddress, hwEmdiRtpLrThreshold, hwEmdiRtpLrValue, hwEmdiChannelSlot, hwEmdiChannelInterface }
			STATUS current
			DESCRIPTION 
				"This trap indicates that outbound RTP-LR of a multicast channel is lower than the threshold in some continuous monitor period."
			::= { hwEmdiNotifications 10 }	

		-- 1.3.6.1.4.1.2011.5.25.349.2.1.11
		hwEmdiOutRtpSerOverThreshold NOTIFICATION-TYPE
			OBJECTS { hwEmdiChannelName, hwEmdiChannelSourceAddress, hwEmdiChannelGroupAddress, hwEmdiRtpSerThreshold, hwEmdiRtpSerValue, hwEmdiChannelSlot, hwEmdiChannelInterface }
			STATUS current
			DESCRIPTION 
				"This trap indicates that outbound RTP-SER of a multicast channel exceeds the threshold in some continuous monitor period."
			::= { hwEmdiNotifications 11 }		

		-- 1.3.6.1.4.1.2011.5.25.349.2.1.12
		hwEmdiOutRtpSerOverThresholdResume NOTIFICATION-TYPE
			OBJECTS { hwEmdiChannelName, hwEmdiChannelSourceAddress, hwEmdiChannelGroupAddress, hwEmdiRtpSerThreshold, hwEmdiRtpSerValue, hwEmdiChannelSlot, hwEmdiChannelInterface }
			STATUS current
			DESCRIPTION 
				"This trap indicates that outbound RTP-SER of a multicast channel is lower than the threshold in some continuous monitor period."
			::= { hwEmdiNotifications 12 } 	
	
	END

--
--	HUAWEI-QOE-MIB
--
