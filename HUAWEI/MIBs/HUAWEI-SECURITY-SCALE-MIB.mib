--
-- HUAWEI-SECURITY-SCALE-MIB.mib
-- MIB generated by MG-SOFT Visual MIB Builder Version 4.0 Build 341
-- Monday, August 7, 2017 at 15:31:13
-- 
-- =================================================================
-- Copyright (C) 2017 by  HUAWEI TECHNOLOGIES. All rights reserved
-- 
-- Description:
-- Reference:
-- Version: V1.00
-- History:
-- =================================================================

	HUAWEI-SECURITY-SCALE-MIB DEFINITIONS ::= BEGIN
 
		IMPORTS
			enterprises			
				FROM RFC1155-SMI			
			OBJECT-GROUP			
				FROM SNMPv2-CONF			
			Integer32, Gauge32, Counter64, OBJECT-TYPE, MODULE-IDENTITY, 
			NOTIFICATION-TYPE			
				FROM SNMPv2-SMI			
			TruthValue			
				FROM SNMPv2-TC;	
	
		-- 1.3.6.1.4.1.2011.6.122.81.1
		hwSecScaleTrap MODULE-IDENTITY 
			LAST-UPDATED "201708071531Z"		-- Aug 07, 2017 at 15:31 GMT
			ORGANIZATION 
				"Huawei Technologies Co.,Ltd."
			CONTACT-INFO
				"Huawei Industrial Base
                                 Bantian, Longgang
                                 Shenzhen 518129
                                 People's Republic of China
                                 Website: http://www.huawei.com
                                 Email: support@huawei.com"
								 
			
			DESCRIPTION 
                "
                V1.00
                The HUAWEI-SECURITY-SCALE-MIB contains objects to manage the firewall SC ALE module.
                "        
			REVISION  "201708071531Z"		
			DESCRIPTION "The HUAWEI-SECURITY-SCALE-MIB contains objects to manage the firewall SCALE module. "  
                 			     ::= { hwSecScaleMib 1 }  		
	
--
-- Node definitions
--
	
		-- 1.3.6.1.4.1.2011
		huawei OBJECT IDENTIFIER ::= { enterprises 2011 }

		
		-- 1.3.6.1.4.1.2011.6
		huaweiUtility OBJECT IDENTIFIER ::= { huawei 6 }
		
		-- 1.3.6.1.4.1.2011.6.122
		hwSecurity OBJECT IDENTIFIER ::= { huaweiUtility 122 }

		-- 1.3.6.1.4.1.2011.6.122.81
		hwSecScaleMib OBJECT IDENTIFIER ::= { hwSecurity 81 }
		
		-- 1.3.6.1.4.1.2011.6.122.81.1.1
		hwSecScaleTrapObject OBJECT IDENTIFIER ::= { hwSecScaleTrap 1 }
		
		-- 1.3.6.1.4.1.2011.6.122.81.1.1.1
		hwSecScaleRecord OBJECT-TYPE
			SYNTAX OCTET STRING (SIZE(0..32))
			MAX-ACCESS read-only
			STATUS current
			DESCRIPTION
				"The scale slot and card infomation."
			::= { hwSecScaleTrapObject 1 }
		
		-- 1.3.6.1.4.1.2011.6.122.81.1.1.2
		hwSecScaleReason OBJECT-TYPE
			SYNTAX OCTET STRING (SIZE(0..64))
			MAX-ACCESS read-only
			STATUS current
			DESCRIPTION
				"The scale time out reason."
			::= { hwSecScaleTrapObject 2 }	
	
		-- 1.3.6.1.4.1.2011.6.122.81.1.2
		hwSecScaleTimerTraps OBJECT IDENTIFIER ::= { hwSecScaleTrap 2 }	
		
		-- 1.3.6.1.4.1.2011.6.122.81.1.2.1
		hwSecScaleOutTrap NOTIFICATION-TYPE		
		OBJECTS { hwSecScaleRecord, hwSecScaleReason }
			STATUS current
			DESCRIPTION 
				"scale in or out time out."
			::= { hwSecScaleTimerTraps 1 }		 		
						
	END

--
-- HUAWEI-SECURITY-SCALE-MIB.mib
--
