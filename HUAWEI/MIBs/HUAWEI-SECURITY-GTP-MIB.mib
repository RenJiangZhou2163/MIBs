--
-- HUAWEI-SECURITY-GTP-MIB-new.mib
-- MIB generated by MG-SOFT Visual MIB Builder Version 6.0  Build 88
-- Tuesday, November 21, 2017 at 17:07:24
--

--  =============================================================================
-- Copyright (C) 2017 by HUAWEI TECHNOLOGIES. All rights reserved.
--    
-- Description: . 
-- Reference: Huawei Enterprise MIB
-- Version: V1.01
-- History: 
--          V1.00 The initial version created by LiShengbai 90004270. 
--          V1.01 The new version created by Weiyingbin w00427251.
-- =============================================================================

	HUAWEI-SECURITY-GTP-MIB DEFINITIONS ::= BEGIN
 
		IMPORTS
			enterprises			
				FROM RFC1155-SMI			
			OBJECT-GROUP, MODULE-COMPLIANCE, NOTIFICATION-GROUP			
				FROM SNMPv2-CONF			
			Gauge32, Counter32, OBJECT-TYPE, MODULE-IDENTITY, NOTIFICATION-TYPE			
				FROM SNMPv2-SMI;
	
	
		-- 1.3.6.1.4.1.2011.6.122.35
		hwGTP MODULE-IDENTITY 
			LAST-UPDATED "201712061000Z"		-- December 06, 2017 at 10:00 GMT
			ORGANIZATION 
				"Huawei Technologies Co.,Ltd."
			CONTACT-INFO 
				"Huawei Industrial Base
				Bantian, Longgang
				Shenzhen 518129
				People's Republic of China
				Website: http://www.huawei.com
				Email: support@huawei.com
				"
			DESCRIPTION 
				"The GTP mib is for Eudemon and USG product series."
				
			REVISION "201712061000Z"		-- December 06, 2017 at 10:00 GMT
			DESCRIPTION 
				"V1.01, Add two traps for tunnels' numbers at 2017-12-06."
				
			REVISION "201002020900Z"		-- February 02, 2010 at 09:00 GMT
			DESCRIPTION 
				"V1.00, initial version."
			::= { hwSecurity 35 }

		
	
--
-- Node definitions
--
	
--  February 2, 2010 at 09:00 GMT
-- ===============================================
-- Node definitions
-- ===============================================
-- 1.3.6.1.4.1.2011
		-- 1.3.6.1.4.1.2011
		huawei OBJECT IDENTIFIER ::= { enterprises 2011 }

		
--  1.3.6.1.4.1.2011.6
		-- 1.3.6.1.4.1.2011.6
		huaweiUtility OBJECT IDENTIFIER ::= { huawei 6 }

		
--  1.3.6.1.4.1.2011.6.122
		-- 1.3.6.1.4.1.2011.6.122
		hwSecurity OBJECT IDENTIFIER ::= { huaweiUtility 122 }

		
--  ===============================================
-- GTPTrapObject.
-- ===============================================
		-- 1.3.6.1.4.1.2011.6.122.35.0
		hwGTPNotification OBJECT IDENTIFIER ::= { hwGTP 0 }

		
		-- 1.3.6.1.4.1.2011.6.122.35.0.1
		hwGTPTrapObject OBJECT IDENTIFIER ::= { hwGTPNotification 1 }

		
		-- 1.3.6.1.4.1.2011.6.122.35.0.1.1
		hwGTPCtrMsgRate OBJECT-TYPE
			SYNTAX Gauge32
			MAX-ACCESS accessible-for-notify
			STATUS current
			DESCRIPTION
				"The GTP control rate."
			::= { hwGTPTrapObject 1 }

		
		-- 1.3.6.1.4.1.2011.6.122.35.0.1.2
		hwGTPActualRate OBJECT-TYPE
			SYNTAX Gauge32
			MAX-ACCESS accessible-for-notify
			STATUS current
			DESCRIPTION
				"The rate for receiving packets on the management plane."
			::= { hwGTPTrapObject 2 }

		
		-- 1.3.6.1.4.1.2011.6.122.35.0.1.3
		hwGTPThresholdTunnel OBJECT-TYPE
			SYNTAX Gauge32
			MAX-ACCESS accessible-for-notify
			STATUS current
			DESCRIPTION
				"Threshold for the number of GTP tunnel entries. "
			::= { hwGTPTrapObject 3 }

		
		-- 1.3.6.1.4.1.2011.6.122.35.0.1.4
		hwGTPActualTunnel OBJECT-TYPE
			SYNTAX Gauge32
			MAX-ACCESS accessible-for-notify
			STATUS current
			DESCRIPTION
				"The number of current GTP tunnels."
			::= { hwGTPTrapObject 4 }

		
--  ===============================================
-- definition of traps.      
-- =============================================== 
		-- 1.3.6.1.4.1.2011.6.122.35.0.2
		hwGTPTraps OBJECT IDENTIFIER ::= { hwGTPNotification 2 }

		
		-- 1.3.6.1.4.1.2011.6.122.35.0.2.1
		hwGTPOverCtrMsgRate NOTIFICATION-TYPE
			OBJECTS { hwGTPCtrMsgRate, hwGTPActualRate }
			STATUS current
			DESCRIPTION 
				"Send the message when the rate for receiving packets on the management plane exceeds the threshold of the GTP control rate."
			::= { hwGTPTraps 1 }

		
		-- 1.3.6.1.4.1.2011.6.122.35.0.2.2
		hwGTPOverThresholdTunnel NOTIFICATION-TYPE
			OBJECTS { hwGTPThresholdTunnel, hwGTPActualTunnel }
			STATUS current
			DESCRIPTION 
				"The message is sent when the number of current GTP tunnels exceeds the configured threshold."
			::= { hwGTPTraps 2 }

		
		-- 1.3.6.1.4.1.2011.6.122.35.0.2.3
		hwGTPRecoverTunnel NOTIFICATION-TYPE
			OBJECTS { hwGTPThresholdTunnel, hwGTPActualTunnel }
			STATUS current
			DESCRIPTION 
				"The message is sent when the number of current GTP tunnels falls below the configured threshold. "
			::= { hwGTPTraps 3 }

		
--  ===============================================
-- Begin the hwGTPGlobalStats.
-- =============================================== 
		-- 1.3.6.1.4.1.2011.6.122.35.1
		hwGTPStats OBJECT IDENTIFIER ::= { hwGTP 1 }

		
		-- 1.3.6.1.4.1.2011.6.122.35.1.1
		hwGTPRcvV0GtpC OBJECT-TYPE
			SYNTAX Counter32
			MAX-ACCESS read-only
			STATUS current
			DESCRIPTION
				"Number of received v0 gtpc packets."
			::= { hwGTPStats 1 }

		
		-- 1.3.6.1.4.1.2011.6.122.35.1.2
		hwGTPDiscardV0GtpC OBJECT-TYPE
			SYNTAX Counter32
			MAX-ACCESS read-only
			STATUS current
			DESCRIPTION
				"Number of discarded v0 gtpc packets."
			::= { hwGTPStats 2 }

		
		-- 1.3.6.1.4.1.2011.6.122.35.1.3
		hwGTPRcvV1GtpC OBJECT-TYPE
			SYNTAX Counter32
			MAX-ACCESS read-only
			STATUS current
			DESCRIPTION
				"Number of received v1 gtpc packets."
			::= { hwGTPStats 3 }

		
		-- 1.3.6.1.4.1.2011.6.122.35.1.4
		hwGTPDiscardV1GtpC OBJECT-TYPE
			SYNTAX Counter32
			MAX-ACCESS read-only
			STATUS current
			DESCRIPTION
				"Number of discarded v1 gtpc packets."
			::= { hwGTPStats 4 }

		
		-- 1.3.6.1.4.1.2011.6.122.35.1.5
		hwGTPRcvV0GtpU OBJECT-TYPE
			SYNTAX Counter32
			MAX-ACCESS read-only
			STATUS current
			DESCRIPTION
				"Number of received v0 gtpu packets."
			::= { hwGTPStats 5 }

		
		-- 1.3.6.1.4.1.2011.6.122.35.1.6
		hwGTPDiscardV0GtpU OBJECT-TYPE
			SYNTAX Counter32
			MAX-ACCESS read-only
			STATUS current
			DESCRIPTION
				"Number of discarded v0 gtpu packets."
			::= { hwGTPStats 6 }

		
		-- 1.3.6.1.4.1.2011.6.122.35.1.7
		hwGTPRcvV1GtpU OBJECT-TYPE
			SYNTAX Counter32
			MAX-ACCESS read-only
			STATUS current
			DESCRIPTION
				"Number of received v1 gtpu packets."
			::= { hwGTPStats 7 }

		
		-- 1.3.6.1.4.1.2011.6.122.35.1.8
		hwGTPDiscardV1GtpU OBJECT-TYPE
			SYNTAX Counter32
			MAX-ACCESS read-only
			STATUS current
			DESCRIPTION
				"Number of discarded v1 gtpu packets."
			::= { hwGTPStats 8 }

		
		-- 1.3.6.1.4.1.2011.6.122.35.1.9
		hwGTPRcvGtpV0 OBJECT-TYPE
			SYNTAX Counter32
			MAX-ACCESS read-only
			STATUS current
			DESCRIPTION
				"Number of received v0 gtp packets."
			::= { hwGTPStats 9 }

		
		-- 1.3.6.1.4.1.2011.6.122.35.1.10
		hwGTPDiscardGtpV0 OBJECT-TYPE
			SYNTAX Counter32
			MAX-ACCESS read-only
			STATUS current
			DESCRIPTION
				"Number of discarded v0 gtp packets."
			::= { hwGTPStats 10 }

		
		-- 1.3.6.1.4.1.2011.6.122.35.1.11
		hwGTPRcvGtpV1 OBJECT-TYPE
			SYNTAX Counter32
			MAX-ACCESS read-only
			STATUS current
			DESCRIPTION
				"Number of received v1 gtp packets ."
			::= { hwGTPStats 11 }

		
		-- 1.3.6.1.4.1.2011.6.122.35.1.12
		hwGTPDiscardGtpV1 OBJECT-TYPE
			SYNTAX Counter32
			MAX-ACCESS read-only
			STATUS current
			DESCRIPTION
				"Number of discarded v1 gtp packets."
			::= { hwGTPStats 12 }

		
		-- 1.3.6.1.4.1.2011.6.122.35.1.13
		hwGTPRcvGtpCharge OBJECT-TYPE
			SYNTAX Counter32
			MAX-ACCESS read-only
			STATUS current
			DESCRIPTION
				"Number of received gtp' packets."
			::= { hwGTPStats 13 }

		
		-- 1.3.6.1.4.1.2011.6.122.35.1.14
		hwGTPDiscardGtpCharge OBJECT-TYPE
			SYNTAX Counter32
			MAX-ACCESS read-only
			STATUS current
			DESCRIPTION
				"Number of discarded gtp' packets."
			::= { hwGTPStats 14 }

		
		-- 1.3.6.1.4.1.2011.6.122.35.1.15
		hwGTPRcvUnknownVersion OBJECT-TYPE
			SYNTAX Counter32
			MAX-ACCESS read-only
			STATUS current
			DESCRIPTION
				"Number of received unknown version packets."
			::= { hwGTPStats 15 }

		
		-- 1.3.6.1.4.1.2011.6.122.35.1.16
		hwGTPDiscardUnknownVersion OBJECT-TYPE
			SYNTAX Counter32
			MAX-ACCESS read-only
			STATUS current
			DESCRIPTION
				"Number of discarded unknown version packets."
			::= { hwGTPStats 16 }

		
		-- 1.3.6.1.4.1.2011.6.122.35.1.17
		hwGTPRcvUnknownMessage OBJECT-TYPE
			SYNTAX Counter32
			MAX-ACCESS read-only
			STATUS current
			DESCRIPTION
				"Number of received unknown message packets."
			::= { hwGTPStats 17 }

		
		-- 1.3.6.1.4.1.2011.6.122.35.1.18
		hwGTPDiscardUnknownMessage OBJECT-TYPE
			SYNTAX Counter32
			MAX-ACCESS read-only
			STATUS current
			DESCRIPTION
				"Number of discarded unknown message packets."
			::= { hwGTPStats 18 }

		
		-- 1.3.6.1.4.1.2011.6.122.35.1.19
		hwGTPRcvGtpCPackets OBJECT-TYPE
			SYNTAX Counter32
			MAX-ACCESS read-only
			STATUS current
			DESCRIPTION
				"Number of received gtpc packets."
			::= { hwGTPStats 19 }

		
		-- 1.3.6.1.4.1.2011.6.122.35.1.20
		hwGTPDiscardGtpCPackets OBJECT-TYPE
			SYNTAX Counter32
			MAX-ACCESS read-only
			STATUS current
			DESCRIPTION
				"Number of discarded gtpc packets."
			::= { hwGTPStats 20 }

		
		-- 1.3.6.1.4.1.2011.6.122.35.1.21
		hwGTPRcvGtpUPackets OBJECT-TYPE
			SYNTAX Counter32
			MAX-ACCESS read-only
			STATUS current
			DESCRIPTION
				"Number of received gtpu packets."
			::= { hwGTPStats 21 }

		
		-- 1.3.6.1.4.1.2011.6.122.35.1.22
		hwGTPDiscardGtpUPackets OBJECT-TYPE
			SYNTAX Counter32
			MAX-ACCESS read-only
			STATUS current
			DESCRIPTION
				"Number of discarded gtpu packets."
			::= { hwGTPStats 22 }

		
		-- 1.3.6.1.4.1.2011.6.122.35.1.23
		hwGTPDropGtpTurnnelPackets OBJECT-TYPE
			SYNTAX Counter32
			MAX-ACCESS read-only
			STATUS current
			DESCRIPTION
				"Number of discarded packets according to gtp tunnel speed."
			::= { hwGTPStats 23 }

		
		-- 1.3.6.1.4.1.2011.6.122.35.1.24
		hwGTPExchangesNotAcceptedByPeerGsnPackets OBJECT-TYPE
			SYNTAX Counter32
			MAX-ACCESS read-only
			STATUS current
			DESCRIPTION
				"Number of packets that GTP exchanges not accepted by peer GSN."
			::= { hwGTPStats 24 }

		
		-- 1.3.6.1.4.1.2011.6.122.35.1.25
		hwGTPTunnelNum OBJECT-TYPE
			SYNTAX Counter32
			MAX-ACCESS read-only
			STATUS current
			DESCRIPTION
				"Number of GTP tunnels."
			::= { hwGTPStats 25 }

		
--  ===============================================
-- Conformance Information             
-- ===============================================
		-- 1.3.6.1.4.1.2011.6.122.35.2
		hwGTPMibConformance OBJECT IDENTIFIER ::= { hwGTP 2 }

		
		-- 1.3.6.1.4.1.2011.6.122.35.2.1
		hwGTPMibCompliances OBJECT IDENTIFIER ::= { hwGTPMibConformance 1 }

		
--  ===============================================
-- Compliance Statements             
-- ===============================================
-- this module
-- hwGTPGlobalStatsGroup
		-- 1.3.6.1.4.1.2011.6.122.35.2.1.1
		hwGTPMibCompliance MODULE-COMPLIANCE
			STATUS current
			DESCRIPTION 
				" "
			MODULE -- this module
				MANDATORY-GROUPS { hwGTPTrapObjectGroup, hwGTPTrapsGroup }
			::= { hwGTPMibCompliances 1 }

		
		-- 1.3.6.1.4.1.2011.6.122.35.2.2
		hwGTPMibGroups OBJECT IDENTIFIER ::= { hwGTPMibConformance 2 }

		
		-- 1.3.6.1.4.1.2011.6.122.35.2.2.1
		hwGTPTrapObjectGroup OBJECT-GROUP
			OBJECTS { hwGTPCtrMsgRate, hwGTPActualRate }
			STATUS current
			DESCRIPTION 
				"This table specifies the objects used for traps."
			::= { hwGTPMibGroups 1 }

		
		-- 1.3.6.1.4.1.2011.6.122.35.2.2.2
		hwGTPTrapsGroup NOTIFICATION-GROUP
			NOTIFICATIONS { hwGTPOverCtrMsgRate }
			STATUS current
			DESCRIPTION 
				"GTP traps."
			::= { hwGTPMibGroups 2 }

		
		-- 1.3.6.1.4.1.2011.6.122.35.2.2.3
		hwIPSecGlobalStatsGroup OBJECT-GROUP
			OBJECTS { hwGTPRcvV0GtpC, hwGTPDiscardV0GtpC, hwGTPRcvV1GtpC, hwGTPDiscardV1GtpC, hwGTPRcvV0GtpU, 
				hwGTPDiscardV0GtpU, hwGTPRcvV1GtpU, hwGTPDiscardV1GtpU, hwGTPRcvGtpV0, hwGTPDiscardGtpV0, 
				hwGTPRcvGtpV1, hwGTPDiscardGtpV1, hwGTPRcvGtpCharge, hwGTPDiscardGtpCharge, hwGTPRcvUnknownVersion, 
				hwGTPDiscardUnknownVersion, hwGTPRcvUnknownMessage, hwGTPDiscardUnknownMessage, hwGTPRcvGtpCPackets, hwGTPDiscardGtpCPackets, 
				hwGTPRcvGtpUPackets, hwGTPDiscardGtpUPackets, hwGTPDropGtpTurnnelPackets, hwGTPExchangesNotAcceptedByPeerGsnPackets, hwGTPTunnelNum
				 }
			STATUS current
			DESCRIPTION 
				"This table specifies the statistics information for GTP."
			::= { hwGTPMibGroups 3 }

		
	
	END

--
-- HUAWEI-SECURITY-GTP-MIB-new.mib
--
