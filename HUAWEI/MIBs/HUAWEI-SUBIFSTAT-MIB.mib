--==================================================================
-- Copyright (C) 2002 by  HUAWEI TECHNOLOGIES. All rights reserved.
-- 
-- Description: HUAWEI SUBIFSTAT MIB
-- Reference:
-- Version: V1.0
-- History:
-- ==================================================================
-- ==================================================================
-- 
-- Varibles and types be imported
--
-- ==================================================================
HUAWEI-SUBIFSTAT-MIB DEFINITIONS ::= BEGIN
IMPORTS
    huaweiMgmt            
        FROM HUAWEI-MIB
    RowStatus,TEXTUAL-CONVENTION
        FROM SNMPv2-TC

    MODULE-COMPLIANCE, OBJECT-GROUP
        FROM SNMPv2-CONF
    MODULE-IDENTITY, OBJECT-TYPE, Integer32
        FROM SNMPv2-SMI  
                          
    ifIndex,InterfaceIndex
        FROM IF-MIB  
              
    hwBaseTrapSeverity, hwBaseTrapProbableCause, hwBaseTrapEventType
        FROM HUAWEI-BASE-TRAP-MIB;    

               
    hwSubIfStatMode MODULE-IDENTITY
        LAST-UPDATED "200901051830Z"        
                ORGANIZATION 
                     "Huawei Technologies Co.,Ltd."
                CONTACT-INFO 
			"Huawei Industrial Base
			  Bantian, Longgang
			   Shenzhen 518129
			   People's Republic of China
			   Website: http://www.huawei.com
			   Email: support@huawei.com
			 "
                DESCRIPTION
            "The SUBIFSTATMIB MIB module is defined to manage the sub interface statistics function of Huawei Technologies co.,Ltd."
            ::= { huaweiMgmt 163 }
 
        hwSubIfStatMIBObjects OBJECT IDENTIFIER ::= { hwSubIfStatMode 1 }
        hwSubIfStatConformance OBJECT IDENTIFIER ::= { hwSubIfStatMode 2 }
              hwLocalSubIfStat OBJECT IDENTIFIER ::= { hwSubIfStatMIBObjects 1 }
        hwGlobalLocalSubIfStat OBJECT IDENTIFIER ::= { hwSubIfStatMIBObjects 2 }             
-- ==================================================================


    hwSubIfStatEnableTable OBJECT-TYPE
        SYNTAX SEQUENCE OF HwSubIfStatEnableEntry
        MAX-ACCESS not-accessible
        STATUS current
        DESCRIPTION 
           "The table contains basic information for this vlan."
        ::= { hwLocalSubIfStat 1 }


    hwSubIfStatEnableEntry OBJECT-TYPE
        SYNTAX HwSubIfStatEnableEntry
        MAX-ACCESS not-accessible
        STATUS current
        DESCRIPTION 
           "Entries of SufIfSTAT MIB table."
        INDEX   { hwSubIfStatEnableInterfaceIndex }
        ::= { hwSubIfStatEnableTable 1}

    HwSubIfStatEnableEntry ::=
    SEQUENCE {
        hwSubIfStatEnableInterfaceIndex    InterfaceIndex,
        hwSubIfStatEnable    INTEGER,
        hwSubIfStatEnableRowStatus    RowStatus
        }

    hwSubIfStatEnableInterfaceIndex OBJECT-TYPE
        SYNTAX  InterfaceIndex
        MAX-ACCESS not-accessible
        STATUS current
        DESCRIPTION 
           "The vlan-id or other identifier referring to this vlan."
        ::= { hwSubIfStatEnableEntry 1 }


    hwSubIfStatEnable  OBJECT-TYPE
        SYNTAX  INTEGER 
        {
        enable(1),
        disable(2)
        }
        MAX-ACCESS read-create
        STATUS current
        DESCRIPTION 
           "Description of the vlan."
        DEFVAL {2}
        ::= { hwSubIfStatEnableEntry 2 }


    hwSubIfStatEnableRowStatus  OBJECT-TYPE
        SYNTAX  RowStatus
        MAX-ACCESS read-create
        STATUS current
        DESCRIPTION 
           "Operation status."
        ::= { hwSubIfStatEnableEntry 3 }  
        

    hwGlobalSubIfStatEnableTable OBJECT-TYPE
        SYNTAX SEQUENCE OF HwGlobalSubIfStatEnableEntry
        MAX-ACCESS not-accessible
        STATUS current
        DESCRIPTION 
           "The table contains basic information for this vlan."
        ::= { hwGlobalLocalSubIfStat 1 }


    hwGlobalSubIfStatEnableEntry OBJECT-TYPE
        SYNTAX HwGlobalSubIfStatEnableEntry
        MAX-ACCESS not-accessible
        STATUS current
        DESCRIPTION 
           "Entries of SufIfSTAT MIB table."
        INDEX   { hwGlobalSubIfStatEnableInterfaceIndex }
        ::= { hwGlobalSubIfStatEnableTable 1}

    HwGlobalSubIfStatEnableEntry ::=
    SEQUENCE {
        hwGlobalSubIfStatEnableInterfaceIndex    InterfaceIndex,
        hwGlobalSubIfStatEnable    INTEGER,
        hwGlobalSubIfStatEnableRowStatus    RowStatus
        }

    hwGlobalSubIfStatEnableInterfaceIndex OBJECT-TYPE
        SYNTAX  InterfaceIndex
        MAX-ACCESS not-accessible
        STATUS current
        DESCRIPTION 
           "The vlan-id or other identifier referring to this vlan."
        ::= { hwGlobalSubIfStatEnableEntry 1 }


    hwGlobalSubIfStatEnable  OBJECT-TYPE
        SYNTAX  INTEGER 
        {
        enable(1),
        disable(2)
        }
        MAX-ACCESS read-create
        STATUS current
        DESCRIPTION 
           "Description of the vlan."
        DEFVAL {2}
        ::= { hwGlobalSubIfStatEnableEntry 2 }


    hwGlobalSubIfStatEnableRowStatus  OBJECT-TYPE
        SYNTAX  RowStatus
        MAX-ACCESS read-create
        STATUS current
        DESCRIPTION 
           "Operation status."
        ::= { hwGlobalSubIfStatEnableEntry 3 }     

    hwSubIfStatGroups
        OBJECT IDENTIFIER ::= { hwSubIfStatConformance 1 }
    hwSubIfStatCompliances
        OBJECT IDENTIFIER ::= { hwSubIfStatConformance 2 }    
        
    -- Compliance requirement for fully compliant implementations.
    hwSubIfStatModuleCompliance MODULE-COMPLIANCE
        STATUS current
        DESCRIPTION
            "Compliance statement for agents that provide full
             support for HUAWEI-SUBIFSTAT-MIB."
    
        MODULE  -- The Interfaces Group MIB, RFC 2863.
        MANDATORY-GROUPS {
            hwSubIfStatEnableGroup,
            hwGlobalSubIfStatEnableGroup
        }
        ::= { hwSubIfStatCompliances 1 }   
     -- Units of conformance.
     hwSubIfStatEnableGroup OBJECT-GROUP
        OBJECTS {
            hwSubIfStatEnableInterfaceIndex, 
            hwSubIfStatEnable,
            hwSubIfStatEnableRowStatus
            }
        STATUS current
        DESCRIPTION
            "Collection of objects that implement enable statistic function of sub interface."
        ::= { hwSubIfStatGroups 1 }
    
    hwGlobalSubIfStatEnableGroup OBJECT-GROUP
        OBJECTS {
            hwGlobalSubIfStatEnableInterfaceIndex,
            hwGlobalSubIfStatEnable,
            hwGlobalSubIfStatEnableRowStatus
            }
        STATUS current
        DESCRIPTION
            "Collection of objects that implement enable statistic function of global sub interface."
        ::= { hwSubIfStatGroups 2 }
    
           
END
