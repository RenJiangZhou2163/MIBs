--==================================================================
-- Copyright (C) 2011 by  HUAWEI TECHNOLOGIES. All rights reserved.
-- 
-- Description: HUAWEI LS MIB
-- Reference:
-- Version: V1.0
-- History:
-- <author>,  <date>,  <contents>
-- xuzhen   2011-6-17
-- ==================================================================

-- ==================================================================
-- 
-- Varibles and types are imported
--
-- ==================================================================
    HUAWEI-LS-MIB DEFINITIONS ::= BEGIN
 
        IMPORTS
            hwDatacomm            
                FROM HUAWEI-MIB            
            DisplayString         
                FROM SNMPv2-TC
            OBJECT-GROUP, MODULE-COMPLIANCE            
                FROM SNMPv2-CONF            
            Integer32, OBJECT-TYPE, MODULE-IDENTITY
                FROM SNMPv2-SMI;           
    
    

        hwLsMIB MODULE-IDENTITY 
            LAST-UPDATED "201106171342Z"        
            ORGANIZATION 
                "Huawei Technologies Co.,Ltd."
            CONTACT-INFO 
                "Huawei Industrial Base
                  Bantian, Longgang
                   Shenzhen 518129
                   People's Republic of China
                   Website: http://www.huawei.com
                   Email: support@huawei.com
                 "   
            DESCRIPTION 
                "The HUAWEI-LS-MIB which contains objects manages logical system name and logical system id. 
                "
            ::= { hwDatacomm 254 }

        
    
    
--
-- Node definitions
--
    
--  ==================================================================
-- 
-- ======================= definition begin =========================
-- 
-- ==================================================================       
        hwLSObjects OBJECT IDENTIFIER ::= { hwLsMIB 1 }

        
        hwLSTable OBJECT-TYPE
            SYNTAX SEQUENCE OF HwLSEntry
            MAX-ACCESS not-accessible
            STATUS current
            DESCRIPTION
                "Table about the id and name of logical system."
            ::= { hwLSObjects 1 }

        
        hwLSEntry OBJECT-TYPE
            SYNTAX HwLSEntry
            MAX-ACCESS not-accessible
            STATUS current
            DESCRIPTION
                "Information about the id and name of logical system."
            INDEX { hwLSLsId }
            ::= { hwLSTable 1 }

        
        HwLSEntry ::=
            SEQUENCE {
                hwLSLsId
                    Integer32, 
                hwLSLsName
                    DisplayString
             }

        hwLSLsId OBJECT-TYPE
            SYNTAX Integer32
            MAX-ACCESS not-accessible
            STATUS current
            DESCRIPTION
                "The object specifies the id of a logical system. A unique value, greater than zero, for each logical system."
            ::= { hwLSEntry 1 }
            
            
        hwLSLsName OBJECT-TYPE
            SYNTAX DisplayString (SIZE (1..31))
            MAX-ACCESS read-only
            STATUS current
            DESCRIPTION
                "The object specifies the name of a logical system. A unique value, for each logical system."
            ::= { hwLSEntry 2 }

   -- conformance information

   hwLSConformance OBJECT IDENTIFIER ::= { hwLsMIB 2 }

   hwLSGroups      OBJECT IDENTIFIER ::= { hwLSConformance 1 }
   hwLSCompliances OBJECT IDENTIFIER ::= { hwLSConformance 2 }


      hwLSCompliance2 MODULE-COMPLIANCE
            STATUS current
            DESCRIPTION 
                "The compliance statement for systems supporting the HUAWEI-LS-MIB."
            MODULE HUAWEI-LS-MIB
                MANDATORY-GROUPS { hwLSInformationGroups }
            ::= { hwLSCompliances 1 }

        
        hwLSBasicGroup OBJECT-GROUP
            OBJECTS { hwLSLsId, hwLSLsName }
            STATUS current
            DESCRIPTION 
                "The logical system attribute group."
            ::= { hwLSGroups 1 }



   -- compliance statements

   
    END

--
-- HUAWEI-LS-MIB.mib
--
