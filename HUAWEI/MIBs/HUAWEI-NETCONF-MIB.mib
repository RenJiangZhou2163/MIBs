-- Copyright (C) 2021 by HUAWEI TECHNOLOGIES. All rights reserved.
--
-- HUAWEI-NETCONF-MIB.mib
-- MIB generated by MG-SOFT Visual MIB Builder Version 4.0 Build 341
-- Thursday, January 11, 2019 at 11:20:00
-- Version: V2.13
--

	HUAWEI-NETCONF-MIB DEFINITIONS ::= BEGIN
 
		IMPORTS
			hwDatacomm			
				FROM HUAWEI-MIB	
			InetAddressType, InetAddress
				FROM INET-ADDRESS-MIB				
			OBJECT-GROUP, MODULE-COMPLIANCE, NOTIFICATION-GROUP			
				FROM SNMPv2-CONF			
			IpAddress, Unsigned32, OBJECT-TYPE, MODULE-IDENTITY, NOTIFICATION-TYPE			
				FROM SNMPv2-SMI;
	
	
		-- 1.3.6.1.4.1.2011.5.25.217
		hwNetconf MODULE-IDENTITY 
			LAST-UPDATED "202104061002Z"		-- April 06, 2021 at 10:02 GMT
			ORGANIZATION 
				"Huawei Technologies Co.,Ltd."
			CONTACT-INFO 
				"Huawei Industrial Base
				  Bantian, Longgang
				   Shenzhen 518129
                                   People's Republic of China
                                   Website: http://www.huawei.com
                                   Email: support@huawei.com
                                 "
			DESCRIPTION 
				"This defines the MIB for the Netconf Agent"
                                REVISION     "202104061002Z"
                                DESCRIPTION "V2.1.3, modify BITS value of hwNetconfMdaResourceType."

                                REVISION     "202103251418Z"
                                DESCRIPTION "V2.1.2, modify hwMdaResouceChange to hwNetconfMdaResourceType and modify the BITS value."

                                REVISION     "202103111100Z"
				DESCRIPTION  "V2.1.1, change hwNetconfClientConfigSynchronizedSucess, hwNetconfClientSyncConfigSucess, hwNetconfClientPeerConnectSucess."

				REVISION     "202103011945Z"
				DESCRIPTION  "V2.1.0, add hwNetconfMdaResourceChange."

				REVISION     "202103011603Z"
				DESCRIPTION  "V2.0.9, add hwMdaResouceChange."

				REVISION     "202008202356Z"
				DESCRIPTION  "V2.0.8, update hwNetconfSessionInetAddrType access."

				REVISION     "201901111120Z"
				DESCRIPTION  "V2.0.7, eliminate warning and change comments."

				REVISION     "201812261645Z"
				DESCRIPTION  "V2.0.6, add hwNetconfSessionId, hwNetconfKilledBySessionId, hwNetconfSessionTerminationReason, hwNetconfServerSessionStart, hwNetconfServerSessionEnd."

				REVISION     "201801082116Z"
				DESCRIPTION  "V2.0.5, add hwNetconfClientConfigFailed, hwNetconfClientConfigSynchronizedSuccess, hwNetconfClientSyncConfigFailed, hwNetconfClientSyncConfigSuccess, hwNetconfClientPeerConnectionInterrupt, hwNetconfClientPeerConnectionResume, hwNetconfClientPeerConnectFailed, hwNetconfClientPeerConnectSuccess."

				REVISION     "201708171649Z"
				DESCRIPTION  "V2.0.4, modify hwNetconfServerConnectionInterrupt, hwNetconfServerConnectionResume."

				REVISION     "201511271225Z"
				DESCRIPTION  "V2.0.3, add hwNetconfServerSyncConfigFail."

				REVISION     "201506081225Z"
				DESCRIPTION  "V2.0.2, modify hwNetconfSessionPeerIPAddress hwNetconfSessionVpnName OID"

				REVISION    "201505151225Z"
				DESCRIPTION  "V2.0.1, add hwNetconfClientConnectionInterrupt, hwNetconfClientConnectionResume, hwNetconfServerConnectionInterrupt, hwNetconfServerConnectionResume."
                        
				REVISION    "201004080000Z"
				DESCRIPTION  
                            "
                            V1.00, Inital version.
                            "     
                            
			::= { hwDatacomm 217 }

		
	
--
-- Node definitions
--

		-- 1.3.6.1.4.1.2011.5.25.217.1
		hwNetconfAgent OBJECT IDENTIFIER ::= { hwNetconf 1 }

		-- 1.3.6.1.4.1.2011.5.25.217.1.1
		hwNetconfSyncFullFtpFilename OBJECT-TYPE
			SYNTAX OCTET STRING (SIZE (1..128))
			MAX-ACCESS accessible-for-notify
			STATUS current
			DESCRIPTION
				"Sync Full file being transferred using FTP."
			::= { hwNetconfAgent 1 }

		-- 1.3.6.1.4.1.2011.5.25.217.1.2
		hwNetconfSyncFullFtpServerAddr OBJECT-TYPE
			SYNTAX IpAddress
			MAX-ACCESS accessible-for-notify
			STATUS current
			DESCRIPTION
				"IP address of the Sync Full file transfer target FTP Server"
			::= { hwNetconfAgent 2 }

		-- 1.3.6.1.4.1.2011.5.25.217.1.3
		hwNetconfSyncFullFtpFailReason OBJECT-TYPE
			SYNTAX INTEGER
			{
				fileOpenError(1),
				fileTransferFailed(2)
			}
			MAX-ACCESS accessible-for-notify
			STATUS current
			DESCRIPTION
				"Reason code of the Sync Full FTP file transfer failure"
			::= { hwNetconfAgent 3 }

		-- 1.3.6.1.4.1.2011.5.25.217.1.4
		hwNetconfSessionInetAddrType OBJECT-TYPE
			SYNTAX InetAddressType
			MAX-ACCESS accessible-for-notify
			STATUS current
			DESCRIPTION
				"This object indicates the IP address type."
			::= { hwNetconfAgent 4 }

		-- 1.3.6.1.4.1.2011.5.25.217.1.5
		hwNetconfSessionPeerIPAddress OBJECT-TYPE
			SYNTAX IpAddress
			MAX-ACCESS accessible-for-notify
			STATUS current
			DESCRIPTION
				"Peer IP address."
			::= { hwNetconfAgent 5 }

		-- 1.3.6.1.4.1.2011.5.25.217.1.6
		hwNetconfSessionVpnName OBJECT-TYPE
			SYNTAX OCTET STRING (SIZE (1..31))
			MAX-ACCESS accessible-for-notify
			STATUS current
			DESCRIPTION
				"The name of VPN interface."
			::= { hwNetconfAgent 6 }

		-- 1.3.6.1.4.1.2011.5.25.217.1.7
		hwNetconfSyncConfigIPAddress OBJECT-TYPE
			SYNTAX InetAddress
			MAX-ACCESS accessible-for-notify
			STATUS current
			DESCRIPTION
				"IP address of the source initiating sync-config operation."
			::= { hwNetconfAgent 7 }

		-- 1.3.6.1.4.1.2011.5.25.217.1.8
		hwNetconfClientPeerName OBJECT-TYPE
			SYNTAX OCTET STRING (SIZE (1..64))
			MAX-ACCESS accessible-for-notify
			STATUS current
			DESCRIPTION
				"Peer name"
			::= { hwNetconfAgent 8 }

		-- 1.3.6.1.4.1.2011.5.25.217.1.9
		hwNetconfClientAppFeatureName OBJECT-TYPE
			SYNTAX OCTET STRING (SIZE (1..32))
			MAX-ACCESS accessible-for-notify
			STATUS current
			DESCRIPTION
				"Feature name"
			::= { hwNetconfAgent 9 }

		-- 1.3.6.1.4.1.2011.5.25.217.1.10
		hwNetconfSessionUserName OBJECT-TYPE
			SYNTAX OCTET STRING (SIZE (1..253))
			MAX-ACCESS accessible-for-notify
			STATUS current
			DESCRIPTION
				"User name of the Netconf session"
			::= { hwNetconfAgent 10 }

		-- 1.3.6.1.4.1.2011.5.25.217.1.11
		hwNetconfSessionId OBJECT-TYPE
			SYNTAX Unsigned32
			MAX-ACCESS accessible-for-notify
			STATUS current
			DESCRIPTION
				"Identifier of the session. A NETCONF session MUST be identified by a non-zero value. A non-NETCONF session MAY be identified by the value zero."
		::= { hwNetconfAgent 11 }

		-- 1.3.6.1.4.1.2011.5.25.217.1.12
		hwNetconfKilledBySessionId OBJECT-TYPE
			SYNTAX Unsigned32
			MAX-ACCESS accessible-for-notify
			STATUS current
			DESCRIPTION
				"The ID of the session that directly caused this session to be abnormally terminated.  If this session was abnormally terminated by a non-NETCONF session unknown to the server, then it MAY be identified by the value 65535."
			::= { hwNetconfAgent 12 }

		-- 1.3.6.1.4.1.2011.5.25.217.1.13
		hwNetconfSessionTerminationReason OBJECT-TYPE
			SYNTAX INTEGER
			{
				closed(0),
				killed(1),
				dropped(2),
				timeout(3),
				badHello(4),
				other(5)
			}
			MAX-ACCESS accessible-for-notify
			STATUS current
			DESCRIPTION
				"The session was terminated by the client in normal fashion, e.g., by the NETCONF &lt;close-session> protocol operation."
			::= { hwNetconfAgent 13 }

		-- 1.3.6.1.4.1.2011.5.25.217.1.14
		hwNetconfMdaResourceType OBJECT-TYPE
			SYNTAX BITS
			{
				yang(7),
				yangPatch(6),
				yangZhCN(5),
				yangZhCNPatch(4),
				alarm(3),
				alarmPatch(2),
				panel(1),
				panelPatch(0)
			}
			MAX-ACCESS accessible-for-notify
			STATUS current
			DESCRIPTION
				"Type of mda resource files that changed."
			::= { hwNetconfAgent 14 }
		
		-- 1.3.6.1.4.1.2011.5.25.217.2
		hwNetconfNotifications OBJECT IDENTIFIER ::= { hwNetconf 2 }

		-- 1.3.6.1.4.1.2011.5.25.217.2.1
		hwNetconfSyncFullFtpFailed NOTIFICATION-TYPE
			OBJECTS { hwNetconfSyncFullFtpFilename, hwNetconfSyncFullFtpServerAddr, hwNetconfSyncFullFtpFailReason }
			STATUS current
			DESCRIPTION 
				"This notification is sent when the FTP transfer of the sync full operation file to the remote FTP Server failed."
			::= { hwNetconfNotifications 1 }

		hwNetconfClientConnectionInterrupt NOTIFICATION-TYPE
			OBJECTS { hwNetconfSessionInetAddrType, hwNetconfSessionPeerIPAddress, hwNetconfSessionVpnName }
			STATUS current
			DESCRIPTION 
				"Remote netconf connection is interrupted."
			::=  {hwNetconfNotifications 2}

		hwNetconfClientConnectionResume NOTIFICATION-TYPE
			OBJECTS { hwNetconfSessionInetAddrType, hwNetconfSessionPeerIPAddress, hwNetconfSessionVpnName }
			STATUS current
			DESCRIPTION 
				"Remote netconf connection is resumed."
			::=  {hwNetconfNotifications 3}

		hwNetconfServerConnectionInterrupt NOTIFICATION-TYPE
			OBJECTS { hwNetconfSessionInetAddrType, hwNetconfSessionPeerIPAddress, hwNetconfSessionVpnName }
			STATUS deprecated
			DESCRIPTION 
				"The connection between a NETCONF server and its peer is torn down."
			::=  {hwNetconfNotifications 4}

		hwNetconfServerConnectionResume NOTIFICATION-TYPE
			OBJECTS { hwNetconfSessionInetAddrType, hwNetconfSessionPeerIPAddress, hwNetconfSessionVpnName }
			STATUS deprecated
			DESCRIPTION 
				"The connection between a NETCONF server and its peer is restored."
			::=  {hwNetconfNotifications 5}

		hwNetconfServerSyncConfigFail NOTIFICATION-TYPE
			OBJECTS { hwNetconfSessionInetAddrType, hwNetconfSyncConfigIPAddress, hwNetconfSessionVpnName }
			STATUS current
			DESCRIPTION 
				"This notification is sent when application virtual access configurations synchronization is failed."
			::= { hwNetconfNotifications 6 }

		-- 1.3.6.1.4.1.2011.5.25.217.2.7
		hwNetconfClientConfigFailed NOTIFICATION-TYPE
			OBJECTS { hwNetconfClientPeerName, hwNetconfSessionInetAddrType, hwNetconfSessionPeerIPAddress, hwNetconfClientAppFeatureName }
			STATUS current
			DESCRIPTION 
				"Failed to deliver configurations to a peer device."
			::=  {hwNetconfNotifications 7}

		-- 1.3.6.1.4.1.2011.5.25.217.2.8
		hwNetconfClientConfigSynchronizedSuccess NOTIFICATION-TYPE
			OBJECTS { hwNetconfClientPeerName, hwNetconfSessionInetAddrType, hwNetconfSessionPeerIPAddress, hwNetconfClientAppFeatureName }
			STATUS current
			DESCRIPTION 
				"Successfully synchronized configurations to a peer device."
			::=  {hwNetconfNotifications 8}

		-- 1.3.6.1.4.1.2011.5.25.217.2.9
		hwNetconfClientSyncConfigFailed NOTIFICATION-TYPE
			OBJECTS { hwNetconfClientPeerName, hwNetconfSessionInetAddrType, hwNetconfSessionPeerIPAddress }
			STATUS current
			DESCRIPTION 
				"Failed to synchronize configurations to a peer device."
			::=  {hwNetconfNotifications 9}

		-- 1.3.6.1.4.1.2011.5.25.217.2.10
		hwNetconfClientSyncConfigSuccess NOTIFICATION-TYPE
			OBJECTS { hwNetconfClientPeerName, hwNetconfSessionInetAddrType, hwNetconfSessionPeerIPAddress }
			STATUS current
			DESCRIPTION 
				"Successfully synchronized configurations to a peer device."
			::=  {hwNetconfNotifications 10}

		-- 1.3.6.1.4.1.2011.5.25.217.2.11
		hwNetconfClientPeerConnectionInterrupt NOTIFICATION-TYPE
			OBJECTS { hwNetconfClientPeerName, hwNetconfSessionInetAddrType, hwNetconfSessionPeerIPAddress, hwNetconfSessionUserName }
			STATUS current
			DESCRIPTION 
				"The NETCONF connection with a peer device was torn down."
			::=  {hwNetconfNotifications 11}

		-- 1.3.6.1.4.1.2011.5.25.217.2.12
		hwNetconfClientPeerConnectionResume NOTIFICATION-TYPE
			OBJECTS { hwNetconfClientPeerName, hwNetconfSessionInetAddrType, hwNetconfSessionPeerIPAddress, hwNetconfSessionUserName }
			STATUS current
			DESCRIPTION 
				"The NETCONF connection with a peer device is resumed."
			::=  {hwNetconfNotifications 12}

		-- 1.3.6.1.4.1.2011.5.25.217.2.13
		hwNetconfClientPeerConnectFailed NOTIFICATION-TYPE
			OBJECTS { hwNetconfClientPeerName, hwNetconfSessionInetAddrType, hwNetconfSessionPeerIPAddress, hwNetconfSessionUserName }
			STATUS current
			DESCRIPTION 
				"Failed to establish NETCONF connection with a peer device."
			::=  {hwNetconfNotifications 13}

		-- 1.3.6.1.4.1.2011.5.25.217.2.14
		hwNetconfClientPeerConnectSuccess NOTIFICATION-TYPE
			OBJECTS { hwNetconfClientPeerName, hwNetconfSessionInetAddrType, hwNetconfSessionPeerIPAddress, hwNetconfSessionUserName }
			STATUS current
			DESCRIPTION 
				"Successfully established NETCONF connection with a peer device."
			::=  {hwNetconfNotifications 14}

		-- 1.3.6.1.4.1.2011.5.25.217.2.15
		hwNetconfServerSessionStart NOTIFICATION-TYPE
			OBJECTS { hwNetconfSessionUserName, hwNetconfSessionId, hwNetconfSessionPeerIPAddress, hwNetconfSessionVpnName }
			STATUS current
			DESCRIPTION 
				"Generated when a NETCONF server detects that a NETCONF session has started. A server MAY generate this event for non-NETCONF management sessions. Indicates the identity of the user that started the session."
			::=  {hwNetconfNotifications 15}
	        
		-- 1.3.6.1.4.1.2011.5.25.217.2.16
		hwNetconfServerSessionEnd NOTIFICATION-TYPE
			OBJECTS { hwNetconfSessionUserName, hwNetconfSessionId, hwNetconfSessionPeerIPAddress, hwNetconfKilledBySessionId, hwNetconfSessionTerminationReason, hwNetconfSessionVpnName }
			STATUS current
			DESCRIPTION 
				"Generated when a NETCONF server detects that a NETCONF session has terminated. A server MAY optionally generate this event for non-NETCONF management sessions.  Indicates the identity of the user that owned the session, and why the session was terminated."
			::=  {hwNetconfNotifications 16}

		-- 1.3.6.1.4.1.2011.5.25.217.2.17
		hwNetconfMdaResourceChange NOTIFICATION-TYPE
			OBJECTS { hwNetconfMdaResourceType }
			STATUS current
			DESCRIPTION
				"The mda resource files changed."
			::=  {hwNetconfNotifications 17}

		-- 1.3.6.1.4.1.2011.5.25.217.3
		hwNetconfMIBConformance OBJECT IDENTIFIER ::= { hwNetconf 3 }

		
		-- 1.3.6.1.4.1.2011.5.25.217.3.1
		hwNetconfMIBCompliances OBJECT IDENTIFIER ::= { hwNetconfMIBConformance 1 }

		-- 1.3.6.1.4.1.2011.5.25.217.3.1.1
		hwNetconfMIBCompliance MODULE-COMPLIANCE
			STATUS current
			DESCRIPTION 
				"The compliance statement for systems supporting the HUAWEI-NETCONF-MIB."
			MODULE -- this module
				MANDATORY-GROUPS { hwNetconfNotificationGroup, hwNetconfAgentGroup, hwNetconfClientGroup }
			::= { hwNetconfMIBCompliances 1 }

		
		-- 1.3.6.1.4.1.2011.5.25.217.3.2
		hwNetconfMIBGroups OBJECT IDENTIFIER ::= { hwNetconfMIBConformance 2 }

		-- 1.3.6.1.4.1.2011.5.25.217.3.2.1
		hwNetconfNotificationGroup NOTIFICATION-GROUP
			NOTIFICATIONS { hwNetconfSyncFullFtpFailed, hwNetconfClientConnectionInterrupt, hwNetconfClientConnectionResume, hwNetconfServerConnectionInterrupt, hwNetconfServerConnectionResume, hwNetconfServerSyncConfigFail,
			hwNetconfClientConfigFailed, hwNetconfClientConfigSynchronizedSuccess, hwNetconfClientSyncConfigFailed, hwNetconfClientSyncConfigSuccess, hwNetconfClientPeerConnectionInterrupt, hwNetconfClientPeerConnectionResume, hwNetconfClientPeerConnectFailed, hwNetconfClientPeerConnectSuccess, hwNetconfServerSessionStart, hwNetconfServerSessionEnd, hwNetconfMdaResourceChange }
			STATUS current
			DESCRIPTION 
				"The NETCONF notification group"
			::= { hwNetconfMIBGroups 1 }

		-- 1.3.6.1.4.1.2011.5.25.217.3.2.2
		hwNetconfAgentGroup OBJECT-GROUP
			OBJECTS { hwNetconfSyncFullFtpFilename, hwNetconfSyncFullFtpServerAddr, hwNetconfSyncFullFtpFailReason, hwNetconfSyncConfigIPAddress, hwNetconfClientPeerName, hwNetconfClientAppFeatureName, hwNetconfSessionUserName, hwNetconfSessionId, hwNetconfKilledBySessionId, hwNetconfSessionTerminationReason, hwNetconfMdaResourceType }
			STATUS current
			DESCRIPTION 
				"Description."
			::= { hwNetconfMIBGroups 2 }

		-- 1.3.6.1.4.1.2011.5.25.217.3.2.3
		hwNetconfClientGroup OBJECT-GROUP
			OBJECTS { hwNetconfSessionInetAddrType, hwNetconfSessionPeerIPAddress, hwNetconfSessionVpnName }
			STATUS current
			DESCRIPTION 
				"Description."
			::= { hwNetconfMIBGroups 3 }
	
	END

--
-- HUAWEI-NETCONF-MIB.mib
--
