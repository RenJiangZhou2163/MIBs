--  =================================================================
-- Copyright (C) 2016 by  HUAWEI TECHNOLOGIES. All rights reserved.
--
-- DESCRIPTION:  HUAWEI-IPRANDCN-MIB
-- Reference:  
-- Version: V2.07
-- History:
--         v1.00
--         created by lixinjie 2011-11-21
-- ================================================================= 

    HUAWEI-IPRANDCN-DCNADA-MIB DEFINITIONS ::= BEGIN            

        IMPORTS
            DisplayString            
                FROM SNMPv2-TC
            OBJECT-GROUP, MODULE-COMPLIANCE, NOTIFICATION-GROUP         
                FROM SNMPv2-CONF            
            MODULE-IDENTITY, OBJECT-TYPE, NOTIFICATION-TYPE, Integer32, IpAddress 
                FROM SNMPv2-SMI
--          iso
--              FROM RFC1155-SMI
            hwDatacomm
                FROM HUAWEI-MIB
            hwIpRanDcnNeInfoNeId
                FROM HUAWEI-IPRAN-DCN-MIB
            VlanList			
                FROM HUAWEI-L2IF-MIB;

        hwIpRanDcnADA MODULE-IDENTITY 
            LAST-UPDATED "201606061009Z"  
            ORGANIZATION 
                "Huawei Technologies Co.,Ltd."
            CONTACT-INFO 
                "Huawei Industrial Base
                 Bantian, Longgang
                 Shenzhen 518129
                 People's Republic of China
                 Website: http://www.huawei.com
                 Email: support@huawei.com "
            DESCRIPTION 
               "Add hwDcnNeidConflictNotifications."

          REVISION "201606061009Z"
            DESCRIPTION
                "Add hwDcnNeipConflictNotifications."

          REVISION "201504200944Z"
            DESCRIPTION
                "modify hwDcnInterfaceVlanListLow and hwDcnInterfaceVlanListHigh description." 

          REVISION "201502111438Z"
            DESCRIPTION
                "delete iso" 

          REVISION "201409301039Z"
            DESCRIPTION
                "moidy hwDcnEntPhyIndex and hwDcnInterfaceIndex MAX-ACCESS to read-only" 

          REVISION "201408261039Z"
            DESCRIPTION
                "Add hwDcnInterfaceVlanListLow,hwDcnInterfaceVlanListHigh" 


          REVISION "201402271557Z"
            DESCRIPTION
                "Modify hwDcnInterfaceIndex  range" 

            REVISION "201309251750Z"
            DESCRIPTION
                "Add hwDcnNeidConflictNotifications."

           REVISION "201105180930Z"
           DESCRIPTION
                "Initial version."
            ::= { hwIpRanDcn 2 }
    

    -- 1.3.6.1.4.1.2011.5.25.300
        hwIpRanDcn OBJECT IDENTIFIER ::= { hwDatacomm 300 }
                      

    -- 1.3.6.1.4.1.2011.5.25.300.2.1
         hwDcnDefaultPortTable OBJECT-TYPE
            SYNTAX SEQUENCE OF HwDcnDefaultPortEntry
            MAX-ACCESS not-accessible
            STATUS current
            DESCRIPTION
                "
                The Dcn Default-port table.
                "
            ::= { hwIpRanDcnADA 1 }
            
        --1.3.6.1.4.1.2011.5.25.300.2.1.1        
        hwDcnDefaultPortEntry OBJECT-TYPE
            SYNTAX  HwDcnDefaultPortEntry
            MAX-ACCESS not-accessible
            STATUS current
            DESCRIPTION
                "
                The Dcn Default-port table struct.
                "
            INDEX { hwDcnEntPhyIndex }
            ::= { hwDcnDefaultPortTable 1 }
        
        HwDcnDefaultPortEntry ::=
            SEQUENCE { 
                hwDcnEntPhyIndex
                    Integer32,
                hwDcnDefaultPort
                    DisplayString,
                hwDcnAllPort
                    DisplayString
             }  
        -- 1.3.6.1.4.1.2011.5.25.300.2.1.1.1
        hwDcnEntPhyIndex OBJECT-TYPE
            SYNTAX Integer32 (1..2147483647)
            MAX-ACCESS read-only
            STATUS current
            DESCRIPTION
                "
                The ID of the Current Board
                "
            ::= { hwDcnDefaultPortEntry 1 }
        -- 1.3.6.1.4.1.2011.5.25.300.2.1.1.2
        hwDcnDefaultPort OBJECT-TYPE
            SYNTAX DisplayString
            MAX-ACCESS read-only
            STATUS current
            DESCRIPTION
                "
                The default ports of this card
                "
            ::= { hwDcnDefaultPortEntry 2 } 
        -- 1.3.6.1.4.1.2011.5.25.300.2.1.1.3
        hwDcnAllPort OBJECT-TYPE
            SYNTAX DisplayString
            MAX-ACCESS read-only
            STATUS current
            DESCRIPTION
                "
                All the support ports of this card
                "
            ::= { hwDcnDefaultPortEntry 3 }             
            
                 
    -- 1.3.6.1.4.1.2011.5.25.300.2.2           
        hwDcnInterfaceTable OBJECT-TYPE
            SYNTAX SEQUENCE OF HwDcnInterfaceEntry
            MAX-ACCESS not-accessible
            STATUS current
            DESCRIPTION
                "
                The Dcn Interface table.
                "
            ::= { hwIpRanDcnADA 2 }
            
        --1.3.6.1.4.1.2011.5.25.300.2.2.1        
        hwDcnInterfaceEntry OBJECT-TYPE
            SYNTAX  HwDcnInterfaceEntry
            MAX-ACCESS not-accessible
            STATUS current
            DESCRIPTION
                "
                The Dcn Interface table struct.
                "
            INDEX { hwDcnInterfaceIndex }
            ::= { hwDcnInterfaceTable 1 }
        
        HwDcnInterfaceEntry ::=
            SEQUENCE { 
                hwDcnInterfaceIndex
                    Integer32,
                hwDcnInterfaceName
                    DisplayString,
                hwDcnInterfaceVlanID
                    Integer32,
                hwDcnInterfaceBandwidth
                    Integer32,
                hwDcnInterfaceState
                    INTEGER,
                hwDcnInterfaceVlanListLow
                    VlanList,
                hwDcnInterfaceVlanListHigh
                    VlanList,
                hwDcnInterfaceNeip
                    IpAddress                  
             }
        -- 1.3.6.1.4.1.2011.5.25.300.2.2.1.1
        hwDcnInterfaceIndex OBJECT-TYPE
            SYNTAX Integer32 (1..2147483647)
            MAX-ACCESS read-only
            STATUS current
            DESCRIPTION
                "
                The Index of the Current Interface
                "
            ::= { hwDcnInterfaceEntry 1 } 
        -- 1.3.6.1.4.1.2011.5.25.300.2.2.1.2
        hwDcnInterfaceName OBJECT-TYPE
            SYNTAX DisplayString
            MAX-ACCESS read-only
            STATUS current
            DESCRIPTION
                "
                The Name of the Current Interface
                "
            ::= { hwDcnInterfaceEntry 2 }     
        -- 1.3.6.1.4.1.2011.5.25.300.2.2.1.3
        hwDcnInterfaceVlanID OBJECT-TYPE
            SYNTAX Integer32 (0..4096)
            MAX-ACCESS read-only
            STATUS current
            DESCRIPTION
                "
                The VlanID of the Current Interface
                "
            ::= { hwDcnInterfaceEntry 3 } 
        -- 1.3.6.1.4.1.2011.5.25.300.2.2.1.4
        hwDcnInterfaceBandwidth OBJECT-TYPE
            SYNTAX Integer32 (1..65535)
            MAX-ACCESS read-only
            STATUS current
            DESCRIPTION
                "
                The Bandwidth of the Current Interface
                "
            ::= { hwDcnInterfaceEntry 4 } 
        -- 1.3.6.1.4.1.2011.5.25.300.2.2.1.5
        -- 1:enable dcn on this interface,
        -- 2:disable dcn on this interface,
        -- 3:dcn on this interface is creating,
        -- 4:there is no dcn on this interface or it is closed.
        -- 5:others
        hwDcnInterfaceState OBJECT-TYPE
            SYNTAX  INTEGER {
                    enable(1),                          
                    disable(2),
                    creating(3),
                    init(4),
                    unknown(5)
                }
                
            MAX-ACCESS read-only
            STATUS current
            DESCRIPTION
                "
                The state of the Current Interface
                "
            ::= { hwDcnInterfaceEntry 5 } 
        -- 1.3.6.1.4.1.2011.5.25.300.2.2.1.6
        hwDcnInterfaceVlanListLow OBJECT-TYPE
            SYNTAX VlanList (SIZE(256))
            MAX-ACCESS read-only
            STATUS current
            DESCRIPTION
                "
                This object indicates bitmap information for an interface's DCN VLANs ranging from 1 to 2048.
                "
            ::= { hwDcnInterfaceEntry 6 }
        -- 1.3.6.1.4.1.2011.5.25.300.2.2.1.7
        hwDcnInterfaceVlanListHigh OBJECT-TYPE
            SYNTAX VlanList (SIZE(256))
            MAX-ACCESS read-only
            STATUS current
            DESCRIPTION
                "
               This object indicates bitmap information for an interface's DCN VLANs ranging from 2049 to 4096.
                "
            ::= { hwDcnInterfaceEntry 7 }
        -- 1.3.6.1.4.1.2011.5.25.300.2.2.1.8
        hwDcnInterfaceNeip  OBJECT-TYPE
            SYNTAX IpAddress
            MAX-ACCESS accessible-for-notify
            STATUS current
            DESCRIPTION
                "This object indicates the NEIP."
            ::= { hwDcnInterfaceEntry 8 }
        -- 1.3.6.1.4.1.2011.5.25.300.2.3
        hwDcnNeidConflictNotifications OBJECT IDENTIFIER ::= { hwIpRanDcnADA 3 }

        -- 1.3.6.1.4.1.2011.5.25.300.2.3.1
        hwDcnNeidConflictRising NOTIFICATION-TYPE
        OBJECTS {
            hwDcnInterfaceName,hwIpRanDcnNeInfoNeId}
        STATUS current
        DESCRIPTION
            "A pppoe negotiation is failed for neid conflicting on this interface."
        ::= { hwDcnNeidConflictNotifications 1 }

        -- 1.3.6.1.4.1.2011.5.25.300.2.3.2
        hwDcnNeidConflictResume NOTIFICATION-TYPE
        OBJECTS {
            hwDcnInterfaceName,hwIpRanDcnNeInfoNeId}
        STATUS current
        DESCRIPTION
            "The pppoe negotiation has succeed,and the alarm of neid conflict is resumed. "
        ::= { hwDcnNeidConflictNotifications 2 }

        -- 1.3.6.1.4.1.2011.5.25.300.2.4
        hwDcnNeipConflictNotifications OBJECT IDENTIFIER ::= { hwIpRanDcnADA 4 }

        -- 1.3.6.1.4.1.2011.5.25.300.2.4.1
        hwDcnNeipConflictRising NOTIFICATION-TYPE
        OBJECTS {
            hwDcnInterfaceName,hwDcnInterfaceNeip}
        STATUS current
        DESCRIPTION
            "A PPP negotiation failed due to NEIP address conflicts on this interface."
        ::= { hwDcnNeipConflictNotifications 1 }

        -- 1.3.6.1.4.1.2011.5.25.300.2.4.2
        hwDcnNeipConflictResume NOTIFICATION-TYPE
        OBJECTS {
            hwDcnInterfaceName,hwDcnInterfaceNeip}
        STATUS current
        DESCRIPTION
            "The PPP negotiation succeeded after the NEIP address conflict fault was rectified. "
        ::= { hwDcnNeipConflictNotifications 2 }

         --  ============== groups ==============   
        hwIPRanDcnConformance  OBJECT IDENTIFIER ::= { hwIpRanDcn 3 }
        hwIPRanDcnCompliances OBJECT IDENTIFIER ::= { hwIPRanDcnConformance 1 }
        hwIPRanDcnCompliance MODULE-COMPLIANCE
               STATUS      current
               DESCRIPTION
                   "The compliance statement for systems supporting 
                the this module."

               MODULE      -- this module
               MANDATORY-GROUPS    {hwDcnDefaultPortTableGroup, 
                                    hwDcnInterfaceTableGroup 
                                    }  
                                               
              ::= { hwIPRanDcnCompliances 1 }

         hwIPRanDcnGroups OBJECT IDENTIFIER ::= { hwIPRanDcnCompliances 2 } 
        
             
         hwDcnDefaultPortTableGroup OBJECT-GROUP
            OBJECTS {
                hwDcnDefaultPort,
                hwDcnAllPort            
                }
            STATUS current
            DESCRIPTION 
                "Dcn Default Port table."
            ::= { hwIPRanDcnGroups 2 } 
              
         hwDcnInterfaceTableGroup OBJECT-GROUP
            OBJECTS {
                hwDcnInterfaceName,
                hwDcnInterfaceVlanID,
                hwDcnInterfaceBandwidth,
                hwDcnInterfaceState,
                hwDcnInterfaceVlanListLow ,
                hwDcnInterfaceVlanListHigh,
                hwDcnInterfaceNeip
                }
            STATUS current
            DESCRIPTION 
                "Dcn Interface table."
            ::= { hwIPRanDcnGroups 3 } 

         hwDcnNeidConflictNotificationsGroup NOTIFICATION-GROUP            
             NOTIFICATIONS {
                hwDcnNeidConflictRising ,
                hwDcnNeidConflictResume
                }
            STATUS current
            DESCRIPTION 
                "Dcn neid conflict Trap."
            ::= { hwIPRanDcnGroups 4 } 

         hwDcnNeipConflictNotificationsGroup NOTIFICATION-GROUP            
             NOTIFICATIONS {
                hwDcnNeipConflictRising ,
                hwDcnNeipConflictResume
                }
            STATUS current
            DESCRIPTION 
                "Dcn neip conflict Trap."
            ::= { hwIPRanDcnGroups 5 } 

    END
