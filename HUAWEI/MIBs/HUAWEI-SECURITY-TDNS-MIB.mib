--
-- HUAWEI-SECURITY-TDNS-MIB.mib
-- MIB generated by MG-SOFT Visual MIB Builder Version 4.0 Build 341
-- Tuesday, July 29, 2014 at 15:23:20
--

--  HUAWEI-SECURITY-TDNS-MIB.mib
-- MIB generated by MG-SOFT Visual MIB Builder Version 4.0 Build 341
-- Tuesday, July 29, 2014 at 15:11:59
-- 
--  HUAWEI-SECURITY-TDNS-MIB.mib
-- MIB generated by MG-SOFT Visual MIB Builder Version 4.0 Build 341
-- Tuesday, July 29, 2014 at 14:58:44
-- 
--  HUAWEI-SECURITY-TDNS-MIB.mib
-- MIB generated by MG-SOFT Visual MIB Builder Version 4.0 Build 341
-- Monday, January 13, 2014 at 16:49:11
-- 
--  HUAWEI-SECURITY-TDNS-MIB.mib
-- MIB generated by MG-SOFT Visual MIB Builder Version 4.0 Build 341
-- Friday, January 10, 2014 at 14:17:55
-- 
--  =============================================================================
-- Copyright (C) 2014 by HUAWEI TECHNOLOGIES. All rights reserved.
--    
-- Description: The MIB is designed to get SLB information. 
-- Reference: Huawei Enterprise MIB
-- Version: V1.00
-- History: 
--          Version: V1.00 The initial version created by maoshanshan 90005469. 
-- =============================================================================

	HUAWEI-SECURITY-TDNS-MIB DEFINITIONS ::= BEGIN
 
		IMPORTS
			enterprises			
				FROM RFC1155-SMI			
			OBJECT-GROUP, MODULE-COMPLIANCE, NOTIFICATION-GROUP			
				FROM SNMPv2-CONF			
			IpAddress, OBJECT-TYPE, MODULE-IDENTITY, NOTIFICATION-TYPE			
				FROM SNMPv2-SMI;
	
	
		-- 1.3.6.1.4.1.2011.6.122.72
		hwTDns MODULE-IDENTITY 
			LAST-UPDATED "201401071609Z"		-- January 07, 2014 at 16:09 GMT
			ORGANIZATION 
				"Huawei Technologies Co.,Ltd."
			CONTACT-INFO 
				"
				Huawei Industrial Base
                Bantian, Longgang
                Shenzhen 518129
                People's Republic of China
                Website: http://www.huawei.com
                Email: support@huawei.com
				"
			DESCRIPTION 
				"
				V1.00
				The HUAWEI-SECURITY-TDNS-MIB contains objects to manage the firewall TDNS module.
				"
				--  Revision history
				 REVISION    "201401071609Z"
                                 DESCRIPTION "V1.00, completed the first draft."
			::= { hwSecurity 72 }

		
	
--
-- Node definitions
--
	
--  1.3.6.1.4.1.2011.6.122.72
-- January 07, 2014 at 16:09 GMT
-- 
-- Node definitions
-- 
--  1.3.6.1.4.1.2011.6.122.72
-- January 07, 2014 at 16:09 GMT
-- 
-- Node definitions
-- 
--  1.3.6.1.4.1.2011.6.122.67
-- January 07, 2014 at 16:09 GMT
-- 
-- Node definitions
-- 
--  1.3.6.1.4.1.2011.6.122.67
-- January 07, 2014 at 16:09 GMT
-- 
-- Node definitions
-- 
--  1.3.6.1.4.1.2011.6.122.68
-- January 07, 2013 at 16:09 GMT
-- 
-- Node definitions
-- 
--  January 07, 2013 at 16:09 GMT
-- 
-- Node definitions
-- 
-- 1.3.6.1.4.1.2011
-- 1.3.6.1.4.1.2011
-- 1.3.6.1.4.1.2011
-- 1.3.6.1.4.1.2011
-- 1.3.6.1.4.1.2011
-- 1.3.6.1.4.1.2011
		-- 1.3.6.1.4.1.2011
		huawei OBJECT IDENTIFIER ::= { enterprises 2011 }

		
--       1.3.6.1.4.1.2011.6
-- 1.3.6.1.4.1.2011.6
-- 1.3.6.1.4.1.2011.6
-- 1.3.6.1.4.1.2011.6
-- 1.3.6.1.4.1.2011.6
-- 1.3.6.1.4.1.2011.6
		-- 1.3.6.1.4.1.2011.6
		huaweiUtility OBJECT IDENTIFIER ::= { huawei 6 }

		
--       1.3.6.1.4.1.2011.6.122
-- 1.3.6.1.4.1.2011.6.122
-- 1.3.6.1.4.1.2011.6.122
-- 1.3.6.1.4.1.2011.6.122
-- 1.3.6.1.4.1.2011.6.122
-- 1.3.6.1.4.1.2011.6.122
		-- 1.3.6.1.4.1.2011.6.122
		hwSecurity OBJECT IDENTIFIER ::= { huaweiUtility 122 }

		
--      1.3.6.1.4.1.2011.6.122.68.1
-- 1.3.6.1.4.1.2011.6.122.67.1
-- 1.3.6.1.4.1.2011.6.122.67.1
-- 1.3.6.1.4.1.2011.6.122.72.1
-- 1.3.6.1.4.1.2011.6.122.72.1
		-- 1.3.6.1.4.1.2011.6.122.72.1
		hwTDnsNotification OBJECT IDENTIFIER ::= { hwTDns 1 }

		
--      1.3.6.1.4.1.2011.6.122.68.1.1
-- 1.3.6.1.4.1.2011.6.122.67.1.1
-- 1.3.6.1.4.1.2011.6.122.67.1.1
-- 1.3.6.1.4.1.2011.6.122.72.1.1
-- 1.3.6.1.4.1.2011.6.122.72.1.1
		-- 1.3.6.1.4.1.2011.6.122.72.1.1
		hwTDnsTrapObjects OBJECT IDENTIFIER ::= { hwTDnsNotification 1 }

		
--       ===============================================
-- TrapObject.
-- ===============================================
-- 1.3.6.1.4.1.2011.6.122.45.1.1.1
-- 1.3.6.1.4.1.2011.6.122.68.1.1.1
-- 1.3.6.1.4.1.2011.6.122.67.1.1.1
-- 1.3.6.1.4.1.2011.6.122.67.1.1.1
-- 1.3.6.1.4.1.2011.6.122.72.1.1.1
-- 1.3.6.1.4.1.2011.6.122.72.1.1.1
		-- 1.3.6.1.4.1.2011.6.122.72.1.1.1
		hwTDnsServerIp OBJECT-TYPE
			SYNTAX IpAddress
			MAX-ACCESS accessible-for-notify
			STATUS current
			DESCRIPTION
				"The TDNS Server Ip Address"
			::= { hwTDnsTrapObjects 1 }

		
--       1.3.6.1.4.1.2011.6.122.45.1.1.1
-- 1.3.6.1.4.1.2011.6.122.45.1.1.2	
-- 1.3.6.1.4.1.2011.6.122.68.1.1.2
-- 1.3.6.1.4.1.2011.6.122.67.1.1.2
-- 1.3.6.1.4.1.2011.6.122.67.1.1.2
-- 1.3.6.1.4.1.2011.6.122.72.1.1.2
-- 1.3.6.1.4.1.2011.6.122.72.1.1.2
		-- 1.3.6.1.4.1.2011.6.122.72.1.1.2
		hwTDnsOldStatus OBJECT-TYPE
			SYNTAX OCTET STRING
			MAX-ACCESS accessible-for-notify
			STATUS current
			DESCRIPTION
				"The Old Status of TDNS Server"
			::= { hwTDnsTrapObjects 2 }

		
--      1.3.6.1.4.1.2011.6.122.68.1.1.3
-- 1.3.6.1.4.1.2011.6.122.67.1.1.3
-- 1.3.6.1.4.1.2011.6.122.67.1.1.3
-- 1.3.6.1.4.1.2011.6.122.72.1.1.3
-- 1.3.6.1.4.1.2011.6.122.72.1.1.3
		-- 1.3.6.1.4.1.2011.6.122.72.1.1.3
		hwTDnsNewStatus OBJECT-TYPE
			SYNTAX OCTET STRING
			MAX-ACCESS accessible-for-notify
			STATUS current
			DESCRIPTION
				"The New Status of TDNS Server"
			::= { hwTDnsTrapObjects 3 }

		
--      1.3.6.1.4.1.2011.6.122.68.2
-- 1.3.6.1.4.1.2011.6.122.67.2
-- 1.3.6.1.4.1.2011.6.122.67.2
-- 1.3.6.1.4.1.2011.6.122.72.2
-- 1.3.6.1.4.1.2011.6.122.72.2
		-- 1.3.6.1.4.1.2011.6.122.72.2
		hwTDnsTraps OBJECT IDENTIFIER ::= { hwTDns 2 }

		
--       ===============================================
-- definition of traps.      
-- ===============================================                                
-- 1.3.6.1.4.1.2011.6.122.68.2.1
-- 1.3.6.1.4.1.2011.6.122.67.2.1
-- 1.3.6.1.4.1.2011.6.122.67.2.1
-- 1.3.6.1.4.1.2011.6.122.72.2.1
-- 1.3.6.1.4.1.2011.6.122.72.2.1
		-- 1.3.6.1.4.1.2011.6.122.72.2.1
		hwTDnsServerStateUp NOTIFICATION-TYPE
			OBJECTS { hwTDnsServerIp, hwTDnsOldStatus, hwTDnsNewStatus }
			STATUS current
			DESCRIPTION 
				"The TDNS rserver changes status to up"
			::= { hwTDnsTraps 1 }

		
--      1.3.6.1.4.1.2011.6.122.68.2.2
-- 1.3.6.1.4.1.2011.6.122.67.2.2
-- 1.3.6.1.4.1.2011.6.122.67.2.2
-- 1.3.6.1.4.1.2011.6.122.72.2.2
-- 1.3.6.1.4.1.2011.6.122.72.2.2
		-- 1.3.6.1.4.1.2011.6.122.72.2.2
		hwTDnsServerStateDown NOTIFICATION-TYPE
			OBJECTS { hwTDnsServerIp, hwTDnsOldStatus, hwTDnsNewStatus }
			STATUS current
			DESCRIPTION 
				"The TDNS rserver changes status to down"
			::= { hwTDnsTraps 2 }

		
--      1.3.6.1.4.1.2011.6.122.68.3
-- 1.3.6.1.4.1.2011.6.122.67.3
-- 1.3.6.1.4.1.2011.6.122.67.3
-- 1.3.6.1.4.1.2011.6.122.72.3
-- 1.3.6.1.4.1.2011.6.122.72.3
		-- 1.3.6.1.4.1.2011.6.122.72.3
		hwTDnsConformance OBJECT IDENTIFIER ::= { hwTDns 3 }

		
--      1.3.6.1.4.1.2011.6.122.68.3.1
-- 1.3.6.1.4.1.2011.6.122.67.3.1
-- 1.3.6.1.4.1.2011.6.122.67.3.1
-- 1.3.6.1.4.1.2011.6.122.72.3.1
-- 1.3.6.1.4.1.2011.6.122.72.3.1
		-- 1.3.6.1.4.1.2011.6.122.72.3.1
		hwTDnsCompliances OBJECT IDENTIFIER ::= { hwTDnsConformance 1 }

		
--      1.3.6.1.4.1.2011.6.122.68.3.1.1
-- this module
-- 1.3.6.1.4.1.2011.6.122.67.3.1.1
-- this module
-- 1.3.6.1.4.1.2011.6.122.67.3.1.1
-- this module
-- 1.3.6.1.4.1.2011.6.122.72.3.1.1
-- 1.3.6.1.4.1.2011.6.122.72.3.1.1
-- this module
		-- 1.3.6.1.4.1.2011.6.122.72.3.1.1
		hwTDnsCompliance MODULE-COMPLIANCE
			STATUS current
			DESCRIPTION 
				"Description."
			MODULE -- this module
				MANDATORY-GROUPS { hwTDnsObjectGroup, hwTDnsTrapGroup }
			::= { hwTDnsCompliances 1 }

		
--      1.3.6.1.4.1.2011.6.122.68.3.2
-- 1.3.6.1.4.1.2011.6.122.67.3.2
-- 1.3.6.1.4.1.2011.6.122.67.3.2
-- 1.3.6.1.4.1.2011.6.122.72.3.2
-- 1.3.6.1.4.1.2011.6.122.72.3.2
		-- 1.3.6.1.4.1.2011.6.122.72.3.2
		hwTDnsMibGroups OBJECT IDENTIFIER ::= { hwTDnsConformance 2 }

		
--      1.3.6.1.4.1.2011.6.122.68.3.2.1
-- 1.3.6.1.4.1.2011.6.122.67.3.2.1
-- 1.3.6.1.4.1.2011.6.122.67.3.2.1
-- 1.3.6.1.4.1.2011.6.122.72.3.2.1
-- 1.3.6.1.4.1.2011.6.122.72.3.2.1
		-- 1.3.6.1.4.1.2011.6.122.72.3.2.1
		hwTDnsObjectGroup OBJECT-GROUP
			OBJECTS { hwTDnsServerIp, hwTDnsOldStatus, hwTDnsNewStatus }
			STATUS current
			DESCRIPTION 
				"Description."
			::= { hwTDnsMibGroups 1 }

		
--      1.3.6.1.4.1.2011.6.122.68.3.2.2
-- 1.3.6.1.4.1.2011.6.122.67.3.2.2
-- 1.3.6.1.4.1.2011.6.122.67.3.2.2
-- 1.3.6.1.4.1.2011.6.122.72.3.2.2
-- 1.3.6.1.4.1.2011.6.122.72.3.2.2
		-- 1.3.6.1.4.1.2011.6.122.72.3.2.2
		hwTDnsTrapGroup NOTIFICATION-GROUP
			NOTIFICATIONS { hwTDnsServerStateUp, hwTDnsServerStateDown }
			STATUS current
			DESCRIPTION 
				"Description."
			::= { hwTDnsMibGroups 2 }

		
	
	END

--
-- HUAWEI-SECURITY-TDNS-MIB.mib
--
