--  =================================================================
-- Copyright (C) 2020 by  HUAWEI TECHNOLOGIES. All rights reserved.
--
-- Description:HUAWEI-BRAS-SRVCFG-INTERFACE-MIB
-- Reference:
-- Version: V2.50
-- History:
--         v2.15
--         modified by huangjun 2009-12-08
--         modified by weibo 2014-03-24
--         modified by liuzhiru 2015-03-09
--         modified by gujun 2015-06-29
--         modified by gujun 2015-07-14
--         modified by yuanbaopeng 2015-11-23
--         modified by liuyao 2015-12-23
--         modified by maodizhe 2015-12-26
--         modified by zhangsai 2016-02-22
--         modified by yangshanjun 2017-10-11
--         modified by ruanyuzhong 2017-11-30
--         modified by zhangdong 2018-01-15
--         modified by zhangdong 2018-01-16
--         modified by ruanyuzhong 2018-05-10
--         modified by wanghaoran 2018-06-16
--         modified by caoxiaohui 2018-07-25
--         modified by wanjiahuan 2019-01-19
--         modified by zhanghui 2019-01-30
--         modified by maxiaoming 2019-02-14
--         modified by zhourui 2019-03-29
--         modified by wenyaowu 2019-04-13
--         modified by tangchen 2019-07-01
--         modified by baojingjing 2019-07-18
--         modified by liuhaijuan  2019-09-21
--         modified by pengjunhua 2019-10-12
--         modified by zhoulisa 2019-12-24
--         modified by gaocan 2020-03-11
--         modified by sunhe 2020-03-31
-- =================================================================

    HUAWEI-BRAS-SRVCFG-INTERFACE-MIB DEFINITIONS ::= BEGIN

        IMPORTS
           hwBRASMib
                                FROM HUAWEI-MIB
                        InterfaceIndex
                                FROM IF-MIB
                        EnabledStatus
                                FROM P-BRIDGE-MIB
                        MODULE-IDENTITY,
                        IpAddress, Integer32, Counter64, OBJECT-TYPE,Unsigned32,NOTIFICATION-TYPE
	           FROM SNMPv2-SMI
	   MODULE-COMPLIANCE,OBJECT-GROUP
                                FROM SNMPv2-CONF
                        RowStatus, MacAddress, TruthValue, DisplayString
                                FROM SNMPv2-TC;


        hwBRASSrvcfgInterface MODULE-IDENTITY
            LAST-UPDATED "202003311018Z"        -- Mar 31, 2020 at 10:18 GMT
            ORGANIZATION
                 "Huawei Technologies Co.,Ltd."
            CONTACT-INFO
		 "Huawei Industrial Base
		  Bantian, Longgang
		   Shenzhen 518129
		   People's Republic of China
		   Website: http://www.huawei.com
		   Email: support@huawei.com
		 "
            DESCRIPTION
                "modify hwBRASIfVlanAccessLimit."
            REVISION    "202003311018Z"
            DESCRIPTION
                "del hwBRASIfCvlanVciStatTable ATM."
            REVISION    "202003111722Z" 
           DESCRIPTION
                "add hwCuVxlanTunnelPlrAlarm hwCuVxlanTunnelPlrResume hwCuVxlanTunnelPlr."
            REVISION    "201912241940Z"
           DESCRIPTION
                "add hwCuUpVxlanTunnelDown hwCuUpVxlanTunnelResume."
            REVISION    "201910121940Z"
          DESCRIPTION
                "add description."
            REVISION    "201909211541Z"
           DESCRIPTION
                "add hwBRASLicenseItemEvent."
            REVISION    "201907190901Z"

            DESCRIPTION
                "modify hwBRASIfDhcpSessionMismatch."
            REVISION    "201907011629Z"
            DESCRIPTION
                "modify hwBRASIfCfgArpFailTimes."
            REVISION    "201904131629Z"
            DESCRIPTION
                "add hwBRASSrvcfgIfVpnAccessNumber."
            REVISION    "201903291339Z"
            DESCRIPTION
                "add hwBRASSrvcfgIfVpnStatTable."
            REVISION    "201902141339Z"
            DESCRIPTION
                "modify hwBRASIfCfgArpFailTimes."
            REVISION    "201901301339Z"
            DESCRIPTION
                "modify hwBRASIfQinQVlanID and hwL3SubscriberIspVpnId ."
            REVISION    "201901261339Z"
            DESCRIPTION
                "add hwBRASActiveBasSlotFailAlarm hwBRASActiveBasSlotFailResume hwBRASBoardLicenseName hwBRASBoardLicenseDescription hwBRASBoardLicenseSlotID."
            REVISION    "201901191339Z"
			
            DESCRIPTION
                "modify nodes for CUVXLANTUNNEL-ALARM:
                 1. hwCuVxlanTunnelUpId
		 2. hwCuVxlanTunnelSrcIpAddr
		 3. hwCuVxlanTunnelPeerIpAddr
		 4. hwCuVxlanTunnelInVni
		 5. hwCuVxlanTunnelVpn
		 6. hwCuVxlanTunnelDown
		 7. hwCuVxlanTunnelResume"
            REVISION    "201807251339Z"
            DESCRIPTION 
                "modify hwBRASIfCfgAccessDelayType."

            REVISION    "201807111339Z"
            DESCRIPTION 
                "modify hwBRASIfDhcpSessionMismatch hwPortAccessLimitLimit hwPortAccessLimitNumber hwPortAccessLimitAuthenedNumber."

            REVISION    "201806161339Z"
            DESCRIPTION 
                "modify hwIpv4FrameRouteUsage."

            REVISION    "201805101339Z"
            DESCRIPTION 
                "modify hwCuVxlanTunnelVpn."
				
            REVISION    "201801221339Z"
            DESCRIPTION 
                "modify hwBRASIfStatisticTable."

            REVISION    "201801171339Z"
            DESCRIPTION 
                "modify hwAccessUserFlowStatisticsEnableFlag."

            REVISION    "201801151339Z"
            DESCRIPTION 
                "modify hwBRASIfVlanAccessTable hwBRASIfSvlanVpiStatTable hwBRASIfCvlanVciStatTable."

            REVISION    "201711301339Z"	 
            		 
            DESCRIPTION
                "added 7 nodes for VXLANTUNNEL-ALARM:
                 1. hwVxlanTunnelEvplId
                 2. hwVxlanTunnelUpId
				 3. hwVxlanTunnelSrcAddr
				 4. hwVxlanTunnelPeerAddr
				 5. hwVxlanTunnelInVni
				 6. hwVxlanTunnelDown
				 7. hwVxlanTunnelResumed"
            REVISION    "201710111339Z"
        
           DESCRIPTION
                "Change description of hwBRASIfCvlanVciStatTable"
			REVISION    "201707291339Z"
			
			DESCRIPTION
                "added 3 nodes for srvcfg TRUNK-ALARM:
                 1. hwSrvcfgSubCardReachMaxRecomNumberSlotId
                 2. hwSrvcfgSubCardReachMaxRecomNumberCardId
                 3. hwSrvcfgSubCardReachMaxRecomNumber"
           

           REVISION    "201707281339Z"
            
           DESCRIPTION
                "Change description of hwBRASIfVlanAccessTable, hwBRASIfSvlanVpiStatTable and hwBRASIfCvlanVciStatTable"

            REVISION    "201603301339Z"
            
           DESCRIPTION
                "added 1 nodes for srvcfg TRUNK-ALARM:
                 1. hwBoardSetGTPModeNotSupportBas"
            REVISION    "201602221339Z"

            DESCRIPTION
                "added 2 nodes for srvcfg TRUNK-ALARM:
                 1. hwSrvcfgInterfaceTrapOid
                 2. hwBRASBoardNotSupportBasAlarm"
            REVISION    "201512262239Z"

            DESCRIPTION
                "Del 6 nodes for dhcpv6 lifetime proxy:
                 1. hwBRASIfCfgDhcpv6ProxyPreferredLifetime
                 2. hwBRASIfCfgDhcpv6ProxyValidLifetime
                 3. hwBRASIfCfgDhcpv6ProxyFirstStepPreferredLifetime
                 4. hwBRASIfCfgDhcpv6ProxyFirstStepValidLifetime
                 5. hwBRASIfCfgDhcpv6ProxySecondStepPreferredLifetime
                 6. hwBRASIfCfgDhcpv6ProxySecondeStepValidLifetime"
            REVISION    "201512231108Z"
				 
            DESCRIPTION
                "Add 2 nodes for dhcpv4 step lease proxy:
                 1. hwBRASIfCfgDhcpLeaseProxyFirstStep
                 2. hwBRASIfCfgDhcpLeaseProxySecondStep"
            REVISION    "201512161745Z"
            
            DESCRIPTION
                "Add 6 nodes for dhcpv6 lease proxy:
                 1. hwBRASIfCfgDhcpv6ProxyPreferredLifetime
                 2. hwBRASIfCfgDhcpv6ProxyValidLifetime
                 3. hwBRASIfCfgDhcpv6ProxyFirstStepPreferredLifetime
                 4. hwBRASIfCfgDhcpv6ProxyFirstStepValidLifetime
                 5. hwBRASIfCfgDhcpv6ProxySecondStepPreferredLifetime
                 6. hwBRASIfCfgDhcpv6ProxySecondeStepValidLifetime"
            REVISION    "201511251745Z"

            DESCRIPTION
                "add hwBRASCvlanStatTable.
                 add hwBRASSvlanStatTable.
                 add hwBRASVpiStatTable.
                "
            REVISION    "201511231608Z"

            DESCRIPTION
                "Modified node hwBRASIfVlanAccessLimit."
            REVISION    "201509111608Z"

            DESCRIPTION
                "Modified node hwBRASIfCfgDhcpLeaseProxy."
            REVISION    "201507141608Z"

            DESCRIPTION
                "Add node hwBRASIfCfgDhcpLeaseProxy."
            REVISION    "201506291608Z"

           DESCRIPTION
                "Modified node hwBRASIfCfgArpInterval."
            REVISION    "201503091608Z"

            DESCRIPTION
                "Add node hwBRASIfDhcpSessionMismatch."
            REVISION    "201408251608Z"

            DESCRIPTION
                "modified add access delay loadbalance group ."
            REVISION    "201408221608Z"
            DESCRIPTION
                "add access delay loadbalance group ."
            REVISION    "201408211608Z"
            DESCRIPTION
                "The MIB contains objects of module SRVCFG INTERFACE."
            REVISION    "201310171104Z"
            DESCRIPTION 
                "add hwBRASIfSvlanVpiStatTable"
            REVISION    "201303242103Z"
            DESCRIPTION 
                "modify hwServiceIfCfgQosProfile"
			REVISION    "200403041608Z"
            DESCRIPTION 
                "add hwBRASIfCfgIPV6AuthMethod"			
            ::= { hwBRASMib 1 }



--
-- Node definitions
--
        hwSrvcfgInterfaceMibObjects OBJECT IDENTIFIER ::= { hwBRASSrvcfgInterface 1 }

        hwBRASIfCfgTable OBJECT-TYPE
            SYNTAX SEQUENCE OF HwBRASIfCfgEntry
            MAX-ACCESS not-accessible
            STATUS current
            DESCRIPTION
                "BRAS interface configure table
                "
            ::= { hwSrvcfgInterfaceMibObjects 1 }

        hwBRASIfCfgEntry OBJECT-TYPE
            SYNTAX HwBRASIfCfgEntry
            MAX-ACCESS not-accessible
            STATUS current
            DESCRIPTION
                "
                BRAS interface entry.
                "
            INDEX { hwBRASIfCfgIfIndex }
            ::= { hwBRASIfCfgTable 1 }

        HwBRASIfCfgEntry ::=
            SEQUENCE {
                hwBRASIfCfgIfIndex
                    InterfaceIndex,
                hwBRASIfCfgAccessType
                    INTEGER,
                hwBRASIfCfgBRASIfName
                    DisplayString,
                hwBRASIfCfgPreAuthDomain
                    DisplayString,
                hwBRASIfCfgAuthDomain
                    DisplayString,
                hwBRASIfCfgForceAuthDomain
                    INTEGER,
                hwBRASIfCfgAcctCpyRdSvr
                    DisplayString,
                hwBRASIfCfgAuthMethod
                    Integer32,
                hwBRASIfCfgNasPortType
                    Integer32,
                hwBRASIfCfgLeaseName
                    DisplayString,
                hwBRASIfCfgLeasePwd
                    DisplayString,
                hwBRASIfCfgArpInterval
                    Integer32,
                hwBRASIfCfgArpFailTimes
                    Integer32,
                hwBRASIfCfgArpProxy
                    TruthValue,
                hwBRASIfCfgRoamIsp
                    TruthValue,
                hwBRASIfCfgDhcpBroadCast
                    TruthValue,
                hwBRASIfCfgHostCar
                    Integer32,
                hwBRASIfCfgRowStatus
                    RowStatus,
                hwBRASIfCfgEapTrigger
                    TruthValue,
                hwBRASIfCfgWlanSwitch
                    Integer32,
                hwBRASIfCfgWlanAuthorization
                    TruthValue,
                hwBRASIfCfgDhcpShortLease
                    Integer32,
                hwBRASIfCfgRoamDomain
                    DisplayString,
                hwBRASIfVsiName
                    DisplayString,
                hwBRASIfCfgOption82
                    TruthValue,
                hwBRASIfVpnInstance
                    DisplayString,
                hwBRASIfCopyMulticasePerUser
                    TruthValue,
                hwBRASIfCfgNDProxy
                    TruthValue,
                hwBRASIfCfgVBasMAC
                    MacAddress,
                hwBRASIfCfgVBasAuthMode
                    INTEGER,
                hwBRASIfCfgPermitDomain1
                    DisplayString,
                hwBRASIfCfgPermitDomain2
                    DisplayString,
                hwBRASIfCfgPermitDomain3
                    DisplayString,
                hwBRASIfCfgPermitDomain4
                    DisplayString,
                hwBRASIfCfgAccessDelayType
                    INTEGER,
                hwBRASIfCfgTermlessDelayTime
                    Integer32,
                hwBRASIfCfgOddMacDelayTime
                    Integer32,
                hwBRASIfCfgEvenMacDelayTime
                    Integer32,
                hwBRASIfCfgAccessNodeIdentify
                    DisplayString,
                hwBRASIfCfgAniDelayTime
                    Integer32,
                hwBRASIfCfgRemoteBackupProfile
                    DisplayString,
                hwBRASIfCfgOption60
                    TruthValue,
                hwBRASIfCfgIpTrigger
                    TruthValue,
                hwBRASIfCfgArpTrigger
                    TruthValue,
                hwBRASIfCfgWlanSSID
                    TruthValue,
                hwBRASIfCfgDhcpProxy
                    TruthValue,
                hwBRASIfCfgTrust8021pProtocol   --added by w00175317
                    TruthValue,          --added by w00175317
                hwOption82ParseMode     --added by w00175317 for Option82ParseMode
                    INTEGER,
                hwBRASIfCfgNasLogicSysname       -- Added by l62892 for DTS2012072805071
                    DisplayString,               -- Added by l62892 for DTS2012072805071
                hwBRASIfCfgLeasePwdKeyType       -- Addded by n00176422 for mib redline
                 INTEGER,
                hwBRASIfCopyMulticasePerVlan
                    TruthValue,
                hwBRASIfCfgIPV6AuthMethod
                   Integer32,
                hwBRASIfAccessNumber   --added by w00175317 for  DTS2013111105691
                   Integer32,
                hwBRASIfCfgDelayLoadBalanceTime
                   Integer32,
               hwBRASIfCfgDelayLoadBalanceName
                   DisplayString,         
               hwBRASIfDhcpSessionMismatch
                   INTEGER,
               hwBRASIfCfgDhcpLeaseProxy
                   Integer32,
               hwBRASIfCfgDhcpLeaseProxyFirstStep
                   Integer32,
               hwBRASIfCfgDhcpLeaseProxySecondStep
                   Integer32
             }

        hwBRASIfCfgIfIndex OBJECT-TYPE
            SYNTAX InterfaceIndex
            MAX-ACCESS read-only
            STATUS current
            DESCRIPTION
                "This object indicates the index of a BAS interface.
                "
            ::= { hwBRASIfCfgEntry 1 }

        hwBRASIfCfgAccessType OBJECT-TYPE
            SYNTAX INTEGER
                {
                interface(0),
                l2subscriber(1),
                l2leasedline(2),
                l3leasedline(3),
                l2vpnleasedline(4),
                l3subscriber(6)
                }
            MAX-ACCESS read-write
            STATUS current
            DESCRIPTION
                "This object indicates the type of an access user on the BAS interface.
                "
            ::= { hwBRASIfCfgEntry 2 }

        hwBRASIfCfgBRASIfName OBJECT-TYPE
            SYNTAX DisplayString (SIZE (1..32))
            MAX-ACCESS read-write
            STATUS current
            DESCRIPTION
                "This object indicates the name of a BAS interface.
                "
            ::= { hwBRASIfCfgEntry 3 }

        hwBRASIfCfgPreAuthDomain OBJECT-TYPE
            SYNTAX DisplayString (SIZE (1..64))
            MAX-ACCESS read-write
            STATUS current
            DESCRIPTION
                "This object indicates the default pre-authentication domain."
            ::= { hwBRASIfCfgEntry 4 }

        hwBRASIfCfgAuthDomain OBJECT-TYPE
            SYNTAX DisplayString (SIZE (1..64))
            MAX-ACCESS read-write
            STATUS current
            DESCRIPTION
                "This object indicates the default authentication domain.
                "
            ::= { hwBRASIfCfgEntry 5 }

        hwBRASIfCfgForceAuthDomain OBJECT-TYPE
            SYNTAX INTEGER
                {
                none(0),
                force(1),
                replace(2)
                }
            MAX-ACCESS read-write
            STATUS current
            DESCRIPTION
                "This object indicates whether the authentication domain is forcibly changed.
                "
            DEFVAL { none }
            ::= { hwBRASIfCfgEntry 6 }

        hwBRASIfCfgAcctCpyRdSvr OBJECT-TYPE
            SYNTAX DisplayString (SIZE (1..32))
            MAX-ACCESS read-write
            STATUS current
            DESCRIPTION
                "This object indicates the name of the RADIUS server to which accounting packets are copied.
                "
            ::= { hwBRASIfCfgEntry 7 }

        hwBRASIfCfgAuthMethod OBJECT-TYPE
            SYNTAX Integer32 (1..16)
            MAX-ACCESS read-write
            STATUS current
            DESCRIPTION
                "
                ppp(1)
                dot1x(2)
                web(4)
                fast(8)
                bind(16)
                "
            DEFVAL { 1 }
            ::= { hwBRASIfCfgEntry 8 }

        hwBRASIfCfgNasPortType OBJECT-TYPE
            SYNTAX Integer32 (0..20)
            MAX-ACCESS read-write
            STATUS current
            DESCRIPTION
                "This object indicates the access interface type.
                "
            ::= { hwBRASIfCfgEntry 9 }

        hwBRASIfCfgLeaseName OBJECT-TYPE
            SYNTAX DisplayString (SIZE (1..253))
            MAX-ACCESS read-write
            STATUS current
            DESCRIPTION
                "This object indicates the name of a VLAN leased line user.
                "
            ::= { hwBRASIfCfgEntry 10 }

        hwBRASIfCfgLeasePwd OBJECT-TYPE
            SYNTAX DisplayString (SIZE (0..128))
            MAX-ACCESS read-write
            STATUS current
            DESCRIPTION
                "This object indicates the password of a VLAN leased line.
                "
            ::= { hwBRASIfCfgEntry 11 }

        hwBRASIfCfgArpInterval OBJECT-TYPE
            SYNTAX Integer32 (0..1801)
            MAX-ACCESS read-write
            STATUS current
            DESCRIPTION
                "This object indicates the interval for sending an ARP packet. 
                "
            DEFVAL { 30 }
            ::= { hwBRASIfCfgEntry 12 }

        hwBRASIfCfgArpFailTimes OBJECT-TYPE
            SYNTAX Integer32 (0..120)
            MAX-ACCESS read-write
            STATUS current
            DESCRIPTION
                "This object indicates the times an ARP packet can be re-transmitted.
                "
            DEFVAL { 5 }
            ::= { hwBRASIfCfgEntry 13 }

        hwBRASIfCfgArpProxy OBJECT-TYPE
            SYNTAX TruthValue
            MAX-ACCESS read-write
            STATUS current
            DESCRIPTION
                "This object indicates whether proxy ARP is applied.
                "
            DEFVAL { false }
            ::= { hwBRASIfCfgEntry 14 }

        hwBRASIfCfgRoamIsp OBJECT-TYPE
            SYNTAX TruthValue
            MAX-ACCESS read-write
            STATUS current
            DESCRIPTION
                "This object indicates whether to use the roaming domain.
                "
            DEFVAL { false }
            ::= { hwBRASIfCfgEntry 15 }

        hwBRASIfCfgDhcpBroadCast OBJECT-TYPE
            SYNTAX TruthValue
            MAX-ACCESS read-write
            STATUS current
            DESCRIPTION
                "This object indicates the DHCP broadcast status.
                "
            DEFVAL { false }
            ::= { hwBRASIfCfgEntry 16 }

        hwBRASIfCfgHostCar OBJECT-TYPE
            SYNTAX Integer32 (0..16)
            MAX-ACCESS read-write
            STATUS current
            DESCRIPTION
                "
                "
            DEFVAL { 0 }
            ::= { hwBRASIfCfgEntry 17 }

        hwBRASIfCfgRowStatus OBJECT-TYPE
            SYNTAX RowStatus
            MAX-ACCESS read-write
            STATUS current
            DESCRIPTION
                "This object indicates the status of a BAS interface.
                "
            ::= { hwBRASIfCfgEntry 18 }

        hwBRASIfCfgEapTrigger OBJECT-TYPE
            SYNTAX TruthValue
            MAX-ACCESS read-write
            STATUS current
            DESCRIPTION
                "
                "
            DEFVAL { false }
            ::= { hwBRASIfCfgEntry 19 }

        hwBRASIfCfgWlanSwitch OBJECT-TYPE
            SYNTAX Integer32 (0..1)
            MAX-ACCESS read-write
            STATUS current
            DESCRIPTION
                "
                "
            DEFVAL { 0 }
            ::= { hwBRASIfCfgEntry 20 }

        hwBRASIfCfgWlanAuthorization OBJECT-TYPE
            SYNTAX TruthValue
            MAX-ACCESS read-write
            STATUS current
            DESCRIPTION
                "
                "
            DEFVAL { false }
            ::= { hwBRASIfCfgEntry 21 }

        hwBRASIfCfgDhcpShortLease OBJECT-TYPE
            SYNTAX Integer32 (9..240)
            MAX-ACCESS read-write
            STATUS current
            DESCRIPTION
                "
                "
            DEFVAL { 9 }
            ::= { hwBRASIfCfgEntry 22 }

        hwBRASIfCfgRoamDomain OBJECT-TYPE
            SYNTAX DisplayString (SIZE (1..64))
            MAX-ACCESS read-write
            STATUS current
            DESCRIPTION
                "This object indicates the name of a roaming domain.
                "
            ::= { hwBRASIfCfgEntry 23 }

        hwBRASIfVsiName OBJECT-TYPE
            SYNTAX DisplayString (SIZE (1..20))
            MAX-ACCESS read-write
            STATUS current
            DESCRIPTION
                "
                VSI Name
                "
            ::= { hwBRASIfCfgEntry 24 }

        hwBRASIfCfgOption82 OBJECT-TYPE
            SYNTAX TruthValue
            MAX-ACCESS read-write
            STATUS current
            DESCRIPTION
                "
                option82 switch
                "
            DEFVAL { false }
            ::= { hwBRASIfCfgEntry 25 }

        hwBRASIfVpnInstance OBJECT-TYPE
            SYNTAX DisplayString (SIZE (1..31))
            MAX-ACCESS read-write
            STATUS current
            DESCRIPTION
                "
                VPN-instance name
                "
            ::= { hwBRASIfCfgEntry 26 }

        hwBRASIfCopyMulticasePerUser OBJECT-TYPE
            SYNTAX TruthValue
            MAX-ACCESS read-write
            STATUS current
            DESCRIPTION
                "This object indicates whether to enable multicast data copying per session.
                "
            DEFVAL { false }
            ::= { hwBRASIfCfgEntry 27 }

        hwBRASIfCfgNDProxy OBJECT-TYPE
            SYNTAX TruthValue
            MAX-ACCESS read-write
            STATUS current
            DESCRIPTION
                "
                "
            DEFVAL { false }
            ::= { hwBRASIfCfgEntry 28 }

        hwBRASIfCfgVBasMAC OBJECT-TYPE
            SYNTAX MacAddress
            MAX-ACCESS read-write
            STATUS current
            DESCRIPTION
                "
                "
            ::= { hwBRASIfCfgEntry 29 }

        hwBRASIfCfgVBasAuthMode OBJECT-TYPE
            SYNTAX INTEGER
                {
                ignore(0),
                reject(1)
                }
            MAX-ACCESS read-write
            STATUS current
            DESCRIPTION
                "
                "
            DEFVAL { reject }
            ::= { hwBRASIfCfgEntry 30 }

        hwBRASIfCfgPermitDomain1 OBJECT-TYPE
            SYNTAX DisplayString (SIZE (1..64))
            MAX-ACCESS read-write
            STATUS current
            DESCRIPTION
                "This object indicates a domain that a BAS interface can access.
                "
            ::= { hwBRASIfCfgEntry 31 }

        hwBRASIfCfgPermitDomain2 OBJECT-TYPE
            SYNTAX DisplayString (SIZE (1..64))
            MAX-ACCESS read-write
            STATUS current
            DESCRIPTION
                "This object indicates a domain that a BAS interface can access.
                "
            ::= { hwBRASIfCfgEntry 32 }

        hwBRASIfCfgPermitDomain3 OBJECT-TYPE
            SYNTAX DisplayString (SIZE (1..64))
            MAX-ACCESS read-write
            STATUS current
            DESCRIPTION
                "This object indicates a domain that a BAS interface can access.
                "
            ::= { hwBRASIfCfgEntry 33 }

        hwBRASIfCfgPermitDomain4 OBJECT-TYPE
            SYNTAX DisplayString (SIZE (1..64))
            MAX-ACCESS read-write
            STATUS current
            DESCRIPTION
                "This object indicates a domain that a BAS interface can access.
                "
            ::= { hwBRASIfCfgEntry 34 }

        hwBRASIfCfgAccessDelayType OBJECT-TYPE
            SYNTAX INTEGER
                {
                none(0),
                termless(1),
                userinfomation(2),
                macaddress(3),
                loadbalancegroup(4), --added by g00248654 
                oddmac(5),
                evenmac(6)
                }
            MAX-ACCESS read-write
            STATUS current
            DESCRIPTION
                "This object indicates the type of the access delay.
                "
            ::= { hwBRASIfCfgEntry 35 }

        hwBRASIfCfgTermlessDelayTime OBJECT-TYPE
            SYNTAX Integer32 (0..2550)
            MAX-ACCESS read-write
            STATUS current
            DESCRIPTION
                "This object indicates the response delay of all access users.
                "
            DEFVAL { 0 }
            ::= { hwBRASIfCfgEntry 36 }

        hwBRASIfCfgOddMacDelayTime OBJECT-TYPE
            SYNTAX Integer32 (0..2550)
            MAX-ACCESS read-write
            STATUS current
            DESCRIPTION
                "This object indicates the response delay time of the users with odd MAC addresses.
                "
            DEFVAL { 0 }
            ::= { hwBRASIfCfgEntry 37 }

        hwBRASIfCfgEvenMacDelayTime OBJECT-TYPE
            SYNTAX Integer32 (0..2550)
            MAX-ACCESS read-write
            STATUS current
            DESCRIPTION
                "This object indicates the response delay time of the users with even MAC addresses.
                "
            DEFVAL { 0 }
            ::= { hwBRASIfCfgEntry 38 }

        hwBRASIfCfgAccessNodeIdentify OBJECT-TYPE
            SYNTAX DisplayString (SIZE (1..200))
            MAX-ACCESS read-write
            STATUS current
            DESCRIPTION
                "This object indicates the user packet's Option 82/PPPoE+ attribute to be matched. The value is a string of 1 to 32 characters.
                "
            ::= { hwBRASIfCfgEntry 39 }

        hwBRASIfCfgAniDelayTime OBJECT-TYPE
            SYNTAX Integer32 (0..2550)
            MAX-ACCESS read-write
            STATUS current
            DESCRIPTION
                "This object indicates the response delay set for access users according to the Option 82/PPPoE+ attribute.
                "
            DEFVAL { 0 }
            ::= { hwBRASIfCfgEntry 40 }

        hwBRASIfCfgRemoteBackupProfile OBJECT-TYPE
            SYNTAX DisplayString (SIZE (1..32))
            MAX-ACCESS read-write
            STATUS current
            DESCRIPTION
                "
                remote-backup-profile
                "
            ::= { hwBRASIfCfgEntry 42 }

        hwBRASIfCfgOption60 OBJECT-TYPE
            SYNTAX TruthValue
            MAX-ACCESS read-write
            STATUS current
            DESCRIPTION
                "
                option60 switch
                "
            DEFVAL { false }
            ::= { hwBRASIfCfgEntry 43 }

        hwBRASIfCfgIpTrigger OBJECT-TYPE
            SYNTAX TruthValue
            MAX-ACCESS read-write
            STATUS current
            DESCRIPTION
                "
                set ip-trigger flag
                "
            DEFVAL { false }
            ::= { hwBRASIfCfgEntry 44 }

        hwBRASIfCfgArpTrigger OBJECT-TYPE
            SYNTAX TruthValue
            MAX-ACCESS read-write
            STATUS current
            DESCRIPTION
                "
                set arp-trigger flag
                "
            DEFVAL { false }
            ::= { hwBRASIfCfgEntry 45 }

        hwBRASIfCfgWlanSSID OBJECT-TYPE
            SYNTAX TruthValue
            MAX-ACCESS read-write
            STATUS current
            DESCRIPTION
                "
                set WLAN-ssid flag
                "
            DEFVAL { false }
            ::= { hwBRASIfCfgEntry 46 }
            
        hwBRASIfCfgDhcpProxy OBJECT-TYPE
            SYNTAX TruthValue
            MAX-ACCESS read-write
            STATUS current
            DESCRIPTION
                "
                set DHCP-proxy flag
                "
            DEFVAL { false }
            ::= { hwBRASIfCfgEntry 47 }

 
 --begin: added by w00175317
        hwBRASIfCfgTrust8021pProtocol OBJECT-TYPE
            SYNTAX TruthValue
            MAX-ACCESS read-write
            STATUS current
            DESCRIPTION
                "
                set trust-8021p-protocol flag
                "
            DEFVAL { false }
            ::= { hwBRASIfCfgEntry 48 }
 --end: added by w00175317
 
        hwOption82ParseMode OBJECT-TYPE
            SYNTAX INTEGER
                {
                none(0),
                binary(1),
                tr101(2),
                cn(3)                
                }
            MAX-ACCESS read-write
            STATUS current
            DESCRIPTION
                "
                Configure access-line-id(dhcpv4 option82/pppoe+/dhcpv6 option18+37+17) parse mode.
                none(0): Configure access-line-id parse mode with default parse mode.
                binary(1): Configure access-line-id parse mode with binary.
                tr-101(2): Configure access-line-id parse mode with tr101.
                cn(3): Configure access-line-id parse mode with China Telecom.       
                "
            ::= { hwBRASIfCfgEntry 49 }

        -- Added by l62892 for DTS2012072805071
        hwBRASIfCfgNasLogicSysname OBJECT-TYPE
            SYNTAX DisplayString (SIZE (1..30))
            MAX-ACCESS read-write
            STATUS current
            DESCRIPTION
                "Set nas logic-sysname value."
            ::= { hwBRASIfCfgEntry 50 }
        -- End addition by l62892 for DTS2012072805071
        -- Begin: added by n00176422 for mib redline
        hwBRASIfCfgLeasePwdKeyType  OBJECT-TYPE
                SYNTAX INTEGER
                {
                    simple(1),
                    cipher(2),
                    none(3)
                }
            MAX-ACCESS read-write
            STATUS current
            DESCRIPTION
                "
        Lease user password type, none indicates not configure password.  
                "
                DEFVAL { cipher }
            ::= { hwBRASIfCfgEntry 51 }
        -- End: added by n00176422 for mib redline
            
        hwBRASIfCopyMulticasePerVlan OBJECT-TYPE
            SYNTAX TruthValue
            MAX-ACCESS read-write
            STATUS current
            DESCRIPTION
                "This object indicates the multicast control status.
                "
            DEFVAL { false }
            ::= { hwBRASIfCfgEntry 52 }

       hwBRASIfCfgIPV6AuthMethod OBJECT-TYPE
            SYNTAX Integer32 (1..16)
            MAX-ACCESS read-write
            STATUS current
            DESCRIPTION
                "
                ppp(1)
                dot1x(2)
                web(4)
                fast(8)
                bind(16)
                "
            DEFVAL { 1 }
            ::= { hwBRASIfCfgEntry 53 }
            
        hwBRASIfAccessNumber OBJECT-TYPE   -- added by w00175317 for DTS2013111105691
            SYNTAX Integer32
            MAX-ACCESS read-only
            STATUS current
            DESCRIPTION
                " 
                The interface access number.
                "
            ::= { hwBRASIfCfgEntry 54 }
        
        hwBRASIfCfgDelayLoadBalanceTime OBJECT-TYPE   -- added by g00248654            
            SYNTAX Integer32 (0..2550)
            MAX-ACCESS read-write
            STATUS current
            DESCRIPTION
                " 
                The according-server-group delay time.    
                "
            DEFVAL { 0 }    
            ::= { hwBRASIfCfgEntry 55 }
        
        hwBRASIfCfgDelayLoadBalanceName OBJECT-TYPE   -- added by g00248654
        	SYNTAX DisplayString (SIZE (1..31))
            MAX-ACCESS read-write
            STATUS current
            DESCRIPTION
                "
                The according-server-group name.
                "
            ::= { hwBRASIfCfgEntry 56 }        
 	         
        hwBRASIfDhcpSessionMismatch OBJECT-TYPE
            SYNTAX INTEGER
             {
                    default(1),
                    offline(2),
                    roamipv4(3),
                    roamipv6(4),
                    roamipv4ipv6(5),
                    roamnd(6),
                    roamipv4nd(7),
                    roamipv6nd(8),
                    roamipv4ipv6nd(9)
            }
            MAX-ACCESS read-write
            STATUS current
            DESCRIPTION
            "
               Set the action when mismatch happens.
               default: the online user not  to go offline.
               offline: the online user to go offline.
               roamipv4: change the online user's  physical location information.
            "
            DEFVAL { default }
            ::= { hwBRASIfCfgEntry 57 }

            hwBRASIfCfgDhcpLeaseProxy OBJECT-TYPE
            SYNTAX Integer32 (0|600..3600)
            MAX-ACCESS read-write
            STATUS current
            DESCRIPTION
            "
               DhcpLeaseProxy
            "
            DEFVAL { 0 }
            ::= { hwBRASIfCfgEntry 58 }

            hwBRASIfCfgDhcpLeaseProxyFirstStep OBJECT-TYPE
            SYNTAX Integer32 (0|300..599)
            MAX-ACCESS read-write
            STATUS current
            DESCRIPTION
            "
               DhcpLeaseProxy first-step
            "
            DEFVAL { 0 }
            ::= { hwBRASIfCfgEntry 59 }
            
            hwBRASIfCfgDhcpLeaseProxySecondStep OBJECT-TYPE
            SYNTAX Integer32 (0|1800..3600)
            MAX-ACCESS read-write
            STATUS current
            DESCRIPTION
            "
               DhcpLeaseProxy second-step
            "
            DEFVAL { 0 }
            ::= { hwBRASIfCfgEntry 60 }
        hwBRASIfVlanTable OBJECT-TYPE
            SYNTAX SEQUENCE OF HwBRASIfVlanEntry
            MAX-ACCESS not-accessible
            STATUS current
            DESCRIPTION
                "
                "
            ::= { hwSrvcfgInterfaceMibObjects 2 }

        hwBRASIfVlanEntry OBJECT-TYPE
            SYNTAX HwBRASIfVlanEntry
            MAX-ACCESS not-accessible
            STATUS current
            DESCRIPTION
                "
                Description.
                "
            INDEX { hwBRASIfVlanIfIndex, hwBRASIfVlanVlanId, hwBRASIfQinQVlanID }
            ::= { hwBRASIfVlanTable 1 }

        HwBRASIfVlanEntry ::=
            SEQUENCE {
                hwBRASIfVlanIfIndex
                    InterfaceIndex,
                hwBRASIfVlanVlanId
                    Integer32,
                hwBRASIfVlanVlanNumber
                    Integer32,
                hwBRASIfVlanAccessLimit
                    Integer32,
                hwBRASIfVlanAccessNumber
                    Integer32,
                hwBRASIfVlanBlock
                    TruthValue,
                hwBRASIfVlanDevAccessNumber
                    Integer32,
                hwBRASIfVlanSchedulerVcName
                    DisplayString,
                hwBRASIfVlanSchedulerVcGroupName
                    DisplayString,
                hwBRASIfVlanSchedulerVpGroupName
                    DisplayString,
                hwBRASIfQinQVlanID
                    Integer32,
                hwBRASIfVlanRowStatus
                    RowStatus
             }

        hwBRASIfVlanIfIndex OBJECT-TYPE
            SYNTAX InterfaceIndex
            MAX-ACCESS read-only
            STATUS current
            DESCRIPTION
                "This object indicates the index of a BAS interface.
                "
            ::= { hwBRASIfVlanEntry 1 }

        hwBRASIfVlanVlanId OBJECT-TYPE
            SYNTAX Integer32 (1..4094)
            MAX-ACCESS read-only
            STATUS current
            DESCRIPTION
                "This object indicates a VLAN ID.
                "
            ::= { hwBRASIfVlanEntry 2 }

        hwBRASIfVlanVlanNumber OBJECT-TYPE
            SYNTAX Integer32 (0..4094)
            MAX-ACCESS read-write
            STATUS current
            DESCRIPTION
                "This object indicates the number of consecutively-configured VLANs.
                "
            ::= { hwBRASIfVlanEntry 3 }

        hwBRASIfVlanAccessLimit OBJECT-TYPE
            SYNTAX Integer32 (0..2147483647)
            MAX-ACCESS read-write
            STATUS current
            DESCRIPTION
                "This object indicates the maximum number of access users allowed.
                "
            ::= { hwBRASIfVlanEntry 4 }

        hwBRASIfVlanAccessNumber OBJECT-TYPE
            SYNTAX Integer32 (0..262144)
            MAX-ACCESS read-only
            STATUS current
            DESCRIPTION
                "The VLAN access number,default is 49152.
                "
            ::= { hwBRASIfVlanEntry 5 }

        hwBRASIfVlanBlock OBJECT-TYPE
            SYNTAX TruthValue
            MAX-ACCESS read-write
            STATUS current
            DESCRIPTION
                "This object indicates whether to block a BAS interface.
                "
            DEFVAL { false }
            ::= { hwBRASIfVlanEntry 6 }

        hwBRASIfVlanDevAccessNumber OBJECT-TYPE
            SYNTAX Integer32 (0..4096)
            MAX-ACCESS read-only
            STATUS current
            DESCRIPTION
                "This object indicates the number of access users on an interface.
                "
            ::= { hwBRASIfVlanEntry 7 }

        hwBRASIfVlanSchedulerVcName OBJECT-TYPE
            SYNTAX DisplayString (SIZE (0..32))
            MAX-ACCESS read-write
            STATUS current
            DESCRIPTION
                "
                scheduler VC name
                "
            ::= { hwBRASIfVlanEntry 8 }

        hwBRASIfVlanSchedulerVcGroupName OBJECT-TYPE
            SYNTAX DisplayString (SIZE (0..32))
            MAX-ACCESS read-write
            STATUS current
            DESCRIPTION
                "
                scheduler VC-group name
                "
            ::= { hwBRASIfVlanEntry 9 }

        hwBRASIfVlanSchedulerVpGroupName OBJECT-TYPE
            SYNTAX DisplayString (SIZE (0..32))
            MAX-ACCESS read-write
            STATUS current
            DESCRIPTION
                "
                scheduler VP-group name
                "
            ::= { hwBRASIfVlanEntry 10 }

        hwBRASIfQinQVlanID OBJECT-TYPE
            SYNTAX Integer32 (0..4094)
            MAX-ACCESS read-only
            STATUS current
            DESCRIPTION
                "
                QinQ VLAN
                "
            ::= { hwBRASIfVlanEntry 11 }

        hwBRASIfVlanRowStatus OBJECT-TYPE
            SYNTAX RowStatus
            MAX-ACCESS read-create
            STATUS current
            DESCRIPTION
                "
                Vlan Access RowStatus
                "
            ::= { hwBRASIfVlanEntry 12 }

        hwBRASIfPvcTable OBJECT-TYPE
            SYNTAX SEQUENCE OF HwBRASIfPvcEntry
            MAX-ACCESS not-accessible
            STATUS current
            DESCRIPTION
                "
                "
            ::= { hwSrvcfgInterfaceMibObjects 3 }

        hwBRASIfPvcEntry OBJECT-TYPE
            SYNTAX HwBRASIfPvcEntry
            MAX-ACCESS not-accessible
            STATUS current
            DESCRIPTION
                "
                Description.
                "
            INDEX { hwBRASIfPvcIfIndex, hwBRASIfPvcVpi, hwBRASIfPvcVci }
            ::= { hwBRASIfPvcTable 1 }

        HwBRASIfPvcEntry ::=
            SEQUENCE {
                hwBRASIfPvcIfIndex
                    InterfaceIndex,
                hwBRASIfPvcVpi
                    Unsigned32,
                hwBRASIfPvcVci
                    Unsigned32,
                hwBRASIfPvcPvcNumber
                    Integer32,
                hwBRASIfPvcAccessLimit
                    Integer32,
                hwBRASIfPvcAccessNumber
                    Integer32,
                hwBRASIfPvcBlock
                    TruthValue,
                hwBRASIfPvcDevAccessNumber
                    Integer32,
                hwBRASIfPvcSchedulerVcGroupName
                    DisplayString,
                hwBRASIfPvcSchedulerVpGroupName
                    DisplayString
             }

        hwBRASIfPvcIfIndex OBJECT-TYPE
            SYNTAX InterfaceIndex
            MAX-ACCESS read-only
            STATUS current
            DESCRIPTION
                "
                "
            ::= { hwBRASIfPvcEntry 1 }

        hwBRASIfPvcVpi OBJECT-TYPE
            SYNTAX Unsigned32 (0..255)
            MAX-ACCESS read-only
            STATUS current
            DESCRIPTION
                "
                "
            ::= { hwBRASIfPvcEntry 2 }

        hwBRASIfPvcVci OBJECT-TYPE
            SYNTAX Unsigned32 (0..65534)
            MAX-ACCESS read-only
            STATUS current
            DESCRIPTION
                "
                "
            ::= { hwBRASIfPvcEntry 3 }

        hwBRASIfPvcPvcNumber OBJECT-TYPE
            SYNTAX Integer32 (0..4094)
            MAX-ACCESS read-write
            STATUS current
            DESCRIPTION
                "
                "
            ::= { hwBRASIfPvcEntry 4 }

        hwBRASIfPvcAccessLimit OBJECT-TYPE
            SYNTAX Integer32 (0..49153)
            MAX-ACCESS read-write
            STATUS current
            DESCRIPTION
                "
                "
            DEFVAL { 49152 }
            ::= { hwBRASIfPvcEntry 5 }

        hwBRASIfPvcAccessNumber OBJECT-TYPE
            SYNTAX Integer32 (0..49152)
            MAX-ACCESS read-only
            STATUS current
            DESCRIPTION
                " PVC access number,default is 49152.
                "
            ::= { hwBRASIfPvcEntry 6 }

        hwBRASIfPvcBlock OBJECT-TYPE
            SYNTAX TruthValue
            MAX-ACCESS read-write
            STATUS current
            DESCRIPTION
                "
                "
            DEFVAL { false }
            ::= { hwBRASIfPvcEntry 7 }

        hwBRASIfPvcDevAccessNumber OBJECT-TYPE
            SYNTAX Integer32 (0..4096)
            MAX-ACCESS read-only
            STATUS current
            DESCRIPTION
                "
                "
            ::= { hwBRASIfPvcEntry 8 }

        hwBRASIfPvcSchedulerVcGroupName OBJECT-TYPE
            SYNTAX DisplayString (SIZE (1..31))
            MAX-ACCESS read-write
            STATUS current
            DESCRIPTION
                "
                scheduler vc-group name
                "
            ::= { hwBRASIfPvcEntry 9 }

        hwBRASIfPvcSchedulerVpGroupName OBJECT-TYPE
            SYNTAX DisplayString (SIZE (1..31))
            MAX-ACCESS read-write
            STATUS current
            DESCRIPTION
                "
                scheduler vp-group name
                "
            ::= { hwBRASIfPvcEntry 10 }

        hwSTPRelayTable OBJECT-TYPE
            SYNTAX SEQUENCE OF HwSTPRelayEntry
            MAX-ACCESS not-accessible
            STATUS current
            DESCRIPTION
                "
                "
            ::= { hwSrvcfgInterfaceMibObjects 4 }

        hwSTPRelayEntry OBJECT-TYPE
            SYNTAX HwSTPRelayEntry
            MAX-ACCESS not-accessible
            STATUS current
            DESCRIPTION
                "
                Description.
                "
            INDEX { hwSTPRelayIndex }
            ::= { hwSTPRelayTable 1 }

        HwSTPRelayEntry ::=
            SEQUENCE {
                hwSTPRelayIndex
                    Unsigned32,
                hwSTPRelayInIfIndex
                    InterfaceIndex,
                hwSTPRelayOutIfIndex
                    InterfaceIndex,
                hwSTPRelayRowStatus
                    RowStatus,
                hwSTPRelayInIfName
                    DisplayString,
                hwSTPRelayOutIfName
                    DisplayString,
                hwSTPRelayInMac
                    MacAddress,
                hwSTPRelayOutMac
                    MacAddress
             }

        hwSTPRelayIndex OBJECT-TYPE
            SYNTAX Unsigned32 (0..127)
            MAX-ACCESS read-only
            STATUS current
            DESCRIPTION
                "
                "
            ::= { hwSTPRelayEntry 1 }

        hwSTPRelayInIfIndex OBJECT-TYPE
            SYNTAX InterfaceIndex
            MAX-ACCESS read-create
            STATUS current
            DESCRIPTION
                "
                "
            ::= { hwSTPRelayEntry 2 }

        hwSTPRelayOutIfIndex OBJECT-TYPE
            SYNTAX InterfaceIndex
            MAX-ACCESS read-create
            STATUS current
            DESCRIPTION
                "
                "
            ::= { hwSTPRelayEntry 3 }

        hwSTPRelayRowStatus OBJECT-TYPE
            SYNTAX RowStatus
            MAX-ACCESS read-create
            STATUS current
            DESCRIPTION
                "
                "
            ::= { hwSTPRelayEntry 4 }

        hwSTPRelayInIfName OBJECT-TYPE
            SYNTAX DisplayString (SIZE (1..47))
            MAX-ACCESS read-create
            STATUS current
            DESCRIPTION
                "
                "
            ::= { hwSTPRelayEntry 5 }

        hwSTPRelayOutIfName OBJECT-TYPE
            SYNTAX DisplayString (SIZE (1..47))
            MAX-ACCESS read-create
            STATUS current
            DESCRIPTION
                "
                "
            ::= { hwSTPRelayEntry 6 }

        hwSTPRelayInMac OBJECT-TYPE
            SYNTAX MacAddress
            MAX-ACCESS read-create
            STATUS current
            DESCRIPTION
                "
                stp-relay-line mac-address of in side
                "
            ::= { hwSTPRelayEntry 7 }

        hwSTPRelayOutMac OBJECT-TYPE
            SYNTAX MacAddress
            MAX-ACCESS read-create
            STATUS current
            DESCRIPTION
                "
                stp-relay-line mac-address of in side
                "
            ::= { hwSTPRelayEntry 8 }

        hwPortAccessLimitTable OBJECT-TYPE
            SYNTAX SEQUENCE OF HwPortAccessLimitEntry
            MAX-ACCESS not-accessible
            STATUS current
            DESCRIPTION
                "
                "
            ::= { hwSrvcfgInterfaceMibObjects 5 }

        hwPortAccessLimitEntry OBJECT-TYPE
            SYNTAX HwPortAccessLimitEntry
            MAX-ACCESS not-accessible
            STATUS current
            DESCRIPTION
                "
                Description.
                "
            INDEX { hwPortAccessLimitIfIndex }
            ::= { hwPortAccessLimitTable 1 }

        HwPortAccessLimitEntry ::=
            SEQUENCE {
                hwPortAccessLimitIfIndex
                    InterfaceIndex,
                hwPortAccessLimitLimit
                    Integer32,
                hwPortAccessLimitNumber
                    Integer32,
                hwPortAccessLimitDevNumber
                    Integer32,                     
                hwPortAccessLimitAuthenedNumber    -- Added by z00170249 for DTS2012080105071
		    Integer32                      -- Added by z00170249 for DTS2012080105071
             }

        hwPortAccessLimitIfIndex OBJECT-TYPE
            SYNTAX InterfaceIndex
            MAX-ACCESS read-only
            STATUS current
            DESCRIPTION
                "This object indicates an interface index.
                "
            ::= { hwPortAccessLimitEntry 1 }

        hwPortAccessLimitLimit OBJECT-TYPE
            SYNTAX Integer32 (0..262144)
            MAX-ACCESS read-write
            STATUS current
            DESCRIPTION
                "This object indicates the maximum number of access users allowed on a physical interface.
                "
            ::= { hwPortAccessLimitEntry 2 }

        hwPortAccessLimitNumber OBJECT-TYPE
            SYNTAX Integer32 (0..65535)
            MAX-ACCESS read-only
            STATUS current
            DESCRIPTION
                "This object indicates the number of users who have accessed the network.
                "
            ::= { hwPortAccessLimitEntry 3 }

        hwPortAccessLimitDevNumber OBJECT-TYPE
            SYNTAX Integer32 (0..262144)
            MAX-ACCESS read-only
            STATUS current
            DESCRIPTION
                "This object indicates the maximum number of access users allowed on a device.
                "
            ::= { hwPortAccessLimitEntry 4 }

        -- Added by z00170249 for DTS2012080105071
        hwPortAccessLimitAuthenedNumber OBJECT-TYPE
            SYNTAX Integer32 (0..65535)
            MAX-ACCESS read-only
            STATUS current
            DESCRIPTION
                "This object indicates the total number of authenticated online users on an interface.
                "
            ::= { hwPortAccessLimitEntry 5 }
         -- End addition by z00170249 for DTS2012080105071
        hwL3SubscriberIspTable OBJECT-TYPE
            SYNTAX SEQUENCE OF HwL3SubscriberIspEntry
            MAX-ACCESS not-accessible
            STATUS current
            DESCRIPTION
                "
                "
            ::= { hwSrvcfgInterfaceMibObjects 6 }

        hwL3SubscriberIspEntry OBJECT-TYPE
            SYNTAX HwL3SubscriberIspEntry
            MAX-ACCESS not-accessible
            STATUS current
            DESCRIPTION
                "
                Description.
                "
            INDEX { hwL3SubscriberIspStartIp, hwL3SubscriberIspVpnId }
            ::= { hwL3SubscriberIspTable 1 }

        HwL3SubscriberIspEntry ::=
            SEQUENCE {
                hwL3SubscriberIspStartIp
                    IpAddress,
                hwL3SubscriberIspVpnId
                    DisplayString,
                hwL3SubscriberIspEndIp
                    IpAddress,
                hwL3SubscriberIspDomainName
                    DisplayString,
                hwL3SubscriberIspRowStatus
                    RowStatus
             }

        hwL3SubscriberIspStartIp OBJECT-TYPE
            SYNTAX IpAddress
            MAX-ACCESS read-only
            STATUS current
            DESCRIPTION
                "This object indicates the start IP address of the network segment for Layer 3 users.
                "
            ::= { hwL3SubscriberIspEntry 1 }

        hwL3SubscriberIspVpnId OBJECT-TYPE
            SYNTAX DisplayString (SIZE (1..31))
            MAX-ACCESS read-only
            STATUS current
            DESCRIPTION
                "This object indicates the VPN instance name of the network segment for Layer 3 users.
                "
            ::= { hwL3SubscriberIspEntry 2 }

        hwL3SubscriberIspEndIp OBJECT-TYPE
            SYNTAX IpAddress
            MAX-ACCESS read-create
            STATUS current
            DESCRIPTION
                "This object indicates the end IP address of the network segment for Layer 3 users.
                "
            ::= { hwL3SubscriberIspEntry 3 }

        hwL3SubscriberIspDomainName OBJECT-TYPE
            SYNTAX DisplayString (SIZE (1..64))
            MAX-ACCESS read-create
            STATUS current
            DESCRIPTION
                "This object indicates the name of the domain where Layer 3 users reside.
                "
            ::= { hwL3SubscriberIspEntry 4 }

        hwL3SubscriberIspRowStatus OBJECT-TYPE
            SYNTAX RowStatus
            MAX-ACCESS read-create
            STATUS current
            DESCRIPTION
                "This object indicates the row status.
                "
            ::= { hwL3SubscriberIspEntry 5 }

        srvcfgScalar OBJECT IDENTIFIER ::= { hwSrvcfgInterfaceMibObjects 8 }

--        The SrvCfg Scalar configuration
--
-- This group of objects describe the global configuration of SrvCfg.
        hwDhcpOption60DomainInclude OBJECT-TYPE
            SYNTAX TruthValue
            MAX-ACCESS read-write
            STATUS current
            DESCRIPTION
                "This object indicates whether to carry domain names in DHCP Option 60.
                "
            ::= { srvcfgScalar 1 }

        hwDhcpOption60PartialMatch OBJECT-TYPE
            SYNTAX TruthValue
            MAX-ACCESS read-write
            STATUS current
            DESCRIPTION
                "This object indicates whether the Option 60 field partially matches the domain name.
                "
            ::= { srvcfgScalar 2 }

  -- Begin: added for device flow stat        
        hwAccessUserFlowStatisticsEnableFlag OBJECT-TYPE
            SYNTAX TruthValue
            MAX-ACCESS read-write
            STATUS current
            DESCRIPTION
                "This object indicates whether user traffic statistics collection is enabled by PE-VLAN ID, CE-VLAN ID, or VPI.
                "
            ::= { srvcfgScalar 3 }
  -- End: added for device flow stat

        hwConnTimeOutTable OBJECT IDENTIFIER ::= { hwSrvcfgInterfaceMibObjects 9 }

        hwConnTimeOutTcp OBJECT-TYPE
            SYNTAX Integer32 (1..255)
            MAX-ACCESS read-write
            STATUS current
            DESCRIPTION
                " The TCP connect time out,default is 5.
                "
            ::= { hwConnTimeOutTable 1 }

        hwConnTimeOutUdp OBJECT-TYPE
            SYNTAX Integer32 (1..255)
            MAX-ACCESS read-write
            STATUS current
            DESCRIPTION
                "The UDP connect time out,default is 5.
                "
            ::= { hwConnTimeOutTable 2 }

        hwBRASIfVlanNumTable OBJECT-TYPE
            SYNTAX SEQUENCE OF HwBRASIfVlanNumEntry
            MAX-ACCESS not-accessible
            STATUS current
            DESCRIPTION
                "
                "
            ::= { hwSrvcfgInterfaceMibObjects 10 }

        hwBRASIfVlanNumEntry OBJECT-TYPE
            SYNTAX HwBRASIfVlanNumEntry
            MAX-ACCESS not-accessible
            STATUS current
            DESCRIPTION
                "
                Description.
                "
            INDEX { hwBRASIfSlot }
            ::= { hwBRASIfVlanNumTable 1 }

        HwBRASIfVlanNumEntry ::=
            SEQUENCE {
                hwBRASIfSlot
                    Unsigned32,
                hwBRASSlotVlanNum
                    Integer32,
                hwBRASSLotStaticVlanNum
                    Integer32
             }

        hwBRASIfSlot OBJECT-TYPE
            SYNTAX Unsigned32 (0..16)
            MAX-ACCESS read-only
            STATUS current
            DESCRIPTION
                "
                "
            ::= { hwBRASIfVlanNumEntry 1 }

        hwBRASSlotVlanNum OBJECT-TYPE
            SYNTAX Integer32 (0..65536)
            MAX-ACCESS read-only
            STATUS current
            DESCRIPTION
                "
                "
            ::= { hwBRASIfVlanNumEntry 2 }

        hwBRASSLotStaticVlanNum OBJECT-TYPE
            SYNTAX Integer32 (0..16384)
            MAX-ACCESS read-only
            STATUS current
            DESCRIPTION
                "
                "
            ::= { hwBRASIfVlanNumEntry 3 }

        hwServiceIfCfgTable OBJECT-TYPE
            SYNTAX SEQUENCE OF HwServiceIfCfgEntry
            MAX-ACCESS not-accessible
            STATUS current
            DESCRIPTION
                "
                "
            ::= { hwSrvcfgInterfaceMibObjects 11 }

        hwServiceIfCfgEntry OBJECT-TYPE
            SYNTAX HwServiceIfCfgEntry
            MAX-ACCESS not-accessible
            STATUS current
            DESCRIPTION
                "
                An entry of hwServiceIfCfgTable.
                "
            INDEX { hwServiceIfCfgIfIndex }
            ::= { hwServiceIfCfgTable 1 }

        HwServiceIfCfgEntry ::=
            SEQUENCE {
                hwServiceIfCfgIfIndex
                    InterfaceIndex,
                hwServiceIfCfgIdentificationMode
                    INTEGER,
                hwServiceIfCfgDomain
                    DisplayString,
                hwServiceIfCfgUserName
                    DisplayString,
                hwServiceIfCfgPassword
                    DisplayString,
                hwServiceIfCfgDetectNum
                    Integer32,
                hwServiceIfCfgDetectInterval
                    Integer32,
                hwServiceIfCfgOption82
                    TruthValue,
                hwServiceIfCfgAccessLimit
                    Integer32,
                hwServiceIfCfgOption60
                    TruthValue,
                hwServiceIfCfgIpTriggerEnable
                    EnabledStatus,
                hwServiceIfCfgArpTriggerEnable
                    EnabledStatus,
                hwServiceIfCfgIfBlock
                    TruthValue,
                hwServiceIfCfgQosProfile
                    DisplayString,
                hwServiceIfCfgBindingUserPasswordMode
                    INTEGER,
                hwServiceIfCfgBindingUserNameFormat
                    Integer32,
                hwServiceIfCfgBindingUserPassword
                    DisplayString,
                hwServiceIfCfgRowStatus
                    RowStatus
             }

        hwServiceIfCfgIfIndex OBJECT-TYPE
            SYNTAX InterfaceIndex
            MAX-ACCESS not-accessible
            STATUS current
            DESCRIPTION
                "The value of this object identifies the index of the service interface.
                "
            ::= { hwServiceIfCfgEntry 1 }

        hwServiceIfCfgIdentificationMode OBJECT-TYPE
            SYNTAX INTEGER
                {
                host(1),
                location(2),
                ceVlan(3)
                }
            MAX-ACCESS read-create
            STATUS current
            DESCRIPTION
                " This value of this object identifies the user identification mode.
                  The QoS resources are allocated and charged according to which user identification mode
                  is configured for the user of the interface.
                   host (1): identifies a user according to the IP address and MAC address.
                   location (2): identifies a user according to the Option 82 information.
                   ceVlan (3): identifies a user according to the CE-VLAN information. In other words,
                   when a group of users of the same inner VLAN tag access multiple interfaces, these
                   users are considered as the same user.
                  The default value is host (1).
                  The latest modification cannot override the previous configurations. You need to change
                  the value to host before choosing another mode.

                "
            ::= { hwServiceIfCfgEntry 2 }

        hwServiceIfCfgDomain OBJECT-TYPE
            SYNTAX DisplayString (SIZE (1..20))
            MAX-ACCESS read-create
            STATUS current
            DESCRIPTION
                "
                 This object indicates the domain to which the user belongs.
                 --: default value.
                 --: deletes the configuration.
                 If the domain has users, you cannot delete the setting of this object.

                "
            ::= { hwServiceIfCfgEntry 3 }

        hwServiceIfCfgUserName OBJECT-TYPE
            SYNTAX DisplayString (SIZE (1..31))
            MAX-ACCESS read-create
            STATUS current
            DESCRIPTION
                "
                Not supported.                "
            ::= { hwServiceIfCfgEntry 4 }

        hwServiceIfCfgPassword OBJECT-TYPE
            SYNTAX DisplayString (SIZE (1..31))
            MAX-ACCESS read-create
            STATUS current
            DESCRIPTION
                "
                   Not supported.                "
            ::= { hwServiceIfCfgEntry 5 }

        hwServiceIfCfgDetectNum OBJECT-TYPE
            SYNTAX Integer32 (2..10)
            MAX-ACCESS read-create
            STATUS current
            DESCRIPTION
                "
                The value of this object identifies the detection times."
            ::= { hwServiceIfCfgEntry 6 }

        hwServiceIfCfgDetectInterval OBJECT-TYPE
            SYNTAX Integer32 (0..120)
            MAX-ACCESS read-create
            STATUS current
            DESCRIPTION
                "
                The value of this object identifies the interval between detection attempts."
            ::= { hwServiceIfCfgEntry 7 }

        hwServiceIfCfgOption82 OBJECT-TYPE
            SYNTAX TruthValue
            MAX-ACCESS read-create
            STATUS current
            DESCRIPTION
                "
                This object indicates whether to trust Option 82.
                 True(1): indicates that Option 82 is trusted.
                 False (2): indicates that Option 82 is not trusted.
                The default value is False (2).
                This object is used to configure the device to trust or not to trust the DHCP Option 82
                information sent from the client.

                "
            ::= { hwServiceIfCfgEntry 8 }

        hwServiceIfCfgAccessLimit OBJECT-TYPE
            SYNTAX Integer32 (0..16384)
            MAX-ACCESS read-create
            STATUS current
            DESCRIPTION
                "
                 The value of this object identifies the user access limit.
                 The default value is 16384.
                 If the number of online users on the interface is more than the value of this object,
                 the setting of this object fails.

                "
            ::= { hwServiceIfCfgEntry 9 }

        hwServiceIfCfgOption60 OBJECT-TYPE
            SYNTAX TruthValue
            MAX-ACCESS read-create
            STATUS current
            DESCRIPTION
                "
                This object indicates whether to trust Option 60.
                 True(1): indicates that Option 60 is trusted.
                 False (2): indicates that Option 60 is not trusted.
                The default value is False (2).
                This object is used to configure the device to trust or not to trust the DHCP Option 60
                information sent from the client.

                "
            ::= { hwServiceIfCfgEntry 10 }

        hwServiceIfCfgIpTriggerEnable OBJECT-TYPE
            SYNTAX EnabledStatus
            MAX-ACCESS read-create
            STATUS current
            DESCRIPTION
                " This object indicates whether the function of IP packet-triggered user online is enabled.
                 By default, the function is disabled.

                "
            DEFVAL { disabled }
            ::= { hwServiceIfCfgEntry 11 }

        hwServiceIfCfgArpTriggerEnable OBJECT-TYPE
            SYNTAX EnabledStatus
            MAX-ACCESS read-create
            STATUS current
            DESCRIPTION
                "
                 This object indicates whether the function of ARP packet-triggered user online is enabled.
                 By default, the function is disabled.

                "
            DEFVAL { disabled }
            ::= { hwServiceIfCfgEntry 12 }

        hwServiceIfCfgIfBlock OBJECT-TYPE
            SYNTAX TruthValue
            MAX-ACCESS read-create
            STATUS current
            DESCRIPTION
                "
                 This object indicates whether the interface is blocked.
                  True(1): indicates that the interface is blocked.
                  False (2): indicates that the interface is not blocked.
                 The default value is False (2).

                "
            ::= { hwServiceIfCfgEntry 13 }

        hwServiceIfCfgQosProfile OBJECT-TYPE
            SYNTAX DisplayString (SIZE (1..63))
            MAX-ACCESS read-create
            STATUS current
            DESCRIPTION
                "
                 This object indicates the QoS profile.
                 This object has no default value.
                 The created QoS profile must be configured. If an interface is already configured
                 with hwServiceIfCfgCarProfile and has users connected to it, this object cannot be configured.
                 If this object is modified when there are users on the interface, only the subsequent
                 online users are affected. The users that are already on line are not affected.
                "
            ::= { hwServiceIfCfgEntry 14 }

        hwServiceIfCfgBindingUserPasswordMode OBJECT-TYPE
            SYNTAX INTEGER
                {
                simple(1),
                cipher(2)
                }
            MAX-ACCESS read-create
            STATUS current
            DESCRIPTION
                "
                  The value of this object identifies the password mode of the binding user.
                "
            ::= { hwServiceIfCfgEntry 15 }

        hwServiceIfCfgBindingUserNameFormat OBJECT-TYPE
            SYNTAX Integer32 (1..7)
            MAX-ACCESS read-create
            STATUS current
            DESCRIPTION
                "
                The value of this object identifies the format in which the bound user name is generated:
                 mac (1): constructs the user name by using the MAC address of the user.
                 option82 (2): constructs the user name by using the Option 82 information of the user.
                 Sys-name (3): constructs the user name by using the name of the router.
                 mac+option82 (4)
                 mac+sys-name (5)
                option82+ host-name (6)
                mac+option82+host-name (7)
                By default, users in host mode and in CE-VLAN mode use the MAC address to construct the user
                names; users in location mode use the option 82 + MAC address to construct the user names.

                "
            ::= { hwServiceIfCfgEntry 16 }

        hwServiceIfCfgBindingUserPassword OBJECT-TYPE
            SYNTAX DisplayString (SIZE (1..16))
            MAX-ACCESS read-create
            STATUS current
            DESCRIPTION
                "
                This object indicates the password of the bound user.
                "
            ::= { hwServiceIfCfgEntry 17 }

        hwServiceIfCfgRowStatus OBJECT-TYPE
            SYNTAX RowStatus
            MAX-ACCESS read-create
            STATUS current
            DESCRIPTION
                "
                 This object indicates the row status.                "
            ::= { hwServiceIfCfgEntry 18 }

        hwBRASIfEnableTable OBJECT-TYPE
            SYNTAX SEQUENCE OF HwBRASIfEnableEntry
            MAX-ACCESS not-accessible
            STATUS current
            DESCRIPTION
                "Description."
            ::= { hwSrvcfgInterfaceMibObjects 12 }

        hwBRASIfEnableEntry OBJECT-TYPE
            SYNTAX HwBRASIfEnableEntry
            MAX-ACCESS not-accessible
            STATUS current
            DESCRIPTION
                "Description."
            INDEX { hwBRASIfEnableIfIndex }
            ::= { hwBRASIfEnableTable 1 }

        HwBRASIfEnableEntry ::=
            SEQUENCE {
                hwBRASIfEnableIfIndex
                    InterfaceIndex,
                hwBRASIfEnableStatus
                    TruthValue
             }

        hwBRASIfEnableIfIndex OBJECT-TYPE
            SYNTAX InterfaceIndex
            MAX-ACCESS read-only
            STATUS current
            DESCRIPTION
                "Description."
            ::= { hwBRASIfEnableEntry 1 }

        hwBRASIfEnableStatus OBJECT-TYPE
            SYNTAX TruthValue (1..2)
            MAX-ACCESS read-write
            STATUS current
            DESCRIPTION
                "Description."
            ::= { hwBRASIfEnableEntry 2 }

        hwBRASIfVlanAccessTable OBJECT-TYPE
        SYNTAX SEQUENCE OF HwBRASIfVlanAccessEntry
            MAX-ACCESS not-accessible
            STATUS current
            DESCRIPTION
                "hwBRASIfVlanAccessTable is used to count the number of VLAN users on a BAS interface."
            ::= { hwSrvcfgInterfaceMibObjects 13 }

        hwBRASIfVlanAccessEntry OBJECT-TYPE
            SYNTAX HwBRASIfVlanAccessEntry
            MAX-ACCESS not-accessible
            STATUS current
            DESCRIPTION
                "The indexes of this table are hwBRASIfVlanAccessIfIndex, hwBRASIfVlanAccessQinqVlanId, and hwBRASIfVlanAccessVlanId."
            INDEX { hwBRASIfVlanAccessIfIndex, hwBRASIfVlanAccessQinqVlanId, hwBRASIfVlanAccessVlanId }
            ::= { hwBRASIfVlanAccessTable 1 }

        HwBRASIfVlanAccessEntry ::=
            SEQUENCE {
                hwBRASIfVlanAccessIfIndex
                    InterfaceIndex,
                hwBRASIfVlanAccessQinqVlanId
                    Integer32,
                hwBRASIfVlanAccessVlanId
                    Integer32,
                hwBRASIfVlanAccessUserNumber
                    Integer32
             }

        hwBRASIfVlanAccessIfIndex OBJECT-TYPE
            SYNTAX InterfaceIndex
            MAX-ACCESS read-only
            STATUS current
            DESCRIPTION
                "This object indicates the index of a BAS interface."
            ::= { hwBRASIfVlanAccessEntry 1 }

        hwBRASIfVlanAccessQinqVlanId OBJECT-TYPE
            SYNTAX Integer32 (0..4094)
            MAX-ACCESS read-only
            STATUS current
            DESCRIPTION
                "This object indicates the outer VLAN ID in the case of QinQ VLAN. The value of this object is zero in the case of a common VLAN. The value ranges from 0 to 4094."
            ::= { hwBRASIfVlanAccessEntry 2 }

        hwBRASIfVlanAccessVlanId OBJECT-TYPE
            SYNTAX Integer32 (1..4094)
            MAX-ACCESS read-only
            STATUS current
            DESCRIPTION
                "This object indicates the inner VLAN ID in the case of QinQ VLAN. This object indicates the VLAN ID in the case of a common VLAN. The value ranges from 1 to 4094."
            ::= { hwBRASIfVlanAccessEntry 3 }

        hwBRASIfVlanAccessUserNumber OBJECT-TYPE
            SYNTAX Integer32
            MAX-ACCESS read-only
            STATUS current
            DESCRIPTION
                "This object indicates the number of access users."
            ::= { hwBRASIfVlanAccessEntry 4 }  
            
--   ====================hwBRASIfSvlanVpiStatTable===========================          
                
        hwBRASIfSvlanVpiStatTable OBJECT-TYPE
        SYNTAX SEQUENCE OF HwBRASIfSvlanVpiStatEntry
            MAX-ACCESS not-accessible
            STATUS current
            DESCRIPTION
                "hwBRASIfSvlanVpiStatTable displays traffic statistics based on a specified outer VLAN ID."
            ::= { hwSrvcfgInterfaceMibObjects 14 }

        hwBRASIfSvlanVpiStatEntry OBJECT-TYPE
            SYNTAX HwBRASIfSvlanVpiStatEntry
            MAX-ACCESS not-accessible
            STATUS current
            DESCRIPTION
                "The indexes of this table are hwBRASIfSvlanVpiStatIfIndex and hwBRASIfSvlanVpiStatIndex."
            INDEX { hwBRASIfSvlanVpiStatIfIndex, hwBRASIfSvlanVpiStatIndex }
            ::= { hwBRASIfSvlanVpiStatTable 1 }

        HwBRASIfSvlanVpiStatEntry ::=
            SEQUENCE {
                hwBRASIfSvlanVpiStatIfIndex
                    InterfaceIndex,
                hwBRASIfSvlanVpiStatIndex
                    Integer32,
                hwBRASIfSvlanVpiStatInPackets
                    Counter64,
                hwBRASIfSvlanVpiStatInBytes
                    Counter64,
                hwBRASIfSvlanVpiStatOutPackets
                    Counter64,
                hwBRASIfSvlanVpiStatOutBytes  
                    Counter64,
                hwBRASIfSvlanVpiStatReset
                    INTEGER,
                hwBRASIPv4IfSvlanVpiStatInPackets
                    Counter64,
                hwBRASIPv4IfSvlanVpiStatInBytes
                    Counter64,
                hwBRASIPv4IfSvlanVpiStatOutPackets
                    Counter64,
                hwBRASIPv4IfSvlanVpiStatOutBytes
                    Counter64,
                hwBRASIPv6IfSvlanVpiStatInPackets  
                    Counter64,
                hwBRASIPv6IfSvlanVpiStatInBytes    
                    Counter64,
                hwBRASIPv6IfSvlanVpiStatOutPackets
                    Counter64,
                hwBRASIPv6IfSvlanVpiStatOutBytes
                    Counter64
             }

        hwBRASIfSvlanVpiStatIfIndex OBJECT-TYPE
            SYNTAX InterfaceIndex
            MAX-ACCESS read-only
            STATUS current
            DESCRIPTION
                "This object indicates the interface index."
            ::= { hwBRASIfSvlanVpiStatEntry 1 }

        hwBRASIfSvlanVpiStatIndex OBJECT-TYPE
            SYNTAX Integer32 (0..4095)
            MAX-ACCESS read-only
            STATUS current
            DESCRIPTION
                "Specifies the outer VLAN ID of a user packet."
            ::= { hwBRASIfSvlanVpiStatEntry 2 }

        hwBRASIfSvlanVpiStatInPackets OBJECT-TYPE
            SYNTAX Counter64 
            MAX-ACCESS read-only
            STATUS current
            DESCRIPTION
                "This object indicates the number of upstream user packets."
            ::= { hwBRASIfSvlanVpiStatEntry 3 }

        hwBRASIfSvlanVpiStatInBytes OBJECT-TYPE
            SYNTAX Counter64
            MAX-ACCESS read-only
            STATUS current
            DESCRIPTION
                "This object indicates the number of upstream user bytes."
            ::= { hwBRASIfSvlanVpiStatEntry 4 }       
       
       hwBRASIfSvlanVpiStatOutPackets OBJECT-TYPE
            SYNTAX Counter64 
            MAX-ACCESS read-only
            STATUS current
            DESCRIPTION
                "This object indicates the number of downstream user packets."
            ::= { hwBRASIfSvlanVpiStatEntry 5 }

        hwBRASIfSvlanVpiStatOutBytes OBJECT-TYPE
            SYNTAX Counter64
            MAX-ACCESS read-only
            STATUS current
            DESCRIPTION
                "This object indicates the number of downstream user bytes."
            ::= { hwBRASIfSvlanVpiStatEntry 6 }
        
        hwBRASIfSvlanVpiStatReset OBJECT-TYPE
            SYNTAX INTEGER
                {
                reset(1)
                }
            MAX-ACCESS read-write
            STATUS current
            DESCRIPTION
                "Reset the statistic information of traffic for specific vlan in the current interface."
            ::= { hwBRASIfSvlanVpiStatEntry 7 }
        
        hwBRASIPv4IfSvlanVpiStatInPackets OBJECT-TYPE
            SYNTAX Counter64
            MAX-ACCESS read-only
            STATUS current
            DESCRIPTION
                "This object indicates the number of upstream IPv4 user packets."
            ::= { hwBRASIfSvlanVpiStatEntry 8 }
         
        hwBRASIPv4IfSvlanVpiStatInBytes OBJECT-TYPE
            SYNTAX Counter64
            MAX-ACCESS read-only
            STATUS current
            DESCRIPTION
                "This object indicates the number of upstream IPv4 user bytes."
            ::= { hwBRASIfSvlanVpiStatEntry 9 }
        
        hwBRASIPv4IfSvlanVpiStatOutPackets OBJECT-TYPE
            SYNTAX Counter64
            MAX-ACCESS read-only
            STATUS current
            DESCRIPTION
                "This object indicates the number of downstream IPv4 user packets."
            ::= { hwBRASIfSvlanVpiStatEntry 10 }
        
        hwBRASIPv4IfSvlanVpiStatOutBytes OBJECT-TYPE
            SYNTAX Counter64
            MAX-ACCESS read-only
            STATUS current
            DESCRIPTION
                "This object indicates the number of downstream IPv4 user bytes."
            ::= { hwBRASIfSvlanVpiStatEntry 11 }
        
        hwBRASIPv6IfSvlanVpiStatInPackets OBJECT-TYPE
            SYNTAX Counter64
            MAX-ACCESS read-only
            STATUS current
            DESCRIPTION
                "This object indicates the number of upstream IPv6 user packets."
            ::= { hwBRASIfSvlanVpiStatEntry 12 }
            
        hwBRASIPv6IfSvlanVpiStatInBytes OBJECT-TYPE
            SYNTAX Counter64
            MAX-ACCESS read-only
            STATUS current
            DESCRIPTION
                "This object indicates the number of upstream IPv6 user bytes."
            ::= { hwBRASIfSvlanVpiStatEntry 13 }    
                                               
        hwBRASIPv6IfSvlanVpiStatOutPackets OBJECT-TYPE
            SYNTAX Counter64
            MAX-ACCESS read-only
            STATUS current
            DESCRIPTION
                "This object indicates the number of downstream IPv6 user packets."
            ::= { hwBRASIfSvlanVpiStatEntry 14 }  
            
        hwBRASIPv6IfSvlanVpiStatOutBytes OBJECT-TYPE
            SYNTAX Counter64
            MAX-ACCESS read-only
            STATUS current
            DESCRIPTION
                "This object indicates the number of downstream IPv6 user bytes."
            ::= { hwBRASIfSvlanVpiStatEntry 15 }      

---  /*Begin: added by w00175317 for vlan-stat*/
--   ====================hwBRASIfSvlanVpiStatTable===========================          
                
        hwBRASIfCvlanVciStatTable OBJECT-TYPE
        SYNTAX SEQUENCE OF HwBRASIfCvlanVciStatEntry
            MAX-ACCESS not-accessible
            STATUS current
            DESCRIPTION
                "hwBRASIfCvlanVciStatTable displays traffic statistics based on a specified inner VLAN ID."
            ::= { hwSrvcfgInterfaceMibObjects 15 }

        hwBRASIfCvlanVciStatEntry OBJECT-TYPE
            SYNTAX HwBRASIfCvlanVciStatEntry
            MAX-ACCESS not-accessible
            STATUS current
            DESCRIPTION
                "The indexes of this table are hwBRASIfCvlanVciStatIfIndex and hwBRASIfCvlanVciStatIndex."
            INDEX { hwBRASIfCvlanVciStatIfIndex, hwBRASIfCvlanVciStatIndex }
            ::= { hwBRASIfCvlanVciStatTable 1 }

        HwBRASIfCvlanVciStatEntry ::=
            SEQUENCE {
                hwBRASIfCvlanVciStatIfIndex
                    InterfaceIndex,
                hwBRASIfCvlanVciStatIndex
                    Integer32,
                hwBRASIfCvlanVciStatInPackets
                    Counter64,
                hwBRASIfCvlanVciStatInBytes
                    Counter64,
                hwBRASIfCvlanVciStatOutPackets
                    Counter64,
                hwBRASIfCvlanVciStatOutBytes  
                    Counter64,
                hwBRASIfCvlanVciStatReset
                    INTEGER,
                hwBRASIPv4IfCvlanVciStatInPackets
                    Counter64,
                hwBRASIPv4IfCvlanVciStatInBytes
                    Counter64,
                hwBRASIPv4IfCvlanVciStatOutPackets
                    Counter64,
                hwBRASIPv4IfCvlanVciStatOutBytes
                    Counter64,
                hwBRASIPv6IfCvlanVciStatInPackets  
                    Counter64,
                hwBRASIPv6IfCvlanVciStatInBytes    
                    Counter64,
                hwBRASIPv6IfCvlanVciStatOutPackets
                    Counter64,
                hwBRASIPv6IfCvlanVciStatOutBytes
                    Counter64
             }

        hwBRASIfCvlanVciStatIfIndex OBJECT-TYPE
            SYNTAX InterfaceIndex
            MAX-ACCESS read-only
            STATUS current
            DESCRIPTION
                "This object indicates the interface index."
            ::= { hwBRASIfCvlanVciStatEntry 1 }

        hwBRASIfCvlanVciStatIndex OBJECT-TYPE
            SYNTAX Integer32 (0..4095)
            MAX-ACCESS read-only
            STATUS current
            DESCRIPTION
                "This object indicates the inner VLAN ID of an Ethernet interface."
            ::= { hwBRASIfCvlanVciStatEntry 2 }

        hwBRASIfCvlanVciStatInPackets OBJECT-TYPE
            SYNTAX Counter64 
            MAX-ACCESS read-only
            STATUS current
            DESCRIPTION
                "This object indicates the number of upstream packets."
            ::= { hwBRASIfCvlanVciStatEntry 3 }

        hwBRASIfCvlanVciStatInBytes OBJECT-TYPE
            SYNTAX Counter64
            MAX-ACCESS read-only
            STATUS current
            DESCRIPTION
                "This object indicates the number of upstream bytes."
            ::= { hwBRASIfCvlanVciStatEntry 4 }       
       
       hwBRASIfCvlanVciStatOutPackets OBJECT-TYPE
            SYNTAX Counter64 
            MAX-ACCESS read-only
            STATUS current
            DESCRIPTION
                "This object indicates the number of downstream packets."
            ::= { hwBRASIfCvlanVciStatEntry 5 }

        hwBRASIfCvlanVciStatOutBytes OBJECT-TYPE
            SYNTAX Counter64
            MAX-ACCESS read-only
            STATUS current
            DESCRIPTION
                "This object indicates the number of downstream bytes."
            ::= { hwBRASIfCvlanVciStatEntry 6 }
        
        hwBRASIfCvlanVciStatReset OBJECT-TYPE
            SYNTAX INTEGER
                {
                reset(1)
                }
            MAX-ACCESS read-write
            STATUS current
            DESCRIPTION
                "Reset the statistic information of traffic for specific vlan in the current interface."
            ::= { hwBRASIfCvlanVciStatEntry 7 }
        
        hwBRASIPv4IfCvlanVciStatInPackets OBJECT-TYPE
            SYNTAX Counter64
            MAX-ACCESS read-only
            STATUS current
            DESCRIPTION
                "This object indicates the number of IPv4 upstream packets."
            ::= { hwBRASIfCvlanVciStatEntry 8 }
         
        hwBRASIPv4IfCvlanVciStatInBytes OBJECT-TYPE
            SYNTAX Counter64
            MAX-ACCESS read-only
            STATUS current
            DESCRIPTION
                "This object indicates the number of IPv4 upstream bytes."
            ::= { hwBRASIfCvlanVciStatEntry 9 }
        
        hwBRASIPv4IfCvlanVciStatOutPackets OBJECT-TYPE
            SYNTAX Counter64
            MAX-ACCESS read-only
            STATUS current
            DESCRIPTION
                "This object indicates the number of IPv4 downstream packets."
            ::= { hwBRASIfCvlanVciStatEntry 10 }
        
        hwBRASIPv4IfCvlanVciStatOutBytes OBJECT-TYPE
            SYNTAX Counter64
            MAX-ACCESS read-only
            STATUS current
            DESCRIPTION
                "This object indicates the number of IPv4 downstream bytes."
            ::= { hwBRASIfCvlanVciStatEntry 11 }
        
        hwBRASIPv6IfCvlanVciStatInPackets OBJECT-TYPE
            SYNTAX Counter64
            MAX-ACCESS read-only
            STATUS current
            DESCRIPTION
                "This object indicates the number of IPv6 upstream packets."
            ::= { hwBRASIfCvlanVciStatEntry 12 }
            
        hwBRASIPv6IfCvlanVciStatInBytes OBJECT-TYPE
            SYNTAX Counter64
            MAX-ACCESS read-only
            STATUS current
            DESCRIPTION
                "This object indicates the number of IPv6 upstream bytes."
            ::= { hwBRASIfCvlanVciStatEntry 13 }    
                                               
        hwBRASIPv6IfCvlanVciStatOutPackets OBJECT-TYPE
            SYNTAX Counter64
            MAX-ACCESS read-only
            STATUS current
            DESCRIPTION
                "This object indicates the number of IPv6 downstream packets."
            ::= { hwBRASIfCvlanVciStatEntry 14 }  
            
        hwBRASIPv6IfCvlanVciStatOutBytes OBJECT-TYPE
            SYNTAX Counter64
            MAX-ACCESS read-only
            STATUS current
            DESCRIPTION
                "This object indicates the number of IPv6 downstream bytes."
            ::= { hwBRASIfCvlanVciStatEntry 15 }      
    
 --- /*End: added by w00175317 for vlan-stat*/
 --- /*begin: added by g00248654 */
  hwBRASIfCfgDelayLoadBalanceGroupTable OBJECT-TYPE
            SYNTAX SEQUENCE OF HwBRASIfCfgDelayLoadBalanceGroupEntry
            MAX-ACCESS not-accessible
            STATUS current
            DESCRIPTION
                "
                "
            ::= { hwSrvcfgInterfaceMibObjects 16 }

        hwBRASIfCfgDelayLoadBalanceGroupEntry OBJECT-TYPE
            SYNTAX HwBRASIfCfgDelayLoadBalanceGroupEntry
            MAX-ACCESS not-accessible
            STATUS current
            DESCRIPTION
                "
                Description.
                "
            INDEX { hwBRASIfCfgDelayLoadBalanceGroupName }
            ::= { hwBRASIfCfgDelayLoadBalanceGroupTable 1 }

        HwBRASIfCfgDelayLoadBalanceGroupEntry ::=
            SEQUENCE {
                hwBRASIfCfgDelayLoadBalanceGroupName
                    DisplayString,
                hwBRASIfCfgDelayLoadBalanceGroupRowStatus
                    RowStatus
             }

        hwBRASIfCfgDelayLoadBalanceGroupName OBJECT-TYPE
            SYNTAX DisplayString (SIZE (1..31))
            MAX-ACCESS read-create
            STATUS current
            DESCRIPTION
                "This object indicates the name of delay group.
                "
            ::= { hwBRASIfCfgDelayLoadBalanceGroupEntry 1 }

        hwBRASIfCfgDelayLoadBalanceGroupRowStatus OBJECT-TYPE
            SYNTAX RowStatus
            MAX-ACCESS read-create
            STATUS current
            DESCRIPTION
                "This object indicates the row status. The row can be created or deleted.
                "
            ::= { hwBRASIfCfgDelayLoadBalanceGroupEntry 2 }

   -- Begin: added for device flow stat 
 --   ====================hwBRASCvlanStatTable===========================          
                
        hwBRASCvlanStatTable OBJECT-TYPE
        SYNTAX SEQUENCE OF HwBRASCvlanStatEntry
            MAX-ACCESS not-accessible
            STATUS current
            DESCRIPTION
                "traffic statistics of cvlan"
            ::= { hwSrvcfgInterfaceMibObjects 17 }

        hwBRASCvlanStatEntry OBJECT-TYPE
            SYNTAX HwBRASCvlanStatEntry
            MAX-ACCESS not-accessible
            STATUS current
            DESCRIPTION
                "traffic statistics of cvlan"
            INDEX { hwBRASUserFlowCvlanStatCvlanId }
            ::= { hwBRASCvlanStatTable 1 }

        HwBRASCvlanStatEntry ::=
            SEQUENCE {
                hwBRASUserFlowCvlanStatCvlanId                
                    Integer32,
                hwBRASUserFlowCvlanStatInboundPackets       
                    Counter64,
                hwBRASUserFlowCvlanStatInboundBytes           
                    Counter64,
                hwBRASUserFlowCvlanStatOutboundPackets
                    Counter64,
                hwBRASUserFlowCvlanStatOutboundBytes  
                    Counter64,
                hwBRASUserFlowCvlanStatIPv4InboundPackets
                    Counter64,
                hwBRASUserFlowCvlanStatIPv4InboundBytes
                    Counter64,
                hwBRASUserFlowCvlanStatIPv4OutboundPackets
                    Counter64,
                hwBRASUserFlowCvlanStatIPv4OutboundBytes  
                    Counter64,
                hwBRASUserFlowCvlanStatIPv6InboundPackets
                    Counter64,
                hwBRASUserFlowCvlanStatIPv6InboundBytes
                    Counter64,
                hwBRASUserFlowCvlanStatIPv6OutboundPackets
                    Counter64,
                hwBRASUserFlowCvlanStatIPv6OutboundBytes  
                    Counter64,   
                hwBRASUserFlowCvlanStatReset
                    INTEGER
             }

        hwBRASUserFlowCvlanStatCvlanId OBJECT-TYPE
            SYNTAX Integer32 (0..4095)
            MAX-ACCESS read-only
            STATUS current
            DESCRIPTION
                "The inner-vlan id of uservlan."
            ::= { hwBRASCvlanStatEntry 1 }

        hwBRASUserFlowCvlanStatInboundPackets OBJECT-TYPE
            SYNTAX Counter64 
            MAX-ACCESS read-only
            STATUS current
            DESCRIPTION
                "Flow Up Packets."
            ::= { hwBRASCvlanStatEntry 2 }

        hwBRASUserFlowCvlanStatInboundBytes OBJECT-TYPE
            SYNTAX Counter64
            MAX-ACCESS read-only
            STATUS current
            DESCRIPTION
                "Flow Up Bytes."
            ::= { hwBRASCvlanStatEntry 3 }       
       
        hwBRASUserFlowCvlanStatOutboundPackets OBJECT-TYPE
            SYNTAX Counter64 
            MAX-ACCESS read-only
            STATUS current
            DESCRIPTION
                "Flow Down Packets."
            ::= { hwBRASCvlanStatEntry 4 }

        hwBRASUserFlowCvlanStatOutboundBytes OBJECT-TYPE
            SYNTAX Counter64
            MAX-ACCESS read-only
            STATUS current
            DESCRIPTION
                "Flow Down Bytes."
            ::= { hwBRASCvlanStatEntry 5 }
        
        
        hwBRASUserFlowCvlanStatIPv4InboundPackets OBJECT-TYPE
            SYNTAX Counter64
            MAX-ACCESS read-only
            STATUS current
            DESCRIPTION
                "Ipv4 flow up packets."
            ::= { hwBRASCvlanStatEntry 6 }
         
        hwBRASUserFlowCvlanStatIPv4InboundBytes OBJECT-TYPE
            SYNTAX Counter64
            MAX-ACCESS read-only
            STATUS current
            DESCRIPTION
                "Ipv4 flow up bytes."
            ::= { hwBRASCvlanStatEntry 7 }
        
        hwBRASUserFlowCvlanStatIPv4OutboundPackets OBJECT-TYPE
            SYNTAX Counter64
            MAX-ACCESS read-only
            STATUS current
            DESCRIPTION
                "Ipv4 flow down packets."
            ::= { hwBRASCvlanStatEntry 8 }
        
        hwBRASUserFlowCvlanStatIPv4OutboundBytes OBJECT-TYPE
            SYNTAX Counter64
            MAX-ACCESS read-only
            STATUS current
            DESCRIPTION
                "Ipv4 flow down bytes."
            ::= { hwBRASCvlanStatEntry 9 }
        
        hwBRASUserFlowCvlanStatIPv6InboundPackets OBJECT-TYPE
            SYNTAX Counter64
            MAX-ACCESS read-only
            STATUS current
            DESCRIPTION
                "Ipv6 flow up packets."
            ::= { hwBRASCvlanStatEntry 10 }
            
        hwBRASUserFlowCvlanStatIPv6InboundBytes OBJECT-TYPE
            SYNTAX Counter64
            MAX-ACCESS read-only
            STATUS current
            DESCRIPTION
                "Ipv6 flow up bytes."
            ::= { hwBRASCvlanStatEntry 11 }    
                                               
        hwBRASUserFlowCvlanStatIPv6OutboundPackets OBJECT-TYPE
            SYNTAX Counter64
            MAX-ACCESS read-only
            STATUS current
            DESCRIPTION
                "Ipv6 flow down packets."
            ::= { hwBRASCvlanStatEntry 12 }  
            
        hwBRASUserFlowCvlanStatIPv6OutboundBytes OBJECT-TYPE
            SYNTAX Counter64
            MAX-ACCESS read-only
            STATUS current
            DESCRIPTION
                "Ipv6 flow down bytes."
            ::= { hwBRASCvlanStatEntry 13 }   
            
        hwBRASUserFlowCvlanStatReset OBJECT-TYPE
            SYNTAX INTEGER
                {
                reset(1)
                }
            MAX-ACCESS read-create
            STATUS current
            DESCRIPTION
                "Reset the statistic information of traffic for specific vlan."
            ::= { hwBRASCvlanStatEntry 50 }    
            
 --   ====================hwBRASSvlanStatTable===========================          
                
        hwBRASSvlanStatTable OBJECT-TYPE
        SYNTAX SEQUENCE OF HwBRASSvlanStatEntry
            MAX-ACCESS not-accessible
            STATUS current
            DESCRIPTION
                "traffic statistics of svlan"
            ::= { hwSrvcfgInterfaceMibObjects 18 }

        hwBRASSvlanStatEntry OBJECT-TYPE
            SYNTAX HwBRASSvlanStatEntry
            MAX-ACCESS not-accessible
            STATUS current
            DESCRIPTION
                "traffic statistics of svlan"
            INDEX { hwBRASUserFlowSvlanStatSvlanId }
            ::= { hwBRASSvlanStatTable 1 }

        HwBRASSvlanStatEntry ::=
            SEQUENCE {
                hwBRASUserFlowSvlanStatSvlanId
                    Integer32,
                hwBRASUserFlowSvlanStatInboundPackets
                    Counter64,
                hwBRASUserFlowSvlanStatInboundBytes
                    Counter64,
                hwBRASUserFlowSvlanStatOutboundPackets
                    Counter64,
                hwBRASUserFlowSvlanStatOutboundBytes  
                    Counter64,
                hwBRASUserFlowSvlanStatIPv4InboundPackets
                    Counter64,
                hwBRASUserFlowSvlanStatIPv4InboundBytes
                    Counter64,
                hwBRASUserFlowSvlanStatIPv4OutboundPackets
                    Counter64,
                hwBRASUserFlowSvlanStatIPv4OutboundBytes  
                    Counter64,
                hwBRASUserFlowSvlanStatIPv6InboundPackets
                    Counter64,
                hwBRASUserFlowSvlanStatIPv6InboundBytes
                    Counter64,
                hwBRASUserFlowSvlanStatIPv6OutboundPackets
                    Counter64,
                hwBRASUserFlowSvlanStatIPv6OutboundBytes  
                    Counter64,   
                hwBRASUserFlowSvlanStatReset
                    INTEGER
             }

        hwBRASUserFlowSvlanStatSvlanId OBJECT-TYPE
            SYNTAX Integer32 (0..4095)
            MAX-ACCESS read-only
            STATUS current
            DESCRIPTION
                "The outer-vlan id of uservlan."
            ::= { hwBRASSvlanStatEntry 1 }

        hwBRASUserFlowSvlanStatInboundPackets OBJECT-TYPE
            SYNTAX Counter64 
            MAX-ACCESS read-only
            STATUS current
            DESCRIPTION
                "Flow Up Packets."
            ::= { hwBRASSvlanStatEntry 2 }

        hwBRASUserFlowSvlanStatInboundBytes OBJECT-TYPE
            SYNTAX Counter64
            MAX-ACCESS read-only
            STATUS current
            DESCRIPTION
                "Flow Up Bytes."
            ::= { hwBRASSvlanStatEntry 3 }       
       
        hwBRASUserFlowSvlanStatOutboundPackets OBJECT-TYPE
            SYNTAX Counter64 
            MAX-ACCESS read-only
            STATUS current
            DESCRIPTION
                "Flow Down Packets."
            ::= { hwBRASSvlanStatEntry 4 }

        hwBRASUserFlowSvlanStatOutboundBytes OBJECT-TYPE
            SYNTAX Counter64
            MAX-ACCESS read-only
            STATUS current
            DESCRIPTION
                "Flow Down Bytes."
            ::= { hwBRASSvlanStatEntry 5 }
        
        
        hwBRASUserFlowSvlanStatIPv4InboundPackets OBJECT-TYPE
            SYNTAX Counter64
            MAX-ACCESS read-only
            STATUS current
            DESCRIPTION
                "Ipv4 flow up packets."
            ::= { hwBRASSvlanStatEntry 6 }
         
        hwBRASUserFlowSvlanStatIPv4InboundBytes OBJECT-TYPE
            SYNTAX Counter64
            MAX-ACCESS read-only
            STATUS current
            DESCRIPTION
                "Ipv4 flow up bytes."
            ::= { hwBRASSvlanStatEntry 7 }
        
        hwBRASUserFlowSvlanStatIPv4OutboundPackets OBJECT-TYPE
            SYNTAX Counter64
            MAX-ACCESS read-only
            STATUS current
            DESCRIPTION
                "Ipv4 flow down packets."
            ::= { hwBRASSvlanStatEntry 8 }
        
        hwBRASUserFlowSvlanStatIPv4OutboundBytes OBJECT-TYPE
            SYNTAX Counter64
            MAX-ACCESS read-only
            STATUS current
            DESCRIPTION
                "Ipv4 flow down bytes."
            ::= { hwBRASSvlanStatEntry 9 }
        
        hwBRASUserFlowSvlanStatIPv6InboundPackets OBJECT-TYPE
            SYNTAX Counter64
            MAX-ACCESS read-only
            STATUS current
            DESCRIPTION
                "Ipv6 flow up packets."
            ::= { hwBRASSvlanStatEntry 10 }
            
        hwBRASUserFlowSvlanStatIPv6InboundBytes OBJECT-TYPE
            SYNTAX Counter64
            MAX-ACCESS read-only
            STATUS current
            DESCRIPTION
                "Ipv6 flow up bytes."
            ::= { hwBRASSvlanStatEntry 11 }    
                                               
        hwBRASUserFlowSvlanStatIPv6OutboundPackets OBJECT-TYPE
            SYNTAX Counter64
            MAX-ACCESS read-only
            STATUS current
            DESCRIPTION
                "Ipv6 flow down packets."
            ::= { hwBRASSvlanStatEntry 12 }  
            
        hwBRASUserFlowSvlanStatIPv6OutboundBytes OBJECT-TYPE
            SYNTAX Counter64
            MAX-ACCESS read-only
            STATUS current
            DESCRIPTION
                "Ipv6 flow down bytes."
            ::= { hwBRASSvlanStatEntry 13 }   
            
        hwBRASUserFlowSvlanStatReset OBJECT-TYPE
            SYNTAX INTEGER
                {
                reset(1)
                }
            MAX-ACCESS read-create
            STATUS current
            DESCRIPTION
                "Reset the statistic information of traffic for specific vlan."
            ::= { hwBRASSvlanStatEntry 50 }   
   
--   ====================hwBRASIfStatisticTable===========================           
                
        hwBRASIfStatisticTable OBJECT-TYPE
        SYNTAX SEQUENCE OF HwBRASIfStatisticEntry
            MAX-ACCESS not-accessible
            STATUS current
            DESCRIPTION
                "Number of users and traffic statistics based on BRAS interface"
            ::= { hwSrvcfgInterfaceMibObjects 20 }

        hwBRASIfStatisticEntry OBJECT-TYPE
            SYNTAX HwBRASIfStatisticEntry
            MAX-ACCESS not-accessible
            STATUS current
            DESCRIPTION
                "This object indicates statistics about a BAS interface, including the power-on time of the interface, number of access users, and uplink and downlink data rates."
            INDEX { hwBasIfIndex }
            ::= { hwBRASIfStatisticTable 1 }

        HwBRASIfStatisticEntry ::=
            SEQUENCE {
                hwBasIfIndex
                    Unsigned32,
                hwBasIfTime
                    DisplayString,
                hwBasIfUpFlowRate
                    Unsigned32,
                hwBasIfDownFlowRate
                    Unsigned32,
                hwBasIfUserNum  
                    Unsigned32,
                hwBasIfName
                    DisplayString
             }  
  
        hwBasIfIndex OBJECT-TYPE
            SYNTAX Unsigned32 (0..4294967295)
            MAX-ACCESS read-only
            STATUS current
            DESCRIPTION
                "This object indicates the index of a BAS interface."
            ::= { hwBRASIfStatisticEntry 1 }

        hwBasIfTime OBJECT-TYPE
            SYNTAX DisplayString (SIZE (0..32))             
            MAX-ACCESS read-only
            STATUS current
            DESCRIPTION
                "This object indicates the time when statistics about a BAS interface is collected."
            ::= { hwBRASIfStatisticEntry 2 }
            
        hwBasIfUpFlowRate OBJECT-TYPE
            SYNTAX Unsigned32 (0..4294967295)
            MAX-ACCESS read-only
            STATUS current
            DESCRIPTION
                "This object indicates the uplink rate on a BAS interface."
            ::= { hwBRASIfStatisticEntry 3 } 

        hwBasIfDownFlowRate OBJECT-TYPE
            SYNTAX Unsigned32 (0..4294967295)
            MAX-ACCESS read-only
            STATUS current
            DESCRIPTION
                "This object indicates the downlink rate on a BAS interface."
            ::= { hwBRASIfStatisticEntry 4 } 

        hwBasIfUserNum OBJECT-TYPE
            SYNTAX Unsigned32 (0..4294967295)
            MAX-ACCESS read-only
            STATUS current
            DESCRIPTION
                "This object indicates the number of online users on a BAS interface."
            ::= { hwBRASIfStatisticEntry 5 } 

        hwBasIfName OBJECT-TYPE
            SYNTAX DisplayString (SIZE (1..32))
            MAX-ACCESS read-only
            STATUS current
            DESCRIPTION
                "This object indicates the name of a BAS interface."
            ::= { hwBRASIfStatisticEntry 6 }            

         
  --   ====================hwBRASVpiStatTable===========================          
                
        hwBRASVpiStatTable OBJECT-TYPE
        SYNTAX SEQUENCE OF HwBRASVpiStatEntry
            MAX-ACCESS not-accessible
            STATUS current
            DESCRIPTION
                "traffic statistics of vpi"
            ::= { hwSrvcfgInterfaceMibObjects 19 }

        hwBRASVpiStatEntry OBJECT-TYPE
            SYNTAX HwBRASVpiStatEntry
            MAX-ACCESS not-accessible
            STATUS current
            DESCRIPTION
                "traffic statistics of vpi"
            INDEX { hwBRASUserFlowVpiStatVpiId }
            ::= { hwBRASVpiStatTable 1 }

        HwBRASVpiStatEntry ::=
            SEQUENCE {
                hwBRASUserFlowVpiStatVpiId
                    Integer32,
                hwBRASUserFlowVpiStatInboundPackets
                    Counter64,
                hwBRASUserFlowVpiStatInboundBytes
                    Counter64,
                hwBRASUserFlowVpiStatOutboundPackets
                    Counter64,
                hwBRASUserFlowVpiStatOutboundBytes  
                    Counter64,
                hwBRASUserFlowVpiStatIPv4InboundPackets
                    Counter64,
                hwBRASUserFlowVpiStatIPv4InboundBytes
                    Counter64,
                hwBRASUserFlowVpiStatIPv4OutboundPackets
                    Counter64,
                hwBRASUserFlowVpiStatIPv4OutboundBytes  
                    Counter64,
                hwBRASUserFlowVpiStatIPv6InboundPackets
                    Counter64,
                hwBRASUserFlowVpiStatIPv6InboundBytes
                    Counter64,
                hwBRASUserFlowVpiStatIPv6OutboundPackets
                    Counter64,
                hwBRASUserFlowVpiStatIPv6OutboundBytes  
                    Counter64,   
                hwBRASUserFlowVpiStatReset
                    INTEGER
             }

        hwBRASUserFlowVpiStatVpiId OBJECT-TYPE
            SYNTAX Integer32 (0..4095)
            MAX-ACCESS read-only
            STATUS current
            DESCRIPTION
                "The outer-vlan id of uservlan."
            ::= { hwBRASVpiStatEntry 1 }

        hwBRASUserFlowVpiStatInboundPackets OBJECT-TYPE
            SYNTAX Counter64 
            MAX-ACCESS read-only
            STATUS current
            DESCRIPTION
                "Flow Up Packets."
            ::= { hwBRASVpiStatEntry 2 }

        hwBRASUserFlowVpiStatInboundBytes OBJECT-TYPE
            SYNTAX Counter64
            MAX-ACCESS read-only
            STATUS current
            DESCRIPTION
                "Flow Up Bytes."
            ::= { hwBRASVpiStatEntry 3 }       
       
        hwBRASUserFlowVpiStatOutboundPackets OBJECT-TYPE
            SYNTAX Counter64 
            MAX-ACCESS read-only
            STATUS current
            DESCRIPTION
                "Flow Down Packets."
            ::= { hwBRASVpiStatEntry 4 }

        hwBRASUserFlowVpiStatOutboundBytes OBJECT-TYPE
            SYNTAX Counter64
            MAX-ACCESS read-only
            STATUS current
            DESCRIPTION
                "Flow Down Bytes."
            ::= { hwBRASVpiStatEntry 5 }
        
        
        hwBRASUserFlowVpiStatIPv4InboundPackets OBJECT-TYPE
            SYNTAX Counter64
            MAX-ACCESS read-only
            STATUS current
            DESCRIPTION
                "Ipv4 flow up packets."
            ::= { hwBRASVpiStatEntry 6 }
         
        hwBRASUserFlowVpiStatIPv4InboundBytes OBJECT-TYPE
            SYNTAX Counter64
            MAX-ACCESS read-only
            STATUS current
            DESCRIPTION
                "Ipv4 flow up bytes."
            ::= { hwBRASVpiStatEntry 7 }
        
        hwBRASUserFlowVpiStatIPv4OutboundPackets OBJECT-TYPE
            SYNTAX Counter64
            MAX-ACCESS read-only
            STATUS current
            DESCRIPTION
                "Ipv4 flow down packets."
            ::= { hwBRASVpiStatEntry 8 }
        
        hwBRASUserFlowVpiStatIPv4OutboundBytes OBJECT-TYPE
            SYNTAX Counter64
            MAX-ACCESS read-only
            STATUS current
            DESCRIPTION
                "Ipv4 flow down bytes."
            ::= { hwBRASVpiStatEntry 9 }
        
        hwBRASUserFlowVpiStatIPv6InboundPackets OBJECT-TYPE
            SYNTAX Counter64
            MAX-ACCESS read-only
            STATUS current
            DESCRIPTION
                "Ipv6 flow up packets."
            ::= { hwBRASVpiStatEntry 10 }
            
        hwBRASUserFlowVpiStatIPv6InboundBytes OBJECT-TYPE
            SYNTAX Counter64
            MAX-ACCESS read-only
            STATUS current
            DESCRIPTION
                "Ipv6 flow up bytes."
            ::= { hwBRASVpiStatEntry 11 }    
                                               
        hwBRASUserFlowVpiStatIPv6OutboundPackets OBJECT-TYPE
            SYNTAX Counter64
            MAX-ACCESS read-only
            STATUS current
            DESCRIPTION
                "Ipv6 flow down packets."
            ::= { hwBRASVpiStatEntry 12 }  
            
        hwBRASUserFlowVpiStatIPv6OutboundBytes OBJECT-TYPE
            SYNTAX Counter64
            MAX-ACCESS read-only
            STATUS current
            DESCRIPTION
                "Ipv6 flow down bytes."
            ::= { hwBRASVpiStatEntry 13 }   
            
        hwBRASUserFlowVpiStatReset OBJECT-TYPE
            SYNTAX INTEGER
                {
                reset(1)
                }
            MAX-ACCESS read-create
            STATUS current
            DESCRIPTION
                "Reset the statistic information of traffic for specific vpi."
            ::= { hwBRASVpiStatEntry 50 }
   
  -- End: added for device flow stat 
                                                
--   ====================hwBRASSrvcfgIfVpnStatTable===========================          
        hwBRASSrvcfgIfVpnStatTable OBJECT-TYPE
        SYNTAX SEQUENCE OF HwBRASSrvcfgIfVpnStatEntry
            MAX-ACCESS not-accessible
            STATUS current
            DESCRIPTION
                "traffic statistics of vpn"
            ::= { hwSrvcfgInterfaceMibObjects 21 }


        hwBRASSrvcfgIfVpnStatEntry OBJECT-TYPE
            SYNTAX HwBRASSrvcfgIfVpnStatEntry
            MAX-ACCESS not-accessible
            STATUS current
            DESCRIPTION
                "traffic statistics of vpn"
            INDEX { hwBRASSrvcfgIfVpnStatIfIndex, hwBRASSrvcfgIfVpnStatVpnName }
            ::= { hwBRASSrvcfgIfVpnStatTable 1 }

        HwBRASSrvcfgIfVpnStatEntry ::=
            SEQUENCE {
                hwBRASSrvcfgIfVpnStatIfIndex
                    InterfaceIndex,
                hwBRASSrvcfgIfVpnStatVpnName
                    DisplayString,
                hwBRASSrvcfgIfVpnStatInPkts
                    Counter64,
                hwBRASSrvcfgIfVpnStatInBytes
                    Counter64,
                hwBRASSrvcfgIfVpnStatOutPkts
                    Counter64,
                hwBRASSrvcfgIfVpnStatOutBytes
                    Counter64,
                hwBRASSrvcfgIfVpnStatReset
                    INTEGER,
                hwBRASSrvcfgIfV4VpnStatInPkts
                    Counter64,
                hwBRASSrvcfgIfV4VpnStatInBytes
                    Counter64,
                hwBRASSrvcfgIfV4VpnStatOutPkts
                    Counter64,
                hwBRASSrvcfgIfV4VpnStatOutBytes
                    Counter64,
                hwBRASSrvcfgIfV6VpnStatInPkts
                    Counter64,
                hwBRASSrvcfgIfV6VpnStatInBytes
                    Counter64,
                hwBRASSrvcfgIfV6VpnStatOutPkts
                    Counter64,
                hwBRASSrvcfgIfV6VpnStatOutBytes
                    Counter64,
               hwBRASSrvcfgIfVpnAccessNumber
                    Integer32
             }

        hwBRASSrvcfgIfVpnStatIfIndex OBJECT-TYPE
            SYNTAX InterfaceIndex
            MAX-ACCESS read-only
            STATUS current
            DESCRIPTION
                "Interface Index."
            ::= { hwBRASSrvcfgIfVpnStatEntry 1 }

        hwBRASSrvcfgIfVpnStatVpnName OBJECT-TYPE
            SYNTAX DisplayString (SIZE (0..31))
            MAX-ACCESS read-only
            STATUS current
            DESCRIPTION
                "The vpn name for ethernet interface."
            ::= { hwBRASSrvcfgIfVpnStatEntry 2 }

        hwBRASSrvcfgIfVpnStatInPkts OBJECT-TYPE
            SYNTAX Counter64 
            MAX-ACCESS read-only
            STATUS current
            DESCRIPTION
                "Flow Up Packets."
            ::= { hwBRASSrvcfgIfVpnStatEntry 3 }

        hwBRASSrvcfgIfVpnStatInBytes OBJECT-TYPE
            SYNTAX Counter64
            MAX-ACCESS read-only
            STATUS current
            DESCRIPTION
                "Flow Up Bytes."
            ::= { hwBRASSrvcfgIfVpnStatEntry 4 }

       hwBRASSrvcfgIfVpnStatOutPkts OBJECT-TYPE
            SYNTAX Counter64 
            MAX-ACCESS read-only
            STATUS current
            DESCRIPTION
                "Flow Down Packets."
            ::= { hwBRASSrvcfgIfVpnStatEntry 5 }

        hwBRASSrvcfgIfVpnStatOutBytes OBJECT-TYPE
            SYNTAX Counter64
            MAX-ACCESS read-only
            STATUS current
            DESCRIPTION
                "Flow Down Bytes."
            ::= { hwBRASSrvcfgIfVpnStatEntry 6 }

        hwBRASSrvcfgIfVpnStatReset OBJECT-TYPE
            SYNTAX INTEGER
                {
                reset(1)
                }
            MAX-ACCESS read-write
            STATUS current
            DESCRIPTION
                "Reset the statistic information of traffic for specific vpn in the current interface."
            ::= { hwBRASSrvcfgIfVpnStatEntry 7 }

        hwBRASSrvcfgIfV4VpnStatInPkts OBJECT-TYPE
            SYNTAX Counter64
            MAX-ACCESS read-only
            STATUS current
            DESCRIPTION
                "Ipv4 flow up packets."
            ::= { hwBRASSrvcfgIfVpnStatEntry 8 }

        hwBRASSrvcfgIfV4VpnStatInBytes OBJECT-TYPE
            SYNTAX Counter64
            MAX-ACCESS read-only
            STATUS current
            DESCRIPTION
                "Ipv4 flow up bytes."
            ::= { hwBRASSrvcfgIfVpnStatEntry 9 }

        hwBRASSrvcfgIfV4VpnStatOutPkts OBJECT-TYPE
            SYNTAX Counter64
            MAX-ACCESS read-only
            STATUS current
            DESCRIPTION
                "Ipv4 flow down packets."
            ::= { hwBRASSrvcfgIfVpnStatEntry 10 }

        hwBRASSrvcfgIfV4VpnStatOutBytes OBJECT-TYPE
            SYNTAX Counter64
            MAX-ACCESS read-only
            STATUS current
            DESCRIPTION
                "Ipv4 flow down bytes."
            ::= { hwBRASSrvcfgIfVpnStatEntry 11 }

        hwBRASSrvcfgIfV6VpnStatInPkts OBJECT-TYPE
            SYNTAX Counter64
            MAX-ACCESS read-only
            STATUS current
            DESCRIPTION
                "Ipv6 flow up packets."
            ::= { hwBRASSrvcfgIfVpnStatEntry 12 }

        hwBRASSrvcfgIfV6VpnStatInBytes OBJECT-TYPE
            SYNTAX Counter64
            MAX-ACCESS read-only
            STATUS current
            DESCRIPTION
                "Ipv6 flow up bytes."
            ::= { hwBRASSrvcfgIfVpnStatEntry 13 }

        hwBRASSrvcfgIfV6VpnStatOutPkts OBJECT-TYPE
            SYNTAX Counter64
            MAX-ACCESS read-only
            STATUS current
            DESCRIPTION
                "Ipv6 flow down packets."
            ::= { hwBRASSrvcfgIfVpnStatEntry 14 }

        hwBRASSrvcfgIfV6VpnStatOutBytes OBJECT-TYPE
            SYNTAX Counter64
            MAX-ACCESS read-only
            STATUS current
            DESCRIPTION
                "Ipv6 flow down bytes."
            ::= { hwBRASSrvcfgIfVpnStatEntry 15 }

        hwBRASSrvcfgIfVpnAccessNumber OBJECT-TYPE
            SYNTAX Integer32
            MAX-ACCESS read-only
            STATUS current
            DESCRIPTION
                "user access number."
            ::= { hwBRASSrvcfgIfVpnStatEntry 16}

--   ====================hwBRASSrvcfgIfVpnStatTable=========================== 

--    ============== conformance information ==============
        hwSrvcfgInterfaceConformance OBJECT IDENTIFIER ::= { hwBRASSrvcfgInterface 2 }

        hwSrvcfgInterfaceCompliances OBJECT IDENTIFIER ::= { hwSrvcfgInterfaceConformance 1 }

--   this module
        hwSrvcfgInterfaceCompliance MODULE-COMPLIANCE
            STATUS current
            DESCRIPTION
                "
                The compliance statement for systems supporting
                the this module.
                "
            MODULE -- this module
                MANDATORY-GROUPS { hwBRASIfCfgGroup, hwBRASIfVlanGroup, hwBRASIfPvcGroup, hwSTPRelayServerGroup, hwPortAccessLimitGroup,
                    hwL3SubscriberIspGroup, hwConnTimeOutGroup, hwSrvcfgScalarGroup, hwBRASIfVlanNumGroup, hwServiceIfCfgGroup,
                    hwBRASIfEnableGroup }
            ::= { hwSrvcfgInterfaceCompliances 1 }

--    ============== groups ==============
        hwSrvcfgInterfaceGroups OBJECT IDENTIFIER ::= { hwSrvcfgInterfaceConformance 2 }

        hwBRASIfCfgGroup OBJECT-GROUP
            OBJECTS { hwBRASIfCfgAccessType, hwBRASIfCfgBRASIfName, hwBRASIfCfgPreAuthDomain, hwBRASIfCfgAuthDomain, hwBRASIfCfgForceAuthDomain,
                hwBRASIfCfgAcctCpyRdSvr, hwBRASIfCfgAuthMethod, hwBRASIfCfgNasPortType, hwBRASIfCfgLeaseName, hwBRASIfCfgLeasePwd,
                hwBRASIfCfgArpInterval, hwBRASIfCfgArpFailTimes, hwBRASIfCfgArpProxy, hwBRASIfCfgRoamIsp, hwBRASIfCfgDhcpBroadCast,
                hwBRASIfCfgHostCar, hwBRASIfCfgRowStatus, hwBRASIfCfgEapTrigger, hwBRASIfCfgWlanSwitch, hwBRASIfCfgWlanAuthorization,
                hwBRASIfCfgDhcpShortLease, hwBRASIfCfgRoamDomain, hwBRASIfVsiName, hwBRASIfCfgOption82, hwBRASIfVpnInstance,
                hwBRASIfCopyMulticasePerUser, hwBRASIfCfgNDProxy, hwBRASIfCfgVBasMAC, hwBRASIfCfgVBasAuthMode, hwBRASIfCfgPermitDomain1,
                hwBRASIfCfgPermitDomain2, hwBRASIfCfgPermitDomain3, hwBRASIfCfgPermitDomain4, hwBRASIfCfgAccessDelayType, hwBRASIfCfgTermlessDelayTime,
                hwBRASIfCfgOddMacDelayTime, hwBRASIfCfgEvenMacDelayTime, hwBRASIfCfgAccessNodeIdentify, hwBRASIfCfgAniDelayTime, hwBRASIfCfgRemoteBackupProfile,
                hwBRASIfCfgOption60, hwBRASIfCfgIpTrigger, hwBRASIfCfgArpTrigger, hwBRASIfCfgWlanSSID, hwBRASIfCfgDhcpProxy, hwBRASIfCfgTrust8021pProtocol, hwBRASIfCfgIfIndex,
                hwBRASIfVlanIfIndex, hwBRASIfVlanVlanId, hwBRASIfDhcpSessionMismatch,hwBRASIfCfgDhcpLeaseProxy,hwBRASIfCfgDhcpLeaseProxyFirstStep,hwBRASIfCfgDhcpLeaseProxySecondStep}
            STATUS current
            DESCRIPTION
                "
                "
            ::= { hwSrvcfgInterfaceGroups 1 }

        hwBRASIfVlanGroup OBJECT-GROUP
            OBJECTS { hwBRASIfVlanVlanNumber, hwBRASIfVlanAccessLimit, hwBRASIfVlanAccessNumber, hwBRASIfVlanBlock, hwBRASIfVlanDevAccessNumber,
                hwBRASIfVlanSchedulerVcName, hwBRASIfVlanSchedulerVcGroupName, hwBRASIfVlanSchedulerVpGroupName, hwBRASIfQinQVlanID, hwBRASIfVlanRowStatus }
            STATUS current
            DESCRIPTION
                "
                "
            ::= { hwSrvcfgInterfaceGroups 2 }

        hwBRASIfPvcGroup OBJECT-GROUP
            OBJECTS { hwBRASIfPvcPvcNumber, hwBRASIfPvcAccessLimit, hwBRASIfPvcAccessNumber, hwBRASIfPvcBlock, hwBRASIfPvcDevAccessNumber,
                hwBRASIfPvcSchedulerVcGroupName, hwBRASIfPvcSchedulerVpGroupName, hwBRASIfPvcIfIndex, hwBRASIfPvcVpi, hwBRASIfPvcVci
                 }
            STATUS current
            DESCRIPTION
                "
                "
            ::= { hwSrvcfgInterfaceGroups 3 }

        hwSTPRelayServerGroup OBJECT-GROUP
            OBJECTS { hwSTPRelayInIfIndex, hwSTPRelayOutIfIndex, hwSTPRelayRowStatus, hwSTPRelayInIfName, hwSTPRelayOutIfName,
                hwSTPRelayInMac, hwSTPRelayOutMac, hwSTPRelayIndex }
            STATUS current
            DESCRIPTION
                "
                "
            ::= { hwSrvcfgInterfaceGroups 4 }

        hwPortAccessLimitGroup OBJECT-GROUP
            OBJECTS { hwPortAccessLimitLimit, hwPortAccessLimitNumber, hwPortAccessLimitDevNumber, hwPortAccessLimitIfIndex }
            STATUS current
            DESCRIPTION
                "
                "
            ::= { hwSrvcfgInterfaceGroups 5 }

        hwL3SubscriberIspGroup OBJECT-GROUP
            OBJECTS { hwL3SubscriberIspEndIp, hwL3SubscriberIspDomainName, hwL3SubscriberIspRowStatus, hwL3SubscriberIspStartIp, hwL3SubscriberIspVpnId
                 }
            STATUS current
            DESCRIPTION
                "
                "
            ::= { hwSrvcfgInterfaceGroups 6 }

        hwConnTimeOutGroup OBJECT-GROUP
            OBJECTS { hwConnTimeOutTcp, hwConnTimeOutUdp }
            STATUS current
            DESCRIPTION
                "
                "
            ::= { hwSrvcfgInterfaceGroups 7 }

        hwSrvcfgScalarGroup OBJECT-GROUP
            OBJECTS { hwDhcpOption60DomainInclude, hwDhcpOption60PartialMatch }
            STATUS current
            DESCRIPTION
                "
                "
            ::= { hwSrvcfgInterfaceGroups 8 }

        hwBRASIfVlanNumGroup OBJECT-GROUP
            OBJECTS { hwBRASSlotVlanNum, hwBRASSLotStaticVlanNum, hwBRASIfSlot }
            STATUS current
            DESCRIPTION
                "
                "
            ::= { hwSrvcfgInterfaceGroups 9 }

        hwServiceIfCfgGroup OBJECT-GROUP
            OBJECTS { hwServiceIfCfgIdentificationMode, hwServiceIfCfgDomain, hwServiceIfCfgUserName, hwServiceIfCfgPassword, hwServiceIfCfgDetectNum,
                hwServiceIfCfgDetectInterval, hwServiceIfCfgOption82, hwServiceIfCfgAccessLimit, hwServiceIfCfgOption60, hwServiceIfCfgIpTriggerEnable,
                hwServiceIfCfgArpTriggerEnable, hwServiceIfCfgIfBlock, hwServiceIfCfgQosProfile, hwServiceIfCfgBindingUserPasswordMode, hwServiceIfCfgBindingUserNameFormat,
                hwServiceIfCfgBindingUserPassword, hwServiceIfCfgRowStatus }
            STATUS current
            DESCRIPTION
                "
                "
            ::= { hwSrvcfgInterfaceGroups 10 }

        hwBRASIfEnableGroup OBJECT-GROUP
            OBJECTS { hwBRASIfEnableIfIndex, hwBRASIfEnableStatus }
            STATUS current
            DESCRIPTION
                "Description."
            ::= { hwSrvcfgInterfaceGroups 11 }

        hwBRASIfVlanAccessGroup OBJECT-GROUP
            OBJECTS { hwBRASIfVlanAccessIfIndex, hwBRASIfVlanAccessQinqVlanId, hwBRASIfVlanAccessVlanId, hwBRASIfVlanAccessUserNumber }
            STATUS current
            DESCRIPTION
                "Description."
            ::= { hwSrvcfgInterfaceGroups 12 }

        hwSrvcfgInterfaceTrap OBJECT IDENTIFIER ::= { hwBRASSrvcfgInterface 3 }
    	  hwSrvcfgInterfaceTrapOid OBJECT IDENTIFIER ::={hwSrvcfgInterfaceTrap 1}
    	  	  hwBRASBoardNotSupportBasSlotId OBJECT-TYPE
    	  	  	SYNTAX Integer32(1..51|255)
    	  	  	MAX-ACCESS accessible-for-notify
    	  	  STATUS current
    	  	  DESCRIPTION
    	  	  	"specified board does not support BAS."
    	  	  ::={hwSrvcfgInterfaceTrapOid 1}
   	  	  hwSrvcfgSubCardReachMaxRecomNumberSlotId OBJECT-TYPE
			SYNTAX DisplayString (SIZE(1..32))
			MAX-ACCESS accessible-for-notify
			STATUS current
			DESCRIPTION
			"
			specified board id
			"
		::= {hwSrvcfgInterfaceTrapOid 2}
    	  	  
	                     hwSrvcfgSubCardReachMaxRecomNumberCardId OBJECT-TYPE
			SYNTAX Integer32 (0..1)
			MAX-ACCESS accessible-for-notify
			STATUS current
			DESCRIPTION
			"
			 specified card id
			"
		::= {hwSrvcfgInterfaceTrapOid 3} 

		hwCuVxlanTunnelUpId OBJECT-TYPE
		    SYNTAX Integer32 (1024..1279)
		    MAX-ACCESS accessible-for-notify
		    STATUS current
		    DESCRIPTION
		    "
		     ID of the UP instance bound to the VXLAN tunnel
		    "
	    ::= {hwSrvcfgInterfaceTrapOid 4}
		
		hwCuVxlanTunnelSrcIpAddr OBJECT-TYPE
		    SYNTAX IpAddress
		    MAX-ACCESS accessible-for-notify
		    STATUS current
		    DESCRIPTION
		    "
		     Source IP address of the VXLAN tunnel in the CU spearation scenario
		    "
	    ::= {hwSrvcfgInterfaceTrapOid 5}
		
		hwCuVxlanTunnelPeerIpAddr OBJECT-TYPE
		    SYNTAX IpAddress
		    MAX-ACCESS accessible-for-notify
		    STATUS current
		    DESCRIPTION
		    "
		     Peer IP address of the VXLAN tunnel in the CU spearation scenario
		    "
	    ::= {hwSrvcfgInterfaceTrapOid 6}
		
		hwCuVxlanTunnelInVni OBJECT-TYPE
		    SYNTAX Integer32 (1..16777215)
		    MAX-ACCESS accessible-for-notify
		    STATUS current
		    DESCRIPTION
		    "
		     VXLAN network identifier
		    "
	    ::= {hwSrvcfgInterfaceTrapOid 7}
		
		hwCuVxlanTunnelVpn OBJECT-TYPE
		    SYNTAX DisplayString (SIZE (1..32))
		    MAX-ACCESS accessible-for-notify
		    STATUS current
		    DESCRIPTION
		    "
		     VXLAN VPN-instance name
		    "
	    ::= {hwSrvcfgInterfaceTrapOid 8}

		hwIpv4FramedRouteUsage OBJECT-TYPE
		    SYNTAX Unsigned32 (0..100)
		    MAX-ACCESS accessible-for-notify
		    STATUS current
		    DESCRIPTION
		    "
		     The usage of ipv4 framed route
		    "
	    ::= {hwSrvcfgInterfaceTrapOid 9}

		hwBRASBoardLicenseName OBJECT-TYPE
		    SYNTAX DisplayString (SIZE (1..32))
		    MAX-ACCESS accessible-for-notify
		    STATUS current
		    DESCRIPTION
		    "
		     BRAS board license item name
		    "
	    ::= {hwSrvcfgInterfaceTrapOid 10}

		hwBRASBoardLicenseDescription OBJECT-TYPE
		    SYNTAX DisplayString (SIZE (1..128))
		    MAX-ACCESS accessible-for-notify
		    STATUS current
		    DESCRIPTION
		    "
		     BRAS board license item description
		    "
	    ::= {hwSrvcfgInterfaceTrapOid 11}

		hwBRASBoardLicenseSlotID OBJECT-TYPE
		    SYNTAX DisplayString (SIZE (1..16))
		    MAX-ACCESS accessible-for-notify
		    STATUS current
		    DESCRIPTION
		    "
		     The board that failed to activate BAS function license
		    "
	    ::= {hwSrvcfgInterfaceTrapOid 12}

                       hwBRASLicenseItemName OBJECT-TYPE
		    SYNTAX DisplayString (SIZE (1..32))
		    MAX-ACCESS accessible-for-notify
		    STATUS current
		    DESCRIPTION
		    "
		     BRAS function license item name
		    "
	    ::= {hwSrvcfgInterfaceTrapOid 13}
		
	   hwBRASServiceEnable OBJECT-TYPE
		    SYNTAX DisplayString (SIZE (1..128))
		    MAX-ACCESS accessible-for-notify
		    STATUS current
		    DESCRIPTION
		    "
		     BRAS function enable configuration
		    "
	    ::= {hwSrvcfgInterfaceTrapOid 14}
		
	   hwBRASLicenseDescription OBJECT-TYPE
		    SYNTAX DisplayString (SIZE (1..128))
		    MAX-ACCESS accessible-for-notify
		    STATUS current
		    DESCRIPTION
		    "
		     BRAS function license item description
		    "
	    ::= {hwSrvcfgInterfaceTrapOid 15}

          hwCuVxlanTunnelPlr OBJECT-TYPE
		    SYNTAX Unsigned32 (0..100)
		    MAX-ACCESS accessible-for-notify
		    STATUS current
		    DESCRIPTION
		    "
		     Packet loss rate of the VXLAN tunnel
		    "
	    ::= {hwSrvcfgInterfaceTrapOid 16}

    	  hwSrvcfgInterfaceTrapsDefine OBJECT IDENTIFIER ::={hwSrvcfgInterfaceTrap 2}
	          hwBRASBoardNotSupportBasAlarm NOTIFICATION-TYPE 
	          	OBJECTS { hwBRASBoardNotSupportBasSlotId }
	            STATUS current
	            DESCRIPTION
	                "                                   
	                1 Notice/Trap name:  hwBRASBoardNotSupportBas
	                2 Notice/Trap generation cause:  specified board does not support BAS.
	                3 Repair suggestions: 
	                    replace it with a BAS-supported board.
	                "
	            ::= { hwSrvcfgInterfaceTrapsDefine 1 }
                           hwBRASBoardNotSupportBasResume NOTIFICATION-TYPE 
	          	OBJECTS { hwBRASBoardNotSupportBasSlotId }
	            STATUS current
	            DESCRIPTION
	                "                                   
	                1 Notice/Trap name:  hwBRASBoardNotSupportBasResume
	                2 Notice/Trap generation cause:  alarm was cleared because the board that does not support BAS was removed or the BAS configuration was deleted from the board.
	                "
	            ::= { hwSrvcfgInterfaceTrapsDefine 2 }
	    hwBoardSetGTPModeNotSupportBas NOTIFICATION-TYPE 
	          	OBJECTS { hwBRASBoardNotSupportBasSlotId }
	            STATUS current
	            DESCRIPTION
	                "         
                                     1 Notice/Trap name:  hwBoardSetGTPModeNotSupportBas
                                     2 Notice/Trap generation cause: The L2TP tunnel keepalive function became abnormal on a board when GTP was enabled on the board, causing L2TP users with LAC-side outbound interfaces on this board to go offline.                 
	                "
	            ::= { hwSrvcfgInterfaceTrapsDefine 3 }    

	        hwSrvcfgSubCardReachMaxRecomNumber NOTIFICATION-TYPE 
	                     OBJECTS { hwSrvcfgSubCardReachMaxRecomNumberSlotId,hwSrvcfgSubCardReachMaxRecomNumberCardId }
	             STATUS current
	             DESCRIPTION
		 "
		1 Notice/Trap name:  hwSrvcfgSubCardReachMaxRecomNumber
		2 Notice/Trap generation cause: The number of reassembly tables delivered by the board exceeded the maximum number of reassembly tables allowed by the subcard.
		 "
	              ::= { hwSrvcfgInterfaceTrapsDefine 4 } 

            hwCuVxlanTunnelDown NOTIFICATION-TYPE 
	                     OBJECTS { hwCuVxlanTunnelSrcIpAddr,hwCuVxlanTunnelPeerIpAddr,hwCuVxlanTunnelInVni,hwCuVxlanTunnelVpn,hwCuVxlanTunnelUpId }
	             STATUS current
	             DESCRIPTION
		 "
		This object indicates that an alarm is generated on the CP side when a VXLAN tunnel connectivity fault is detected.
		 "
	              ::= { hwSrvcfgInterfaceTrapsDefine 5 }

            hwCuVxlanTunnelResume NOTIFICATION-TYPE 
	                     OBJECTS { hwCuVxlanTunnelSrcIpAddr,hwCuVxlanTunnelPeerIpAddr,hwCuVxlanTunnelInVni,hwCuVxlanTunnelVpn,hwCuVxlanTunnelUpId }
	             STATUS current
	             DESCRIPTION
		 "
		This object indicates that a clear alarm is generated on the CP side when a VXLAN tunnel connectivity fault is rectified.
		 "
	              ::= { hwSrvcfgInterfaceTrapsDefine 6 }
			
            hwIpv4FramedRouteThresholdAlarm NOTIFICATION-TYPE
            OBJECTS {hwIpv4FramedRouteUsage}
            STATUS current
            DESCRIPTION
                "
                This object indicates that the usage of ipv4 framed route exceeds the threshold.
                "
            ::= { hwSrvcfgInterfaceTrapsDefine 7 }
		
            hwIpv4FramedRouteThresholdAlarmResume NOTIFICATION-TYPE
            OBJECTS {hwIpv4FramedRouteUsage}
            STATUS current
            DESCRIPTION
                "
                This object indicates that the alarm generated when the usage of ipv4 framed route falls below the threshold is cleared.
                "
            ::= { hwSrvcfgInterfaceTrapsDefine 8 }		
			
            hwBRASActiveBasSlotFailAlarm NOTIFICATION-TYPE
            OBJECTS {hwBRASBoardLicenseName,hwBRASBoardLicenseDescription,hwBRASBoardLicenseSlotID}
            STATUS current
            DESCRIPTION
                "
                1 Notice/Trap name:  hwBRASActiveBasSlotFailAlarm
                2 Notice/Trap generation cause:  The BAS function license on the board failed to be activated.
                3 Repair suggestions:  a. Purchase and activate the corresponding license resource item.
                                                     b. Delete the configuration for activating the BAS function license on the board. 
                                                     c. Remove the board with the active bas slot command configured.
                "
            ::= { hwSrvcfgInterfaceTrapsDefine 9 }
		
            hwBRASActiveBasSlotFailResume NOTIFICATION-TYPE
            OBJECTS {hwBRASBoardLicenseName,hwBRASBoardLicenseDescription,hwBRASBoardLicenseSlotID}
            STATUS current
            DESCRIPTION
                "
                1 Notice/Trap name:  hwBRASBoardNotSupportBasResume
                2 Notice/Trap generation cause: The corresponding license resources became sufficient and the BAS function license on the board had been activated, 
                                                                    the configuration for activating the BAS function license on the board was deleted, 
                                                                    or the board with the active bas slot command configured had been removed. 
                "
            ::= { hwSrvcfgInterfaceTrapsDefine 10 }		
           
           hwBRASLicenseItemEvent NOTIFICATION-TYPE
            OBJECTS {hwBRASServiceEnable,hwBRASLicenseItemName,hwBRASLicenseDescription}
            STATUS current
            DESCRIPTION
                "
                1 Notice/Trap name:  hwBRASLicenseItemEvent
                2 Notice/Trap generation cause: Service configuration exist, but the corresponding license is deactived. 
                "
            ::= { hwSrvcfgInterfaceTrapsDefine 11 }	

            hwCuUpVxlanTunnelDown NOTIFICATION-TYPE
             OBJECTS { hwCuVxlanTunnelSrcIpAddr,hwCuVxlanTunnelPeerIpAddr,hwCuVxlanTunnelInVni,hwCuVxlanTunnelVpn }
             STATUS current
             DESCRIPTION
                "
                This object indicates that an alarm is generated on the UP side when a VXLAN tunnel connectivity fault is detected.
                "
              ::= { hwSrvcfgInterfaceTrapsDefine 12 }

            hwCuUpVxlanTunnelResume NOTIFICATION-TYPE 
             OBJECTS { hwCuVxlanTunnelSrcIpAddr,hwCuVxlanTunnelPeerIpAddr,hwCuVxlanTunnelInVni,hwCuVxlanTunnelVpn }
             STATUS current
             DESCRIPTION
              "
              This object indicates that a clear alarm is generated on the UP side when a VXLAN tunnel connectivity fault is rectified.
              "
             ::= { hwSrvcfgInterfaceTrapsDefine 13 }
           hwCuVxlanTunnelPlrAlarm NOTIFICATION-TYPE 
            OBJECTS { hwCuVxlanTunnelSrcIpAddr,hwCuVxlanTunnelPeerIpAddr,hwCuVxlanTunnelInVni,hwCuVxlanTunnelVpn,hwCuVxlanTunnelUpId,hwCuVxlanTunnelPlr }
            STATUS current
            DESCRIPTION
               "
               This object indicates that an alarm is generated on the CP side when the network of a VXLAN tunnel is abnormal.
               "
            ::= { hwSrvcfgInterfaceTrapsDefine 14 }
			
           hwCuVxlanTunnelPlrResume NOTIFICATION-TYPE 
            OBJECTS { hwCuVxlanTunnelSrcIpAddr,hwCuVxlanTunnelPeerIpAddr,hwCuVxlanTunnelInVni,hwCuVxlanTunnelVpn,hwCuVxlanTunnelUpId,hwCuVxlanTunnelPlr }
            STATUS current
            DESCRIPTION
              "
              This object indicates that a clear alarm is generated on the CP side when the network of a VXLAN tunnel recovers.
              "
           ::= { hwSrvcfgInterfaceTrapsDefine 15 }
    END

--
-- HUAWEI-BRAS-SRVCFG-INTERFACE-MIB.mib
--
