--========================================================
-- ZXR10-TRILL-COMMON-MIB.mib
--
-- Copyright(c) 2013 by ZTE Corporaton
--
-- All rights reservered
--========================================================

ZXR10-TRILL-COMMON-MIB DEFINITIONS ::= BEGIN

IMPORTS
    MODULE-IDENTITY, OBJECT-TYPE,
--    enterprises, Unsigned32, Counter64, IpAddress
    enterprises, Unsigned32
        FROM SNMPv2-SMI
    DisplayString,MacAddress
        FROM SNMPv2-TC;


zxr10TrillCommonMIB MODULE-IDENTITY
    LAST-UPDATED "201406101424Z"
    ORGANIZATION "ZTE Corporation."
    CONTACT-INFO
        " Sun jinsong
        Tel    : 0086-0755-633865
        E-mail : sun.jinsong@zte.com.cn"
    DESCRIPTION
        "This document describes a management information
        base for the TRILL IS-IS Routing protocol." 
    REVISION "201406101424Z"
    DESCRIPTION
        "Destory trill common mode."
    REVISION "201306211000Z"
    DESCRIPTION
        "Initial version."
    ::= {zxr10RosngMIB 164}

    zte           OBJECT IDENTIFIER ::= { enterprises 3902 }
    zxr10         OBJECT IDENTIFIER ::= { zte 3}
    zxr10RosngMIB OBJECT IDENTIFIER ::= { zxr10 6000}

    zxr10TrillCommonGlobalObjects   OBJECT IDENTIFIER ::= { zxr10TrillCommonMIB 1}
    zxr10TrillCommonObjects         OBJECT IDENTIFIER ::= { zxr10TrillCommonMIB 2}
    zxr10TrillCommonGlobalTraps     OBJECT IDENTIFIER ::= { zxr10TrillCommonMIB 3}
    zxr10TrillCommonConformance     OBJECT IDENTIFIER ::= { zxr10TrillCommonMIB 4}

--======================================================
-- 1. zxr10TrillCommonGlobalObjects
--======================================================

--======================================================
-- 2. zxr10TrillCommonObjects
--======================================================
--======================================================
-- 2.1 zxr10TrillIsisInstTable
--======================================================
--TRILL-COMMON begin
zxr10TrillCommonPortTable OBJECT-TYPE
        SYNTAX  SEQUENCE OF Zxr10TrillCommonPortEntry
        MAX-ACCESS  not-accessible
        STATUS  obsolete
        DESCRIPTION
            "A table to TRILL-COMMON-PORT."
        ::= { zxr10TrillCommonObjects 1 }
        
zxr10TrillCommonPortEntry OBJECT-TYPE
        SYNTAX Zxr10TrillCommonPortEntry
        MAX-ACCESS  not-accessible
        STATUS  obsolete
        DESCRIPTION
            "An entry to TRILL-COMMON-PORT."
        INDEX  { zxr10TrillCommonIntfName }
        ::= { zxr10TrillCommonPortTable 1 }  
        
Zxr10TrillCommonPortEntry ::=
        SEQUENCE {
            zxr10TrillCommonIntfName
                DisplayString,
            zxr10TrillCommonIntfMode
                INTEGER
            } 
     
zxr10TrillCommonIntfName OBJECT-TYPE
        SYNTAX DisplayString (SIZE (0..255))
        MAX-ACCESS  not-accessible
        STATUS  obsolete
        DESCRIPTION
            "TRILL-COMMON interface name."
        ::= { zxr10TrillCommonPortEntry 1 }

zxr10TrillCommonIntfMode OBJECT-TYPE
        SYNTAX INTEGER
               {
                  access(1),
                  trunk(2),
                  hybrid(3),
                  disable(4)
               }
        MAX-ACCESS  read-only
        STATUS  obsolete
        DESCRIPTION
            "TRILL-COMMON interface mode."
        ::= { zxr10TrillCommonPortEntry 2 }

--TRILL-COMMON end         
--======================================================
-- 3. zxr10TrillIsisGlobalTraps
--======================================================

--======================================================
-- 4. zxr10TrillIsisConformance
--======================================================  

END
