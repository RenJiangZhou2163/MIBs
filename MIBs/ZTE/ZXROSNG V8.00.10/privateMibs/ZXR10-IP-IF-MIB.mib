--  ************************************************
--  $Id: ZXR10-IP-IF.mib 13 2005-07-13 01:01:26Z taowq $
--
--  zxr10-IP-IF.mib: ZXR10 IP Interface Configuration MIB file
--  
--  Jun. 2005, Tao wenqiang
--   
--  Copyright(c) 2005 by ZTE Corporaton
--  All rights reservered
--
--  ************************************************

ZXR10-IP-IF-MIB DEFINITIONS ::= BEGIN

IMPORTS
    MODULE-IDENTITY, 
    OBJECT-TYPE, 
    Integer32 
        FROM SNMPv2-SMI

    DisplayString,
    TEXTUAL-CONVENTION,
    RowStatus                           
        FROM SNMPv2-TC

    IpAddress
        FROM SNMPv2-SMI
        
    zxr10interfaces
        FROM ZXR10-SMI

    ifIndex            
         FROM RFC1213-MIB;
         
         
         
    zxr10IPIfMIB MODULE-IDENTITY
    LAST-UPDATED "201308270000Z"  
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS v4.6.02 Interfaces config MIB"
    
    REVISION "201308270000Z"  
    DESCRIPTION
             "Change the SYNTAX INTEGER into Interfer32 of the leaf zxr10IfIPAddrConfigIfIndex"

    REVISION "201305030000Z"  
    DESCRIPTION
             "Import SNMP data type:DisplayString,TEXTUAL-CONVENTION;
              Change RFC1155-SMI into SNMPv2-SMI;
              Delete data type definition:DisplayString;
              Correct the definition of Type IpAddrAttr;
              Change SEQUENCE identifier to startwith upper case;
              Change SYNTAX INTEGER into Integer32"

    REVISION "201304070900Z"  
    DESCRIPTION
             "Add description for zxr10IfIPAddrConfigTable"

    REVISION "201303210000Z"  
    DESCRIPTION
       "Be consistent with the needs"
    REVISION "200504120000Z"  -- April 12, 2005
    DESCRIPTION
       ""

    ::= { zxr10interfaces 1 }

    zxr10IPIfMIBObjects       OBJECT IDENTIFIER ::= { zxr10IPIfMIB 1 }   
    
    zxr10IPAddressConfiguration OBJECT IDENTIFIER
        ::=  { zxr10IPIfMIBObjects 1 }

    IpAddrAttr ::=  TEXTUAL-CONVENTION
        STATUS       current
        DESCRIPTION
            "IP address type, the value of 1 indicates that the primary address, 
             the value of 2 indicates that the secondary address"
        SYNTAX       INTEGER{primary(1),secondary(2)}


--- Primary Ip address table

    zxr10IPAddrTable  OBJECT-TYPE
        SYNTAX  SEQUENCE OF Zxr10IPAddrEntry
        MAX-ACCESS  not-accessible
        STATUS  current
        DESCRIPTION
            "Ip address config table."
        ::= { zxr10IPAddressConfiguration 1 }

    zxr10IPAddrEntry  OBJECT-TYPE
        SYNTAX  Zxr10IPAddrEntry
        MAX-ACCESS  not-accessible
        STATUS  current
        DESCRIPTION
            ""
        INDEX  { ifIndex }
        ::= { zxr10IPAddrTable 1 }

    Zxr10IPAddrEntry ::=
        SEQUENCE {
            zxr10IPAddrPrimaryIp
                IpAddress,
            zxr10IPAddrPrimaryIpMask
                IpAddress,
            zxr10IPAddrBroadcast
                IpAddress,
            zxr10IPAddrRowStatus
                RowStatus,
            zxr10IPAddrIfName
                DisplayString
    }

    zxr10IPAddrPrimaryIp  OBJECT-TYPE
        SYNTAX  IpAddress 
        MAX-ACCESS  read-only 
        STATUS  current
        DESCRIPTION
            "The main Ip address on this interface "
        ::= { zxr10IPAddrEntry 1 }

    zxr10IPAddrPrimaryIpMask  OBJECT-TYPE
        SYNTAX   IpAddress
        MAX-ACCESS  read-only
        STATUS  current
        DESCRIPTION
            "The mask of primary Ip address on this interface"
        ::= { zxr10IPAddrEntry 2 }
     
    zxr10IPAddrBroadcast    OBJECT-TYPE
        SYNTAX   IpAddress
        MAX-ACCESS  read-only
        STATUS  current
        DESCRIPTION
            "The Broadcast address on this interface"
        ::= { zxr10IPAddrEntry 3}

       
    zxr10IPAddrRowStatus  OBJECT-TYPE
        SYNTAX   RowStatus
        MAX-ACCESS  read-only
        STATUS  current
        DESCRIPTION
        "This object is used to manage creation and deletion of rows
         in this table.

         zxr10IpAddrRowStatus must be set to 'creatAndGo' to create 
         an entry and set to 'destroy' to delete an entry.

         The value in any column may be modified any time even the
         value of this entry rowStatus object is 'active'.

         Caution has to be taken before destroying any entry. 
         Example: Need to change the IP address of an interface,
         which provides sole network connectivity.
         This has to be done by destroying the entry and creating
         a new one. The device would loose network connectivity
         after the entry is destroyed. In this case, the destroy 
         of the old entry and the creation on the new entry
         should be packed in the same PDU."        
         ::= { zxr10IPAddrEntry 4 }        

    zxr10IPAddrIfName    OBJECT-TYPE
        SYNTAX   DisplayString(SIZE(0..32))
        MAX-ACCESS  read-only
        STATUS  current
        DESCRIPTION
            "Interface name"
        ::= { zxr10IPAddrEntry 5}

-- secondary Ip address configration table

    zxr10IPSecondaryAddrTable  OBJECT-TYPE
        SYNTAX  SEQUENCE OF Zxr10IPSecondaryAddrEntry
        MAX-ACCESS  not-accessible
        STATUS  current
        DESCRIPTION
            "Secondary Ip address config table."
        ::= { zxr10IPAddressConfiguration 2 }
        
    zxr10IPSecondaryAddrEntry  OBJECT-TYPE
        SYNTAX  Zxr10IPSecondaryAddrEntry
        MAX-ACCESS  not-accessible
        STATUS  current
        DESCRIPTION
            ""
        INDEX  { ifIndex,zxr10IPSecondaryAddr }
        ::= { zxr10IPSecondaryAddrTable 1 }

    Zxr10IPSecondaryAddrEntry ::=
        SEQUENCE {
            zxr10IPSecondaryAddr
                IpAddress,
            zxr10IPSecondaryAddrMask
                IpAddress,
            zxr10IPSecondaryAddrRowStatus
                RowStatus,
            zxr10IPSecondaryIfName
                DisplayString                
    }

    zxr10IPSecondaryAddr OBJECT-TYPE
        SYNTAX   IpAddress
        MAX-ACCESS  read-only
        STATUS  current
        DESCRIPTION
            "  Secondary Ip address on this interface"
        ::= { zxr10IPSecondaryAddrEntry 1 }          

    zxr10IPSecondaryAddrMask OBJECT-TYPE
        SYNTAX   IpAddress
        MAX-ACCESS  read-only
        STATUS  current
        DESCRIPTION
            "  Secondary Ip mask on this interface   "
        ::= { zxr10IPSecondaryAddrEntry 2 }          

    zxr10IPSecondaryAddrRowStatus OBJECT-TYPE
        SYNTAX   RowStatus
        MAX-ACCESS  read-only
        STATUS  current
        DESCRIPTION
        "This object is used to manage creation and deletion of rows
         in this table.

         zxr10SecondaryIpAddrRowStatus must be set to 'creatAndGo' to create 
         an entry and set to 'destroy' to delete an entry.

         The value in any column may be modified any time even the
         value of this entry rowStatus object is 'active'.

         Caution has to be taken before destroying any entry. 
         Example: Need to change the IP address of an interface,
         which provides sole network connectivity.
         This has to be done by destroying the entry and creating
         a new one. The device would loose network connectivity
         after the entry is destroyed. In this case, the destroy 
         of the old entry and the creation on the new entry
         should be packed in the same PDU."
        ::= { zxr10IPSecondaryAddrEntry 3 }           

    zxr10IPSecondaryIfName OBJECT-TYPE
        SYNTAX   DisplayString(SIZE(0..32))
        MAX-ACCESS  read-only
        STATUS  current
        DESCRIPTION
            "  Interface name   "
        ::= { zxr10IPSecondaryAddrEntry 4 }     

    -- 1.3.6.1.4.1.3902.3.103.1.1.1.3
zxr10IfIPAddrConfigTable OBJECT-TYPE
    SYNTAX SEQUENCE OF Zxr10IfIPAddrConfigEntry
    MAX-ACCESS not-accessible
    STATUS current
    DESCRIPTION  " IP address config table ,just for vbui interfaces"
    ::= { zxr10IPAddressConfiguration 3 }
    
-- 1.3.6.1.4.1.3902.3.103.1.1.1.3.1
zxr10IfIPAddrConfigEntry OBJECT-TYPE
    SYNTAX Zxr10IfIPAddrConfigEntry
    MAX-ACCESS not-accessible
    STATUS current
    DESCRIPTION "An entry for IP address config table,
                         which is just used for vbui interfaces"
    INDEX { zxr10IfIPAddrConfigIfName, zxr10IfIPAddrConfigIpAddrAttr, zxr10IfIPAddrConfigIpAddr, zxr10IfIPAddrConfigIpMask }
    ::= { zxr10IfIPAddrConfigTable 1 }
    
Zxr10IfIPAddrConfigEntry ::=
        SEQUENCE {
            zxr10IfIPAddrConfigIfName
                DisplayString,
            zxr10IfIPAddrConfigIfIndex
                Integer32,
            zxr10IfIPAddrConfigIpAddrAttr
                IpAddrAttr,
            zxr10IfIPAddrConfigIpAddr
                IpAddress,
        zxr10IfIPAddrConfigIpMask
                IpAddress,
        zxr10IfIPAddrConfigRowStatus
                RowStatus
    }
-- 1.3.6.1.4.1.3902.3.103.1.1.1.3.1.1
zxr10IfIPAddrConfigIfName OBJECT-TYPE
    SYNTAX DisplayString (SIZE (0..32))
    MAX-ACCESS not-accessible
    STATUS current
    DESCRIPTION "The vbui interface name ,which has IP address(es)"
    ::= { zxr10IfIPAddrConfigEntry 1 }
-- 1.3.6.1.4.1.3902.3.103.1.1.1.3.1.2
zxr10IfIPAddrConfigIfIndex OBJECT-TYPE
    SYNTAX Integer32
    MAX-ACCESS read-only
    STATUS current
    DESCRIPTION "The vbui interface index,which has IP address(es)"
    ::= { zxr10IfIPAddrConfigEntry 2 }
-- 1.3.6.1.4.1.3902.3.103.1.1.1.3.1.3
zxr10IfIPAddrConfigIpAddrAttr OBJECT-TYPE
    SYNTAX IpAddrAttr
    MAX-ACCESS not-accessible
    STATUS current
    DESCRIPTION "The flag used to indicate Primary or Secondary IP address(es)"
    ::= { zxr10IfIPAddrConfigEntry 3 }
-- 1.3.6.1.4.1.3902.3.103.1.1.1.3.1.4
zxr10IfIPAddrConfigIpAddr OBJECT-TYPE
    SYNTAX IpAddress
    MAX-ACCESS not-accessible
    STATUS current
    DESCRIPTION "The IP address of a vbui interface"
    ::= { zxr10IfIPAddrConfigEntry 4 }
-- 1.3.6.1.4.1.3902.3.103.1.1.1.3.1.5
zxr10IfIPAddrConfigIpMask OBJECT-TYPE
    SYNTAX IpAddress
    MAX-ACCESS not-accessible
    STATUS current
    DESCRIPTION "The IP address mask of a vbui interface"
    ::= { zxr10IfIPAddrConfigEntry 5 }
-- 1.3.6.1.4.1.3902.3.103.1.1.1.3.1.6
zxr10IfIPAddrConfigRowStatus OBJECT-TYPE
    SYNTAX RowStatus
    MAX-ACCESS read-create
    STATUS current
    DESCRIPTION  "This object is used to manage creation and deletion of rows
                  in this table"
    ::= { zxr10IfIPAddrConfigEntry 6 }


    END
