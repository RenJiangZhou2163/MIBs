--  ***************************************************
--  $Id: ZXR10-EFM-MIB.mib 3 2013-06-14 01:34:21Z jyt $
--
--  ZXR10-EFM-MIB.mib: ZXR10 Ethernet OAM MIB file
--  
--  June. 2013, Jiang yuting
--   
--  Copyright(c) 2013 by ZTE Corporaton
--  All rights reservered
--
--  ***************************************************

ZXR10-EFM-MIB DEFINITIONS ::= BEGIN

IMPORTS
    MODULE-IDENTITY, OBJECT-TYPE,
    Unsigned32, enterprises          FROM SNMPv2-SMI -- [RFC2578]
    ifIndex                          FROM RFC1213-MIB
--  RowStatus                        FROM SNMPv2-TC
--  mgmt, NetworkAddress, IpAddress, Counter, Gauge
--                                   FROM RFC1155-SMI
--  Counter, TimeTicks               FROM RFC1155-SMI
--  IpAddress,DisplayString, mib-2   FROM RFC1213-MIB
    DisplayString                    FROM RFC1213-MIB
    TEXTUAL-CONVENTION, TruthValue   FROM SNMPv2-TC -- [RFC2579]
    TRAP-TYPE                        FROM RFC-1215
    zxr10                            FROM ZXR10-SMI;


    zxr10ethernetOam MODULE-IDENTITY
        LAST-UPDATED "201611151000Z" --2016-11-15 10:00
        ORGANIZATION "ZTE Corporation"
        CONTACT-INFO  
            "       Jiang yuting
            Tel:    +86-25-52870000
            E-Mail: jiang.yuting@zte.com.cn
            " 
        DESCRIPTION
            "The MIB module to describe the 802.3ah Ethernet OAM protocol. "
                    
        REVISION "201611151000Z" --2016-11-15 10:00 
        DESCRIPTION 
            "Add:   zxr10EFMSymPerSetIfDownEnable
                    zxr10EFMFrameSetIfDownEnable
                    zxr10EFMFramePerSetIfDownEnable
                    zxr10EFMFrameSecSetIfDownEnable
                    zxr10EFMSetIfUp"
            
        REVISION "201401211000Z" --2014-01-21 10:00 
        DESCRIPTION 
            "Modify DESCRIPTION of zxr10ethernetOamiftimeout"

        REVISION "201311111000Z" --2013-11-11 10:00 
        DESCRIPTION 
            "Add UNITS for zxr10ethernetOamifLinkMonitorSymbolPeriodwindow
                           zxr10ethernetOamifLinkMonitorFramePeriodwindow"

        REVISION "201308201000Z" --2013-08-20 10:00 
        DESCRIPTION 
            "Add: zxr10ethernetOamifVariRetrieval in 
                       zxr10ethernetOamIfConfigEntry,
                  zxr10ethernetOamIfVariableTable"

        REVISION "201306171000Z" --2013-06-17 10:00 
        DESCRIPTION 
            "Add UNITS for zxr10ethernetOamifLinkMonitorSymbolPeriodthreshold
                           zxr10ethernetOamifLinkMonitorFramethreshold
                           zxr10ethernetOamifLinkMonitorFramewindow
                           zxr10ethernetOamifLinkMonitorFramePeriodthreshold
                           zxr10ethernetOamifLinkMonitorFrameSecondsthreshold
                           zxr10ethernetOamifLinkMonitorFrameSecondswindow"

        REVISION "201303261000Z" --2013-03-26 10:00 
        DESCRIPTION 
            "Modify DESCRIPTION of zxr10ethernetOamiffastflag,
             zxr10ethernetOamifTimeoutFast, and zxr10ethernetOamiftimeout."

        REVISION "201303171000Z" --2013-03-17 10:00 
        DESCRIPTION 
            "Add:   zxr10ethernetOamifRmtLoopbackMode
                    zxr10ethernetOamifRmtLoopbackGuard"

        ::= { zxr10 902}

    EFM_StateValue ::= TEXTUAL-CONVENTION
        STATUS current
        DESCRIPTION
            "Ethernet OAM state switch. "
        SYNTAX INTEGER {
            enable(1),
            disable(2)
        }


    --***************************************
    -- zxr10ethernetOamGlobalObjects
    --***************************************      
    zxr10ethernetOamGlobalObjects OBJECT IDENTIFIER
        ::= { zxr10ethernetOam 1 }

    zxr10ethernetOamGlobalCfgObjects OBJECT IDENTIFIER
        ::= { zxr10ethernetOamGlobalObjects 1 }


    zxr10ethernetOamGlobalEnable OBJECT-TYPE
        SYNTAX            INTEGER(0..1)
        MAX-ACCESS        read-write
        STATUS            current
        DESCRIPTION
            "Configure Ethernet OAM enable(0-disable, 1-enable)."
        ::=  {  zxr10ethernetOamGlobalCfgObjects  1  }

       zxr10ethernetOamOuiInformation    OBJECT-TYPE
        SYNTAX            DisplayString  
        MAX-ACCESS        read-write
        STATUS            current
        DESCRIPTION
            "Configure Ethernet OAM OUI information."
        DEFVAL            {"ZTE"}
        ::=  {  zxr10ethernetOamGlobalCfgObjects  2  }

    zxr10ethernetOamRemoteLoopbackTimeout    OBJECT-TYPE
        SYNTAX            Unsigned32(1..10)
        UNITS             "seconds"
        MAX-ACCESS        read-write
        STATUS            current
        DESCRIPTION
            "Configure Ethernet OAM remote loopback time-out."
        DEFVAL            {3}
        ::=  {  zxr10ethernetOamGlobalCfgObjects  3  }


    --***************************************
    -- zxr10ethernetOamIfConfigTable
    --***************************************
    zxr10ethernetOamIfConfigTable    OBJECT-TYPE
        SYNTAX        SEQUENCE  OF  Zxr10ethernetOamIfConfigEntry
        MAX-ACCESS    not-accessible
        STATUS        current
        DESCRIPTION
            "Configure Ethernet OAM interface parameters."
        ::=  { zxr10ethernetOam 2 }

    zxr10ethernetOamIfConfigEntry    OBJECT-TYPE
        SYNTAX        Zxr10ethernetOamIfConfigEntry
        MAX-ACCESS    not-accessible
        STATUS        current
        DESCRIPTION    
            "Configure Ethernet OAM interface config parameters."
        INDEX        {  ifIndex  }
        ::=  { zxr10ethernetOamIfConfigTable 1 }

    Zxr10ethernetOamIfConfigEntry  ::=  SEQUENCE {
            zxr10ethernetOamifName
                DisplayString,
            zxr10ethernetOamIfEnable
                INTEGER,
            zxr10ethernetOamRemoteLoopbackEnable
                INTEGER,
            zxr10ethernetOamifmode
                Unsigned32,
            zxr10ethernetOamiftimeout
                Unsigned32,
            zxr10ethernetOamifLinkMonitorEnable
                INTEGER,
            zxr10ethernetOamifLinkMonitorSymbolPeriodthreshold
                Unsigned32,
            zxr10ethernetOamifLinkMonitorSymbolPeriodwindow
                Unsigned32,
            zxr10ethernetOamifLinkMonitorFramethreshold
                Unsigned32,
            zxr10ethernetOamifLinkMonitorFramewindow
                Unsigned32,
            zxr10ethernetOamifLinkMonitorFramePeriodthreshold
                Unsigned32,
            zxr10ethernetOamifLinkMonitorFramePeriodwindow
                Unsigned32,
            zxr10ethernetOamifLinkMonitorFrameSecondsthreshold
                Unsigned32,
            zxr10ethernetOamifLinkMonitorFrameSecondswindow  
                Unsigned32,
            zxr10ethernetOamifperiod
                Unsigned32,
            zxr10ethernetOamiffastflag
                INTEGER,
            zxr10ethernetOamifTimeoutFast
                Unsigned32,
            zxr10ethernetOamifUnidirection
                INTEGER,
            zxr10ethernetOamifRmtLbMode
                EFM_StateValue,
            zxr10ethernetOamifRmtLbGuard
                TruthValue,
            zxr10ethernetOamifVariRetrieval
                EFM_StateValue,
            zxr10EFMSymPerSetIfDownEnable
                INTEGER,
            zxr10EFMFrameSetIfDownEnable
                INTEGER,
            zxr10EFMFramePerSetIfDownEnable
                INTEGER,
            zxr10EFMFrameSecSetIfDownEnable
                INTEGER,
            zxr10EFMSetIfUp
                INTEGER
       }

    zxr10ethernetOamifName    OBJECT-TYPE
        SYNTAX            DisplayString
        MAX-ACCESS        read-only
        STATUS            current
        DESCRIPTION
            "Show interface name."
        ::=  {  zxr10ethernetOamIfConfigEntry  1  }

    zxr10ethernetOamIfEnable    OBJECT-TYPE
        SYNTAX            INTEGER(0..1)
        MAX-ACCESS        read-write
        STATUS            current
        DESCRIPTION
            "Configure interface Ethernet OAM enable(0-disable, 1-enable)."
        ::=  {  zxr10ethernetOamIfConfigEntry  2  }

    zxr10ethernetOamRemoteLoopbackEnable    OBJECT-TYPE
        SYNTAX            INTEGER(0..1)
        MAX-ACCESS        read-write
        STATUS            current
        DESCRIPTION
            "Configure Ethernet OAM remote loopback start/stop(0-stop,
            1-start). 
            As an interactive operation, zxr10ethernetOamRemoteLoopbackEnable
            will always be zero(0) because it can not reflect the value be set."
        ::=  {  zxr10ethernetOamIfConfigEntry  3  }

    zxr10ethernetOamifmode    OBJECT-TYPE
        SYNTAX            Unsigned32(0..1)
        MAX-ACCESS        read-write
        STATUS            current
        DESCRIPTION        
            "Configure Ethernet OAM mode(0-passive mode, 1-active mode)."
        ::=  {  zxr10ethernetOamIfConfigEntry  4  }

    zxr10ethernetOamiftimeout    OBJECT-TYPE
        SYNTAX            Unsigned32(3..20)
        UNITS             "seconds"
        MAX-ACCESS        read-write
        STATUS            current
        DESCRIPTION
            "Configure Ethernet OAM link timeout value, in seconds, to indicate
            that during this time, if no OAMPDUs can be received, the link will
            be lost. 
            It is available when zxr10ethernetOamiffastflag is 0."
        DEFVAL            {5}
        ::=  {  zxr10ethernetOamIfConfigEntry  5  }

    zxr10ethernetOamifLinkMonitorEnable    OBJECT-TYPE
        SYNTAX            INTEGER(0..1)
        MAX-ACCESS        read-write
        STATUS            current
        DESCRIPTION
            "Configure Ethernet OAM link monitor enable(0-disable, 1-enable)."
        ::=  {  zxr10ethernetOamIfConfigEntry  6  }

    zxr10ethernetOamifLinkMonitorSymbolPeriodthreshold    OBJECT-TYPE
        SYNTAX            Unsigned32
        UNITS             "symbols"
        MAX-ACCESS        read-write
        STATUS            current
        DESCRIPTION
            "Configure Ethernet OAM link monitor Symbol Period threshold.
            Each project has different range and default value of 
            zxr10ethernetOamifLinkMonitorSymbolPeriodthreshold."
        ::=  {  zxr10ethernetOamIfConfigEntry  7  }

    zxr10ethernetOamifLinkMonitorSymbolPeriodwindow    OBJECT-TYPE
        SYNTAX            Unsigned32
        UNITS             "million symbols"
        MAX-ACCESS        read-write
        STATUS            current
        DESCRIPTION
            "Configure Ethernet OAM link monitor Symbol Period window.
            Each project has different range, units and default value of 
            zxr10ethernetOamifLinkMonitorSymbolPeriodwindow."
        ::=  {  zxr10ethernetOamIfConfigEntry  8  }

    zxr10ethernetOamifLinkMonitorFramethreshold    OBJECT-TYPE
        SYNTAX            Unsigned32  
        UNITS             "frames"
        MAX-ACCESS        read-write
        STATUS            current
        DESCRIPTION
            "Configure Ethernet OAM link monitor Frame threshold.
            Each project has different range and default value of 
            zxr10ethernetOamifLinkMonitorFramethreshold."
        ::=  {  zxr10ethernetOamIfConfigEntry  9  }

    zxr10ethernetOamifLinkMonitorFramewindow    OBJECT-TYPE
        SYNTAX            Unsigned32
        UNITS             "seconds"
        MAX-ACCESS        read-write
        STATUS            current
        DESCRIPTION
            "Configure Ethernet OAM link monitor Frame window.
            Each project has different range and default value of 
            zxr10ethernetOamifLinkMonitorFramewindow."
        ::=  {  zxr10ethernetOamIfConfigEntry  10  }

    zxr10ethernetOamifLinkMonitorFramePeriodthreshold    OBJECT-TYPE
        SYNTAX            Unsigned32
        UNITS             "frames"
        MAX-ACCESS        read-write
        STATUS            current
        DESCRIPTION
            "Configure Ethernet OAM link monitor Frame Period threshold.
            Each project has different range and default value of 
            zxr10ethernetOamifLinkMonitorFramePeriodthreshold."
        ::=  {  zxr10ethernetOamIfConfigEntry  11  }

    zxr10ethernetOamifLinkMonitorFramePeriodwindow    OBJECT-TYPE
        SYNTAX            Unsigned32
        UNITS             "ten thousand frames"
        MAX-ACCESS        read-write
        STATUS            current
        DESCRIPTION        
            "Configure Ethernet OAM link monitor Frame Period window.
            Each project has different range, units and default value of 
            zxr10ethernetOamifLinkMonitorFramePeriodwindow."
        ::=  {  zxr10ethernetOamIfConfigEntry  12  }

    zxr10ethernetOamifLinkMonitorFrameSecondsthreshold    OBJECT-TYPE
        SYNTAX            Unsigned32
        UNITS             "seconds"
        MAX-ACCESS        read-write
        STATUS            current
        DESCRIPTION
            "Configure Ethernet OAM link monitor Frame Seconds threshold.
            Each project has different range and default value of 
            zxr10ethernetOamifLinkMonitorFrameSecondsthreshold."
        ::=  {  zxr10ethernetOamIfConfigEntry  13  }

    zxr10ethernetOamifLinkMonitorFrameSecondswindow    OBJECT-TYPE
        SYNTAX            Unsigned32
        UNITS             "seconds"
        MAX-ACCESS        read-write
        STATUS            current
        DESCRIPTION        
            "Configure Ethernet OAM link monitor Frame Seconds window.
            Each project has different range and default value of 
            zxr10ethernetOamifLinkMonitorFrameSecondswindow."
        ::=  {  zxr10ethernetOamIfConfigEntry  14  }

    zxr10ethernetOamifperiod    OBJECT-TYPE
        SYNTAX            Unsigned32(1..10)
        UNITS             "100 milliseconds"
        MAX-ACCESS        read-write
        STATUS            current
        DESCRIPTION        
            "Configure Ethernet OAM PDU period."
        DEFVAL            {10}
        ::=  {  zxr10ethernetOamIfConfigEntry  15  }

    zxr10ethernetOamiffastflag    OBJECT-TYPE
        SYNTAX            INTEGER(0..1)
        MAX-ACCESS        read-only
        STATUS            current
        DESCRIPTION        
            "Ethernet OAM timeout setting mode. 
            The link operates on slow mode and at this mode, hello OAMPDUs
            transmit in 1 pps rate when zxr10ethernetOamiffastflag is 0.
            The link operates on fast mode and at this mode, hello OAMPDUs
            transmit one packet per zxr10ethernetOamifperiod*100 milliseconds
            when zxr10ethernetOamiffastflag is 1.
            If zxr10ethernetOamiffastflag is 1, zxr10ethernetOamifTimeoutFast
            is available other than zxr10ethernetOamiftimeout."
        ::=  {  zxr10ethernetOamIfConfigEntry  16  }

    zxr10ethernetOamifTimeoutFast     OBJECT-TYPE
        SYNTAX            Unsigned32(3..200)
        UNITS             "100 milliseconds"
        MAX-ACCESS        read-write
        STATUS            current
        DESCRIPTION        
            "Configure Ethernet OAM link timeout value, in milliseconds, to
            indicate that juring this time, if no OAMPDUs can be received,
            the link will be lost.
            It is available when zxr10ethernetOamiffastflag is 1."
        DEFVAL            {50}
        ::=  {  zxr10ethernetOamIfConfigEntry  17  }

    zxr10ethernetOamifUnidirection    OBJECT-TYPE    --obsolete
        SYNTAX            INTEGER(0..1)
        MAX-ACCESS        read-write
        STATUS            obsolete
        DESCRIPTION
            "Configure Ethernet OAM unidirection function enable."
        ::=  {  zxr10ethernetOamIfConfigEntry  18  }

    zxr10ethernetOamifRmtLbMode    OBJECT-TYPE
        SYNTAX            EFM_StateValue
        MAX-ACCESS        read-write
        STATUS            current
        DESCRIPTION
            "Configure Ethernet OAM capability of responding to remote loopback
            request."
        DEFVAL          {enable}
        ::=  {  zxr10ethernetOamIfConfigEntry  19  }

    zxr10ethernetOamifRmtLbGuard    OBJECT-TYPE
        SYNTAX            TruthValue
        MAX-ACCESS        read-write
        STATUS            current
        DESCRIPTION
            "Configure Ethernet OAM guard mode of disabling remote loopback mode
            from attack. True means recovering local slave state from LB to FWD
            forcefully."
        DEFVAL          {false}
        ::=  {  zxr10ethernetOamIfConfigEntry  20  }

    zxr10ethernetOamifVariRetrieval    OBJECT-TYPE
        SYNTAX            EFM_StateValue
        MAX-ACCESS        read-write
        STATUS            current
        DESCRIPTION
            "Configure Ethernet OAM capability of responding to variable
            request."
        DEFVAL          {enable}
        ::=  {  zxr10ethernetOamIfConfigEntry  21  }

    zxr10EFMSymPerSetIfDownEnable    OBJECT-TYPE
        SYNTAX            INTEGER(0..1)
        MAX-ACCESS        read-write
        STATUS            current
        DESCRIPTION
            "Configure the function enable(0-disable, 1-enable) that the
            event of link monitor Symbol Period notify the interface down."
        ::=  {  zxr10ethernetOamIfConfigEntry  22  }

    zxr10EFMFrameSetIfDownEnable    OBJECT-TYPE
        SYNTAX            INTEGER(0..1)
        MAX-ACCESS        read-write
        STATUS            current
        DESCRIPTION
            "Configure the function enable(0-disable, 1-enable) that the
            event of link monitor frame notify the interface down."
        ::=  {  zxr10ethernetOamIfConfigEntry  23  }

    zxr10EFMFramePerSetIfDownEnable    OBJECT-TYPE
        SYNTAX            INTEGER(0..1)
        MAX-ACCESS        read-write
        STATUS            current
        DESCRIPTION
            "Configure the function enable(0-disable, 1-enable) that the
            event of link monitor frame period notify the interface down."
        ::=  {  zxr10ethernetOamIfConfigEntry  24  }

    zxr10EFMFrameSecSetIfDownEnable    OBJECT-TYPE
        SYNTAX            INTEGER(0..1)
        MAX-ACCESS        read-write
        STATUS            current
        DESCRIPTION
            "Configure the function enable(0-disable, 1-enable) that the
            event of link monitor frame seconds notify the interface down."
        ::=  {  zxr10ethernetOamIfConfigEntry  25  }

    zxr10EFMSetIfUp    OBJECT-TYPE
        SYNTAX        INTEGER
                      {
                         up(1)                      
                      }
        MAX-ACCESS        read-write
        STATUS            current
        DESCRIPTION
            "Set the interface status to up because the 
            event of LM notify the interface to down.
            As an operation, zxr10EFMSetIfUp
            will always be got one(1) and be set one(1)."
        ::=  {  zxr10ethernetOamIfConfigEntry  26  }
        
    --***************************************
    -- zxr10ethernetOamShowTable
    --***************************************
    zxr10ethernetOamShowTable    OBJECT-TYPE
        SYNTAX        SEQUENCE  OF  Zxr10ethernetOamShowEntry
        MAX-ACCESS    not-accessible
        STATUS        current
        DESCRIPTION
            "Show Ethernet OAM config parameters and state."
        ::=  { zxr10ethernetOam 3 }

    zxr10ethernetOamShowEntry    OBJECT-TYPE
        SYNTAX        Zxr10ethernetOamShowEntry
        MAX-ACCESS    not-accessible
        STATUS        current
        DESCRIPTION
            "Show Ethernet OAM interface config parameters and state."
        INDEX        {  ifIndex  }
        ::=  { zxr10ethernetOamShowTable 1 }

    Zxr10ethernetOamShowEntry  ::=  SEQUENCE {
            zxr10ethernetOamShowDiscovery
                DisplayString,
            zxr10ethernetOamShowLinkMonitor
                DisplayString,
            zxr10ethernetOamShowStatistics  
                DisplayString
     }

    zxr10ethernetOamShowDiscovery    OBJECT-TYPE
        SYNTAX            DisplayString
        MAX-ACCESS        read-only
        STATUS            current
        DESCRIPTION
            "Show Ethernet OAM discovery parameters."
        ::=  {  zxr10ethernetOamShowEntry  1  }

       zxr10ethernetOamShowLinkMonitor    OBJECT-TYPE
        SYNTAX            DisplayString
        MAX-ACCESS        read-only
        STATUS            current
        DESCRIPTION
            "Show Ethernet OAM link monitor parameters."
        ::=  {  zxr10ethernetOamShowEntry  2  }

    zxr10ethernetOamShowStatistics    OBJECT-TYPE
        SYNTAX            DisplayString
        MAX-ACCESS        read-only
        STATUS            current
        DESCRIPTION
            "Show Ethernet OAM PDU statistics."
        ::=  {  zxr10ethernetOamShowEntry  3  }

    --***************************************
    -- zxr10ethernetOamIfVariableTable
    --***************************************
    zxr10ethernetOamIfVariableTable    OBJECT-TYPE
        SYNTAX        SEQUENCE  OF  Zxr10ethernetOamIfVariableEntry
        MAX-ACCESS    not-accessible
        STATUS        current
        DESCRIPTION
            "Configure Ethernet OAM interface variable retrieval operation and parameters."
        ::=  { zxr10ethernetOam 4 }

    zxr10ethernetOamIfVariableEntry    OBJECT-TYPE
        SYNTAX        Zxr10ethernetOamIfVariableEntry
        MAX-ACCESS    not-accessible
        STATUS        current
        DESCRIPTION    
            "Configure Ethernet OAM interface variable retrieval operation and parameters."
        INDEX        {  ifIndex, zxr10ethernetOamifVariLeafID  }
        ::=  { zxr10ethernetOamIfVariableTable 1 }

    Zxr10ethernetOamIfVariableEntry  ::=  SEQUENCE {
            zxr10ethernetOamifVariLeafID
                INTEGER,
            zxr10ethernetOamifVariRequest
                INTEGER,
            zxr10ethernetOamifVariResponse
                DisplayString
       }     

    zxr10ethernetOamifVariLeafID OBJECT-TYPE
        SYNTAX INTEGER(1..65535)
        MAX-ACCESS not-accessible
        STATUS current
        DESCRIPTION
            "The value of variable leaf id.
            Supported variable leaf id as follows:
            value  description                       
            236    OAMID                             
            237    OAMAdminState                     
            238    OAMMode                           
            239    OAMRemoteMACaddress               
            240    OAMRemoteConfiguration            
            241    OAMRemotePDUConfiguration         
            242    OAMLocalFlagsField                
            243    OAMRemoteFlagsField               
            244    OAMRemoteRevision                 
            245    OAMRemoteState                    
            246    OAMRemoteVendorOUI                
            247    OAMRemoteVendorSpecificinfo       
            250    OAMUnsupportedCodesRX             
            251    OAMInformationTX                  
            252    OAMInformationRX                  
            254    OAMUniqueEventNotificationRX      
            255    OAMDuplicateEventNotificationRX   
            256    OAMLoopbackControlTX              
            257    OAMLoopbackControlRX              
            258    OAMVariableRequestTX              
            259    OAMVariableRequestRX              
            260    OAMVariableResponseTX             
            261    OAMVariableResponseRX             
            262    OAMOrganizationSpecificTX         
            263    OAMOrganizationSpecificRX         
            264    OAMLocalErrSymPeriodConfig        
            265    OAMLocalErrSymPeriodEvent         
            266    OAMLocalErrFrameConfig            
            267    OAMLocalErrFrameEvent             
            268    OAMLocalErrFramePeriodConfig      
            269    OAMLocalErrFramePeriodEvent       
            270    OAMLocalErrFrameSecsSummaryConfig 
            271    OAMLocalErrFrameSecsSummaryEvent  
            272    OAMRemoteErrSymPEriodEvent        
            273    OAMRemoteErrFrameEvent            
            274    OAMRemoteErrFramePeriodEvent      
            275    OAMRemoteErrFrameSecsSummaryEvent 
            333    OAMDiscoveryState                 
            334    OAMLocalConfiguration             
            335    OAMLocalPDUConfiguration          
            336    OAMLocalRevision                  
            337    OAMLocalState                     
            338    OAMUnsupportedCodesTX             
            339    OAMUniqueEventNotificationTX      
            340    OAMDuplicateEventNotificationTX   
            "
        ::= { zxr10ethernetOamIfVariableEntry 1 }

    zxr10ethernetOamifVariRequest    OBJECT-TYPE
        SYNTAX            INTEGER(0|1)
        MAX-ACCESS        read-write
        STATUS            current
        DESCRIPTION
            "Configure interface Ethernet OAM variable request operation.
            The operation can request MIB attributes, objects and packages,
            while only MIB attributes can be requested by the device.
            It can only be set 1 which means request operation, 
            when get 0 only for it's unmeaningful.
            "
        ::=  {  zxr10ethernetOamIfVariableEntry  2  }

    zxr10ethernetOamifVariResponse    OBJECT-TYPE
        SYNTAX            DisplayString
        MAX-ACCESS        read-only
        STATUS            current
        DESCRIPTION
            "Show interface Ethernet OAM variable response value, as value
            of set zxr10ethernetOamifVariRequest."
        ::=  {  zxr10ethernetOamIfVariableEntry  3  }

    END
