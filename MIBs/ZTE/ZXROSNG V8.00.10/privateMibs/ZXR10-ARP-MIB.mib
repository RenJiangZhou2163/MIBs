--  ************************************************
--  $Id: ZXR10-arp.mib 2008-12-16 $
--
--  ZXR10-arp.mib: ZXR10 arp configuration MIB file
--  
--  Mar. 2008, Sheng w
--   
--  Copyright(c) 2008 by ZTE Corporaton
--  All rights reservered
--
--  ************************************************
    ZXR10-ARP-MIB DEFINITIONS ::= BEGIN
    IMPORTS
          MODULE-IDENTITY,
          OBJECT-TYPE,
          enterprises,
          IpAddress
              FROM  SNMPv2-SMI -- [RFC2578]
          TEXTUAL-CONVENTION,
          PhysAddress,
          DisplayString          
              FROM  SNMPv2-TC -- [RFC2579]     
          zxr10 
              FROM ZXR10-SMI;


    zxr10ArpMIB MODULE-IDENTITY
        LAST-UPDATED "201410310000Z"
        ORGANIZATION "ZTE Corp."
        CONTACT-INFO
            "ZTE Corporation
            Nanjing Institute of ZTE Corporation
            No.68 Zijinghua Rd. Yuhuatai District, Nanjing, China
            Tel: +86-25-52870000"
        DESCRIPTION  "This MIB describes objects for ZXROSNG ARP 
                      configuration information."
        REVISION     "201507280000Z"
        DESCRIPTION  "Update the range of arpCommMacProtectNum and arpWholeProtectNum from 1-65535 to 1-262144."
        REVISION     "201410310000Z"
        DESCRIPTION  "Add VXLAN ARP item information."
        REVISION     "201405090000Z"
        DESCRIPTION  "Add ARP item number information."
        REVISION     "201402120000Z"
        DESCRIPTION  "Update the lower limit value of arpLimitSpeed from 0 to 1."
        REVISION     "201311080000Z"
        DESCRIPTION  "Add ARP item information."
        REVISION     "201309020000Z"       
        DESCRIPTION  
            "Revise descriptions those are not accord with custom of english. "
        REVISION     "201306090000Z"
        DESCRIPTION  
            "Recover the configuration information of 
            arpIpSourceGuardMode and arpIpSourceGuardVlan"
        REVISION     "201305290000Z"
        DESCRIPTION  
            "Update the MAX-ACCESS of zxr10ArpSpecificMacProtectNum
            from not-accessible to read-only "
        REVISION     "201305120000Z"
        DESCRIPTION  
            "Add zxr10ArpPeriodicalFreeFlag 
            and zxr10ArpProxyPeriodicalFreeFlag configuration information "
        REVISION     "201303210000Z"
        DESCRIPTION  
            "Add interface and global configuration information "
        REVISION     "200812160000Z"
        DESCRIPTION  
            ""            
        REVISION     "200807160000Z"
        DESCRIPTION
            "Initial version of this MIB module"
    ::= { zxr10 326 }

    ArpFuncType ::= TEXTUAL-CONVENTION
     STATUS   current
     DESCRIPTION
       "Function type.Enable this function or disable this function." 
     SYNTAX   INTEGER 
                  {
                     disable(0),
                     enable(1)
                  }   

    IpSourceGuardMode ::= TEXTUAL-CONVENTION
        STATUS        current
        DESCRIPTION   "Ip Source Guard Mode"
        SYNTAX        INTEGER
                      {  
                         none(0),    
                         macBase(1),
                         ipBase(2),
                         macIpBase(3)         
                      }  
                      
    ArpItemType ::= TEXTUAL-CONVENTION
        STATUS        current
        DESCRIPTION   "Arp item type"
        SYNTAX        INTEGER
                      {  
                         vrrp(1),    
                         host(2),
                         permanent(3),
                         static(4),
                         dhcp(5),
                         tostatic(6),
                         dynamic(7),
                         temp(8)                     
                      }                        
    
--  arp interface attribute table
    arpIfAttributeTable  OBJECT-TYPE
        SYNTAX  SEQUENCE OF ArpIfAttributeEntry
        MAX-ACCESS  not-accessible
        STATUS  current
        DESCRIPTION
           "Arp L3 Interface Configure."
        ::= { zxr10ArpMIB 1 }
   

--  arp interface attribute entry
    arpIfAttributeEntry  OBJECT-TYPE
        SYNTAX  ArpIfAttributeEntry
        MAX-ACCESS  not-accessible
        STATUS  current
        DESCRIPTION
           "Arp interface configure table."
        INDEX  { arpL3IfIndex }
        ::= { arpIfAttributeTable 1 } 
 
--  type ArpIfAttributeEntry define        
    ArpIfAttributeEntry ::= 
            SEQUENCE   {
                 arpL3IfIndex                        INTEGER,  
                 arpLearning                         ArpFuncType,
                 arpTimeOut                          INTEGER, 
                 arpProtectNum                       INTEGER,  
                 arpSourceFilter                     ArpFuncType,
                 arpProxy                            ArpFuncType,
                 arpPurgeDelay                       INTEGER,
                 arpLimitSpeed                       INTEGER,
                 arpLimitTime                        INTEGER,
                 arpPeriodicalFreeTime               INTEGER,
                 arpL3IfName                         DisplayString,  
                 arpIpSourceGuardMode                IpSourceGuardMode,
                 arpIpSourceGuardVlan                INTEGER,  
                 zxr10ArpInspectionLimit             INTEGER,
                 zxr10ArpInspectionTrust             INTEGER,
                 zxr10ArpLearnLimitAlarmThreshold    INTEGER,
                 zxr10ArpSrcFiltedAlarmThreshold     INTEGER,
                 zxr10ArpProxyPeriodicalFreeTime     INTEGER, 
                 zxr10ArpBackupVrrpLearn             INTEGER,
                 zxr10ArpGratuitousLearn             INTEGER,
                 zxr10ArpNetworkLearn                INTEGER,
                 zxr10ArpPeriodicalFreeFlag          INTEGER,
                 zxr10ArpProxyPeriodicalFreeFlag     INTEGER, 
                 zxr10ArpLocalProxy                  INTEGER, 
                 zxr10ArpLearnLimit                  INTEGER                 
       } 

--  interface index
    arpL3IfIndex  OBJECT-TYPE
        SYNTAX  INTEGER(1..65535)
        MAX-ACCESS  read-only
        STATUS  current
        DESCRIPTION
            "Interface index."
        ::= { arpIfAttributeEntry 1}     
 
--  arp learning flag       
    arpLearning  OBJECT-TYPE
        SYNTAX  ArpFuncType
        MAX-ACCESS  read-only
        STATUS  current
        DESCRIPTION
            "Enable arp learning?"
        ::= { arpIfAttributeEntry 2}
  
--  arp timeout 
    arpTimeOut  OBJECT-TYPE
        SYNTAX  INTEGER(1..2147483) 
        UNITS       "seconds"
        MAX-ACCESS  read-only
        STATUS  current
        DESCRIPTION
            "Arp aging time."
        ::= { arpIfAttributeEntry 3}

--  arp interface protect number
    arpProtectNum  OBJECT-TYPE
        SYNTAX  INTEGER(1..65535)
        MAX-ACCESS  read-only
        STATUS  current
        DESCRIPTION
            "Arp learning max number."
        ::= { arpIfAttributeEntry 4}
    
--  arp source filter flag
    arpSourceFilter  OBJECT-TYPE
        SYNTAX  ArpFuncType
        MAX-ACCESS  read-only
        STATUS  current
        DESCRIPTION
            "The status of arp source filter."
        ::= { arpIfAttributeEntry 5}
  
--  arp proxy flag
    arpProxy  OBJECT-TYPE
        SYNTAX  ArpFuncType
        MAX-ACCESS  read-only
        STATUS  current
        DESCRIPTION
            "The status of arp proxy."
        ::= { arpIfAttributeEntry 7}    
    
--  arp purge delay time    
    arpPurgeDelay  OBJECT-TYPE
        SYNTAX  INTEGER(1..36000) 
        UNITS       "seconds"
        MAX-ACCESS  read-only
        STATUS  current
        DESCRIPTION
            "Arp purge delay time."
        ::= { arpIfAttributeEntry 8}      
 
--  arp port speed       
    arpLimitSpeed  OBJECT-TYPE
        SYNTAX  INTEGER(1..1000)
        MAX-ACCESS  read-only
        STATUS  current
        DESCRIPTION
            "Max arp packets per second."
        ::= { arpIfAttributeEntry 9}    

--  arp limit time        
    arpLimitTime  OBJECT-TYPE
        SYNTAX  INTEGER(0..1000)
        UNITS       "seconds"
        MAX-ACCESS  read-only
        STATUS  current   
        DESCRIPTION
            "Arp port limit time."
        ::= { arpIfAttributeEntry 10}    
        
--  arp periodical free arp time
    arpPeriodicalFreeTime  OBJECT-TYPE
        SYNTAX  INTEGER(10..14400) 
        UNITS       "seconds"
        MAX-ACCESS  read-only
        STATUS  current
        DESCRIPTION
            "Arp periodical free arp time."
        ::= { arpIfAttributeEntry 11}    
 
--  arp interface name                
    arpL3IfName OBJECT-TYPE
        SYNTAX  DisplayString (SIZE (0..255))
        MAX-ACCESS  read-only
        STATUS  current
        DESCRIPTION
                "Interface name."
        ::= { arpIfAttributeEntry 12 } 
        
--  arp ip source guard mode  
    arpIpSourceGuardMode  OBJECT-TYPE
        SYNTAX  IpSourceGuardMode 
        MAX-ACCESS  read-only
        STATUS  obsolete
        DESCRIPTION
            "Set ip-source-guard mode base on mac,ip or mac and ip."
        ::= { arpIfAttributeEntry 13}  
  
--  arp ip source guard vlan  
    arpIpSourceGuardVlan  OBJECT-TYPE
        SYNTAX  INTEGER(0..65535) 
        MAX-ACCESS  read-only
        STATUS  obsolete
        DESCRIPTION
            "Designate vlan id of ip-source-guard. 
            The value of 0 means no vlan being designated.
            The range from 1 to 4094 means appointed vlan id.
            The value of 65535 means default vlan.
            The other values is invalid "
        ::= { arpIfAttributeEntry 14} 
    
--  arp inspection limit rate    
    zxr10ArpInspectionLimit  OBJECT-TYPE
        SYNTAX  INTEGER(1..100)
        MAX-ACCESS  read-only
        STATUS  current
        DESCRIPTION
            "Upper of ARP packets rate."
        DEFVAL    { 15 }
        ::= { arpIfAttributeEntry 15}
 
--  arp inspection trust flag       
    zxr10ArpInspectionTrust  OBJECT-TYPE
        SYNTAX  INTEGER {enable (1), disable (2)}
        MAX-ACCESS  read-only
        STATUS  current
        DESCRIPTION
            "The status of arp inspection trust."
        DEFVAL    { disable }
        ::= { arpIfAttributeEntry 16} 
 
--  arp drop packets number per 10 seconds (learn limit)      
    zxr10ArpLearnLimitAlarmThreshold  OBJECT-TYPE
        SYNTAX  INTEGER(1..65535)
        MAX-ACCESS  read-only
        STATUS  current
        DESCRIPTION
            "Drop packets number per 10 seconds with learn limit."
        DEFVAL    { 300 }
        ::= { arpIfAttributeEntry 17} 
   
--  arp drop packets number per 10 seconds (source filted)         
    zxr10ArpSrcFiltedAlarmThreshold  OBJECT-TYPE
        SYNTAX  INTEGER(1..65535)
        MAX-ACCESS  read-only
        STATUS  current
        DESCRIPTION
            "Drop packets number per 10 seconds with source filted."
        DEFVAL    { 300 }
        ::= { arpIfAttributeEntry 18} 
    
--  arp proxy periodical free time   
    zxr10ArpProxyPeriodicalFreeTime  OBJECT-TYPE
        SYNTAX  INTEGER(1..14400) 
        UNITS       "seconds"
        MAX-ACCESS  read-only
        STATUS  current
        DESCRIPTION
            "Arp proxy periodical free arp time."
        DEFVAL    { 30 }
        ::= { arpIfAttributeEntry 19}
 
-- arp back vrrp learn flag       
    zxr10ArpBackupVrrpLearn  OBJECT-TYPE
        SYNTAX  INTEGER {enable (1), disable (2)}
        MAX-ACCESS  read-only
        STATUS  current
        DESCRIPTION
            "The status of arp backup vrrp learn."
        DEFVAL    { disable }
        ::= { arpIfAttributeEntry 20}
   
--  arp gratuitous learn flag        
    zxr10ArpGratuitousLearn  OBJECT-TYPE
        SYNTAX  INTEGER {enable (1), disable (2)}
        MAX-ACCESS  read-only
        STATUS  current
        DESCRIPTION
            "The status of arp gratuitous learn."
        DEFVAL    { disable }
        ::= { arpIfAttributeEntry 21}
        
--  arp network learn flag
    zxr10ArpNetworkLearn  OBJECT-TYPE
        SYNTAX  INTEGER {enable (1), disable (2)}
        MAX-ACCESS  read-only
        STATUS  current
        DESCRIPTION
            "The status of arp network learn."
        DEFVAL    { disable }
        ::= { arpIfAttributeEntry 22}  

--  arp periodical free flag
    zxr10ArpPeriodicalFreeFlag  OBJECT-TYPE
        SYNTAX  INTEGER {enable (1), disable (2)}
        MAX-ACCESS  read-only
        STATUS  current
        DESCRIPTION
            "The status of arp periodical free."
        DEFVAL    { disable }
        ::= { arpIfAttributeEntry 23}    

--  arp proxy periodical free flag
    zxr10ArpProxyPeriodicalFreeFlag  OBJECT-TYPE
        SYNTAX  INTEGER {enable (1), disable (2)}
        MAX-ACCESS  read-only
        STATUS  current
        DESCRIPTION
            "The status of arp proxy periodical free."
        DEFVAL    { disable }
        ::= { arpIfAttributeEntry 24}      

--  arp local proxy flag              
    zxr10ArpLocalProxy  OBJECT-TYPE
        SYNTAX  INTEGER {enable (1), disable (2)}
        MAX-ACCESS  read-only
        STATUS  current
        DESCRIPTION
            "The status of arp local proxy."
        DEFVAL    { disable }
        ::= { arpIfAttributeEntry 25}
    
--  arp learn limit flag        
    zxr10ArpLearnLimit  OBJECT-TYPE
        SYNTAX  INTEGER {enable (1), disable (2)}
        MAX-ACCESS  read-only
        STATUS  current
        DESCRIPTION
            "The status of arp learn limit."
        DEFVAL    { disable }
        ::= { arpIfAttributeEntry 26}            

--  arp specific MAC protect table
    zxr10ArpSpecificMacProtectTable  OBJECT-TYPE
        SYNTAX  SEQUENCE OF Zxr10ArpSpecificMacProtectEntry
        MAX-ACCESS  not-accessible
        STATUS  current
        DESCRIPTION
           "Arp specific MAC protect configure table."
        ::= { zxr10ArpMIB 5 }        
        
--  arp specific MAC protect entry
    zxr10ArpSpecificMacProtectEntry  OBJECT-TYPE
        SYNTAX  Zxr10ArpSpecificMacProtectEntry
        MAX-ACCESS  not-accessible
        STATUS  current
        DESCRIPTION
           "Arp specific MAC protect configure entry."
        INDEX  { zxr10ArpSpecificMacProtectMac}
        ::= { zxr10ArpSpecificMacProtectTable 1 }
               
--  type Zxr10ArpSpecificMacProtectEntry define  
    Zxr10ArpSpecificMacProtectEntry ::=       
            SEQUENCE   {
                 zxr10ArpSpecificMacProtectMac       PhysAddress,
                 zxr10ArpSpecificMacProtectNum       INTEGER                 
       }
  
--  arp specific MAC protect MAC
    zxr10ArpSpecificMacProtectMac  OBJECT-TYPE
        SYNTAX  PhysAddress
        MAX-ACCESS  not-accessible
        STATUS  current
        DESCRIPTION
            "The MAC who configed protect num."
        ::= { zxr10ArpSpecificMacProtectEntry 1}
        
--  arp specific MAC protect Num
    zxr10ArpSpecificMacProtectNum  OBJECT-TYPE
        SYNTAX  INTEGER(1..65535)
        MAX-ACCESS  read-only
        STATUS  current
        DESCRIPTION
            "The specific MAC protect num.
             The max value is controlled by performance parameter."
        DEFVAL    { 65535 }
        ::= { zxr10ArpSpecificMacProtectEntry 2}
        
--  arp proxy IP gratuitous table
    zxr10ArpProxyIPGratuitousTable  OBJECT-TYPE
        SYNTAX  SEQUENCE OF Zxr10ArpProxyIPGratuitousEntry
        MAX-ACCESS  not-accessible
        STATUS  current
        DESCRIPTION
           "Arp Proxy IP gratuitous Configure table."
        ::= { zxr10ArpMIB 6 }        
        
--  arp proxy IP gratuitous entry
    zxr10ArpProxyIPGratuitousEntry  OBJECT-TYPE
        SYNTAX  Zxr10ArpProxyIPGratuitousEntry
        MAX-ACCESS  not-accessible
        STATUS  current
        DESCRIPTION
           "Arp Proxy IP gratuitous Configure entry"
        INDEX  { zxr10ArpProxyIPGratuitousIfIndex,
                 zxr10ArpProxyIPGratuitousBegin,
                 zxr10ArpProxyIPGratuitousEnd }
        ::= { zxr10ArpProxyIPGratuitousTable 1 }
               
--  type Zxr10ArpProxyIPGratuitousEntry define  
    Zxr10ArpProxyIPGratuitousEntry ::=       
            SEQUENCE   {
                 zxr10ArpProxyIPGratuitousIfIndex    INTEGER,
                 zxr10ArpProxyIPGratuitousBegin      IpAddress,
                 zxr10ArpProxyIPGratuitousEnd        IpAddress,
                 zxr10ArpProxyIPGratuitousIfName     DisplayString                
       }
  
--  arp proxy IP gratuitous interface index
    zxr10ArpProxyIPGratuitousIfIndex  OBJECT-TYPE
        SYNTAX  INTEGER(1..65535)
        MAX-ACCESS  not-accessible
        STATUS  current
        DESCRIPTION
            "The index of interface who configed proxy gratuitou arp IP."
        ::= { zxr10ArpProxyIPGratuitousEntry 1}
 
-- arp proxy gratuitous IP       
    zxr10ArpProxyIPGratuitousBegin OBJECT-TYPE
        SYNTAX      IpAddress
        MAX-ACCESS  not-accessible
        STATUS      current
        DESCRIPTION
                "The begin IpAddress of proxy gratuitous arp IP range."
        ::= { zxr10ArpProxyIPGratuitousEntry 2 } 
        
    zxr10ArpProxyIPGratuitousEnd OBJECT-TYPE
        SYNTAX      IpAddress
        MAX-ACCESS  not-accessible
        STATUS      current
        DESCRIPTION
                "The end IpAddress of proxy gratuitous arp IP range."
        ::= { zxr10ArpProxyIPGratuitousEntry 3 }  

--  arp proxy gratuitous arp interface name     
    zxr10ArpProxyIPGratuitousIfName OBJECT-TYPE
        SYNTAX  DisplayString (SIZE (0..255))
        MAX-ACCESS  read-only
        STATUS  current
        DESCRIPTION
                "proxy gratuitous arp interface name."
        ::= { zxr10ArpProxyIPGratuitousEntry 4 }          
    
--  arp whole protect number        
    arpWholeProtectNum OBJECT-TYPE
        SYNTAX  INTEGER(1..262144)
        MAX-ACCESS  read-only
        STATUS  current
        DESCRIPTION
                "Arp whole protect number. 
                The max value is controlled by performance parameter."
        DEFVAL    { 65535 }
        ::= { zxr10ArpMIB 2 }   

 
--  arp common MAC protect number        
    arpCommMacProtectNum OBJECT-TYPE
        SYNTAX  INTEGER(1..262144)
        MAX-ACCESS  read-only
        STATUS  current
        DESCRIPTION
                "Arp common MAC protect number. 
                The max value is controlled by performance parameter."
        DEFVAL    { 65535 }
        ::= { zxr10ArpMIB 3 }

--  arp global objects         
    zxr10ArpGlobalObjects OBJECT IDENTIFIER 
        ::= { zxr10ArpMIB 4 }
        
--  arp inspection validate attribute      
    zxr10ArpInsptValidateSrcMac OBJECT-TYPE
        SYNTAX  INTEGER {enable (1), disable (2)}
        MAX-ACCESS  read-only
        STATUS  current
        DESCRIPTION
                "The status of arp inspection validate source MAC."
        DEFVAL    { disable }
        ::= { zxr10ArpGlobalObjects 1 }
        
    zxr10ArpInsptValidateIP OBJECT-TYPE
        SYNTAX  INTEGER {enable (1), disable (2)}
        MAX-ACCESS  read-only
        STATUS  current
        DESCRIPTION
                "The status of arp inspection validate IP."
        DEFVAL    { disable }
        ::= { zxr10ArpGlobalObjects 2 }
        
    zxr10ArpInsptValidateDetMac OBJECT-TYPE
        SYNTAX  INTEGER {enable (1), disable (2)}
        MAX-ACCESS  read-only
        STATUS  current
        DESCRIPTION
                "The status of arp inspection validate dest MAC."
        DEFVAL    { disable }
        ::= { zxr10ArpGlobalObjects 3 } 
        
    
--  arp keep alive periodic time         
    zxr10ArpKeepalivePeriodicTime OBJECT-TYPE
        SYNTAX  INTEGER(10..14400) 
        UNITS       "seconds"
        MAX-ACCESS  read-only
        STATUS  current
        DESCRIPTION
                "Arp keepalive periodical time."
        DEFVAL    { 30 }
        ::= { zxr10ArpGlobalObjects 4 }  

--  arp global limit item number         
    zxr10ArpGlobalLimitItemNum OBJECT-TYPE
        SYNTAX  INTEGER(1..65535)
        MAX-ACCESS  read-only
        STATUS  current
        DESCRIPTION
                "Arp global limit item number."
        DEFVAL    { 65535 }
        ::= { zxr10ArpGlobalObjects 5 } 
        
--  arp interface limit item number      
    zxr10ArpInterfaceLimitNum OBJECT-TYPE
        SYNTAX  INTEGER(1..65535)
        MAX-ACCESS  read-only
        STATUS  current
        DESCRIPTION
                "Arp interface limit item number."
        DEFVAL    { 65535 }
        ::= { zxr10ArpGlobalObjects 6 } 
        
--  arp global exist item number      
    zxr10ArpGlobalExistItemNum OBJECT-TYPE
        SYNTAX  INTEGER(1..65535)
        MAX-ACCESS  read-only
        STATUS  current
        DESCRIPTION
                "Arp global exist item number."
        DEFVAL    { 65535 }
        ::= { zxr10ArpGlobalObjects 7 } 

--  arp item table
    zxr10ArpItemTable  OBJECT-TYPE
        SYNTAX  SEQUENCE OF Zxr10ArpItemEntry
        MAX-ACCESS  not-accessible
        STATUS  current
        DESCRIPTION
           "Arp item table."
        ::= { zxr10ArpMIB 7 } 

--  arp item entry
    zxr10ArpItemEntry  OBJECT-TYPE
        SYNTAX  Zxr10ArpItemEntry
        MAX-ACCESS  not-accessible
        STATUS  current
        DESCRIPTION
           "Arp item entry"
        INDEX  { zxr10ArpItemIfIndex,
                 zxr10ArpItemIPAddress }
        ::= { zxr10ArpItemTable 1 }
               
--  type Zxr10ArpItemEntry define  
    Zxr10ArpItemEntry ::=       
            SEQUENCE   {
                 zxr10ArpItemIfIndex      INTEGER,
                 zxr10ArpItemIPAddress    IpAddress,
                 zxr10ArpItemIfName       DisplayString,
                 zxr10ArpItemType         ArpItemType,
                 zxr10ArpItemPhysAddress  PhysAddress,
                 zxr10ArpItemInterVlan    INTEGER,
                 zxr10ArpItemOutVlan      INTEGER,    
                 zxr10ArpItemSubIfName    DisplayString,
                 zxr10ArpItemVtepIfName   DisplayString,
                 zxr10ArpItemVnid         INTEGER,
                 zxr10ArpItemRemoteIP     IpAddress
       }
  
--  arp item interface index
    zxr10ArpItemIfIndex  OBJECT-TYPE
        SYNTAX  INTEGER(1..65535)
        MAX-ACCESS  not-accessible
        STATUS  current
        DESCRIPTION
            "The interface index of arp item."
        ::= { zxr10ArpItemEntry 1}
 
-- arp item IP address     
    zxr10ArpItemIPAddress OBJECT-TYPE
        SYNTAX      IpAddress
        MAX-ACCESS  not-accessible
        STATUS      current
        DESCRIPTION
                "The IP address of arp item."
        ::= { zxr10ArpItemEntry 2 }  

--  arp item interface name     
    zxr10ArpItemIfName OBJECT-TYPE
        SYNTAX  DisplayString (SIZE (0..255))
        MAX-ACCESS  read-only
        STATUS  current
        DESCRIPTION
                "The interface name of arp item."
        ::= { zxr10ArpItemEntry 3 } 

--  arp item type      
    zxr10ArpItemType  OBJECT-TYPE
        SYNTAX  ArpItemType
        MAX-ACCESS  read-only
        STATUS  current
        DESCRIPTION
            "The type of arp item."
        ::= { zxr10ArpItemEntry 4}     

--  arp item physic address
    zxr10ArpItemPhysAddress  OBJECT-TYPE
        SYNTAX  PhysAddress
        MAX-ACCESS  read-only
        STATUS  current
        DESCRIPTION
            "The physic address of arp item."
        ::= { zxr10ArpItemEntry 5}    

--  arp item inter vlan
    zxr10ArpItemInterVlan  OBJECT-TYPE
        SYNTAX  INTEGER(1..65535)
        MAX-ACCESS  read-only
        STATUS  current
        DESCRIPTION
            "The inter vlan of arp item."
        ::= { zxr10ArpItemEntry 6}    

--  arp item out vlan
    zxr10ArpItemOutVlan  OBJECT-TYPE
        SYNTAX  INTEGER(1..65535)
        MAX-ACCESS  read-only
        STATUS  current
        DESCRIPTION
            "The out vlan of arp item."
        ::= { zxr10ArpItemEntry 7}

--  arp item sub interface name     
    zxr10ArpItemSubIfName OBJECT-TYPE
        SYNTAX  DisplayString (SIZE (0..255))
        MAX-ACCESS  read-only
        STATUS  current
        DESCRIPTION
                "The sub interface name of arp item."
        ::= { zxr10ArpItemEntry 8 }  

--  arp item vtep interface name     
    zxr10ArpItemVtepIfName OBJECT-TYPE
        SYNTAX  DisplayString (SIZE (0..255))
        MAX-ACCESS  read-only
        STATUS  current
        DESCRIPTION
                "The vtep interface name of arp item."
        ::= { zxr10ArpItemEntry 9 }      

--  arp item vnid   
    zxr10ArpItemVnid  OBJECT-TYPE
        SYNTAX  INTEGER(1..65535)
        MAX-ACCESS  read-only
        STATUS  current
        DESCRIPTION
            "The vnid of arp item."
        ::= { zxr10ArpItemEntry 10}    

--  arp item remote ip   
    zxr10ArpItemRemoteIP  OBJECT-TYPE
        SYNTAX  IpAddress
        MAX-ACCESS  read-only
        STATUS  current
        DESCRIPTION
            "The remote ip of arp item."
        ::= { zxr10ArpItemEntry 11}            

--  arp interface item number table
    zxr10ArpIntfItemNumTable  OBJECT-TYPE
        SYNTAX  SEQUENCE OF Zxr10ArpIntfItemNumEntry
        MAX-ACCESS  not-accessible
        STATUS  current
        DESCRIPTION
           "Arp interface item number table."
        ::= { zxr10ArpMIB 8 } 

--  arp interface item number entry
    zxr10ArpIntfItemNumEntry  OBJECT-TYPE
        SYNTAX  Zxr10ArpIntfItemNumEntry
        MAX-ACCESS  not-accessible
        STATUS  current
        DESCRIPTION
           "Arp interface item number entry"
        INDEX  { zxr10ArpIntfItemNumIfIndex}
        ::= { zxr10ArpIntfItemNumTable 1 }
               
--  type Zxr10ArpIntfItemNumEntry define  
    Zxr10ArpIntfItemNumEntry ::=       
            SEQUENCE   {
                 zxr10ArpIntfItemNumIfIndex INTEGER,
                 zxr10ArpIntfItemNumIfName  DisplayString,
                 zxr10ArpIntfItemNumExist   INTEGER                 
       }
  
--  arp interface item number interface index
    zxr10ArpIntfItemNumIfIndex  OBJECT-TYPE
        SYNTAX  INTEGER(1..65535)
        MAX-ACCESS  not-accessible
        STATUS  current
        DESCRIPTION
            "The interface index of arp interface item number."
        ::= { zxr10ArpIntfItemNumEntry 1} 

--  arp interface item number interface name     
    zxr10ArpIntfItemNumIfName OBJECT-TYPE
        SYNTAX  DisplayString (SIZE (0..255))
        MAX-ACCESS  read-only
        STATUS  current
        DESCRIPTION
                "The interface name of arp interface item number."
        ::= { zxr10ArpIntfItemNumEntry 2 }  

--  arp interface item number that exists
    zxr10ArpIntfItemNumExist  OBJECT-TYPE
        SYNTAX  INTEGER(1..65535)
        MAX-ACCESS  read-only
        STATUS  current
        DESCRIPTION
            "The arp interface item number that exists."
        ::= { zxr10ArpIntfItemNumEntry 3}          
END
