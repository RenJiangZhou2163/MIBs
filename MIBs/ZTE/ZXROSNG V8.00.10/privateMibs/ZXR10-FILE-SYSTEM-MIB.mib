-- *****************************************************************
--
-- Copyright (c) 2009 by ZTE Corporation
-- All rights reserved.
-- 
-- *****************************************************************
--
ZXR10-FILE-SYSTEM-MIB DEFINITIONS ::= BEGIN
IMPORTS
        MODULE-IDENTITY, OBJECT-TYPE,Counter64,Counter32,
        Integer32, NOTIFICATION-TYPE,enterprises, Unsigned32
                FROM SNMPv2-SMI
        TEXTUAL-CONVENTION, DisplayString, TimeStamp, RowStatus,
        TruthValue
                FROM SNMPv2-TC
        OBJECT-GROUP, NOTIFICATION-GROUP
                FROM SNMPv2-CONF;

zte MODULE-IDENTITY
    LAST-UPDATED "201504140000Z"  
    ORGANIZATION "ZTE Corporation"
    CONTACT-INFO
        "ZTE Corporation 
         Nanjing Institute of ZTE Corporation
         
         No.68 Zijinghua Rd. Yuhuatai District, Nanjing, China
         
         Tel: +86-25-52870000"

    DESCRIPTION  
        "ZXR10 T8000 ZXR10FILESYSTEM-MIB"
    REVISION "201504140000Z"
       DESCRIPTION
            "Delete the TAB char,
            modify SYNTAX of zxr10FSCopyTable,
                   SYNTAX of zxr10fileEntry,
                   definition of Zxr10fileEntry,
                   SYNTAX of zxr10fileIndex,
                   SYNTAX of zxr10FSCopyTable,
                   SYNTAX of zxr10FSCopyEntry,
                   and SYNTAX of zxr10FSCopyNotificationOnCompletion.
            " 
    REVISION "200908120000Z"  
    DESCRIPTION  " "
    ::= { enterprises 3902 }   -- assigned by IANA

zxr10      OBJECT IDENTIFIER ::= { zte 3}
zxr10RosngMIB      OBJECT IDENTIFIER ::= { zxr10 6000 }
zxr10fileSystemMib OBJECT IDENTIFIER ::= {zxr10RosngMIB 5 }

 
 -- The storage Control Group
zxr10storageTable  OBJECT-TYPE
        SYNTAX  SEQUENCE OF zxr10storageEntry
        MAX-ACCESS  not-accessible
        STATUS  obsolete
        DESCRIPTION " "
        ::= { zxr10fileSystemMib 1 } 

zxr10storageEntry   OBJECT-TYPE
        SYNTAX  zxr10storageEntry
        MAX-ACCESS  not-accessible
        STATUS  obsolete
        DESCRIPTION " "
        INDEX  {zxr10storageIndex}
        ::= { zxr10storageTable 1 } 
    zxr10storageEntry ::=
        SEQUENCE {
            zxr10storageIndex
                INTEGER,
            zxr10storageName
                DisplayString,
            zxr10storageType
                INTEGER,
            zxr10storageDesc
                DisplayString,
            zxr10storageVolumTotal
                Counter64,
            zxr10storageVolumAvailable
                Counter64,
            zxr10storageRemoved
                INTEGER,   
            zxr10storageInitTime
                DisplayString,
            zxr10storageDistrictNum
                Counter32
    }
zxr10storageIndex  OBJECT-TYPE
     SYNTAX     INTEGER 
     MAX-ACCESS read-only
     STATUS     obsolete
     DESCRIPTION  " "  
     ::= { zxr10storageEntry 1 }

zxr10storageName   OBJECT-TYPE
     SYNTAX     DisplayString 
     MAX-ACCESS read-only
     STATUS     obsolete
     DESCRIPTION  " "  
     ::= { zxr10storageEntry 2 }

zxr10storageType  OBJECT-TYPE
     SYNTAX     INTEGER 
     MAX-ACCESS read-only
     STATUS     obsolete
     DESCRIPTION  " " 
     ::= { zxr10storageEntry 3 }

zxr10storageDesc   OBJECT-TYPE
     SYNTAX     DisplayString 
     MAX-ACCESS read-write
     STATUS     obsolete
     DESCRIPTION  " " 
     ::= { zxr10storageEntry 4 }

zxr10storageVolumTotal    OBJECT-TYPE
     SYNTAX     Counter64 
     MAX-ACCESS read-only
     STATUS     obsolete
     DESCRIPTION  " "
     ::= { zxr10storageEntry 5 }

zxr10storageVolumAvailable   OBJECT-TYPE
     SYNTAX     Counter64 
     MAX-ACCESS read-only
     STATUS     obsolete
     DESCRIPTION  " "
     ::= { zxr10storageEntry 6 }

zxr10storageRemoved   OBJECT-TYPE
     SYNTAX     INTEGER 
     MAX-ACCESS read-only
     STATUS     obsolete
     DESCRIPTION  " "
     ::= { zxr10storageEntry 7 }

zxr10storageInitTime   OBJECT-TYPE
     SYNTAX     DisplayString 
     MAX-ACCESS read-only
     STATUS     obsolete
     DESCRIPTION  " "
     ::= { zxr10storageEntry 8 }

zxr10storageDistrictNum   OBJECT-TYPE
     SYNTAX     Counter32
     MAX-ACCESS read-only
     STATUS     obsolete
     DESCRIPTION  " "
     ::= { zxr10storageEntry 9 }



 -- The partition Control Group
zxr10partitionTable  OBJECT-TYPE
        SYNTAX  SEQUENCE OF zxr10partitionEntry
        MAX-ACCESS  not-accessible
        STATUS  obsolete
        DESCRIPTION " "
        ::= { zxr10fileSystemMib 2 } 

zxr10partitionEntry  OBJECT-TYPE
        SYNTAX  zxr10partitionEntry
        MAX-ACCESS  not-accessible
        STATUS  obsolete
        DESCRIPTION " "
        INDEX  {zxr10partitionIndex}
        ::= { zxr10partitionTable 1 } 

    zxr10partitionEntry ::=
        SEQUENCE {
            zxr10partitionIndex
                INTEGER,
            zxr10partitionName
                DisplayString,
            zxr10partitionDesc
                DisplayString,                
            zxr10partitionVolumTotal
                Counter64,
            zxr10partitionVolumAvailable
                Counter64,
            zxr10partitionTotalFiles
                Counter32,
            zxr10partitionAttribute
                DisplayString
    }
zxr10partitionIndex  OBJECT-TYPE
     SYNTAX     INTEGER 
     MAX-ACCESS read-only
     STATUS     obsolete
     DESCRIPTION  " "
     ::= { zxr10partitionEntry 1 }
 
zxr10partitionName    OBJECT-TYPE
     SYNTAX     DisplayString 
     MAX-ACCESS read-only
     STATUS     obsolete
     DESCRIPTION  " "
     ::= { zxr10partitionEntry 2 }
 
zxr10partitionDesc   OBJECT-TYPE
     SYNTAX     DisplayString 
     MAX-ACCESS read-write
     STATUS     obsolete
     DESCRIPTION  " "
     ::= { zxr10partitionEntry 3 }
 
zxr10partitionVolumTotal   OBJECT-TYPE
     SYNTAX     Counter64 
     MAX-ACCESS read-only
     STATUS     obsolete
     DESCRIPTION  " "
     ::= { zxr10partitionEntry 4 }
 
zxr10partitionVolumAvailable   OBJECT-TYPE
     SYNTAX     Counter64 
     MAX-ACCESS read-only
     STATUS     obsolete
     DESCRIPTION  " "
     ::= { zxr10partitionEntry 5 }
 
zxr10partitionTotalFiles    OBJECT-TYPE
     SYNTAX     Counter32 
     MAX-ACCESS read-only
     STATUS     obsolete
     DESCRIPTION  " "
     ::= { zxr10partitionEntry 6 }
 
zxr10partitionAttribute    OBJECT-TYPE
     SYNTAX     DisplayString 
     MAX-ACCESS read-only
     STATUS     obsolete
     DESCRIPTION  " "
     ::= { zxr10partitionEntry 7 }

 -- The filetable Control Group
zxr10fileTable    OBJECT-TYPE
        SYNTAX  SEQUENCE OF Zxr10fileEntry
        MAX-ACCESS  not-accessible
        STATUS  current
        DESCRIPTION  "The table of file information "
        ::= { zxr10fileSystemMib 3 } 

zxr10fileEntry  OBJECT-TYPE
        SYNTAX  Zxr10fileEntry
        MAX-ACCESS  not-accessible
        STATUS  current
        DESCRIPTION  "An entry containing file information "
        INDEX  {zxr10fileIndex}
        ::= { zxr10fileTable 1 } 

    Zxr10fileEntry ::=
        SEQUENCE {
            zxr10fileIndex
                Integer32,
            zxr10fileName
                DisplayString,
            zxr10fileAttribute
                DisplayString,                
            zxr10fileSize
                Counter32,
            zxr10fileModifyTime
                DisplayString,
            zxr10fileLocation
                DisplayString
    }
 zxr10fileIndex  OBJECT-TYPE
     SYNTAX     Integer32 
     MAX-ACCESS read-only
     STATUS     current
     DESCRIPTION  "The index number of the file "
     ::= { zxr10fileEntry 1 }

 zxr10fileName  OBJECT-TYPE
     SYNTAX     DisplayString
     MAX-ACCESS read-only
     STATUS     current
     DESCRIPTION  "The name of the file"
     ::= { zxr10fileEntry 2 }

 zxr10fileAttribute OBJECT-TYPE
     SYNTAX     DisplayString
     MAX-ACCESS read-only
     STATUS     current
     DESCRIPTION  "The attribute of the item. Use <DIR> to describe the attribute of the item 
                   if the attribute is directory, else use ---- to describe the attribute of the item."
     ::= { zxr10fileEntry 3 }

 zxr10fileSize OBJECT-TYPE
     SYNTAX     Counter32
     UNITS      "Octets"
     MAX-ACCESS read-only
     STATUS     current
     DESCRIPTION  "The size of the file"

     ::= { zxr10fileEntry 4 }

 zxr10fileModifyTime OBJECT-TYPE
     SYNTAX     DisplayString
     UNITS      "Packets"
     MAX-ACCESS read-only
     STATUS     current
     DESCRIPTION  "The last modification time of the file"
     ::= { zxr10fileEntry 5 }

 zxr10fileLocation OBJECT-TYPE
     SYNTAX     DisplayString
     UNITS      "Packets"
     MAX-ACCESS read-only
     STATUS     current
     DESCRIPTION  "The location of the file"
     ::= { zxr10fileEntry 6 }

FSCopyState ::= TEXTUAL-CONVENTION
        STATUS current
        DESCRIPTION                "The state of a copy operation. 
                 The description of each state is given below:

                 waiting:     only one file-copy request can run 
                              at any time. A newly activated 
                              file-copy request is placed in this 
                              state if another request has already 
                              been activated.

                 running:     this state signifies that the file-copy
                              request is running.

                 successsful: the state when a file-copy request is
                              successfully completed.

                 failed:      the file-copy request was unsuccesful.
                "
        SYNTAX        INTEGER {
                waiting(1),
                running(2),
                successful(3),
                failed(4)
        }

FSCopyFailCause ::= TEXTUAL-CONVENTION
        STATUS current
        DESCRIPTION                "The reason a file-copy request failed."
        SYNTAX INTEGER {
                unknown(1),     -- very descriptive
                badFileName(2), -- check your file name/path/permissions and cpu node
                fileNameTooLong(3), --source/destination filepath/name too long
                fileLevelTooLong(4), -- source/destination filepath level too long
                                     -- max level 10
                fileOprForbid(5), -- file access forbidden   
                srcNotExist(6),  -- source file is not exist
                dstExist(7),     -- destination file is exist 
                dstDirNotExist(8) -- destination directory is not exist
        } 
        
 -- The filemib copy
zxr10FSCopyTable OBJECT-TYPE
        SYNTAX  SEQUENCE OF Zxr10FSCopyEntry
        MAX-ACCESS  not-accessible
        STATUS  current
        DESCRIPTION "The table of file-copy"
        ::= { zxr10fileSystemMib 4 } 

zxr10FSCopyEntry  OBJECT-TYPE
        SYNTAX  Zxr10FSCopyEntry
        MAX-ACCESS  not-accessible
        STATUS  current
        DESCRIPTION "This list contains file-copy parameters "
        INDEX  {zxr10FSCopyIndex}
        ::= { zxr10FSCopyTable 1 } 

    Zxr10FSCopyEntry ::=
        SEQUENCE {
                zxr10FSCopyIndex                       Unsigned32,
                -- configuration items
                zxr10FSCopySrcFileName                 DisplayString, 
                zxr10FSCopySrcCpuNode                  DisplayString,
                zxr10FSCopyDstFileName                 DisplayString,
                zxr10FSCopyDstCpuNode                  DisplayString, 
                zxr10FSCopyNotificationOnCompletion    TruthValue,
                -- status items
                zxr10FSCopyState                       FSCopyState,
                zxr10FSCopyTimeStarted                 TimeStamp,
                zxr10FSCopyTimeCompleted               TimeStamp,
                zxr10FSCopyFailCause                   FSCopyFailCause,
                zxr10FSCopyRowStatus                   RowStatus  
    }
 zxr10FSCopyIndex OBJECT-TYPE
        SYNTAX           Unsigned32(1..2147483647)
        MAX-ACCESS not-accessible
        STATUS     current
        DESCRIPTION                "Object which specifies a unique entry in the
                copyTable.  A management station wishing
                to initiate a config-copy operation should use a
                random value for this object when creating
                or modifying an instance of a copyEntry.
                The RowStatus semantics of the copyEntryRowStatus
                object will prevent access conflicts."
        ::= { zxr10FSCopyEntry 1 }

zxr10FSCopySrcFileName OBJECT-TYPE
        SYNTAX     DisplayString(SIZE (1..159))
        MAX-ACCESS read-create
        STATUS     current
        DESCRIPTION                "The source file name (including the path, if applicable) of
                the file. This object must be created when either the
                copySourceFileType or copyDestFileType has the value
                networkFile or localFile."
        ::= { zxr10FSCopyEntry 2 }   
        
zxr10FSCopySrcCpuNode OBJECT-TYPE
        SYNTAX     DisplayString(SIZE (0..80))
        MAX-ACCESS read-create
        STATUS     current
        DESCRIPTION                "The cpu-node of source file."
        ::= { zxr10FSCopyEntry 3 }
        
zxr10FSCopyDstFileName OBJECT-TYPE
        SYNTAX     DisplayString(SIZE (1..159))
        MAX-ACCESS read-create
        STATUS     current
        DESCRIPTION                "The destination file name (including the path, if applicable) of
                the file. This object must be created when either the
                copySourceFileType or copyDestFileType has the value
                networkFile or localFile."
        ::= { zxr10FSCopyEntry 4 }     
                
zxr10FSCopyDstCpuNode OBJECT-TYPE
        SYNTAX     DisplayString(SIZE (0..80))
        MAX-ACCESS read-create
        STATUS     current
        DESCRIPTION                "The cpu-node of destination file."
        ::= { zxr10FSCopyEntry 5 }
        
zxr10FSCopyNotificationOnCompletion OBJECT-TYPE
        SYNTAX     TruthValue
        MAX-ACCESS read-create
        STATUS     current
        DESCRIPTION                "Specifies whether or not a copyCompletion
                notification should be issued on completion of copy
                . If such a notification is desired, it is the
                responsibility of the management entity to ensure 
                that the SNMP administrative model is configured in 
                such a way as to allow the notification to be 
                delivered."
        ::= { zxr10FSCopyEntry 6 }

zxr10FSCopyState OBJECT-TYPE
        SYNTAX     FSCopyState
        MAX-ACCESS read-only
        STATUS     current
        DESCRIPTION                "Specifies the state of this config-copy request.
                This value of this object is instantiated only after 
                the row has been instantiated, i.e. after the 
                copyEntryRowStatus has been made active."
        ::= { zxr10FSCopyEntry 7 }

zxr10FSCopyTimeStarted OBJECT-TYPE
        SYNTAX     TimeStamp
        MAX-ACCESS read-only
        STATUS     current
        DESCRIPTION                "Specifies the time the copyState last transitioned
                to running, or 0 if the state has never transitioned to
                running        (for e.g., stuck in waiting state).
                This object is instantiated only after the row has been
                instantiated."
        ::= { zxr10FSCopyEntry 8 }

zxr10FSCopyTimeCompleted OBJECT-TYPE
        SYNTAX     TimeStamp
        MAX-ACCESS read-only
        STATUS     current
        DESCRIPTION                "Specifies the time the copyState last transitioned
                from running to successful or failed states. This
                object is instantiated only after the row has been 
                instantiated.
                Its value will remain 0 until he request has completed."
        ::= { zxr10FSCopyEntry 9 }

zxr10FSCopyFailCause OBJECT-TYPE
        SYNTAX     FSCopyFailCause
        MAX-ACCESS read-only
        STATUS     current
        DESCRIPTION                "The reason why the config-copy operation failed.
                This object is instantiated only when the copyState 
                for this entry is in the failed state."
        ::= { zxr10FSCopyEntry 10 }

zxr10FSCopyRowStatus OBJECT-TYPE
        SYNTAX     RowStatus
        MAX-ACCESS read-create
        STATUS     current
        DESCRIPTION                "The status of this table entry.  Once the entry 
                status is set to active, the associated entry cannot 
                be modified until the request completes (copyState 
                transitions to successful or failed state)."
        ::= { zxr10FSCopyEntry 11 }

 -- The filecopymib traps
zxr10FSCopyMIBTraps OBJECT IDENTIFIER 
                              ::= { zxr10fileSystemMib 5 }

zxr10FSCopyCompletion NOTIFICATION-TYPE
        OBJECTS           {
                        zxr10FSCopySrcFileName,  
                        zxr10FSCopySrcCpuNode,
                        zxr10FSCopyDstFileName,
                        zxr10FSCopyDstCpuNode,
                        zxr10FSCopyState,
                        zxr10FSCopyTimeStarted,
                        zxr10FSCopyTimeCompleted,
                        zxr10FSCopyFailCause
                   }
        STATUS           current
        DESCRIPTION                "A copyCompletion trap is sent at the completion
                of a config-copy request. The copyFailCause is not
                instantiated, and hence not included in a trap, when 
                the copyState is success."
        ::= { zxr10FSCopyMIBTraps 1 }
END
