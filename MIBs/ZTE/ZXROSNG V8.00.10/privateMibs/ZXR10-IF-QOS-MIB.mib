--*****************************************************************
--ZXR10-IF-QOS-MIB
--OAM
--2011-8-5 9:35
--
--
--Copyright (c) 1985-2011 by ZTE Corp.
--All rights reserved.
--*****************************************************************



ZXR10-IF-QOS-MIB DEFINITIONS ::= BEGIN

IMPORTS
        MODULE-IDENTITY, OBJECT-TYPE,NOTIFICATION-TYPE,
        Unsigned32, Integer32, enterprises, IpAddress
                FROM SNMPv2-SMI 
        MODULE-COMPLIANCE, OBJECT-GROUP, NOTIFICATION-GROUP
                FROM SNMPv2-CONF
        DisplayString,MacAddress,TEXTUAL-CONVENTION,RowStatus
                FROM SNMPv2-TC
        zxr10,zxr10RosngMIB
                FROM ZXR10-SMI;

zxr10IfQosMIB MODULE-IDENTITY
        LAST-UPDATED  "201408250910Z"
        ORGANIZATION  "ZTE Corporation"
        CONTACT-INFO
            "       Hu Jun
            Tel:    +86-25-52870000
            E-Mail: hu.jun11@zte.com.cn "
        DESCRIPTION   "The MIB module to describe the IF QoS protocol."

        REVISION      "201408250910Z"
        DESCRIPTION   "Modify the mib file based on criterion."

        REVISION      "201307231420Z"
        DESCRIPTION   "Add new leaf nodes.
                       Modify the mib file based on criterion."
        REVISION      "201106270000Z"
        DESCRIPTION   "add:   zxr10IfQosMIB
                       Initial version of this MIB module."        
        ::= { zxr10QosMIBObjects 3 }

zxr10QosMIBObjects      OBJECT IDENTIFIER ::= { zxr10RosngMIB 30 }

--******************************************************
--    he follow part defined some data types which will 
--    be used in this mib file later  
--******************************************************   
QosIfSrvClass ::= TEXTUAL-CONVENTION
    STATUS       current
    DESCRIPTION
            "server class of PHB info ,see below:
             be  Best effort
             af1 Assured forwarding class 1
             af2 Assured forwarding class 2
             af3 Assured forwarding class 3
             af4 Assured forwarding class 4
             ef  Expedited forward
             cs6 Internetwork control service class
             cs7 Network control service class"
    SYNTAX   INTEGER {be(1),af1(2),af2(3),af3(4),
                      af4(5),ef(6),cs6(7),cs7(8)} 
    
QosIfColor ::= TEXTUAL-CONVENTION
    STATUS       current
    DESCRIPTION
            "Color of PHB info, see below:
             green   Green packets
             yellow  Yellow packets
             red     Red packets"
    SYNTAX   INTEGER {green(1),yellow(2),red(3)} 

--*****************************************************************
--*****************************************************************
--zQosDot1pTable
--*****************************************************************
zQosDot1pTable OBJECT-TYPE
        SYNTAX  SEQUENCE OF ZQosDot1pEntry
        MAX-ACCESS  not-accessible
        STATUS  obsolete
        DESCRIPTION
                "QOS_DOT1P TABLE"
        ::= { zxr10IfQosMIB 1  }

zQosDot1pEntry OBJECT-TYPE
        SYNTAX   ZQosDot1pEntry
        MAX-ACCESS  not-accessible
        STATUS  obsolete
        DESCRIPTION
                "802.1p inherit on the interface"
        INDEX {zQosDot1pStrifname,
               zQosDot1pBcvlanin,
               zQosDot1pBsvlanin,
               zQosDot1pBoutput}
        ::= { zQosDot1pTable 1 }

ZQosDot1pEntry ::=
        SEQUENCE {
                zQosDot1pStrifname                                
                    DisplayString,
                zQosDot1pBcvlanin                                 
                    INTEGER,
                zQosDot1pBsvlanin                                 
                    INTEGER,
                zQosDot1pBoutput                                  
                    INTEGER
        }

zQosDot1pStrifname OBJECT-TYPE
        SYNTAX   DisplayString(SIZE(0..31))
        MAX-ACCESS  read-only
        STATUS  obsolete
        DESCRIPTION
                "WORD Name of the attaching interface"
        ::= { zQosDot1pEntry  1  }

zQosDot1pBcvlanin OBJECT-TYPE
        SYNTAX   INTEGER{no_cvlan_in(0),cvlan_in(1)}
        MAX-ACCESS  read-only
        STATUS  obsolete
        DESCRIPTION
                "Inherit from ingress 802.1p on inner VLAN"
        ::= { zQosDot1pEntry  2  }

zQosDot1pBsvlanin OBJECT-TYPE
        SYNTAX   INTEGER{no_svlan_in(0),svlan_in(1)}
        MAX-ACCESS  read-only
        STATUS  obsolete
        DESCRIPTION
                "bSvlanIn"
        ::= { zQosDot1pEntry  3  }

zQosDot1pBoutput OBJECT-TYPE
        SYNTAX   INTEGER{no_out(0),out(1)}
        MAX-ACCESS  read-only
        STATUS  obsolete
        DESCRIPTION
                "bOutput"
        ::= { zQosDot1pEntry  4  }



--*****************************************************************
--*****************************************************************
--zTtlQosModeTable
--*****************************************************************
zTtlQosModeTable OBJECT-TYPE
        SYNTAX  SEQUENCE OF ZTtlQosModeEntry
        MAX-ACCESS  not-accessible
        STATUS  current
        DESCRIPTION
                "TTL_QOS_MODE TABLE"
        ::= { zxr10IfQosMIB 2  }

zTtlQosModeEntry OBJECT-TYPE
        SYNTAX   ZTtlQosModeEntry
        MAX-ACCESS  not-accessible
        STATUS  current
        DESCRIPTION
                "TTL duplicate on the interface"
        INDEX {zTtlQosModeStrifname }
        ::= { zTtlQosModeTable 1 }

ZTtlQosModeEntry ::=
        SEQUENCE {
                zTtlQosModeStrifname                              
                    DisplayString,
                zTtlQosModeUcinherimode                           
                    INTEGER
        }

zTtlQosModeStrifname OBJECT-TYPE
        SYNTAX   DisplayString(SIZE(0..31))
        MAX-ACCESS  read-only
        STATUS  current
        DESCRIPTION
                "WORD Name of the attaching interface"
        ::= { zTtlQosModeEntry  1  }

zTtlQosModeUcinherimode OBJECT-TYPE
        SYNTAX   INTEGER{uniform(1),pipe(2)}
        MAX-ACCESS  read-only
        STATUS  current
        DESCRIPTION
                "pipe    Select pipe mode
                 uniform Select uniform mode"
        ::= { zTtlQosModeEntry  2  }



--*****************************************************************
--*****************************************************************
--zMlsQosModeTable
--*****************************************************************
zMlsQosModeTable OBJECT-TYPE
        SYNTAX  SEQUENCE OF ZMlsQosModeEntry
        MAX-ACCESS  not-accessible
        STATUS  current
        DESCRIPTION
                "MLS_QOS_MODE TABLE"
        ::= { zxr10IfQosMIB 3  }

zMlsQosModeEntry OBJECT-TYPE
        SYNTAX   ZMlsQosModeEntry
        MAX-ACCESS  not-accessible
        STATUS  current
        DESCRIPTION
                "Priority inherit on the interface"
        INDEX {zMlsQosModeStrifname }
        ::= { zMlsQosModeTable 1 }

ZMlsQosModeEntry ::=
        SEQUENCE {
                zMlsQosModeStrifname                              
                    DisplayString,
                zMlsQosModeUcinheritmode                         
                    INTEGER,
                zMlsQosModeServClass
                    QosIfSrvClass,
                zMlsQosModeColor
                    QosIfColor
        }

zMlsQosModeStrifname OBJECT-TYPE
        SYNTAX   DisplayString(SIZE(0..31))
        MAX-ACCESS  read-only
        STATUS  current
        DESCRIPTION
                "WORD Name of the attaching interface"
        ::= { zMlsQosModeEntry  1  }

zMlsQosModeUcinheritmode OBJECT-TYPE
        SYNTAX   INTEGER{uniform(1),pipe(2),short_pipe(3)}
        MAX-ACCESS  read-only
        STATUS  current
        DESCRIPTION
                "pipe       Select pipe inherit mode
                 short_pipe Select short-pipe inherit mode
                 uniform    Select uniform inherit mode"
        ::= { zMlsQosModeEntry  2  }

zMlsQosModeServClass OBJECT-TYPE
        SYNTAX   QosIfSrvClass
        MAX-ACCESS  read-only
        STATUS  current
        DESCRIPTION
                "service class:
                server class of PHB info ,see below:
                be  Best effort
                af1 Assured forwarding class 1
                af2 Assured forwarding class 2
                af3 Assured forwarding class 3
                af4 Assured forwarding class 4
                ef  Expedited forward
                cs6 Internetwork control service class
                cs7 Network control service class"
        ::= { zMlsQosModeEntry  3  } 
        
zMlsQosModeColor OBJECT-TYPE
        SYNTAX   QosIfColor
        MAX-ACCESS  read-only
        STATUS  current
        DESCRIPTION
                "color:
                green   Green packets
                yellow  Yellow packets
                red     Red packets"
        ::= { zMlsQosModeEntry  4  }
 
--*****************************************************************
--*****************************************************************
--zxr10QosDot1pTable
--*****************************************************************
zxr10QosDot1pTable OBJECT-TYPE
        SYNTAX  SEQUENCE OF Zxr10QosDot1pEntry
        MAX-ACCESS  not-accessible
        STATUS  current
        DESCRIPTION
                "QOS_DOT1P TABLE"
        ::= { zxr10IfQosMIB 4  }

zxr10QosDot1pEntry OBJECT-TYPE
        SYNTAX   Zxr10QosDot1pEntry
        MAX-ACCESS  not-accessible
        STATUS  current
        DESCRIPTION
                "802.1p inherit on the interface"
        INDEX {zxr10QosDot1pStrifname,
               zxr10QosDot1pBcvlanin,
               zxr10QosDot1pBsvlanin,
               zxr10QosDot1pBoutput,
               zxr10QosDot1pBcvlanOut}
        ::= { zxr10QosDot1pTable 1 }

Zxr10QosDot1pEntry ::=
        SEQUENCE {
                zxr10QosDot1pStrifname
                    DisplayString,
                zxr10QosDot1pBcvlanin
                    INTEGER,
                zxr10QosDot1pBsvlanin
                    INTEGER,
                zxr10QosDot1pBoutput
                    INTEGER,
                zxr10QosDot1pBcvlanOut
                    INTEGER
        }

zxr10QosDot1pStrifname OBJECT-TYPE
        SYNTAX   DisplayString(SIZE(0..31))
        MAX-ACCESS  not-accessible
        STATUS  current
        DESCRIPTION
                "WORD Name of the attaching interface"
        ::= { zxr10QosDot1pEntry  1  }

zxr10QosDot1pBcvlanin OBJECT-TYPE
        SYNTAX   INTEGER{no_cvlan_in(0),cvlan_in(1)}
        MAX-ACCESS  not-accessible
        STATUS  current
        DESCRIPTION
                "Inherit from ingress 802.1p on inner VLAN"
        ::= { zxr10QosDot1pEntry  2  }

zxr10QosDot1pBsvlanin OBJECT-TYPE
        SYNTAX   INTEGER{no_svlan_in(0),svlan_in(1)}
        MAX-ACCESS  not-accessible
        STATUS  current
        DESCRIPTION
                "bSvlanIn"
        ::= { zxr10QosDot1pEntry  3  }

zxr10QosDot1pBoutput OBJECT-TYPE
        SYNTAX   INTEGER{no_out(0),out(1)}
        MAX-ACCESS  not-accessible
        STATUS  current
        DESCRIPTION
                "bOutput"
        ::= { zxr10QosDot1pEntry  4  }

zxr10QosDot1pBcvlanOut OBJECT-TYPE
        SYNTAX   INTEGER{no_cvlan_out(0),cvlan_out(1)}
        MAX-ACCESS  read-only
        STATUS  current
        DESCRIPTION
                "Inherit from egress 802.1p on inner VLAN"
        ::= { zxr10QosDot1pEntry  5 }
 
END
