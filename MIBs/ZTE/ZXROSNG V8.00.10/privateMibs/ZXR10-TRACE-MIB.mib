--  ******************************************************
--  $Id: trace.mib 2008-03$
--
--  zesr.mib: ZXR10 Access List MIB file
--
--  Nov. 2008, Zhong Yan
--
--  Copyright(c) 2008 by ZTE Corporaton
--  All rights reservered
--  ******************************************************
ZXR10-TRACE-MIB DEFINITIONS ::= BEGIN

    IMPORTS
        MODULE-IDENTITY, OBJECT-TYPE,
        Integer32,Unsigned32,IpAddress,
        enterprises,NOTIFICATION-TYPE
            FROM SNMPv2-SMI
        DisplayString,TruthValue,DateAndTime,
        TEXTUAL-CONVENTION
            FROM SNMPv2-TC
        InetAddressType, InetAddress
            FROM INET-ADDRESS-MIB
        Ipv6Address
            FROM IPV6-TC;

    trace MODULE-IDENTITY
        LAST-UPDATED "201408251939Z"
        ORGANIZATION "ZTE Corporation."
        CONTACT-INFO
            "       Zhao yanhua
            Tel:    +86-25-52870000
            E-Mail: zhao.yanhua3@zte.com.cn
            "
        DESCRIPTION
            "ZTE TRACE MIB
            "
        REVISION "201408251939Z"
        DESCRIPTION
            "Add     MactraceHopsResult;
             update  DESCRIPTION of zxr10LspTraceCtlTable;
                     DESCRIPTION of zxr10LspTraceCtlEntry;
                     DESCRIPTION of zxr10LspTraceResultsTabl;
                     DESCRIPTION of zxr10LspTraceHopsTable;
                     DESCRIPTION of zxr10MacTraceCtlTable;
                     DESCRIPTION of zxr10MacTraceHopsTable;
                     DESCRIPTION of zxr10TraceRouteCtlVrfType;
                     DESCRIPTION of lspTraceTrapResult;
                     DESCRIPTION of lspTraceTrapHops;
                     DESCRIPTION of macTraceTrapResult;
                     Zxr10MacTraceHopsEntry;
                     DESCRIPTION and SYNTAX of zxr10MacTraceHopsResultValidHop0;
                     DESCRIPTION and SYNTAX of zxr10MacTraceHopsResultValidHop1;
                     DESCRIPTION and SYNTAX of zxr10MacTraceHopsResultValidHop2;
                     DESCRIPTION and SYNTAX of zxr10MacTraceHopsResultValidHop3;
                     DESCRIPTION and SYNTAX of zxr10MacTraceHopsResultValidHop4;
                     DESCRIPTION and SYNTAX of zxr10MacTraceHopsResultValidHop5;
                     DESCRIPTION and SYNTAX of zxr10MacTraceHopsResultValidHop6;
                     DESCRIPTION and SYNTAX of zxr10MacTraceHopsResultValidHop7;
                     DESCRIPTION and SYNTAX of zxr10MacTraceHopsResultValidHop8;
                     DESCRIPTION and SYNTAX of zxr10MacTraceHopsResultValidHop9.
            "
        REVISION "201403071004Z"
        DESCRIPTION
            "Add     zxr10TraceRouteCtlDataSize
            "
        REVISION "201309051924Z"
        DESCRIPTION
            "Add     zxr10LspTraceCtlReplyMode for pw ping ttl tlv;
                     zxr10LspTraceHopsV6Addr for ipv6 trace;
                     zxr10LspTraceHopsV6Addr in lspTraceTrapHops 
                     for ipv6 trace;
                     zxr10LspTraceHopsResultValid in lspTraceTrapHops 
                     because it's omitted before
            "
        REVISION "201308080930Z"
        DESCRIPTION
            "Add description for zxr10MacTraceHopsEntryOwner
            "
        REVISION "201305310930Z"
        DESCRIPTION
            "update  zxr10LspTraceCtlPwDestAddr to obsolete
                     zxr10LspTraceCtlPwVcId to obsolete
                     zxr10LspTraceCtlPwType to obsolete
                     zxr10LspTraceCtlTraceType add v6ldp(3)
                     zxr10LspTraceCtlLspType add tunnel(3)
             fix comling error and update descriptions.
            "
            
        REVISION "201303191130Z"
        DESCRIPTION
            "Add trace MIB (zte.zxr10.trace.zxr10TraceRoute)
             Add    zxr10LspTraceCtlMultiSegment
                    zxr10LspTraceCtlLdpV6Prefix
                    zxr10LspTraceCtlLdpV6PrefixLen
                    zxr10LspTraceCtlOutInterface
                    zxr10LspTraceCtlLspType
                    zxr10LspTraceCtlSrcIpAddr
                    zxr10LspTraceCtlV6SrcIpAddr
                    zxr10LspTraceCtlDownstreamMapType
             fix comling error and update descriptions.
            "
        REVISION "200811240000Z"
        DESCRIPTION
            "Initial version of this MIB module.
            "
        ::= { zxr10 318 }

    zxr10LspTrace OBJECT IDENTIFIER ::= { trace 1 }

    zxr10MacTrace OBJECT IDENTIFIER ::= { trace 2 }

    zxr10TraceRoute OBJECT IDENTIFIER    ::= { trace 3 }

    lspTraceNotifications OBJECT IDENTIFIER ::= { zxr10LspTrace 4 }

    macTraceNotifications OBJECT IDENTIFIER ::= { zxr10MacTrace 4 }

    zxr10TraceRouteObjects OBJECT IDENTIFIER ::= { zxr10TraceRoute 1 }

    zte OBJECT IDENTIFIER ::= { enterprises 3902 }

    zxr10 OBJECT IDENTIFIER ::= { zte 3 }

    LspTraceType ::= TEXTUAL-CONVENTION
        STATUS       current
        DESCRIPTION
            "lsp trace type"
        SYNTAX      INTEGER {
                        ldp(0),
                        rsvpTe(1),
                        vccv(2),
                        v6ldp(3)
                    }

    LspTraceIfOption ::= TEXTUAL-CONVENTION
        STATUS       current
        DESCRIPTION
            "lsp trace option"
        SYNTAX      INTEGER {
                        none(0),
                        option(1)
                    }

    LspTracePwType ::= TEXTUAL-CONVENTION
        STATUS       current
        DESCRIPTION
            "lsp trace pw type"
        SYNTAX      INTEGER {
                        etherVlan(0),
                        ether(1)
                    }    


    TraceRosStatus ::= TEXTUAL-CONVENTION
        STATUS       current
        DESCRIPTION
            "The type used to crontrol tracing"
        SYNTAX      INTEGER {
                        notActive(1),
                        startTrace(2),
                        traceProcessing(3),
                        traceCompleted(4)
                    }

    TraceHopsResult ::= TEXTUAL-CONVENTION
        STATUS       current
        DESCRIPTION
            "The type of trace hop result"
        SYNTAX      INTEGER {
                        valid(0),
                        success(1),
                        downstreamRouterButNotTarget(2),
                        requestNotTransmitted(3),
                        timeout(4),
                        unreachable(5)
                    }
    
    MactraceHopsResult ::= TEXTUAL-CONVENTION
        STATUS       current
        DESCRIPTION
            "The type of mac trace hop result"
        SYNTAX      INTEGER {
                        valid(0),
                        success(1)
                    }

    HopType ::= TEXTUAL-CONVENTION
        STATUS       current
        DESCRIPTION
            "Hop type"
        SYNTAX      INTEGER {
                        ingress(0),
                        downstream(1),
                        egress(2)
                    }

    MacTraceIfPeOption ::= TEXTUAL-CONVENTION
        STATUS       current
        DESCRIPTION
            "if PE option of mac trace"
        SYNTAX      INTEGER {
                        ce(0),
                        pe(1)
                    }

--  ******************************************************
--                Lsp Trace Control Table
--  ******************************************************
    zxr10LspTraceCtlTable OBJECT-TYPE
              SYNTAX  SEQUENCE OF Zxr10LspTraceCtlEntry
              MAX-ACCESS  not-accessible
              STATUS  current
              DESCRIPTION
                      "the description of lsp trace information."
               ::= { zxr10LspTrace 1 }

    zxr10LspTraceCtlEntry  OBJECT-TYPE
              SYNTAX  Zxr10LspTraceCtlEntry
              MAX-ACCESS  not-accessible
              STATUS  current
              DESCRIPTION
                      "lsp trace control entry"
              INDEX  {
                        zxr10LspTraceCtlSerial
                     }
              ::= { zxr10LspTraceCtlTable 1 }

    Zxr10LspTraceCtlEntry ::=
              SEQUENCE {
                zxr10LspTraceCtlSerial
                    Integer32,
                zxr10LspTraceCtlTraceType
                    LspTraceType,
                zxr10LspTraceCtlLdpPrefix
                    IpAddress,
                zxr10LspTraceCtlLdpPrefixLength
                    Integer32,
                zxr10LspTraceCtlTeTunnelIfName
                    DisplayString,
                zxr10LspTraceCtlPwDestAddr
                    IpAddress,
                zxr10LspTraceCtlPwVcId
                    Unsigned32,
--                zxr10LspTraceCtlPwTTL 
--                    Integer32,
                zxr10LspTraceCtlIfOption
                    LspTraceIfOption,
                zxr10LspTraceCtlTimeOut
                    Integer32,
                zxr10LspTraceCtlTTL
                    Integer32,
                zxr10LspTraceCtlTrapOncompletion
                    TruthValue,
                zxr10LspTraceRosStatus
                    TraceRosStatus,
                zxr10LspTraceEntryOwner
                    DisplayString,
                zxr10LspTraceCtlPwType
                    LspTracePwType,
                zxr10LspTraceCtlPwName
                    DisplayString,
                zxr10LspTraceCtlMultiSegment
                    TruthValue,
                zxr10LspTraceCtlV6LdpPrefix
                    Ipv6Address,
                zxr10LspTraceCtlV6LdpPrefixLen
                    Integer32,
                zxr10LspTraceCtlOutInterface
                    DisplayString,
                zxr10LspTraceCtlLspType
                    INTEGER,
                zxr10LspTraceCtlSrcIpAddr
                    IpAddress,
                zxr10LspTraceCtlV6SrcIpAddr
                    Ipv6Address,
                zxr10LspTraceCtlDownstrMapType
                    INTEGER,
                zxr10LspTraceCtlReplyMode
                    INTEGER
              }

    zxr10LspTraceCtlSerial OBJECT-TYPE
              SYNTAX  Integer32
              MAX-ACCESS  read-only
              STATUS  current
              DESCRIPTION
                  "lsp trace control serial number"
              ::= { zxr10LspTraceCtlEntry 1 }

    zxr10LspTraceCtlTraceType OBJECT-TYPE
              SYNTAX  LspTraceType
              MAX-ACCESS  read-write
              STATUS  current
              DESCRIPTION
                  "lsp trace type (0:ldp, 1:rsvpTe, 2:vccv, 3:v6ldp)"
              ::= { zxr10LspTraceCtlEntry 2 }

    zxr10LspTraceCtlLdpPrefix OBJECT-TYPE
              SYNTAX  IpAddress
              MAX-ACCESS  read-write
              STATUS  current
              DESCRIPTION
                      "ldp prefix"
              ::= { zxr10LspTraceCtlEntry 3 }

    zxr10LspTraceCtlLdpPrefixLength OBJECT-TYPE
              SYNTAX  Integer32
              MAX-ACCESS  read-write
              STATUS  current
              DESCRIPTION
                      "ldp prefix length"
              ::= { zxr10LspTraceCtlEntry 4 }

     zxr10LspTraceCtlTeTunnelIfName OBJECT-TYPE
              SYNTAX  DisplayString(SIZE(0..32))
              MAX-ACCESS  read-write
              STATUS  current
              DESCRIPTION
                      "tunnel name "
              ::= { zxr10LspTraceCtlEntry 5 }
    zxr10LspTraceCtlPwDestAddr OBJECT-TYPE
              SYNTAX  IpAddress
              MAX-ACCESS  read-write
              STATUS  obsolete
              DESCRIPTION
                      "pw peer address"
              ::= { zxr10LspTraceCtlEntry 6 }
    zxr10LspTraceCtlPwVcId OBJECT-TYPE
              SYNTAX  Unsigned32 (1..4294967294)
              MAX-ACCESS  read-write
              STATUS  obsolete
              DESCRIPTION
                      "pw vcid"
              ::= { zxr10LspTraceCtlEntry 7 }

--    zxr10LspTraceCtlPwTTL OBJECT-TYPE
--              SYNTAX  Integer32 (1..255)
--              MAX-ACCESS  read-write
--              STATUS  current
--              DESCRIPTION
--                      "pw label ttl"   
--              DEFVAL  { 1 }
--              ::= { zxr10LspTraceCtlEntry 8 }   

    zxr10LspTraceCtlIfOption OBJECT-TYPE
              SYNTAX  LspTraceIfOption
              MAX-ACCESS  read-write
              STATUS  current
              DESCRIPTION
                      "if select option,default:none"
              ::= { zxr10LspTraceCtlEntry 9 }

    zxr10LspTraceCtlTimeOut OBJECT-TYPE
              SYNTAX  Integer32 (1..20)
              MAX-ACCESS  read-write
              STATUS  current
              DESCRIPTION
                      "timeout,default:3"
              ::= { zxr10LspTraceCtlEntry 10 }

    zxr10LspTraceCtlTTL OBJECT-TYPE
              SYNTAX  Integer32 (1..255)
              MAX-ACCESS  read-write
              STATUS  current
              DESCRIPTION
                      "ttl,default:30"
              ::= { zxr10LspTraceCtlEntry 11 }

    zxr10LspTraceCtlTrapOncompletion OBJECT-TYPE
              SYNTAX  TruthValue
              MAX-ACCESS  read-write
              STATUS  current
              DESCRIPTION
                      "if trap"
              ::= { zxr10LspTraceCtlEntry 12 }

    zxr10LspTraceRosStatus OBJECT-TYPE
              SYNTAX  TraceRosStatus
              MAX-ACCESS  read-write
              STATUS  current
              DESCRIPTION
                      "controls to start lsp trace"
              ::= { zxr10LspTraceCtlEntry 13 }

    zxr10LspTraceEntryOwner OBJECT-TYPE
              SYNTAX  DisplayString
              MAX-ACCESS  read-write
              STATUS  current
              DESCRIPTION
                  "entry owner"
              ::= { zxr10LspTraceCtlEntry 14 }

    zxr10LspTraceCtlPwType OBJECT-TYPE
              SYNTAX  LspTracePwType
              MAX-ACCESS  read-write
              STATUS  obsolete
              DESCRIPTION
                      "lsp pw type (0:etherVlan,1:ether)"
              DEFVAL       { 0 }  
              ::= { zxr10LspTraceCtlEntry 15 }

    zxr10LspTraceCtlPwName OBJECT-TYPE
        SYNTAX      DisplayString
        MAX-ACCESS  read-write
        STATUS      current
        DESCRIPTION
            "pw name"
        ::= { zxr10LspTraceCtlEntry 16 }

    zxr10LspTraceCtlMultiSegment OBJECT-TYPE
        SYNTAX      TruthValue
        MAX-ACCESS  read-write
        STATUS      current
        DESCRIPTION
            "Indicate if the pw is multi-segment or not."
        ::= { zxr10LspTraceCtlEntry 17 }

    zxr10LspTraceCtlV6LdpPrefix OBJECT-TYPE
        SYNTAX      Ipv6Address
        MAX-ACCESS  read-write
        STATUS      current
        DESCRIPTION
            "IPv6 ldp prefix"
        ::= { zxr10LspTraceCtlEntry 18 }

    zxr10LspTraceCtlV6LdpPrefixLen OBJECT-TYPE
        SYNTAX      Integer32 (0..128)
        MAX-ACCESS  read-write
        STATUS      current
        DESCRIPTION
            "IPv6 ldp prefix length"
        ::= { zxr10LspTraceCtlEntry 19 }

    zxr10LspTraceCtlOutInterface OBJECT-TYPE
        SYNTAX      DisplayString
        MAX-ACCESS  read-write
        STATUS      current
        DESCRIPTION
            "out-interface for tracing packets"
        ::= { zxr10LspTraceCtlEntry 20 }

    zxr10LspTraceCtlLspType OBJECT-TYPE
        SYNTAX      INTEGER { master(1), slave(2), tunnel(3) }
        MAX-ACCESS  read-write
        STATUS      current
        DESCRIPTION
            "te-tunnel lsp type"
        ::= { zxr10LspTraceCtlEntry 21 }

    zxr10LspTraceCtlSrcIpAddr OBJECT-TYPE
        SYNTAX      IpAddress
        MAX-ACCESS  read-write
        STATUS      current
        DESCRIPTION
            "Source IPv4 address for tracing"
        ::= { zxr10LspTraceCtlEntry 22 }

    zxr10LspTraceCtlV6SrcIpAddr OBJECT-TYPE
        SYNTAX      Ipv6Address
        MAX-ACCESS  read-write
        STATUS      current
        DESCRIPTION
            "Source IPv6 address for tracing"
        ::= { zxr10LspTraceCtlEntry 23 }

    zxr10LspTraceCtlDownstrMapType OBJECT-TYPE
        SYNTAX      INTEGER (0..1)
        MAX-ACCESS  read-write
        STATUS      current
        DESCRIPTION
            "Downstream mapping type
            - 0, Downstream Mapping in RFC4379
            - 1, Downstream Detailed Mapping in RFC6424"
        DEFVAL      { 0 }
        ::= { zxr10LspTraceCtlEntry 24 }

    zxr10LspTraceCtlReplyMode  OBJECT-TYPE
        SYNTAX      INTEGER  {
                       notReply(1),
                       ip(2),
                       routerAlert(3),
                       applicationChannel(4)
                    }
        MAX-ACCESS  read-write
        STATUS      current
        DESCRIPTION
            "The reply mode by the receiving router receive an MPLS echo request"
        DEFVAL      { 2 }
        ::= { zxr10LspTraceCtlEntry 25 }

-- *******************************************************
--               Lsp Trace Results Table
-- *******************************************************
    zxr10LspTraceResultsTable OBJECT-TYPE
              SYNTAX  SEQUENCE OF Zxr10LspTraceResultsEntry
              MAX-ACCESS  not-accessible
              STATUS  current
              DESCRIPTION
                      "the description of lsp trace results information"
               ::= { zxr10LspTrace 2 }

    zxr10LspTraceResultsEntry  OBJECT-TYPE
              SYNTAX  Zxr10LspTraceResultsEntry
              MAX-ACCESS  not-accessible
              STATUS  current
              DESCRIPTION
                      "lsp trace result entry"
              INDEX  {
                        zxr10LspTraceResultsSerial
                     }
              ::= { zxr10LspTraceResultsTable 1 }

    Zxr10LspTraceResultsEntry ::=
              SEQUENCE {
                zxr10LspTraceResultsSerial
                    Integer32,
                zxr10LspTraceResultsCurHopCount
                    Integer32,
                zxr10LspTraceResultsEntryOwner
                    DisplayString
              }

    zxr10LspTraceResultsSerial OBJECT-TYPE
              SYNTAX  Integer32
              MAX-ACCESS  read-only
              STATUS  current
              DESCRIPTION
                      "lsp trace result serial number"
              ::= { zxr10LspTraceResultsEntry 1 }

    zxr10LspTraceResultsCurHopCount OBJECT-TYPE
              SYNTAX  Integer32
              MAX-ACCESS  read-only
              STATUS  current
              DESCRIPTION
                      "valid hops count"
              ::= { zxr10LspTraceResultsEntry 2 }

    zxr10LspTraceResultsEntryOwner OBJECT-TYPE
              SYNTAX  DisplayString
              MAX-ACCESS  read-only
              STATUS  current
              DESCRIPTION
                      "entry owner"
              ::= { zxr10LspTraceResultsEntry 3 }

-- *******************************************************
--               Lsp Trace Hops Table
-- *******************************************************
    zxr10LspTraceHopsTable OBJECT-TYPE
              SYNTAX  SEQUENCE OF Zxr10LspTraceHopsEntry
              MAX-ACCESS  not-accessible
              STATUS  current
              DESCRIPTION
                      "the description of lsp trace hops information."
               ::= { zxr10LspTrace 3 }

    zxr10LspTraceHopsEntry  OBJECT-TYPE
              SYNTAX  Zxr10LspTraceHopsEntry
              MAX-ACCESS  not-accessible
              STATUS  current
              DESCRIPTION
                      "lsp trace hops entry"
              INDEX  {
                        zxr10LspTraceHopsSerial,
                        zxr10LspTraceHopsHopIndex
                     }
              ::= { zxr10LspTraceHopsTable 1 }

    Zxr10LspTraceHopsEntry ::=
              SEQUENCE {
                zxr10LspTraceHopsSerial
                    Integer32,
                zxr10LspTraceHopsHopIndex
                    Integer32,
                zxr10LspTraceHopsResultValid
                    TraceHopsResult,
                zxr10LspTraceHopsType
                    HopType,
                zxr10LspTraceHopsAddr
                    IpAddress,
                zxr10LspTraceHopsLabel
                    Integer32,
                zxr10LspTraceHopsMtu
                    Integer32,
                zxr10LspTraceHopsRtt
                    Integer32,
                zxr10LspTraceHopsV6Addr
                    Ipv6Address
              }

    zxr10LspTraceHopsSerial OBJECT-TYPE
              SYNTAX  Integer32
              MAX-ACCESS  read-only
              STATUS  current
              DESCRIPTION
                      "lsp trace hops serial number"
              ::= { zxr10LspTraceHopsEntry 1 }

    zxr10LspTraceHopsHopIndex OBJECT-TYPE
              SYNTAX  Integer32
              MAX-ACCESS  read-only
              STATUS  current
              DESCRIPTION
                      "Hop index"
              ::= { zxr10LspTraceHopsEntry 2 }

    zxr10LspTraceHopsResultValid OBJECT-TYPE
              SYNTAX  TraceHopsResult
              MAX-ACCESS  read-only
              STATUS  current
              DESCRIPTION
                      "Hop Result (0:valid,1:success,2:downstreamRouterButNotTarget,
                      3:requestNotTransmitted,4:timeout,5:unreachable)"
              ::= { zxr10LspTraceHopsEntry 3 }

    zxr10LspTraceHopsType OBJECT-TYPE
              SYNTAX  HopType
              MAX-ACCESS  read-only
              STATUS  current
              DESCRIPTION
                      "Hop Type (0:Ingress,1:Downstream,2:Egress)"
              ::= { zxr10LspTraceHopsEntry 4 }

    zxr10LspTraceHopsAddr OBJECT-TYPE
              SYNTAX  IpAddress
              MAX-ACCESS  read-only
              STATUS  current
              DESCRIPTION
                      "Hop Address"
              ::= { zxr10LspTraceHopsEntry 5 }

    zxr10LspTraceHopsLabel OBJECT-TYPE
              SYNTAX  Integer32
              MAX-ACCESS  read-only
              STATUS  current
              DESCRIPTION
                      "Hop Label"
              ::= { zxr10LspTraceHopsEntry 6 }

    zxr10LspTraceHopsMtu OBJECT-TYPE
              SYNTAX  Integer32
              MAX-ACCESS  read-only
              STATUS  current
              DESCRIPTION
                      "Hop Mtu"
              ::= { zxr10LspTraceHopsEntry 7 }

    zxr10LspTraceHopsRtt OBJECT-TYPE
              SYNTAX  Integer32
              MAX-ACCESS  read-only
              STATUS  current
              DESCRIPTION
                      "Hop Rtt"
              ::= { zxr10LspTraceHopsEntry 8 }

    zxr10LspTraceHopsV6Addr OBJECT-TYPE
              SYNTAX  Ipv6Address
              MAX-ACCESS  read-only
              STATUS  current
              DESCRIPTION
                      "IPv6 hop address"
              ::= { zxr10LspTraceHopsEntry 9 }


-- *******************************************************
--               Lsp Trace Result Trap Definitions
-- *******************************************************
    lspTraceTrapResult NOTIFICATION-TYPE
     OBJECTS  { zxr10LspTraceResultsSerial,
                zxr10LspTraceResultsCurHopCount,
                zxr10LspTraceResultsEntryOwner
              }
              STATUS  current
              DESCRIPTION
         "The object will return a value while trace finish."
     ::= { lspTraceNotifications 1 }

-- *******************************************************
--               Lsp Trace Hops Trap Definitions
-- *******************************************************
    lspTraceTrapHops NOTIFICATION-TYPE
     OBJECTS  { zxr10LspTraceHopsSerial,
                zxr10LspTraceHopsHopIndex,
                zxr10LspTraceHopsResultValid,
                zxr10LspTraceHopsType,
                zxr10LspTraceHopsAddr,
                zxr10LspTraceHopsLabel,
                zxr10LspTraceHopsMtu,
                zxr10LspTraceHopsRtt,
                zxr10LspTraceHopsV6Addr
              }
     STATUS  current
     DESCRIPTION
         "The object will return a value while trace finish."
     ::= { lspTraceNotifications 2 }

--  ******************************************************
--                Mac Trace Control Table
--  ******************************************************
    zxr10MacTraceCtlTable OBJECT-TYPE
              SYNTAX  SEQUENCE OF Zxr10MacTraceCtlEntry
              MAX-ACCESS  not-accessible
              STATUS  current
              DESCRIPTION
                      "the description of mac trace information."
               ::= { zxr10MacTrace 1 }

    zxr10MacTraceCtlEntry  OBJECT-TYPE
              SYNTAX  Zxr10MacTraceCtlEntry
              MAX-ACCESS  not-accessible
              STATUS  current
              DESCRIPTION
                      "mac trace control entry"
              INDEX  {
                        zxr10MacTraceCtlSerial
                     }
              ::= { zxr10MacTraceCtlTable 1 }

    Zxr10MacTraceCtlEntry ::=
              SEQUENCE {
                zxr10MacTraceCtlSerial
                    Integer32,
                zxr10MacTraceCtlDestMac
                    DisplayString,
                zxr10MacTraceCtlIfPeOption
                    MacTraceIfPeOption,
                zxr10MacTraceCtlOutEtherIfIndex
                    Integer32,
                zxr10MacTraceCtlVfiName
                    DisplayString,
                zxr10MacTraceCtlPeerAddress
                    IpAddress,
                zxr10MacTraceCtlVlanCount
                    Integer32,
                zxr10MacTraceCtlInternalVlanId
                    Integer32,
                zxr10MacTraceCtlExternalVlanId
                    Integer32,
                zxr10MacTraceCtlTrapOncompletion
                    TruthValue,
                zxr10MacTraceCtlRosStatus
                    TraceRosStatus,
                zxr10MacTraceCtlEntryOwner
                    DisplayString
              }

    zxr10MacTraceCtlSerial OBJECT-TYPE
              SYNTAX  Integer32
              MAX-ACCESS  read-only
              STATUS  current
              DESCRIPTION
                      "mac trace control serial number"
              ::= { zxr10MacTraceCtlEntry 1 }

    zxr10MacTraceCtlDestMac OBJECT-TYPE
              SYNTAX  DisplayString
              MAX-ACCESS  read-write
              STATUS  current
              DESCRIPTION
                      "destination mac address"
              ::= { zxr10MacTraceCtlEntry 2 }

    zxr10MacTraceCtlIfPeOption OBJECT-TYPE
              SYNTAX  MacTraceIfPeOption
              MAX-ACCESS  read-write
              STATUS  current
              DESCRIPTION
                      "if PE option (0:CE,1:PE)"
              ::= { zxr10MacTraceCtlEntry 3 }

    zxr10MacTraceCtlOutEtherIfIndex OBJECT-TYPE
              SYNTAX  Integer32
              MAX-ACCESS  read-write
              STATUS  current
              DESCRIPTION
                      "index of out interface on CE"
              ::= { zxr10MacTraceCtlEntry 4 }

    zxr10MacTraceCtlVfiName OBJECT-TYPE
              SYNTAX  DisplayString
              MAX-ACCESS  read-write
              STATUS  current
              DESCRIPTION
                      "VFI name"
              ::= { zxr10MacTraceCtlEntry 5 }

    zxr10MacTraceCtlPeerAddress OBJECT-TYPE
              SYNTAX  IpAddress
              MAX-ACCESS  read-write
              STATUS  current
              DESCRIPTION
                      "Peer Address"
              ::= { zxr10MacTraceCtlEntry 6 }

    zxr10MacTraceCtlVlanCount OBJECT-TYPE
              SYNTAX  Integer32
              MAX-ACCESS  read-write
              STATUS  current
              DESCRIPTION
                      "vlan count"
              ::= { zxr10MacTraceCtlEntry 7 }

    zxr10MacTraceCtlInternalVlanId OBJECT-TYPE
              SYNTAX  Integer32
              MAX-ACCESS  read-write
              STATUS  current
              DESCRIPTION
                      "Internal VlanId"
              ::= { zxr10MacTraceCtlEntry 8 }

    zxr10MacTraceCtlExternalVlanId OBJECT-TYPE
              SYNTAX  Integer32
              MAX-ACCESS  read-write
              STATUS  current
              DESCRIPTION
                      "External VlanId"
              ::= { zxr10MacTraceCtlEntry 9 }

    zxr10MacTraceCtlTrapOncompletion OBJECT-TYPE
              SYNTAX  TruthValue
              MAX-ACCESS  read-write
              STATUS  current
              DESCRIPTION
                      "if trap"
              ::= { zxr10MacTraceCtlEntry 10 }

    zxr10MacTraceCtlRosStatus OBJECT-TYPE
              SYNTAX  TraceRosStatus
              MAX-ACCESS  read-write
              STATUS  current
              DESCRIPTION
                      "control to start mac trace"
              ::= { zxr10MacTraceCtlEntry 11 }

    zxr10MacTraceCtlEntryOwner OBJECT-TYPE
              SYNTAX  DisplayString
              MAX-ACCESS  read-write
              STATUS  current
              DESCRIPTION
                      "entry owner"
              ::= { zxr10MacTraceCtlEntry 12 }

-- *******************************************************
--               Mac Trace Result Table
-- *******************************************************
    zxr10MacTraceHopsTable OBJECT-TYPE
              SYNTAX  SEQUENCE OF Zxr10MacTraceHopsEntry
              MAX-ACCESS  not-accessible
              STATUS  current
              DESCRIPTION
                      "the description of mac trace hops information."
               ::= { zxr10MacTrace 2 }

    zxr10MacTraceHopsEntry  OBJECT-TYPE
              SYNTAX  Zxr10MacTraceHopsEntry
              MAX-ACCESS  not-accessible
              STATUS  current
              DESCRIPTION
                      "mac trace hops entry"
              INDEX  {
                        zxr10MacTraceHopsSerial
                     }
              ::= { zxr10MacTraceHopsTable 1 }

    Zxr10MacTraceHopsEntry ::=
              SEQUENCE {
                zxr10MacTraceHopsSerial
                    Integer32,
                zxr10MacTraceHopsResultValidHop0
                    MactraceHopsResult,
                zxr10MacTraceHopsHostNameHop0
                    DisplayString,
                zxr10MacTraceHopsIfNameHop0
                    DisplayString,
                zxr10MacTraceHopsMacAddrHop0
                    DisplayString,
                zxr10MacTraceHopsResultValidHop1
                    MactraceHopsResult,
                zxr10MacTraceHopsHostNameHop1
                    DisplayString,
                zxr10MacTraceHopsIfNameHop1
                    DisplayString,
                zxr10MacTraceHopsMacAddrHop1
                    DisplayString,
                zxr10MacTraceHopsResultValidHop2
                    MactraceHopsResult,
                zxr10MacTraceHopsHostNameHop2
                    DisplayString,
                zxr10MacTraceHopsIfNameHop2
                    DisplayString,
                zxr10MacTraceHopsMacAddrHop2
                    DisplayString,
                zxr10MacTraceHopsResultValidHop3
                    MactraceHopsResult,
                zxr10MacTraceHopsHostNameHop3
                    DisplayString,
                zxr10MacTraceHopsIfNameHop3
                    DisplayString,
                zxr10MacTraceHopsMacAddrHop3
                    DisplayString,
                zxr10MacTraceHopsResultValidHop4
                    MactraceHopsResult,
                zxr10MacTraceHopsHostNameHop4
                    DisplayString,
                zxr10MacTraceHopsIfNameHop4
                    DisplayString,
                zxr10MacTraceHopsMacAddrHop4
                    DisplayString,
                zxr10MacTraceHopsResultValidHop5
                    MactraceHopsResult,
                zxr10MacTraceHopsHostNameHop5
                    DisplayString,
                zxr10MacTraceHopsIfNameHop5
                    DisplayString,
                zxr10MacTraceHopsMacAddrHop5
                    DisplayString,
                zxr10MacTraceHopsResultValidHop6
                    MactraceHopsResult,
                zxr10MacTraceHopsHostNameHop6
                    DisplayString,
                zxr10MacTraceHopsIfNameHop6
                    DisplayString,
                zxr10MacTraceHopsMacAddrHop6
                    DisplayString,
                zxr10MacTraceHopsResultValidHop7
                    MactraceHopsResult,
                zxr10MacTraceHopsHostNameHop7
                    DisplayString,
                zxr10MacTraceHopsIfNameHop7
                    DisplayString,
                zxr10MacTraceHopsMacAddrHop7
                    DisplayString,
                zxr10MacTraceHopsResultValidHop8
                    MactraceHopsResult,
                zxr10MacTraceHopsHostNameHop8
                    DisplayString,
                zxr10MacTraceHopsIfNameHop8
                    DisplayString,
                zxr10MacTraceHopsMacAddrHop8
                    DisplayString,
                zxr10MacTraceHopsResultValidHop9
                    MactraceHopsResult,
                zxr10MacTraceHopsHostNameHop9
                    DisplayString,
                zxr10MacTraceHopsIfNameHop9
                    DisplayString,
                zxr10MacTraceHopsMacAddrHop9
                    DisplayString,
                zxr10MacTraceHopsEntryOwner
                    DisplayString
              }

    zxr10MacTraceHopsSerial OBJECT-TYPE
              SYNTAX  Integer32
              MAX-ACCESS  read-only
              STATUS  current
              DESCRIPTION
                      "mac trace hops serial number"
              ::= { zxr10MacTraceHopsEntry 1 }

    zxr10MacTraceHopsResultValidHop0 OBJECT-TYPE
              SYNTAX  MactraceHopsResult
              MAX-ACCESS  read-only
              STATUS  current
              DESCRIPTION
                      "Hop0 Result (0:valid,1:success)"
              ::= { zxr10MacTraceHopsEntry 2 }

    zxr10MacTraceHopsHostNameHop0 OBJECT-TYPE
              SYNTAX  DisplayString
              MAX-ACCESS  read-only
              STATUS  current
              DESCRIPTION
                      "Hop0 Host Name"
              ::= { zxr10MacTraceHopsEntry 3 }

    zxr10MacTraceHopsIfNameHop0 OBJECT-TYPE
              SYNTAX  DisplayString
              MAX-ACCESS  read-only
              STATUS  current
              DESCRIPTION
                      "Hop0 Interface Name"
              ::= { zxr10MacTraceHopsEntry 4 }

    zxr10MacTraceHopsMacAddrHop0 OBJECT-TYPE
              SYNTAX  DisplayString
              MAX-ACCESS  read-only
              STATUS  current
              DESCRIPTION
                      "Hop0 Mac Address"
              ::= { zxr10MacTraceHopsEntry 5 }

    zxr10MacTraceHopsResultValidHop1 OBJECT-TYPE
              SYNTAX  MactraceHopsResult
              MAX-ACCESS  read-only
              STATUS  current
              DESCRIPTION
                      "Hop1 Result (0:valid,1:success)"
              ::= { zxr10MacTraceHopsEntry 6 }

    zxr10MacTraceHopsHostNameHop1 OBJECT-TYPE
              SYNTAX  DisplayString
              MAX-ACCESS  read-only
              STATUS  current
              DESCRIPTION
                      "Hop1 Host Name"
              ::= { zxr10MacTraceHopsEntry 7 }

    zxr10MacTraceHopsIfNameHop1 OBJECT-TYPE
              SYNTAX  DisplayString
              MAX-ACCESS  read-only
              STATUS  current
              DESCRIPTION
                      "Hop1 Interface Name"
              ::= { zxr10MacTraceHopsEntry 8 }

    zxr10MacTraceHopsMacAddrHop1 OBJECT-TYPE
              SYNTAX  DisplayString
              MAX-ACCESS  read-only
              STATUS  current
              DESCRIPTION
                      "Hop1 Mac Address"
              ::= { zxr10MacTraceHopsEntry 9 }

    zxr10MacTraceHopsResultValidHop2 OBJECT-TYPE
              SYNTAX  MactraceHopsResult
              MAX-ACCESS  read-only
              STATUS  current
              DESCRIPTION
                      "Hop2 Result (0:valid,1:success)"
              ::= { zxr10MacTraceHopsEntry 10 }

    zxr10MacTraceHopsHostNameHop2 OBJECT-TYPE
              SYNTAX  DisplayString
              MAX-ACCESS  read-only
              STATUS  current
              DESCRIPTION
                      "Hop2 Host Name"
              ::= { zxr10MacTraceHopsEntry 11 }

    zxr10MacTraceHopsIfNameHop2 OBJECT-TYPE
              SYNTAX  DisplayString
              MAX-ACCESS  read-only
              STATUS  current
              DESCRIPTION
                      "Hop2 Interface Name"
              ::= { zxr10MacTraceHopsEntry 12 }

    zxr10MacTraceHopsMacAddrHop2 OBJECT-TYPE
              SYNTAX  DisplayString
              MAX-ACCESS  read-only
              STATUS  current
              DESCRIPTION
                      "Hop2 Mac Address"
              ::= { zxr10MacTraceHopsEntry 13 }

    zxr10MacTraceHopsResultValidHop3 OBJECT-TYPE
              SYNTAX  MactraceHopsResult
              MAX-ACCESS  read-only
              STATUS  current
              DESCRIPTION
                      "Hop3 Result (0:valid,1:success)"
              ::= { zxr10MacTraceHopsEntry 14 }

    zxr10MacTraceHopsHostNameHop3 OBJECT-TYPE
              SYNTAX  DisplayString
              MAX-ACCESS  read-only
              STATUS  current
              DESCRIPTION
                      "Hop3 Host Name"
              ::= { zxr10MacTraceHopsEntry 15 }

    zxr10MacTraceHopsIfNameHop3 OBJECT-TYPE
              SYNTAX  DisplayString
              MAX-ACCESS  read-only
              STATUS  current
              DESCRIPTION
                      "Hop3 Interface Name"
              ::= { zxr10MacTraceHopsEntry 16 }

    zxr10MacTraceHopsMacAddrHop3 OBJECT-TYPE
              SYNTAX  DisplayString
              MAX-ACCESS  read-only
              STATUS  current
              DESCRIPTION
                      "Hop3 Mac Address"
              ::= { zxr10MacTraceHopsEntry 17 }

    zxr10MacTraceHopsResultValidHop4 OBJECT-TYPE
              SYNTAX  MactraceHopsResult
              MAX-ACCESS  read-only
              STATUS  current
              DESCRIPTION
                      "Hop4 Result (0:valid,1:success)"
              ::= { zxr10MacTraceHopsEntry 18 }

    zxr10MacTraceHopsHostNameHop4 OBJECT-TYPE
              SYNTAX  DisplayString
              MAX-ACCESS  read-only
              STATUS  current
              DESCRIPTION
                      "Hop4 Host Name"
              ::= { zxr10MacTraceHopsEntry 19 }

    zxr10MacTraceHopsIfNameHop4 OBJECT-TYPE
              SYNTAX  DisplayString
              MAX-ACCESS  read-only
              STATUS  current
              DESCRIPTION
                      "Hop4 Interface Name"
              ::= { zxr10MacTraceHopsEntry 20 }

    zxr10MacTraceHopsMacAddrHop4 OBJECT-TYPE
              SYNTAX  DisplayString
              MAX-ACCESS  read-only
              STATUS  current
              DESCRIPTION
                      "Hop4 Mac Address"
              ::= { zxr10MacTraceHopsEntry 21 }

    zxr10MacTraceHopsResultValidHop5 OBJECT-TYPE
              SYNTAX  MactraceHopsResult
              MAX-ACCESS  read-only
              STATUS  current
              DESCRIPTION
                      "Hop5 Result (0:valid,1:success)"
              ::= { zxr10MacTraceHopsEntry 22 }

    zxr10MacTraceHopsHostNameHop5 OBJECT-TYPE
              SYNTAX  DisplayString
              MAX-ACCESS  read-only
              STATUS  current
              DESCRIPTION
                      "Hop5 Host Name"
              ::= { zxr10MacTraceHopsEntry 23 }

    zxr10MacTraceHopsIfNameHop5 OBJECT-TYPE
              SYNTAX  DisplayString
              MAX-ACCESS  read-only
              STATUS  current
              DESCRIPTION
                      "Hop5 Interface Name"
              ::= { zxr10MacTraceHopsEntry 24 }

    zxr10MacTraceHopsMacAddrHop5 OBJECT-TYPE
              SYNTAX  DisplayString
              MAX-ACCESS  read-only
              STATUS  current
              DESCRIPTION
                      "Hop5 Mac Address"
              ::= { zxr10MacTraceHopsEntry 25 }

    zxr10MacTraceHopsResultValidHop6 OBJECT-TYPE
              SYNTAX  MactraceHopsResult
              MAX-ACCESS  read-only
              STATUS  current
              DESCRIPTION
                      "Hop6 Result (0:valid,1:success)"
              ::= { zxr10MacTraceHopsEntry 26 }

    zxr10MacTraceHopsHostNameHop6 OBJECT-TYPE
              SYNTAX  DisplayString
              MAX-ACCESS  read-only
              STATUS  current
              DESCRIPTION
                      "Hop6 Host Name"
              ::= { zxr10MacTraceHopsEntry 27 }

    zxr10MacTraceHopsIfNameHop6 OBJECT-TYPE
              SYNTAX  DisplayString
              MAX-ACCESS  read-only
              STATUS  current
              DESCRIPTION
                      "Hop6 Interface Name"
              ::= { zxr10MacTraceHopsEntry 28 }

    zxr10MacTraceHopsMacAddrHop6 OBJECT-TYPE
              SYNTAX  DisplayString
              MAX-ACCESS  read-only
              STATUS  current
              DESCRIPTION
                      "Hop6 Mac Address"
              ::= { zxr10MacTraceHopsEntry 29 }

    zxr10MacTraceHopsResultValidHop7 OBJECT-TYPE
              SYNTAX  MactraceHopsResult
              MAX-ACCESS  read-only
              STATUS  current
              DESCRIPTION
                      "Hop7 Result (0:valid,1:success)"
              ::= { zxr10MacTraceHopsEntry 30 }

    zxr10MacTraceHopsHostNameHop7 OBJECT-TYPE
              SYNTAX  DisplayString
              MAX-ACCESS  read-only
              STATUS  current
              DESCRIPTION
                      "Hop7 Host Name"
              ::= { zxr10MacTraceHopsEntry 31 }

    zxr10MacTraceHopsIfNameHop7 OBJECT-TYPE
              SYNTAX  DisplayString
              MAX-ACCESS  read-only
              STATUS  current
              DESCRIPTION
                      "Hop7 Interface Name"
              ::= { zxr10MacTraceHopsEntry 32 }

    zxr10MacTraceHopsMacAddrHop7 OBJECT-TYPE
              SYNTAX  DisplayString
              MAX-ACCESS  read-only
              STATUS  current
              DESCRIPTION
                      "Hop7 Mac Address"
              ::= { zxr10MacTraceHopsEntry 33 }

    zxr10MacTraceHopsResultValidHop8 OBJECT-TYPE
              SYNTAX  MactraceHopsResult
              MAX-ACCESS  read-only
              STATUS  current
              DESCRIPTION
                      "Hop8 Result (0:valid,1:success)"
              ::= { zxr10MacTraceHopsEntry 34 }

    zxr10MacTraceHopsHostNameHop8 OBJECT-TYPE
              SYNTAX  DisplayString
              MAX-ACCESS  read-only
              STATUS  current
              DESCRIPTION
                      "Hop8 Host Name"
              ::= { zxr10MacTraceHopsEntry 35 }

    zxr10MacTraceHopsIfNameHop8 OBJECT-TYPE
              SYNTAX  DisplayString
              MAX-ACCESS  read-only
              STATUS  current
              DESCRIPTION
                      "Hop8 Interface Name"
              ::= { zxr10MacTraceHopsEntry 36 }

    zxr10MacTraceHopsMacAddrHop8 OBJECT-TYPE
              SYNTAX  DisplayString
              MAX-ACCESS  read-only
              STATUS  current
              DESCRIPTION
                      "Hop8 Mac Address"
              ::= { zxr10MacTraceHopsEntry 37 }

    zxr10MacTraceHopsResultValidHop9 OBJECT-TYPE
              SYNTAX  MactraceHopsResult
              MAX-ACCESS  read-only
              STATUS  current
              DESCRIPTION
                      "Hop9 Result (0:valid,1:success)"
              ::= { zxr10MacTraceHopsEntry 38 }

    zxr10MacTraceHopsHostNameHop9 OBJECT-TYPE
              SYNTAX  DisplayString
              MAX-ACCESS  read-only
              STATUS  current
              DESCRIPTION
                      "Hop9 Host Name"
              ::= { zxr10MacTraceHopsEntry 39 }

    zxr10MacTraceHopsIfNameHop9 OBJECT-TYPE
              SYNTAX  DisplayString
              MAX-ACCESS  read-only
              STATUS  current
              DESCRIPTION
                      "Hop9 Interface Name"
              ::= { zxr10MacTraceHopsEntry 40 }

    zxr10MacTraceHopsMacAddrHop9 OBJECT-TYPE
              SYNTAX  DisplayString
              MAX-ACCESS  read-only
              STATUS  current
              DESCRIPTION
                      "Hop9 Mac Address"
              ::= { zxr10MacTraceHopsEntry 41 }

    zxr10MacTraceHopsEntryOwner OBJECT-TYPE
              SYNTAX  DisplayString
              MAX-ACCESS  read-only
              STATUS  current
              DESCRIPTION
                      "Hop entry owner"
              ::= { zxr10MacTraceHopsEntry 42 }

-- *******************************************************
--                Mac Trace Trap Definitions
-- *******************************************************
    macTraceTrapResult NOTIFICATION-TYPE
     OBJECTS  { zxr10MacTraceHopsSerial,
                zxr10MacTraceHopsResultValidHop0,
                zxr10MacTraceHopsHostNameHop0,
                zxr10MacTraceHopsIfNameHop0,
                zxr10MacTraceHopsMacAddrHop0,
                zxr10MacTraceHopsResultValidHop1,
                zxr10MacTraceHopsHostNameHop1,
                zxr10MacTraceHopsIfNameHop1,
                zxr10MacTraceHopsMacAddrHop1,
                zxr10MacTraceHopsResultValidHop2,
                zxr10MacTraceHopsHostNameHop2,
                zxr10MacTraceHopsIfNameHop2,
                zxr10MacTraceHopsMacAddrHop2,
                zxr10MacTraceHopsResultValidHop3,
                zxr10MacTraceHopsHostNameHop3,
                zxr10MacTraceHopsIfNameHop3,
                zxr10MacTraceHopsMacAddrHop3,
                zxr10MacTraceHopsResultValidHop4,
                zxr10MacTraceHopsHostNameHop4,
                zxr10MacTraceHopsIfNameHop4,
                zxr10MacTraceHopsMacAddrHop4,
                zxr10MacTraceHopsResultValidHop5,
                zxr10MacTraceHopsHostNameHop5,
                zxr10MacTraceHopsIfNameHop5,
                zxr10MacTraceHopsMacAddrHop5,
                zxr10MacTraceHopsResultValidHop6,
                zxr10MacTraceHopsHostNameHop6,
                zxr10MacTraceHopsIfNameHop6,
                zxr10MacTraceHopsMacAddrHop6,
                zxr10MacTraceHopsResultValidHop7,
                zxr10MacTraceHopsHostNameHop7,
                zxr10MacTraceHopsIfNameHop7,
                zxr10MacTraceHopsMacAddrHop7,
                zxr10MacTraceHopsResultValidHop8,
                zxr10MacTraceHopsHostNameHop8,
                zxr10MacTraceHopsIfNameHop8,
                zxr10MacTraceHopsMacAddrHop8,
                zxr10MacTraceHopsResultValidHop9,
                zxr10MacTraceHopsHostNameHop9,
                zxr10MacTraceHopsIfNameHop9,
                zxr10MacTraceHopsMacAddrHop9,
                zxr10MacTraceHopsEntryOwner
              }
     STATUS  current
     DESCRIPTION
         "The object will return a value while trace finish."
     ::= { macTraceNotifications 1 }

-- *******************************************************
--                Trace Control Table
-- *******************************************************

    zxr10TraceRouteCtlTable OBJECT-TYPE
        SYNTAX      SEQUENCE OF Zxr10TraceRouteCtlEntry
        MAX-ACCESS  not-accessible
        STATUS      current
        DESCRIPTION
            "Defines the Remote Operations Traceroute Control Table for
            providing the capability of invoking traceroute from a remote
            host.  The results of traceroute operations can be stored in
            the zxr10TraceRouteResultsTable, and the zxr10TraceRouteHopsTable."
        ::= { zxr10TraceRouteObjects 1 }

    zxr10TraceRouteCtlEntry OBJECT-TYPE
        SYNTAX      Zxr10TraceRouteCtlEntry
        MAX-ACCESS  not-accessible
        STATUS      current
        DESCRIPTION
            "Defines an entry in the zxr10TraceRouteCtlTable.  The index
            element, zxr10TraceRouteCtlSerial, is of type Integer32, limited
            to 100 entries."
       INDEX {
               zxr10TraceRouteCtlSerial
             }
       ::= { zxr10TraceRouteCtlTable 1 }

    Zxr10TraceRouteCtlEntry ::=
        SEQUENCE {
            zxr10TraceRouteCtlSerial        Integer32,
            zxr10TraceRouteCtlTraceType     INTEGER,
            zxr10TraceRouteCtlIpAddrType    InetAddressType,
            zxr10TraceRouteCtlTgtAddr       InetAddress,
            zxr10TraceRouteCtlDomainName    DisplayString,
            zxr10TraceRouteCtlVrfType       INTEGER,
            zxr10TraceRouteCtlVrfName       DisplayString,
            zxr10TraceRouteCtlMaxTtl        Unsigned32,
            zxr10TraceRouteCtlTimeOut       Unsigned32,
            zxr10TraceRouteCtlProbPerHop    Unsigned32,
            zxr10TraceRouteCtlSrcAddr       InetAddress,
            zxr10TraceRouteCtlGenHopEntry   TruthValue,
            zxr10TraceRouteCtlRowStatus     INTEGER,
            zxr10TraceRouteCtlDataSize      Unsigned32
       }

    zxr10TraceRouteCtlSerial OBJECT-TYPE
        SYNTAX      Integer32
        MAX-ACCESS  not-accessible
        STATUS      current
        DESCRIPTION
          "serial number"
        ::= { zxr10TraceRouteCtlEntry 1 }

     zxr10TraceRouteCtlTraceType OBJECT-TYPE
        SYNTAX      INTEGER { ip(1),domain(2) }
        MAX-ACCESS  read-create
        STATUS      current
        DESCRIPTION
           "The type of a traceroute destination.
             1: IP address, uses zxr10TraceRouteCtlTgtAddr
             2: domain name, uses zxr10TraceRouteCtlDomainName"
        DEFVAL      { 1 }
        ::= { zxr10TraceRouteCtlEntry 2 }

     zxr10TraceRouteCtlIpAddrType OBJECT-TYPE
        SYNTAX      InetAddressType
        MAX-ACCESS  read-create
        STATUS      current
        DESCRIPTION
           "Specifies the IP address type for the traceroute
           request, including zxr10TraceRouteCtlDstAddr
           and zxr10TraceRouteCtlSrcAddr."
        ::= { zxr10TraceRouteCtlEntry 3 }

    zxr10TraceRouteCtlTgtAddr OBJECT-TYPE
        SYNTAX      InetAddress
        MAX-ACCESS  read-create
        STATUS      current
        DESCRIPTION
            "Specifies the host address used on the traceroute
            request at the remote host."
        ::= { zxr10TraceRouteCtlEntry 4 }

    zxr10TraceRouteCtlDomainName OBJECT-TYPE
        SYNTAX      DisplayString (SIZE(0..128))
        MAX-ACCESS  read-create
        STATUS      current
        DESCRIPTION
            "The name of a traceroute domain. This is locally unique,
            within the scope of a zxr10TraceRouteCtlSerial."
        ::= { zxr10TraceRouteCtlEntry 5 }

    zxr10TraceRouteCtlVrfType OBJECT-TYPE
        SYNTAX      INTEGER { noneVrf(1), normalVrf(2), dcnVrf(3) }
        MAX-ACCESS  read-create
        STATUS      current
        DESCRIPTION
            "Controls the vrf type of traceroute test. This is locally
            unique, within the scope of a zxr10TraceRouteCtlSerial.
              1: not vrf
              2: normal vrf, uses zxr10TraceRouteCtlVrfName
              3: dcn vrf, the vrf name is ?_dcn
            "
        DEFVAL { noneVrf }
        ::= { zxr10TraceRouteCtlEntry 6 }

    zxr10TraceRouteCtlVrfName OBJECT-TYPE
        SYNTAX      DisplayString (SIZE(0..32))
        MAX-ACCESS  read-create
        STATUS      current
        DESCRIPTION
            "The name of a traceroute vrf. This is locally unique,
            within the scope of a zxr10TraceRouteCtlSerial."
        ::= { zxr10TraceRouteCtlEntry 7 }

    zxr10TraceRouteCtlMaxTtl OBJECT-TYPE
        SYNTAX      Unsigned32 (1..255)
        MAX-ACCESS  read-create
        STATUS      current
        DESCRIPTION
            "Specifies the maximum time-to-live value."
        DEFVAL { 30 }
        ::= { zxr10TraceRouteCtlEntry 8 }

    zxr10TraceRouteCtlTimeOut OBJECT-TYPE
        SYNTAX      Unsigned32 (1..60)
        MAX-ACCESS  read-create
        STATUS      current
        DESCRIPTION
            "Specifies the time-out value, in seconds, for
            a traceroute request."
        DEFVAL { 3 }
        ::= { zxr10TraceRouteCtlEntry 9 }

    zxr10TraceRouteCtlProbPerHop OBJECT-TYPE
       SYNTAX      Unsigned32 (1..10)
       MAX-ACCESS  read-create
       STATUS      current
       DESCRIPTION
           "Specifies the number of times to reissue a traceroute
           request with the same time-to-live (TTL) value."
       DEFVAL { 3 }
       ::= { zxr10TraceRouteCtlEntry 10 }

    zxr10TraceRouteCtlSrcAddr OBJECT-TYPE
        SYNTAX      InetAddress
        MAX-ACCESS  read-create
        STATUS      current
        DESCRIPTION
            "Use the specified IP address (which must be given as an
            IP number, not a hostname) as the source address in
            outgoing probe packets.  On hosts with more than one IP
            address, this option can be used to select the address
            to be used.  If the IP address is not one of this
            machine's interface addresses, an error is returned, and
            nothing is sent.  A zero-length octet string value for
            this object disables source address specification."
        ::= { zxr10TraceRouteCtlEntry 11 }

    zxr10TraceRouteCtlGenHopEntry OBJECT-TYPE
        SYNTAX      TruthValue
        MAX-ACCESS  read-create
        STATUS      current
        DESCRIPTION
            "The current path for a traceroute test is kept in the
            zxr10TraceRouteHopsTable on a per-hop basis when the value
            of this object is true(1)."
        DEFVAL { false }
        ::= { zxr10TraceRouteCtlEntry 12 }

    zxr10TraceRouteCtlRowStatus OBJECT-TYPE
        SYNTAX      INTEGER {
                        notActive(1),
                        startTrace(2),
                        traceProcessing(3),
                        traceCompleted(4),
                        destroy(5)
                    }
        MAX-ACCESS  read-create
        STATUS      current
        DESCRIPTION
            "This object allows to start tracing or destroy entries
            in the zxr10TraceRouteCtlTable."
        ::= { zxr10TraceRouteCtlEntry 13 }

    zxr10TraceRouteCtlDataSize OBJECT-TYPE
       SYNTAX      Unsigned32 (36..8192)
       MAX-ACCESS  read-create
       STATUS      current
       DESCRIPTION
           "Specifies the size of the data portion of a traceroute
           request, in octets.
           The value for this object includes IP header size and 
           UDP header size."
       DEFVAL { 100 }
       ::= { zxr10TraceRouteCtlEntry 14 }

-- *******************************************************
--                Trace Result Table
-- *******************************************************

    zxr10TraceRouteResultsTable OBJECT-TYPE
        SYNTAX      SEQUENCE OF Zxr10TraceRouteResultsEntry
        MAX-ACCESS  not-accessible
        STATUS      current
        DESCRIPTION
            "Defines the Remote Operations Traceroute Results Table for
            keeping track of the status of a zxr10TraceRouteCtlEntry.

            An entry is added to the zxr10TraceRouteResultsTable when an
            zxr10TraceRouteCtlEntry is started.

            An entry is removed from the zxr10TraceRouteResultsTable when
            its corresponding zxr10TraceRouteCtlEntry is deleted."
        ::= { zxr10TraceRouteObjects 2 }

    zxr10TraceRouteResultsEntry OBJECT-TYPE
        SYNTAX      Zxr10TraceRouteResultsEntry
        MAX-ACCESS  not-accessible
        STATUS      current
        DESCRIPTION
            "Defines an entry in the zxr10TraceRouteResultsTable.  The
            zxr10TraceRouteResultsTable has the same indexing as the
            zxr10TraceRouteCtlTable."
        INDEX {
                zxr10TraceRouteCtlSerial
              }
        ::= { zxr10TraceRouteResultsTable 1 }

    Zxr10TraceRouteResultsEntry ::=
        SEQUENCE {
          zxr10TraceRouteResCurHopCount      Unsigned32,
          zxr10TraceRouteResCurProbCount     Unsigned32,
          zxr10TraceRouteResIpTgtAddrType    InetAddressType,
          zxr10TraceRouteResIpTgtAddr        InetAddress,
          zxr10TraceRouteResTestAttempts     Unsigned32,
          zxr10TraceRouteResTestSuccesses    Unsigned32,
          zxr10TraceRouteResLastGoodPath     DateAndTime
        }

    zxr10TraceRouteResCurHopCount OBJECT-TYPE
        SYNTAX      Unsigned32
        MAX-ACCESS  read-only
        STATUS      current
        DESCRIPTION
            "Reflects the current TTL value (from 1 to
            255) for a remote traceroute operation.
            Maximum TTL value is determined by
            zxr10TraceRouteCtlMaxTtl."
        ::= { zxr10TraceRouteResultsEntry 1 }

    zxr10TraceRouteResCurProbCount OBJECT-TYPE
        SYNTAX      Unsigned32
        MAX-ACCESS  read-only
        STATUS      current
        DESCRIPTION
            "Reflects the current probe count (1..10) for
            a remote traceroute operation.  The maximum
            probe count is determined by
            zxr10TraceRouteCtlProbPerHop."
        ::= { zxr10TraceRouteResultsEntry 2 }

    zxr10TraceRouteResIpTgtAddrType OBJECT-TYPE
        SYNTAX      InetAddressType

        MAX-ACCESS  read-only
        STATUS      current
        DESCRIPTION
            "This object indicates the type of address stored
            in the corresponding zxr10TraceRouteResIpTgtAddr
            object."
        ::= { zxr10TraceRouteResultsEntry 3 }

    zxr10TraceRouteResIpTgtAddr OBJECT-TYPE
        SYNTAX      InetAddress
        MAX-ACCESS  read-only
        STATUS      current
        DESCRIPTION
            "This object reports the IP address associated
            with a zxr10TraceRouteCtlTgtAddr value when the
            destination address is specified as a DNS name.
            The value of this object should be a zero-length
            octet string when a DNS name is not specified or
            when a specified DNS name fails to resolve."
        ::= { zxr10TraceRouteResultsEntry 4 }

    zxr10TraceRouteResTestAttempts OBJECT-TYPE
        SYNTAX      Unsigned32
        MAX-ACCESS  read-only
        STATUS      current
        DESCRIPTION
            "The current number of attempts to determine a path
            to a target.  The value of this object MUST be started
            at 0."
        ::= { zxr10TraceRouteResultsEntry 5 }

    zxr10TraceRouteResTestSuccesses OBJECT-TYPE
        SYNTAX      Unsigned32
        MAX-ACCESS  read-only
        STATUS      current
        DESCRIPTION
            "The current number of attempts to determine a path
            to a target that have succeeded.  The value of this
            object MUST be reported as 0 when no attempts have
            succeeded."
        ::= { zxr10TraceRouteResultsEntry 6 }

    zxr10TraceRouteResLastGoodPath OBJECT-TYPE
        SYNTAX      DateAndTime
        MAX-ACCESS  read-only
        STATUS      current
        DESCRIPTION
            "The date and time when the last complete path
            was determined.  A path is complete if responses
            were received or timeout occurred for each hop on
            the path."
        ::= { zxr10TraceRouteResultsEntry 7 }

-- *******************************************************
--                Trace Hop Result Table
-- *******************************************************

    zxr10TraceRouteHopsTable OBJECT-TYPE
        SYNTAX      SEQUENCE OF Zxr10TraceRouteHopsEntry
        MAX-ACCESS  not-accessible
        STATUS      current
        DESCRIPTION
            "Defines the Remote Operations Traceroute Hop Table for
            keeping track of the results of traceroute tests on a
            per-hop basis."
        ::= { zxr10TraceRouteObjects 4 }

    zxr10TraceRouteHopsEntry OBJECT-TYPE
        SYNTAX      Zxr10TraceRouteHopsEntry
        MAX-ACCESS  not-accessible
        STATUS      current
        DESCRIPTION
            "Defines an entry in the zxr10TraceRouteHopsTable.
            The index elements identify the zxr10TraceRouteCtlEntry
            that a zxr10TraceRouteHopsEntry belongs to."
        INDEX {
                zxr10TraceRouteCtlSerial,
                zxr10TraceRouteHopsIndex
              }

        ::= { zxr10TraceRouteHopsTable 1 }

    Zxr10TraceRouteHopsEntry ::=
        SEQUENCE {
            zxr10TraceRouteHopsIndex            Integer32,
            zxr10TraceRouteHopsIpTgtAddrType    InetAddressType,
            zxr10TraceRouteHopsIpTgtAddr        InetAddress,
            zxr10TraceRouteHopsMinRtt           Unsigned32,
            zxr10TraceRouteHopsMaxRtt           Unsigned32,
            zxr10TraceRouteHopsAverageRtt       Unsigned32,
            zxr10TraceRouteHopsRttSumOfSquar    Unsigned32,
            zxr10TraceRouteHopsSentProbs        Unsigned32,
            zxr10TraceRouteHopsProbResponses    Unsigned32,
            zxr10TraceRouteHopsLastGoodProb     DateAndTime
          }

    zxr10TraceRouteHopsIndex OBJECT-TYPE
        SYNTAX      Integer32
        MAX-ACCESS  not-accessible
        STATUS      current
        DESCRIPTION
           "Specifies the hop index for a traceroute hop."
        ::= { zxr10TraceRouteHopsEntry 1 }

    zxr10TraceRouteHopsIpTgtAddrType OBJECT-TYPE
        SYNTAX      InetAddressType
        MAX-ACCESS  read-only
        STATUS      current
        DESCRIPTION
            "This object indicates the type of address stored
            in the corresponding zxr10TraceRouteHopsIpTgtAddr
            object."
        ::= { zxr10TraceRouteHopsEntry 2 }

    zxr10TraceRouteHopsIpTgtAddr OBJECT-TYPE
        SYNTAX      InetAddress
        MAX-ACCESS  read-only
        STATUS      current
        DESCRIPTION
            "This object reports the IP address associated with
            the hop.  A value for this object should be reported
            as a numeric IP address, not as a DNS name."
        ::= { zxr10TraceRouteHopsEntry 3 }

    zxr10TraceRouteHopsMinRtt OBJECT-TYPE
        SYNTAX      Unsigned32
        MAX-ACCESS  read-only
        STATUS      current
        DESCRIPTION
            "The minimum traceroute round-trip-time (RTT) received for
            this hop.  A value of 0 for this object implies that no
            RTT has been received."
        ::= { zxr10TraceRouteHopsEntry 4 }

    zxr10TraceRouteHopsMaxRtt OBJECT-TYPE
        SYNTAX      Unsigned32
        MAX-ACCESS  read-only
        STATUS      current
        DESCRIPTION
            "The maximum traceroute round-trip-time (RTT) received for
            this hop.  A value of 0 for this object implies that no
            RTT has been received."
        ::= { zxr10TraceRouteHopsEntry 5 }

    zxr10TraceRouteHopsAverageRtt OBJECT-TYPE
        SYNTAX      Unsigned32
        MAX-ACCESS  read-only
        STATUS      current
        DESCRIPTION
            "The current average traceroute round-trip-time (RTT) for
            this hop."
        ::= { zxr10TraceRouteHopsEntry 6 }

    zxr10TraceRouteHopsRttSumOfSquar OBJECT-TYPE
        SYNTAX      Unsigned32
        MAX-ACCESS  read-only
        STATUS      current
        DESCRIPTION
            "This object contains the sum of the squares of all
            round-trip-times received for this hop.  Its purpose is
            to enable standard deviation calculation."
        ::= { zxr10TraceRouteHopsEntry 7 }

    zxr10TraceRouteHopsSentProbs OBJECT-TYPE
        SYNTAX      Unsigned32
        MAX-ACCESS  read-only
        STATUS      current
        DESCRIPTION
            "The value of this object reflects the number of probes sent
            for this hop during this traceroute test.  The value of this
            object should start at 0."
        ::= { zxr10TraceRouteHopsEntry 8 }

    zxr10TraceRouteHopsProbResponses OBJECT-TYPE
        SYNTAX      Unsigned32
        MAX-ACCESS  read-only
        STATUS      current
        DESCRIPTION
            "Number of responses received for this hop during this
            traceroute test.  This value of this object should start
            at 0."
        ::= { zxr10TraceRouteHopsEntry 9 }

    zxr10TraceRouteHopsLastGoodProb OBJECT-TYPE
        SYNTAX      DateAndTime
        MAX-ACCESS  read-only
        STATUS      current
        DESCRIPTION
            "Date and time at which the last response was received for a
             probe for this hop during this traceroute test."
        ::= { zxr10TraceRouteHopsEntry 10 }

END
