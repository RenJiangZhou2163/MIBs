ZXR10-TC DEFINITIONS ::= BEGIN

IMPORTS
TEXTUAL-CONVENTION                 FROM SNMPv2-TC;

ZXR10Chinese ::= TEXTUAL-CONVENTION
    DISPLAY-HINT "4096t"
    STATUS       current
    DESCRIPTION
                 "UTF-8 encoding, does not support question marks and spaces."
    SYNTAX       OCTET STRING (SIZE (0..4096))

ZXR10ChineseWithQuestion ::= TEXTUAL-CONVENTION
    DISPLAY-HINT "4096t"
    STATUS       current
    DESCRIPTION
                 "UTF-8 encoding, does not support spaces."
    SYNTAX       OCTET STRING (SIZE (0..4096))

ZXR10ChineseWithBlank ::= TEXTUAL-CONVENTION
    DISPLAY-HINT "4096t"
    STATUS       current
    DESCRIPTION
                 "UTF-8 encoding, does not support question marks."
    SYNTAX       OCTET STRING (SIZE (0..4096))

ZXR10ChineseWithQB ::= TEXTUAL-CONVENTION
    DISPLAY-HINT "4096t"
    STATUS       current
    DESCRIPTION
                 "UTF-8 encoding."
    SYNTAX       OCTET STRING (SIZE (0..4096))

END
