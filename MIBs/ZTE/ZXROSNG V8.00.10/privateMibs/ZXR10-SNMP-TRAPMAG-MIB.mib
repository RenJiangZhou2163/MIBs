-- *****************************************************************
-- $Id: zxr10SNMPTrapMagMib.mib  2009-11-23 08:47:59Z zhaoqicheng $
--
-- zxr10SNMPTrapMagMib.mib: ZTE Corporation Enterprise Structure of Management 
-- Information
--
-- Copyright (c) 2009 by ZTE Corporation
-- All rights reserved.
-- *****************************************************************
--
ZXR10-SNMP-TRAPMAG-MIB DEFINITIONS ::= BEGIN

IMPORTS
    RowStatus, DisplayString            FROM SNMPv2-TC
    MODULE-IDENTITY, OBJECT-IDENTITY, OBJECT-TYPE, enterprises, Integer32          
                                        FROM SNMPv2-SMI
    InetAddressIPv4, InetAddressIPv6    FROM INET-ADDRESS-MIB;
    
    zxr10SnmpTrapMagMib MODULE-IDENTITY
        LAST-UPDATED "201709261200Z"
        ORGANIZATION "ZTE Corporation"
        CONTACT-INFO "ZTE Corporation about snmp_private_trap_enable 
                      Structure Structure of Management Information"
        DESCRIPTION  "The MIB module to describe the information for SNMP trap."
        REVISION     "201709261200Z"
        DESCRIPTION  "Add all(255) for zxr10SnmpTrapEnableType.
                      Add zxr10SnmpTrapSvrTable."

        REVISION     "201211261200Z"
        DESCRIPTION  "Obsolete zxr10SnmpEnableTrap,
                               zxr10SnmpEnableTrapBgp,
                               zxr10SnmpEnableTrapOspf,
                               zxr10SnmpEnableTrapRmon,
                               zxr10SnmpEnableTrapSnmp,
                               zxr10SnmpEnableTrapStalarm,
                               zxr10SnmpEnableTrapVpn.
                      Add zxr10SnmpTrapEnableTable. "

        REVISION     "200504120000Z"
        DESCRIPTION  "Initial version of this MIB module."
        ::= {zxr10RosngMIB 100} 

        
    zte                     OBJECT IDENTIFIER ::= { enterprises 3902 }
    zxr10                   OBJECT IDENTIFIER ::= { zte 3}
    zxr10RosngMIB           OBJECT IDENTIFIER ::= { zxr10 6000}      



    zxr10SnmpTrapMag OBJECT IDENTIFIER ::= { zxr10SnmpTrapMagMib 1 }

    --  mib object in zxr10SNMPTrapMag group
        zxr10SnmpEnableTrap  OBJECT-TYPE
             SYNTAX  INTEGER {
                          disable(0),      
                          enable(1)
                      }
              MAX-ACCESS  read-write
              STATUS  obsolete
              DESCRIPTION
                      "An integer description all of the zxr10SnmpEnableTrap."
              ::= { zxr10SnmpTrapMag 1 }

        zxr10SnmpEnableTrapBgp OBJECT-TYPE
             SYNTAX  INTEGER {
                          disable(0),      
                          enable(1)
                      }
              MAX-ACCESS  read-write
              STATUS  obsolete
              DESCRIPTION
                      "An integer description of the zxr10SnmpEnableTrapBgp."
              ::= { zxr10SnmpTrapMag 2 }
           
        zxr10SnmpEnableTrapOspf OBJECT-TYPE
             SYNTAX  INTEGER {
                          disable(0),      
                          enable(1)
                      }
              MAX-ACCESS  read-write
              STATUS  obsolete
              DESCRIPTION
                      "An integer description of the zxr10SnmpEnableTrapOspf."
              ::= { zxr10SnmpTrapMag 3 }    
        zxr10SnmpEnableTrapRmon OBJECT-TYPE
             SYNTAX  INTEGER {
                          disable(0),      
                          enable(1)
                      }
              MAX-ACCESS  read-write
              STATUS  obsolete
              DESCRIPTION
                      "An integer description of the zxr10SnmpEnableTrapRmon."
              ::= { zxr10SnmpTrapMag 4 }      
        zxr10SnmpEnableTrapSnmp OBJECT-TYPE
                SYNTAX  INTEGER {
                          disable(0),      
                          enable(1)
                      }
              MAX-ACCESS  read-write
              STATUS  obsolete
              DESCRIPTION
                      "An integer description of the zxr10SnmpEnableTrapSnmp."
              ::= { zxr10SnmpTrapMag 5 }
        zxr10SnmpEnableTrapStalarm OBJECT-TYPE
             SYNTAX  INTEGER {
                          disable(0),      
                          enable(1)
                      }
              MAX-ACCESS  read-write
              STATUS  obsolete
              DESCRIPTION
                      "An integer description of the zxr10SnmpEnableTrapStalarm."
              ::= { zxr10SnmpTrapMag 6 }
        zxr10SnmpEnableTrapVpn OBJECT-TYPE
             SYNTAX  INTEGER {
                          disable(0),      
                          enable(1)
                      }
              MAX-ACCESS  read-write
              STATUS  obsolete
              DESCRIPTION
                      "An integer description of the zxr10SnmpEnableTrapVpn."
              ::= { zxr10SnmpTrapMag 7 }
  
    zxr10SnmpTrapEnableTable  OBJECT-TYPE
        SYNTAX SEQUENCE OF Zxr10SnmpTrapEnableEntry
        MAX-ACCESS  not-accessible
        STATUS      current  
        DESCRIPTION "snmp Trap Enable entity configuration table"                  
        ::={ zxr10SnmpTrapMagMib 4} 
                     
    zxr10SnmpTrapEnableEntry  OBJECT-TYPE
        SYNTAX Zxr10SnmpTrapEnableEntry
        MAX-ACCESS  not-accessible
        STATUS current
        DESCRIPTION "snmp Trap Enable entity configuration entry"
        INDEX {zxr10SnmpTrapEnableType} 
        ::={zxr10SnmpTrapEnableTable 1}    

    Zxr10SnmpTrapEnableEntry ::= SEQUENCE {     
        zxr10SnmpTrapEnableType         INTEGER,
        zxr10SnmpTrapEnableRowStatus    RowStatus
        }  
        
    zxr10SnmpTrapEnableType   OBJECT-TYPE 
        SYNTAX  INTEGER {
            snmp(1),       
            bgp(2),        
            mac(3),        
            ospf(4),       
            stp(5),        
            ppp(6),        
            arp(7),        
            rmon(8),       
            udld(9),       
            cfm(10),       
            efm(11),       
            lacp(12),      
            mcelam(13),   
            tcp(14),       
            sctp(15),      
            stalarm(16),   
            cps(17),       
            interface(18), 
            acl(19),       
            fib(20),       
            pim(21),       
            isis(22),      
            rip(23),       
            msdp(24),      
            aps(25),       
            config(26),    
            am(27),        
            um(28),        
            system(29),    
            ldp(30),       
            pwe3(31),      
            vpn(32),       
            mplsoam(33),  
            ptp(34),       
            tunnelte(35), 
            radius(36),    
            dhcp(37),      
            bfd(38),       
            ppool(39),     
            ntp(40),       
            ssm(41),       
            sqa(42),       
            ipsec(43),     
            cgn(44),       
            vrrp(45),      
            ftptftp(46),  
            pingtrace(47),
            gm(48),
            all(255)
        }
        MAX-ACCESS   not-accessible
        STATUS       current
        DESCRIPTION "trap type"
        ::= {zxr10SnmpTrapEnableEntry 1}  
    
    zxr10SnmpTrapEnableRowStatus   OBJECT-TYPE 
        SYNTAX RowStatus   
        MAX-ACCESS read-create
        STATUS current
        DESCRIPTION "trap type RowStatus"
        ::= {zxr10SnmpTrapEnableEntry 100}
       
       
    zxr10SnmpTrapSvrTable  OBJECT-TYPE
        SYNTAX SEQUENCE OF Zxr10SnmpTrapSvrEntry
        MAX-ACCESS  not-accessible
        STATUS      current  
        DESCRIPTION 
            "SNMP trap server entity configuration table"                  
        ::={zxr10SnmpTrapMagMib 5}
                     
    zxr10SnmpTrapSvrEntry  OBJECT-TYPE
        SYNTAX      Zxr10SnmpTrapSvrEntry
        MAX-ACCESS  not-accessible
        STATUS      current
        DESCRIPTION 
            "SNMP trap server entity configuration entry"
        INDEX {zxr10TrapSvrVrfName,
               zxr10TrapSvrIpv4Address, 
               zxr10TrapSvrIpv6Address,
               zxr10TrapSvrCommunityOrUserName, 
               zxr10TrapSvrFormat } 
        ::={zxr10SnmpTrapSvrTable 1}

    Zxr10SnmpTrapSvrEntry ::= SEQUENCE {
        zxr10TrapSvrVrfName               DisplayString,
        zxr10TrapSvrIpv4Address           InetAddressIPv4,
        zxr10TrapSvrIpv6Address           InetAddressIPv6,
        zxr10TrapSvrCommunityOrUserName   DisplayString,
        zxr10TrapSvrFormat                INTEGER,
        zxr10TrapSvrVersion               INTEGER,
        zxr10TrapSvrSecurityLevel         INTEGER,
        zxr10TrapSvrUdpPort               Integer32,
        zxr10TrapSvrRowStatus             RowStatus
    }
    
    zxr10TrapSvrVrfName  OBJECT-TYPE
        SYNTAX      DisplayString(SIZE(0..32))
        MAX-ACCESS  not-accessible
        STATUS      current
        DESCRIPTION
            "The VRF name."
        ::= { zxr10SnmpTrapSvrEntry 1 }
        
    zxr10TrapSvrIpv4Address  OBJECT-TYPE
        SYNTAX      InetAddressIPv4
        MAX-ACCESS  not-accessible
        STATUS      current
        DESCRIPTION
            "The trap server IPv4 address. If the server address type is IPv6, 
             the value of zxr10TrapSvrIpv4Address is '00000000'H ."
        ::= { zxr10SnmpTrapSvrEntry 2 }
        
    zxr10TrapSvrIpv6Address  OBJECT-TYPE
        SYNTAX      InetAddressIPv6
        MAX-ACCESS  not-accessible
        STATUS      current
        DESCRIPTION
            "The trap server IPv6 address. If the server address type is IPv4, 
             the value of zxr10TrapSvrIpv6Address is 
             '00000000000000000000000000000000'H ."
        ::= { zxr10SnmpTrapSvrEntry 3 }
        
    zxr10TrapSvrCommunityOrUserName  OBJECT-TYPE
        SYNTAX      DisplayString (SIZE(1..32))
        MAX-ACCESS  not-accessible
        STATUS      current
        DESCRIPTION
            "If the zxr10TrapSvrVersion is v1/v2c, this value means community.
             If the zxr10TrapSvrVersion is v3, this value means user name."
        ::= { zxr10SnmpTrapSvrEntry 4 }
        
    zxr10TrapSvrFormat  OBJECT-TYPE
        SYNTAX      INTEGER {
            snmpTrap(1),
            snmpInform(2)
        }
        MAX-ACCESS  not-accessible
        STATUS      current
        DESCRIPTION
            "Trap format.
             snmpTrap   - trap is sent to server and no confirm is needed
             snmpInform - need the confirm from a server."
        DEFVAL { snmpTrap }
        ::= { zxr10SnmpTrapSvrEntry 5 }
        
    zxr10TrapSvrVersion  OBJECT-TYPE
        SYNTAX      INTEGER {
            v1(1),
            v2c(2),
            v3(3)
        }
        MAX-ACCESS  read-create
        STATUS      current
        DESCRIPTION
            "The SNMP version."
        ::= { zxr10SnmpTrapSvrEntry 6 }
        
    zxr10TrapSvrSecurityLevel  OBJECT-TYPE
        SYNTAX      INTEGER {
            noAuthNoPriv(1),
            authNoPriv(2),
            authPriv(3),
            none(4)
        }
        MAX-ACCESS  read-create
        STATUS      current
        DESCRIPTION
            "SNMPv3 security level.
             noAuthNoPriv - without authentication and without privacy,
             authNoPriv   - with authentication but without privacy,
             authPriv     - with authentication and with privacy."
        ::= { zxr10SnmpTrapSvrEntry 7 }
        
    zxr10TrapSvrUdpPort  OBJECT-TYPE
        SYNTAX      Integer32(1..65535) 
        MAX-ACCESS  read-create
        STATUS      current
        DESCRIPTION
            "The received port number of the trap server."
        DEFVAL { 162 }
        ::= { zxr10SnmpTrapSvrEntry 8 }
     
    zxr10TrapSvrRowStatus  OBJECT-TYPE
        SYNTAX      RowStatus
        MAX-ACCESS  read-create
        STATUS      current
        DESCRIPTION
            "The status of this conceptual row.
            
             The supported actions of this conceptual row only include:
             'createAndGo' and 'destroy'.

             To create a row in this table, a manager must set this object to 
             createAndGo(4), and must comply with the multi-variables binding 
             rule described in zxr10SnmpTrapSvrEntry.
    
             To delete a row in this table, a manager must set this object to 
             destroy(6). 
             
             To get this object, the agent always returns active(1)."
        ::= { zxr10SnmpTrapSvrEntry 100 }
                           
END
