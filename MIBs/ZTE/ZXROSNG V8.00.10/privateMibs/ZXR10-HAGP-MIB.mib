ZXR10-HAGP-MIB DEFINITIONS ::= BEGIN

 IMPORTS
     MODULE-IDENTITY, OBJECT-TYPE,
     NOTIFICATION-TYPE, Counter32, Unsigned32, Counter64,
     Integer32, enterprises, TimeTicks
        FROM SNMPv2-SMI
     TEXTUAL-CONVENTION, RowStatus,
     MacAddress, TruthValue, TimeStamp, DisplayString
        FROM SNMPv2-TC
     MODULE-COMPLIANCE, OBJECT-GROUP,
     NOTIFICATION-GROUP
        FROM SNMPv2-CONF
     InetAddressType, InetAddress
        FROM INET-ADDRESS-MIB
     ifIndex
        FROM RFC1213-MIB;
     

zxr10HAGPMIB  MODULE-IDENTITY
    LAST-UPDATED    "201806261600Z"
    ORGANIZATION    "ZTE Corporation."
    CONTACT-INFO
        "       Zhao yanhua
        Tel:    +86-25-52870000
        E-Mail: zhao.yanhua3@zte.com.cn
        "
     DESCRIPTION
         "This MIB describes objects used for managing Hybrid Access
          Gateway Protocol (HAGP)."
    
    REVISION "201806261600Z"
    DESCRIPTION
        "add:       zxr10HagpCustomerEntry
                    zxr10HagpCustomerProfileUp
                    zxr10HagpCustomerProfileDown
                    zxr10HagpCustomerTotalBandwidth
                    zxr10HagpCustomerDslBandwidth
                    zxr10HagpCustomerLteBandwidth
                    zxr10HagpCustomerDslMode
                    zxr10HagpCustomerSessionId

        "
    
     REVISION        "201703291630Z"     
     DESCRIPTION "Initial version."
     ::= { zxr10RosngMIB 605 }
     
     zte OBJECT IDENTIFIER ::= { enterprises 3902 }
     zxr10 OBJECT IDENTIFIER ::= { zte 3 }
     zxr10RosngMIB OBJECT IDENTIFIER ::= { zxr10 6000 }  
     
-- *******************************************************************
--  HAGP MIB Groups
-- *******************************************************************
 zxr10HagpGlobalObjects   OBJECT IDENTIFIER ::= { zxr10HAGPMIB 1 }
 zxr10HagpCustomerObjects OBJECT IDENTIFIER ::= { zxr10HAGPMIB 2 } 

-- *******************************************************************
--  Start of MIB objects
-- *******************************************************************

-- *******************************************************************
--  HAGP Global Information
-- *******************************************************************
zxr10HagpLteActiveCustomerNum  OBJECT-TYPE
        SYNTAX      Unsigned32
        MAX-ACCESS  read-only
        STATUS      current
        DESCRIPTION
            "Number of customers with LTE tunnel active."
        ::= { zxr10HagpGlobalObjects 1 }
        
zxr10HagpDslActiveCustomerNum  OBJECT-TYPE
        SYNTAX      Unsigned32
        MAX-ACCESS  read-only
        STATUS      current
        DESCRIPTION
            "Number of customers with DSL tunnel active."
        ::= { zxr10HagpGlobalObjects 2 }
        
zxr10HagpBoundingCustomerNum  OBJECT-TYPE
        SYNTAX      Unsigned32
        MAX-ACCESS  read-only
        STATUS      current
        DESCRIPTION
            "Number of customers working in bounding mode."
        ::= { zxr10HagpGlobalObjects 3 }
        
zxr10HagpLteCongestCustomerNum  OBJECT-TYPE
        SYNTAX      Unsigned32
        MAX-ACCESS  read-only
        STATUS      current
        DESCRIPTION
            "Number of customer with LTE congestion problems."
        ::= { zxr10HagpGlobalObjects 4 }
        
zxr10HagpDslCongestCustomerNum  OBJECT-TYPE
        SYNTAX      Unsigned32
        MAX-ACCESS  read-only
        STATUS      current
        DESCRIPTION
            "Number of customer with DSL congestion problems."
        ::= { zxr10HagpGlobalObjects 5 }
        
zxr10HagpLteAuthSuccessNum  OBJECT-TYPE
        SYNTAX      Unsigned32
        MAX-ACCESS  read-only
        STATUS      current
        DESCRIPTION
            "Number of LTE tunnels authenticate successfully."
        ::= { zxr10HagpGlobalObjects 6 }
        
zxr10HagpDslAuthSuccessNum  OBJECT-TYPE
        SYNTAX      Unsigned32
        MAX-ACCESS  read-only
        STATUS      current
        DESCRIPTION
            "Number of DSL tunnels authenticate successfully."
        ::= { zxr10HagpGlobalObjects 7 }
        
zxr10HagpLteAuthFailNum  OBJECT-TYPE
        SYNTAX      Unsigned32
        MAX-ACCESS  read-only
        STATUS      current
        DESCRIPTION
            "Number of LTE tunnels authenticate failed."
        ::= { zxr10HagpGlobalObjects 8 }
     
zxr10HagpDslAuthFailNum  OBJECT-TYPE
        SYNTAX      Unsigned32
        MAX-ACCESS  read-only
        STATUS      current
        DESCRIPTION
            "Number of DSL tunnels authenticate failed."
        ::= { zxr10HagpGlobalObjects 9 }
        
zxr10HagpSessionNumShorterThan5m  OBJECT-TYPE
        SYNTAX      Unsigned32
        MAX-ACCESS  read-only
        STATUS      current
        DESCRIPTION
            "Number of hybrid sessions with duration shorter than 5m."
        ::= { zxr10HagpGlobalObjects 10 }
        
zxr10HagpSessionNum5mTo1h  OBJECT-TYPE
        SYNTAX      Unsigned32
        MAX-ACCESS  read-only
        STATUS      current
        DESCRIPTION
            "Number of hybrid sessions with duration 5m-1h."
        ::= { zxr10HagpGlobalObjects 11 }
        
zxr10HagpSessionNum1hTo1d  OBJECT-TYPE
        SYNTAX      Unsigned32
        MAX-ACCESS  read-only
        STATUS      current
        DESCRIPTION
            "Number of hybrid sessions with duration 1h-1d."
        ::= { zxr10HagpGlobalObjects 12 }
        
zxr10HagpSessionNumLongerThan1d  OBJECT-TYPE
        SYNTAX      Unsigned32
        MAX-ACCESS  read-only
        STATUS      current
        DESCRIPTION
            "Number of hybrid sessions with duration longer than 1d."
        ::= { zxr10HagpGlobalObjects 13 }
        
-- *******************************************************************
--  HAGP Customer Information
-- *******************************************************************  
zxr10HagpCustomerTable OBJECT-TYPE
    SYNTAX       SEQUENCE OF Zxr10HagpCustomerEntry
    MAX-ACCESS   not-accessible
    STATUS       current
    DESCRIPTION
        "The table of HAGP customer."
    ::= { zxr10HagpCustomerObjects 1 }
    
zxr10HagpCustomerEntry OBJECT-TYPE
    SYNTAX          Zxr10HagpCustomerEntry
    MAX-ACCESS      not-accessible
    STATUS          current
    DESCRIPTION
        "The entry of HAGP customer detail information."
    INDEX           { zxr10HagpCustomerUserName } 
    ::= { zxr10HagpCustomerTable 1 }
    
Zxr10HagpCustomerEntry ::=
    SEQUENCE {
        zxr10HagpCustomerUserName             DisplayString,
        zxr10HagpCustomerLteULVolume          Counter64,
        zxr10HagpCustomerDslULVolume          Counter64,
        zxr10HagpCustomerLteDLVolume          Counter64,
        zxr10HagpCustomerDslDLVolume          Counter64,
        zxr10HagpCustomerLteULThrougput       Counter64,
        zxr10HagpCustomerDslULThrougput       Counter64,
        zxr10HagpCustomerLteDLThrougput       Counter64,
        zxr10HagpCustomerDslDLThrougput       Counter64,
        zxr10HagpCustomerLteTime              TimeTicks,
        zxr10HagpCustomerDslTime              TimeTicks,
        zxr10HagpCustomerLteDslBondTime       TimeTicks,
        zxr10HagpCustomerLteState             INTEGER,
        zxr10HagpCustomerDslState             INTEGER,
        zxr10HagpCustomerLteIpType            InetAddressType,
        zxr10HagpCustomerLteIp                InetAddress,
        zxr10HagpCustomerDslIpType            InetAddressType,
        zxr10HagpCustomerDslIp                InetAddress,
        zxr10HagpCustomerPublicIpType         InetAddressType,
        zxr10HagpCustomerPublicIp             InetAddress,
        zxr10HagpCustomerProfileUp            DisplayString,
        zxr10HagpCustomerProfileDown          DisplayString,
        zxr10HagpCustomerTotalBandwidth       Unsigned32,
        zxr10HagpCustomerDslBandwidth         Unsigned32,
        zxr10HagpCustomerLteBandwidth         Unsigned32,
        zxr10HagpCustomerDslMode              INTEGER,
        zxr10HagpCustomerSessionId            Unsigned32
        }
        
zxr10HagpCustomerUserName OBJECT-TYPE
    SYNTAX       DisplayString
    MAX-ACCESS   not-accessible
    STATUS       current
    DESCRIPTION
        "User name of HAGP customer."
    ::= { zxr10HagpCustomerEntry 1 }
    
zxr10HagpCustomerLteULVolume OBJECT-TYPE
    SYNTAX       Counter64
    UNITS        "bytes"
    MAX-ACCESS   read-only
    STATUS       current
    DESCRIPTION
        "Data volume of LTE uplink."
    ::= { zxr10HagpCustomerEntry 2 }
    
zxr10HagpCustomerDslULVolume OBJECT-TYPE
    SYNTAX       Counter64
    UNITS        "bytes"
    MAX-ACCESS   read-only
    STATUS       current
    DESCRIPTION
        "Data volume of DSL uplink."
    ::= { zxr10HagpCustomerEntry 3 }
    
zxr10HagpCustomerLteDLVolume OBJECT-TYPE
    SYNTAX       Counter64
    UNITS        "bytes"
    MAX-ACCESS   read-only
    STATUS       current
    DESCRIPTION
        "Data volume of LTE downlink."
    ::= { zxr10HagpCustomerEntry 4 }
    
zxr10HagpCustomerDslDLVolume OBJECT-TYPE
    SYNTAX       Counter64
    UNITS        "bytes"
    MAX-ACCESS   read-only
    STATUS       current
    DESCRIPTION
        "Data volume of DSL downlink."
    ::= { zxr10HagpCustomerEntry 5 }
    
zxr10HagpCustomerLteULThrougput OBJECT-TYPE
    SYNTAX       Counter64
    UNITS        "bps"
    MAX-ACCESS   read-only
    STATUS       current
    DESCRIPTION
        "Data througput of LTE uplink."
    ::= { zxr10HagpCustomerEntry 6 }
    
zxr10HagpCustomerDslULThrougput OBJECT-TYPE
    SYNTAX       Counter64
    UNITS        "bps"
    MAX-ACCESS   read-only
    STATUS       current
    DESCRIPTION
        "Data througput of DSL uplink."
    ::= { zxr10HagpCustomerEntry 7 }
    
zxr10HagpCustomerLteDLThrougput OBJECT-TYPE
    SYNTAX       Counter64
    UNITS        "bps"
    MAX-ACCESS   read-only
    STATUS       current
    DESCRIPTION
        "Data througput of LTE downlink."
    ::= { zxr10HagpCustomerEntry 8 }
    
zxr10HagpCustomerDslDLThrougput OBJECT-TYPE
    SYNTAX       Counter64
    UNITS        "bps"
    MAX-ACCESS   read-only
    STATUS       current
    DESCRIPTION
        "Data througput of DSL downlink."
    ::= { zxr10HagpCustomerEntry 9 }
    
zxr10HagpCustomerLteTime OBJECT-TYPE
    SYNTAX       TimeTicks
    MAX-ACCESS   read-only
    STATUS       current
    DESCRIPTION
        "LTE session time."
    ::= { zxr10HagpCustomerEntry 10 }
    
zxr10HagpCustomerDslTime OBJECT-TYPE
    SYNTAX       TimeTicks
    MAX-ACCESS   read-only
    STATUS       current
    DESCRIPTION
        "DSL session time."
    ::= { zxr10HagpCustomerEntry 11 }
    
zxr10HagpCustomerLteDslBondTime OBJECT-TYPE
    SYNTAX       TimeTicks
    MAX-ACCESS   read-only
    STATUS       current
    DESCRIPTION
        "DSL and LTE bonding session time."
    ::= { zxr10HagpCustomerEntry 12 }
    
zxr10HagpCustomerLteState OBJECT-TYPE
    SYNTAX       INTEGER  {
                        invalid(1),
                        ok(2)
                    }
    MAX-ACCESS   read-only
    STATUS       current
    DESCRIPTION
        "LTE link state."
    ::= { zxr10HagpCustomerEntry 13 }
    
zxr10HagpCustomerDslState OBJECT-TYPE
    SYNTAX       INTEGER  {
                        invalid(1),
                        ok(2)
                    }
    MAX-ACCESS   read-only
    STATUS       current
    DESCRIPTION
        "DSL link state."
    ::= { zxr10HagpCustomerEntry 14 }
    
zxr10HagpCustomerLteIpType OBJECT-TYPE
    SYNTAX       InetAddressType
    MAX-ACCESS   read-only
    STATUS       current
    DESCRIPTION
        "LTE IP address type."
    ::= { zxr10HagpCustomerEntry 15 }
    
zxr10HagpCustomerLteIp OBJECT-TYPE
    SYNTAX       InetAddress
    MAX-ACCESS   read-only
    STATUS       current
    DESCRIPTION
        "LTE IP address."
    ::= { zxr10HagpCustomerEntry 16 }
    
zxr10HagpCustomerDslIpType OBJECT-TYPE
    SYNTAX       InetAddressType
    MAX-ACCESS   read-only
    STATUS       current
    DESCRIPTION
        "DSL IP address type."
    ::= { zxr10HagpCustomerEntry 17 }
    
zxr10HagpCustomerDslIp OBJECT-TYPE
    SYNTAX       InetAddress
    MAX-ACCESS   read-only
    STATUS       current
    DESCRIPTION
        "DSL IP address."
    ::= { zxr10HagpCustomerEntry 18 }
    
zxr10HagpCustomerPublicIpType OBJECT-TYPE
    SYNTAX       InetAddressType
    MAX-ACCESS   read-only
    STATUS       current
    DESCRIPTION
        "Public IP address type."
    ::= { zxr10HagpCustomerEntry 19 }
    
zxr10HagpCustomerPublicIp OBJECT-TYPE
    SYNTAX       InetAddress
    MAX-ACCESS   read-only
    STATUS       current
    DESCRIPTION
        "Public IP address."
    ::= { zxr10HagpCustomerEntry 20 }
    
zxr10HagpCustomerProfileUp OBJECT-TYPE
    SYNTAX       DisplayString
    MAX-ACCESS   read-only
    STATUS       current
    DESCRIPTION
        "Upstream profile name."
    ::= { zxr10HagpCustomerEntry 21 }
    
zxr10HagpCustomerProfileDown OBJECT-TYPE
    SYNTAX       DisplayString
    MAX-ACCESS   read-only
    STATUS       current
    DESCRIPTION
        "Downstream profile name."
    ::= { zxr10HagpCustomerEntry 22 }
    
zxr10HagpCustomerTotalBandwidth OBJECT-TYPE
    SYNTAX       Unsigned32
    UNITS        "Kbps"
    MAX-ACCESS   read-only
    STATUS       current
    DESCRIPTION
        "Available downstream total bandwidth."
    ::= { zxr10HagpCustomerEntry 23 }

zxr10HagpCustomerDslBandwidth OBJECT-TYPE
    SYNTAX       Unsigned32
    UNITS        "Kbps"
    MAX-ACCESS   read-only
    STATUS       current
    DESCRIPTION
        "Available downstream DSL bandwidth."
    ::= { zxr10HagpCustomerEntry 24 }

zxr10HagpCustomerLteBandwidth OBJECT-TYPE
    SYNTAX       Unsigned32
    UNITS        "Kbps"
    MAX-ACCESS   read-only
    STATUS       current
    DESCRIPTION
        "Available downstream LTE bandwidth."
    ::= { zxr10HagpCustomerEntry 25 }

zxr10HagpCustomerDslMode OBJECT-TYPE
    SYNTAX       INTEGER  {                  
                        adsl(1),
                        vdsl(2)
                    }
    MAX-ACCESS   read-only
    STATUS       current
    DESCRIPTION
        "DSL mode."
    ::= { zxr10HagpCustomerEntry 26 }

zxr10HagpCustomerSessionId OBJECT-TYPE
    SYNTAX       Unsigned32   
    MAX-ACCESS   read-only
    STATUS       current
    DESCRIPTION
        "Session ID."
    ::= { zxr10HagpCustomerEntry 27 }

END
