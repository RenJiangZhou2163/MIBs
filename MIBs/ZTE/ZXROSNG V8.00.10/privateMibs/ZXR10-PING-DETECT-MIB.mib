--  ************************************************
--  $Id: zxr10pingdetect.mib 8 2010-05-27 14:52:08Z xingyeping $
--
--  zxr10pingdetect.mib: ZXR10 Ping Detect MIB file
--  
--  May. 2010, Xing YePing
--   
--  Copyright(c) 2010 by ZTE Corporaton
--  All rights reservered
--
--  ************************************************

ZXR10-PING-DETECT-MIB DEFINITIONS ::= BEGIN

IMPORTS
    MODULE-IDENTITY, 
    OBJECT-TYPE, 
	OBJECT-IDENTITY,
--  NOTIFICATION-TYPE,
--  experimental, 
    Integer32 
--  Unsigned32, 
--  Counter32
        FROM SNMPv2-SMI

--  MODULE-COMPLIANCE, 
--  OBJECT-GROUP, 
--  NOTIFICATION-GROUP
--      FROM SNMPv2-CONF
    enterprises                      
        FROM SNMPv2-SMI     
        
--  MacAddress,RowStatus,TruthValue  
    DisplayString                       
        FROM SNMPv2-TC   
      

--  mgmt, 
--  NetworkAddress, 
    IpAddress 
--  Counter, 
--  Gauge
        FROM RFC1155-SMI;

    zte MODULE-IDENTITY
    LAST-UPDATED "200504120000Z"  -- April 12, 2005
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS SMI MIB"

    REVISION "200504120000Z"  -- April 12, 2005
    DESCRIPTION
       ""
	::= { enterprises 3902 }	-- assigned by IANA


  zxr10 OBJECT-IDENTITY
	STATUS	current
	DESCRIPTION
		"zxr10 is the root OBJECT IDENTIFIER for ZTE
		 routers and switches pruducts"
	::= { zte 3 }
	 
    zxr10L2vpn  OBJECT IDENTIFIER ::= {zxr10  104}
    zxr10PingDetectMIB OBJECT IDENTIFIER ::= { zxr10L2vpn 20}

--    DisplayString ::= OCTET STRING
    --  This data type is used to model textual information taken
    --  from the NVT ASCII character set.  By convention, objects
    --  with this syntax are declared as having
    --  SIZE (0..255)

    DetectOptionType ::= INTEGER
                      {
                        or(0),
                        and(1)
                      }

    zxr10PingDetectTable  OBJECT-TYPE
        SYNTAX  SEQUENCE OF Zxr10PingDetectEntry
        MAX-ACCESS  not-accessible
        STATUS  obsolete
        DESCRIPTION
            "ping detect information table."
        ::= { zxr10PingDetectMIB 1 }

    zxr10PingDetectEntry  OBJECT-TYPE
        SYNTAX  Zxr10PingDetectEntry
        MAX-ACCESS  not-accessible
        STATUS  obsolete
        DESCRIPTION
            ""
        INDEX  { zxr10PingDetectGroup }
        ::= { zxr10PingDetectTable 1 }

    Zxr10PingDetectEntry ::=
        SEQUENCE {        
            zxr10PingDetectGroup
                Integer32,
            zxr10PingDetectTimeout
                Integer32,
            zxr10PingDetectRetrytimes
                Integer32,    
            zxr10PingDetectLooptime
                Integer32,    
            zxr10PingDetectOption
                DetectOptionType,  
            zxr10PingDetectListVrfName1
                DisplayString, 
            zxr10PingDetectListIpAddr1
                IpAddress,  
            zxr10PingDetectListNextHop1
                IpAddress,    
            zxr10PingDetectListVrfName2
                DisplayString, 
            zxr10PingDetectListIpAddr2
                IpAddress,  
            zxr10PingDetectListNextHop2
                IpAddress,
            zxr10PingDetectListVrfName3
                DisplayString, 
            zxr10PingDetectListIpAddr3
                IpAddress,  
            zxr10PingDetectListNextHop3
                IpAddress,
            zxr10PingDetectListVrfName4
                DisplayString, 
            zxr10PingDetectListIpAddr4
                IpAddress,  
            zxr10PingDetectListNextHop4
                IpAddress,    
            zxr10PingDetectListVrfName5
                DisplayString, 
            zxr10PingDetectListIpAddr5
                IpAddress,  
            zxr10PingDetectListNextHop5
                IpAddress,
            zxr10PingDetectListVrfName6
                DisplayString, 
            zxr10PingDetectListIpAddr6
                IpAddress,  
            zxr10PingDetectListNextHop6
                IpAddress,    
            zxr10PingDetectListVrfName7
                DisplayString, 
            zxr10PingDetectListIpAddr7
                IpAddress,  
            zxr10PingDetectListNextHop7
                IpAddress,
            zxr10PingDetectListVrfName8
                DisplayString, 
            zxr10PingDetectListIpAddr8
                IpAddress,  
            zxr10PingDetectListNextHop8
                IpAddress,
            zxr10PingDetectListVrfName9
                DisplayString, 
            zxr10PingDetectListIpAddr9
                IpAddress,  
            zxr10PingDetectListNextHop9
                IpAddress,    
            zxr10PingDetectListVrfName10
                DisplayString, 
            zxr10PingDetectListIpAddr10
                IpAddress,  
            zxr10PingDetectListNextHop10
                IpAddress,
			zxr10PingDetectGroupStatus
                INTEGER			
    }

    zxr10PingDetectGroup  OBJECT-TYPE
        SYNTAX  Integer32 (1..10) 
        MAX-ACCESS  read-only 
        STATUS  obsolete
        DESCRIPTION
            "group number"
        ::= { zxr10PingDetectEntry 1 }      
        
    zxr10PingDetectTimeout  OBJECT-TYPE
        SYNTAX  Integer32 (1..20) 
        MAX-ACCESS  read-only 
        STATUS  obsolete
        DESCRIPTION
            "time out"
        ::= { zxr10PingDetectEntry 2 }          
        
    zxr10PingDetectRetrytimes  OBJECT-TYPE
        SYNTAX  Integer32 (1..10) 
        MAX-ACCESS  read-only 
        STATUS  obsolete
        DESCRIPTION
            "retry times"
        ::= { zxr10PingDetectEntry 3 }     
        
    zxr10PingDetectLooptime  OBJECT-TYPE
        SYNTAX  Integer32 (2..86400) 
        MAX-ACCESS  read-only 
        STATUS  obsolete
        DESCRIPTION
            "loop time"
        ::= { zxr10PingDetectEntry 4 }        
                
        
    zxr10PingDetectOption  OBJECT-TYPE
        SYNTAX  DetectOptionType
        MAX-ACCESS  read-only 
        STATUS  obsolete
        DESCRIPTION
            "option"
        ::= { zxr10PingDetectEntry 5 }    
          
    zxr10PingDetectListVrfName1  OBJECT-TYPE
        SYNTAX  DisplayString
        MAX-ACCESS  read-only 
        STATUS  obsolete
        DESCRIPTION
            "list 1 vrf name"
        ::= { zxr10PingDetectEntry 6 }  
              
    zxr10PingDetectListIpAddr1  OBJECT-TYPE
        SYNTAX  IpAddress
        MAX-ACCESS  read-only 
        STATUS  obsolete
        DESCRIPTION
            "list 1 ip address"
        ::= { zxr10PingDetectEntry 7 }      
        
    zxr10PingDetectListNextHop1  OBJECT-TYPE
        SYNTAX  IpAddress
        MAX-ACCESS  read-only 
        STATUS  obsolete
        DESCRIPTION
            "list 1 next hop"
        ::= { zxr10PingDetectEntry 8 }     
        
    zxr10PingDetectListVrfName2  OBJECT-TYPE
        SYNTAX  DisplayString
        MAX-ACCESS  read-only 
        STATUS  obsolete
        DESCRIPTION
            "list 2 vrf name"
        ::= { zxr10PingDetectEntry 9 }  
        
    zxr10PingDetectListIpAddr2  OBJECT-TYPE
        SYNTAX  IpAddress
        MAX-ACCESS  read-only 
        STATUS  obsolete
        DESCRIPTION
            "list 2 ip address"
        ::= { zxr10PingDetectEntry 10 }      
        
    zxr10PingDetectListNextHop2  OBJECT-TYPE
        SYNTAX  IpAddress
        MAX-ACCESS  read-only 
        STATUS  obsolete
        DESCRIPTION
            "list 2 next hop"
        ::= { zxr10PingDetectEntry 11 }   

    zxr10PingDetectListVrfName3  OBJECT-TYPE
        SYNTAX  DisplayString
        MAX-ACCESS  read-only 
        STATUS  obsolete
        DESCRIPTION
            "list 3 vrf name"
        ::= { zxr10PingDetectEntry 12 }  
        
    zxr10PingDetectListIpAddr3  OBJECT-TYPE
        SYNTAX  IpAddress
        MAX-ACCESS  read-only 
        STATUS  obsolete
        DESCRIPTION
            "list 3 ip address"
        ::= { zxr10PingDetectEntry 13 }      
        
    zxr10PingDetectListNextHop3  OBJECT-TYPE
        SYNTAX  IpAddress
        MAX-ACCESS  read-only 
        STATUS  obsolete
        DESCRIPTION
            "list 3 next hop"
        ::= { zxr10PingDetectEntry 14 }   

    zxr10PingDetectListVrfName4  OBJECT-TYPE
        SYNTAX  DisplayString
        MAX-ACCESS  read-only 
        STATUS  obsolete
        DESCRIPTION
            "list 4 vrf name"
        ::= { zxr10PingDetectEntry 15 }  
        
    zxr10PingDetectListIpAddr4  OBJECT-TYPE
        SYNTAX  IpAddress
        MAX-ACCESS  read-only 
        STATUS  obsolete
        DESCRIPTION
            "list 4 ip address"
        ::= { zxr10PingDetectEntry 16 }      
        
    zxr10PingDetectListNextHop4  OBJECT-TYPE
        SYNTAX  IpAddress
        MAX-ACCESS  read-only 
        STATUS  obsolete
        DESCRIPTION
            "list 4 next hop"
        ::= { zxr10PingDetectEntry 17 }   

    zxr10PingDetectListVrfName5  OBJECT-TYPE
        SYNTAX  DisplayString
        MAX-ACCESS  read-only 
        STATUS  obsolete
        DESCRIPTION
            "list 5 vrf name"
        ::= { zxr10PingDetectEntry 18 }  
        
    zxr10PingDetectListIpAddr5  OBJECT-TYPE
        SYNTAX  IpAddress
        MAX-ACCESS  read-only 
        STATUS  obsolete
        DESCRIPTION
            "list 5 ip address"
        ::= { zxr10PingDetectEntry 19 }      
        
    zxr10PingDetectListNextHop5  OBJECT-TYPE
        SYNTAX  IpAddress
        MAX-ACCESS  read-only 
        STATUS  obsolete
        DESCRIPTION
            "list 5 next hop"
        ::= { zxr10PingDetectEntry 20 }   		

    zxr10PingDetectListVrfName6  OBJECT-TYPE
        SYNTAX  DisplayString
        MAX-ACCESS  read-only 
        STATUS  obsolete
        DESCRIPTION
            "list 6 vrf name"
        ::= { zxr10PingDetectEntry 21 }  
        
    zxr10PingDetectListIpAddr6  OBJECT-TYPE
        SYNTAX  IpAddress
        MAX-ACCESS  read-only 
        STATUS  obsolete
        DESCRIPTION
            "list 6 ip address"
        ::= { zxr10PingDetectEntry 22 }      
        
    zxr10PingDetectListNextHop6  OBJECT-TYPE
        SYNTAX  IpAddress
        MAX-ACCESS  read-only 
        STATUS  obsolete
        DESCRIPTION
            "list 6 next hop"
        ::= { zxr10PingDetectEntry 23 }     

    zxr10PingDetectListVrfName7  OBJECT-TYPE
        SYNTAX  DisplayString
        MAX-ACCESS  read-only 
        STATUS  obsolete
        DESCRIPTION
            "list 7 vrf name"
        ::= { zxr10PingDetectEntry 24 }  
        
    zxr10PingDetectListIpAddr7  OBJECT-TYPE
        SYNTAX  IpAddress
        MAX-ACCESS  read-only 
        STATUS  obsolete
        DESCRIPTION
            "list 7 ip address"
        ::= { zxr10PingDetectEntry 25 }      
        
    zxr10PingDetectListNextHop7  OBJECT-TYPE
        SYNTAX  IpAddress
        MAX-ACCESS  read-only 
        STATUS  obsolete
        DESCRIPTION
            "list 7 next hop"
        ::= { zxr10PingDetectEntry 26 }   

    zxr10PingDetectListVrfName8  OBJECT-TYPE
        SYNTAX  DisplayString
        MAX-ACCESS  read-only 
        STATUS  obsolete
        DESCRIPTION
            "list 8 vrf name"
        ::= { zxr10PingDetectEntry 27 }  
        
    zxr10PingDetectListIpAddr8  OBJECT-TYPE
        SYNTAX  IpAddress
        MAX-ACCESS  read-only 
        STATUS  obsolete
        DESCRIPTION
            "list 8 ip address"
        ::= { zxr10PingDetectEntry 28 }      
        
    zxr10PingDetectListNextHop8  OBJECT-TYPE
        SYNTAX  IpAddress
        MAX-ACCESS  read-only 
        STATUS  obsolete
        DESCRIPTION
            "list 8 next hop"
        ::= { zxr10PingDetectEntry 29 }   

    zxr10PingDetectListVrfName9  OBJECT-TYPE
        SYNTAX  DisplayString
        MAX-ACCESS  read-only 
        STATUS  obsolete
        DESCRIPTION
            "list 9 vrf name"
        ::= { zxr10PingDetectEntry 30 }  
        
    zxr10PingDetectListIpAddr9  OBJECT-TYPE
        SYNTAX  IpAddress
        MAX-ACCESS  read-only 
        STATUS  obsolete
        DESCRIPTION
            "list 9 ip address"
        ::= { zxr10PingDetectEntry 31 }      
        
    zxr10PingDetectListNextHop9  OBJECT-TYPE
        SYNTAX  IpAddress
        MAX-ACCESS  read-only 
        STATUS  obsolete
        DESCRIPTION
            "list 9 next hop"
        ::= { zxr10PingDetectEntry 32 }   

    zxr10PingDetectListVrfName10  OBJECT-TYPE
        SYNTAX  DisplayString
        MAX-ACCESS  read-only 
        STATUS  obsolete
        DESCRIPTION
            "list 10 vrf name"
        ::= { zxr10PingDetectEntry 33 }  
        
    zxr10PingDetectListIpAddr10  OBJECT-TYPE
        SYNTAX  IpAddress
        MAX-ACCESS  read-only 
        STATUS  obsolete
        DESCRIPTION
            "list 10 ip address"
        ::= { zxr10PingDetectEntry 34 }      
        
    zxr10PingDetectListNextHop10  OBJECT-TYPE
        SYNTAX  IpAddress
        MAX-ACCESS  read-only 
        STATUS  obsolete
        DESCRIPTION
            "list 10 next hop"
        ::= { zxr10PingDetectEntry 35 }   		

    zxr10PingDetectGroupStatus  OBJECT-TYPE
        SYNTAX  INTEGER{unkown(0),up(1),down(2)}  
        MAX-ACCESS  read-only 
        STATUS  obsolete
        DESCRIPTION
            "group status"
        ::= { zxr10PingDetectEntry 36 }  
                   
    END
