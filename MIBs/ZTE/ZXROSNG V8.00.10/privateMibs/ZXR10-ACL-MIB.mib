--  ******************************************************
--  $Id: zxr10T8kACL.mib  2010-09-25  liulele $
--
--  zxr10T8kACL.mib: ZXR10 T8000 Access List MIB file
--  
--  Sep. 2010, liu lele 
--   
--  Copyright(c) 2010 by ZTE Corporaton
--  All rights reservered
--
-- 
--  ******************************************************



ZXR10-ACL-MIB DEFINITIONS ::= BEGIN

IMPORTS
    MODULE-IDENTITY, 
    OBJECT-TYPE, 
    NOTIFICATION-TYPE,
    ----experimental, 
    Integer32,     
    Unsigned32, 
    Counter32,
    IpAddress, 
    Counter, 
    Gauge
        FROM SNMPv2-SMI

    MODULE-COMPLIANCE, 
    OBJECT-GROUP, 
    NOTIFICATION-GROUP
        FROM SNMPv2-CONF
    enterprises                      
        FROM SNMPv2-SMI
    MacAddress,
    TEXTUAL-CONVENTION,
    RowStatus,
    DisplayString
        FROM SNMPv2-TC
    zxr10
        FROM ZXR10-SMI;

    
    zxr10ACL MODULE-IDENTITY
        LAST-UPDATED "201308081500Z"
        ORGANIZATION "ZTE Corporation"
        CONTACT-INFO
            "       Hu Jun
            Tel:    +86-25-52870000
            E-Mail: hu.jun11@zte.com.cn "
        DESCRIPTION
            "The MIB module to describe the ACL protocol."
            REVISION "201308081500Z"
        DESCRIPTION 
            "Modify syntax of icmptype icmpcode and HeaderOption:
             1. change the range of icmptype and icmpcode 
             from 0-15 to 0-255
             2. change the descriptino of HeaderOption"
        REVISION "201308051500Z"
        DESCRIPTION 
            "Modify syntax of port and protcol:
             1. Correct enumeration of port: change pim_atup_rp 
             to pim_auto_rp.
             2. Delete error enumeration of protcol: ip(0)."
        REVISION "201306081000Z"
        DESCRIPTION 
            "Modify description of bitmap.
             Change hyphen to underline in the labels of 
             the enumeration list.
             Delete some unused definition.
             Add definition about MODULE-IDENTITY."
        ::= { zxr10AclMIB 1 }  
        
    zxr10AclMIB OBJECT IDENTIFIER ::= { zxr10 1100}


   --- IPv4 ACL 

    zxr10IPv4ACLTable  OBJECT-TYPE
        SYNTAX  SEQUENCE OF Zxr10IPv4ACLEntry
        MAX-ACCESS  not-accessible
        STATUS  current
        DESCRIPTION
            "IPv4 ACL Table"
        ::= { zxr10ACL 1 }

    zxr10IPv4ACLEntry  OBJECT-TYPE
        SYNTAX  Zxr10IPv4ACLEntry
        MAX-ACCESS  not-accessible
        STATUS  current
        DESCRIPTION
            "IPv4 ACL"
        INDEX  { zxr10IPv4ACLName,
                 zxr10IPv4ACLRuleID }
        ::= { zxr10IPv4ACLTable 1 }
        
    Zxr10IPv4ACLEntry ::=
        SEQUENCE {
            zxr10IPv4ACLName
                DisplayString,            
            zxr10IPv4ACLRuleID
                Integer32,
            zxr10IPv4ACLPermitDeny
                INTEGER,
            zxr10IPv4ACLSrcAddr
                IpAddress,
            zxr10IPv4ACLSrcWildcard
                IpAddress,         
            zxr10IPv4ACLSrcAny
                INTEGER,
            zxr10IPv4ACLDestAddr
                IpAddress,
            zxr10IPv4ACLDestWildcard
                IpAddress,         
            zxr10IPv4ACLDestAny
                INTEGER,
            zxr10IPv4ACLProtocol
                INTEGER,
            zxr10IPv4ACLSrcOpr 
                INTEGER,
            zxr10IPv4ACLSrcPort
                INTEGER,
            zxr10IPv4ACLSrcPort2
                INTEGER,
            zxr10IPv4ACLDestOpr
                INTEGER,
            zxr10IPv4ACLDestPort
                INTEGER,
            zxr10IPv4ACLDestPort2
                INTEGER,
            zxr10IPv4ACLTCPEstablish 
                INTEGER, 
            zxr10IPv4ACLICMPType
                INTEGER,  
            zxr10IPv4ACLICMPCode
                INTEGER,                
            zxr10IPv4ACLPrecedence
                Integer32,                
            zxr10IPv4ACLTOS
                Integer32,                
            zxr10IPv4ACLDSCP
                Integer32,            
            zxr10IPv4ACLStateFlag
                INTEGER,
            zxr10IPv4ACLTimerangeName
                DisplayString,
            zxr10IPv4ACLRowStatus
                RowStatus,
            zxr10IPv4ACLFragment
                INTEGER,
            zxr10IPv4ACLTcpFlagOprBitMap
                INTEGER,
            zxr10IPv4ACLTcpFlagVlaBitMap
                INTEGER,
            zxr10IPv4ACLIpBitMap
                INTEGER,
            zxr10IPv4ACLTtlOpr
                INTEGER,
            zxr10IPv4ACLTtlValue
                INTEGER,
            zxr10IPv4ACLTtlBegin
                INTEGER,
            zxr10IPv4ACLTtlEnd
                INTEGER,
            zxr10IPv4ACLRuleType
                INTEGER
    }
    
           
    zxr10IPv4ACLName  OBJECT-TYPE
        SYNTAX   DisplayString
        MAX-ACCESS  read-only
        STATUS  current
        DESCRIPTION
            "ipv4-access-list
             WORD  Name of an IPv4 access-list (1-31 characters)"
        ::= { zxr10IPv4ACLEntry 1 } 
        
            
    zxr10IPv4ACLRuleID  OBJECT-TYPE
        SYNTAX   Integer32(1..2147483644)
        MAX-ACCESS  read-only
        STATUS  current
        DESCRIPTION
            "rule
            <1-2147483644>  (Optional)ID of this rule"
        ::= { zxr10IPv4ACLEntry 2 }    

    zxr10IPv4ACLPermitDeny  OBJECT-TYPE
        SYNTAX   INTEGER{deny(0),permit(1)}
        MAX-ACCESS  read-only
        STATUS  current
        DESCRIPTION
            "deny    Specify packets to reject
             permit  Specify packets to forward"
        ::= { zxr10IPv4ACLEntry 3 }    

    zxr10IPv4ACLSrcAddr  OBJECT-TYPE
        SYNTAX   IpAddress
        MAX-ACCESS  read-only
        STATUS  current
        DESCRIPTION
            "A.B.C.D  Source address"
        ::= { zxr10IPv4ACLEntry 4 }    

    zxr10IPv4ACLSrcWildcard  OBJECT-TYPE
        SYNTAX   IpAddress
        MAX-ACCESS  read-only
        STATUS  current
        DESCRIPTION
            "A.B.C.D  Wildcard bits"
        ::= { zxr10IPv4ACLEntry 5 } 
        
    zxr10IPv4ACLSrcAny  OBJECT-TYPE 
        SYNTAX   INTEGER{invalid(0),valid(1)}
        MAX-ACCESS  read-only
        STATUS  current
        DESCRIPTION
            "Any source address"
        ::= { zxr10IPv4ACLEntry 6 } 
        
    zxr10IPv4ACLDestAddr  OBJECT-TYPE
        SYNTAX   IpAddress
        MAX-ACCESS  read-only
        STATUS  current
        DESCRIPTION
            "A.B.C.D  Destination address"
        ::= { zxr10IPv4ACLEntry 7 } 
           
    zxr10IPv4ACLDestWildcard  OBJECT-TYPE
        SYNTAX   IpAddress
        MAX-ACCESS  read-only
        STATUS  current
        DESCRIPTION
            "A.B.C.D  Destination wildcard bits"
        ::= { zxr10IPv4ACLEntry 8 } 
        
    zxr10IPv4ACLDestAny  OBJECT-TYPE 
        SYNTAX   INTEGER{invalid(0),valid(1)}
        MAX-ACCESS  read-only
        STATUS  current
        DESCRIPTION
            "Any destination address"
        ::= { zxr10IPv4ACLEntry 9 } 
  
         
    zxr10IPv4ACLProtocol  OBJECT-TYPE
        SYNTAX   INTEGER{icmp(1),igmp(2),tcp(6),udp(17),gre(47),ospf(89),
                        pim(103),vrrp(112)}
        MAX-ACCESS  read-only
        STATUS  current
        DESCRIPTION
            "<0-255>   An IP protocol number
              gre      Generic Routing Encapsulation (47)
              icmp     Internet Control Message Protocol(1)
              igmp     Internet Group Management Protocol (2)
              ip       Any internet protocol
              ospf     Open Shortest Path First Protocol (89)
              pim      Protocol Independent Multicast (103)
              tcp      Transmission Control Protocol(6)
              udp      User Datagram Protocol(17)
              vrrp     Virtual Router Redundancy Protocol (112)"
        ::= { zxr10IPv4ACLEntry 10 }
            
    zxr10IPv4ACLSrcOpr  OBJECT-TYPE
        SYNTAX   INTEGER{oprTypeInvalid(0),eq(1),ge(2),le(3),range(7)}
        MAX-ACCESS  read-only
        STATUS  current
        DESCRIPTION
            "eq       (Optional)Match only packets on a given port number                                                                                
            ge       (Optional)Match only packets with a no lower port number                                                                           
            le       (Optional)Match only packets with a no greater port number                                                                         
            range    (Optional)Match only packet on a given port range "
        ::= { zxr10IPv4ACLEntry 11 }    

      
    zxr10IPv4ACLSrcPort  OBJECT-TYPE
        SYNTAX   INTEGER{ftp(21),telnet(23),smtp(25),domain(53),bootps(67),
                 bootpc(68),tftp(69),finger(79), www(80),pop2(109),
                 pop3(110),ntp(123),snmp(161), snmptrap(162),bgp(179), 
                 pim_auto_rp(496),login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv4ACLEntry 12 }    
        
    zxr10IPv4ACLSrcPort2  OBJECT-TYPE
        SYNTAX   INTEGER{ftp(21),telnet(23),smtp(25),domain(53),bootps(67),
                 bootpc(68),tftp(69),finger(79), www(80),pop2(109),pop3(110),
                 ntp(123),snmp(161),snmptrap(162),bgp(179),pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
          ::= { zxr10IPv4ACLEntry 13 }    
        
    zxr10IPv4ACLDestOpr  OBJECT-TYPE
        SYNTAX   INTEGER{oprTypeInvalid(0),eq(1),ge(2),le(3),range(7)}
        MAX-ACCESS  read-only
        STATUS  current
        DESCRIPTION
            "eq       (Optional)Match only packets on a given port number                                                                                
            ge       (Optional)Match only packets with a no lower port number                                                                           
            le       (Optional)Match only packets with a no greater port number                                                                         
            range    (Optional)Match only packet on a given port range "
        ::= { zxr10IPv4ACLEntry 14 }    
        
    zxr10IPv4ACLDestPort  OBJECT-TYPE
        SYNTAX   INTEGER{ftp(21),telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                         
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv4ACLEntry 15 }    
        
    zxr10IPv4ACLDestPort2  OBJECT-TYPE
        SYNTAX   INTEGER{ftp(21), telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv4ACLEntry 16 }   
         
    zxr10IPv4ACLTCPEstablish  OBJECT-TYPE
        SYNTAX    INTEGER{true(1),false(0)}
        MAX-ACCESS  read-only
        STATUS  current
        DESCRIPTION
            "(Optional)Match established connections"
        ::= { zxr10IPv4ACLEntry 17 }  
     
     
        
    zxr10IPv4ACLICMPType  OBJECT-TYPE
        SYNTAX   INTEGER(0..256)
        MAX-ACCESS  read-only
        STATUS  current
        DESCRIPTION
            "0-254|256            ICMP code
            255                   Any ICMP code
            alternate-address     Alternate address (6)
            echo                  Echo (ping, 8)
            echo-reply            Echo reply (0)
            information-reply     Information replies (16)
            information-request   Information requests (15)
            mask-request          Mask requests (17)
            mask-reply            Mask replies (18)
            parameter-problem     All parameter problems (12)
            redirect              All redirects (5)
            router-advertisement  Router discovery advertisements (9)
            router-solicitation   Router discovery solicitations (10)
            source-quench         Source quenches (4)
            time-exceeded         All time exceededs (11)
            timestamp-reply       Timestamp replies (14)
            timestamp-request     Timestamp requests (13)
            traceroute            Traceroute (30)
            unreachable           All unreachables (3)"
        ::= { zxr10IPv4ACLEntry 18 }    
        
    zxr10IPv4ACLICMPCode  OBJECT-TYPE
        SYNTAX   INTEGER(0..256)
        MAX-ACCESS  read-only
        STATUS  current
        DESCRIPTION
            "0-254|256      (Optional)ICMP code
             255            Any ICMP code"
        ::= { zxr10IPv4ACLEntry 19 }    
        
    zxr10IPv4ACLPrecedence  OBJECT-TYPE
        SYNTAX   Integer32(0..7)
        MAX-ACCESS  read-only
        STATUS  current
        DESCRIPTION
            "<0-7>  Precedence level"
        ::= { zxr10IPv4ACLEntry 20 }    
        
    zxr10IPv4ACLTOS  OBJECT-TYPE
        SYNTAX   Integer32(0..15)
        MAX-ACCESS  read-only
        STATUS  current
        DESCRIPTION
            "<0-15>  Type of service(ToS)"
        ::= { zxr10IPv4ACLEntry 21 }  
          
    zxr10IPv4ACLDSCP  OBJECT-TYPE
        SYNTAX   Integer32(0..63)
        MAX-ACCESS  read-only
        STATUS  current
        DESCRIPTION
            "<0-63>  DSCP value"
        ::= { zxr10IPv4ACLEntry 22 } 
    
        
    zxr10IPv4ACLStateFlag  OBJECT-TYPE
        SYNTAX   INTEGER {active(0),inactive(1)}
        MAX-ACCESS  read-only
        STATUS  current
        DESCRIPTION
            "Timerange enable or disable flag"
        ::= { zxr10IPv4ACLEntry 23 }   
               
            
    zxr10IPv4ACLTimerangeName  OBJECT-TYPE
        SYNTAX   DisplayString
        MAX-ACCESS  read-only
        STATUS  current
        DESCRIPTION
             "time-range  (Optional)Configure time range"
        ::= { zxr10IPv4ACLEntry 24 }  
              
    zxr10IPv4ACLRowStatus   OBJECT-TYPE  
        SYNTAX   RowStatus
        MAX-ACCESS  read-only
        STATUS  current
        DESCRIPTION
       "createAndGo(4)  Configure IPv4 ACL or rule
        destroy(6)  Delete IPv4 ACL or rule"        
        ::= { zxr10IPv4ACLEntry 25 }  
       
    zxr10IPv4ACLFragment  OBJECT-TYPE
        SYNTAX     INTEGER {match_unfragment(0), match_fragment(1)}
        MAX-ACCESS  read-only        
        STATUS  current
        DESCRIPTION
            "Fragment enable or disable flag"
        ::= { zxr10IPv4ACLEntry 26 }         
    
    zxr10IPv4ACLTcpFlagOprBitMap  OBJECT-TYPE
        SYNTAX   INTEGER(0..63)
        MAX-ACCESS  read-only
        STATUS  current
        DESCRIPTION
            "Match on the specify TCP flag bit.  
            1 means + , and 0 means -.
            Bit from low to high represents:
            first     :  ack
            second    :  fin
            third     :  psh
            fourth    :  rst
            fifth     :  syn
            sixth     :  urg"
        ::= { zxr10IPv4ACLEntry 27 }
        
     zxr10IPv4ACLTcpFlagVlaBitMap  OBJECT-TYPE
        SYNTAX   INTEGER(0..63)
        MAX-ACCESS  read-only
        STATUS  current
        DESCRIPTION
            "Match when the TCP flag set or not. 
            1 means setted , and 0 means not.
            Bit from low to high represents:
            first     :  ack
            second    :  fin
            third     :  psh
            fourth    :  rst
            fifth     :  syn
            sixth     :  urg"
        ::= { zxr10IPv4ACLEntry 28 }  
    
     zxr10IPv4ACLIpBitMap  OBJECT-TYPE
        SYNTAX   INTEGER(0..127)
        MAX-ACCESS  read-only
        STATUS  current
        DESCRIPTION
            "Match on the specify ip flag bit. 
            1 means setted , and 0 means not.
            Bit from low to high represents:
            first     :  DSCP
            second    :  TOS
            third     :  Precedence
            fourth    :  ICMPCode
            fifth     :  ICMPType
            sixth     :  ipprotocol
            seventh   :  fragment    (obsolete, default value 1)"
        ::= { zxr10IPv4ACLEntry 29 }
    
    
     zxr10IPv4ACLTtlOpr  OBJECT-TYPE
        SYNTAX   INTEGER{invalid(0),eq(1),ge(2),le(3),neq(6),range(7)}
        MAX-ACCESS  read-only
        STATUS  current
        DESCRIPTION
            "eq       (Optional)Match only packets on a given ttl value                                                                                
            ge       (Optional)Match only packets with a no lower ttl value                                                                           
            le       (Optional)Match only packets with a no greater ttl value
            neq      (Optional)Match only packets with a no equeal ttl value                                                           
            range    (Optional)Match only packet on a given ttl value range "
        ::= { zxr10IPv4ACLEntry 30 }     
        
     zxr10IPv4ACLTtlValue  OBJECT-TYPE
        SYNTAX   INTEGER(0..63)
        MAX-ACCESS  read-only
        STATUS  current
        DESCRIPTION
            "The TTL value"
        ::= { zxr10IPv4ACLEntry 31 }
    
     zxr10IPv4ACLTtlBegin  OBJECT-TYPE
        SYNTAX   INTEGER(0..63)
        MAX-ACCESS  read-only
        STATUS  current
        DESCRIPTION
            "The TTL value Begin"
        ::= { zxr10IPv4ACLEntry 32 }    
    
     zxr10IPv4ACLTtlEnd  OBJECT-TYPE
        SYNTAX   INTEGER(0..63)
        MAX-ACCESS  read-only
        STATUS  current
        DESCRIPTION
            "The TTL value Begin"
        ::= { zxr10IPv4ACLEntry 33 }       
    
     zxr10IPv4ACLRuleType  OBJECT-TYPE
        SYNTAX   INTEGER{standard_rule(1),extend_rule(2)}
        MAX-ACCESS  read-only
        STATUS  current
        DESCRIPTION
            "The acl rule type"
        ::= { zxr10IPv4ACLEntry 34 }    
    
    
    --- IPv6 ACL
    zxr10IPv6ACLTable  OBJECT-TYPE
        SYNTAX  SEQUENCE OF Zxr10IPv6ACLEntry
        MAX-ACCESS  not-accessible
        STATUS  current
        DESCRIPTION
            "IPv6 ACL Table"
        ::= { zxr10ACL 2 }

    zxr10IPv6ACLEntry  OBJECT-TYPE
        SYNTAX  Zxr10IPv6ACLEntry
        MAX-ACCESS  not-accessible
        STATUS  current
        DESCRIPTION
            "IPv6 ACL"
        INDEX  { zxr10IPv6ACLName,
                 zxr10IPv6ACLRuleID }
        ::= { zxr10IPv6ACLTable 1 }
        
    Zxr10IPv6ACLEntry ::=
        SEQUENCE {
            zxr10IPv6ACLName
                DisplayString,            
            zxr10IPv6ACLRuleID
                Integer32,
            zxr10IPv6ACLPermitDeny
                INTEGER, 
            zxr10IPv6ACLflowlabel
                Integer32,
            zxr10IPv6ACLSrcAddr
                DisplayString,
            zxr10IPv6ACLSrcWildcard
                INTEGER,         
            zxr10IPv6ACLSrcAny
                INTEGER,
            zxr10IPv6ACLDestAddr   
                DisplayString,
            zxr10IPv6ACLDestWildcard
                INTEGER,         
            zxr10IPv6ACLDestAny
                INTEGER,
            zxr10IPv6ACLProtocol
                INTEGER,
            zxr10IPv6ACLSrcOpr 
                INTEGER,
            zxr10IPv6ACLSrcPort
                INTEGER,
            zxr10IPv6ACLSrcPort2
                INTEGER,
            zxr10IPv6ACLDestOpr
                INTEGER,
            zxr10IPv6ACLDestPort
                INTEGER,
            zxr10IPv6ACLDestPort2
                INTEGER,
            zxr10IPv6ACLTCPEstablish 
                INTEGER,             
            zxr10IPv6ACLTcpFlagOprBitMap
                INTEGER,                 
            zxr10IPv6ACLTcpFlagVlaBitMap
                INTEGER,                 
            zxr10IPv6ACLHeaderOptionBitMap
                INTEGER,             
            zxr10IPv6ACLICMPType
                INTEGER,  
            zxr10IPv6ACLICMPCode
                INTEGER, 
            zxr10IPv6ACLDSCP
                Integer32,
            zxr10IPv6ACLStateFlag
                INTEGER,
            zxr10IPv6ACLTimerangeName
                DisplayString,
            zxr10IPv6ACLRowStatus
                RowStatus,
            zxr10IPv6ACLIpBitMap
                INTEGER                 
    }
    
           
    zxr10IPv6ACLName  OBJECT-TYPE
        SYNTAX   DisplayString
        MAX-ACCESS  read-only
        STATUS  current
        DESCRIPTION
            "ipv6-access-list  
             WORD  Name of an IPv6 access-list (1-31 characters)"
        ::= { zxr10IPv6ACLEntry 1 } 
        
            
    zxr10IPv6ACLRuleID  OBJECT-TYPE
        SYNTAX   Integer32(1..2147483644)
        MAX-ACCESS  read-only
        STATUS  current
        DESCRIPTION
            "rule
            <1-2147483644>  (Optional)ID of this rule"
        ::= { zxr10IPv6ACLEntry 2 }    

    zxr10IPv6ACLPermitDeny  OBJECT-TYPE
        SYNTAX   INTEGER{deny(0),permit(1)}
        MAX-ACCESS  read-only
        STATUS  current
        DESCRIPTION
            "deny    Specify packets to reject
             permit  Specify packets to forward"
        ::= { zxr10IPv6ACLEntry 3 }  
        
    zxr10IPv6ACLflowlabel  OBJECT-TYPE
        SYNTAX   Integer32(0..1048575)
        MAX-ACCESS  read-only
        STATUS  current
        DESCRIPTION
            "<0-1048575>  Flowlabel value"
        ::= { zxr10IPv6ACLEntry 4 }   

    zxr10IPv6ACLSrcAddr  OBJECT-TYPE
        SYNTAX   DisplayString
        MAX-ACCESS  read-only
        STATUS  current
        DESCRIPTION
            "<X:X::X:X>  Source address"
        ::= { zxr10IPv6ACLEntry 5 } 
    
    zxr10IPv6ACLSrcWildcard  OBJECT-TYPE
        SYNTAX   INTEGER(0..128)
        MAX-ACCESS  read-only
        STATUS  current
        DESCRIPTION
            "<0-128>  Source Wildcard"
        ::= { zxr10IPv6ACLEntry 6 }    

     
    zxr10IPv6ACLSrcAny  OBJECT-TYPE 
        SYNTAX   INTEGER{invalid(0),valid(1)}
        MAX-ACCESS  read-only
        STATUS  current
        DESCRIPTION
            "Any source address"
        ::= { zxr10IPv6ACLEntry 7 } 
        
    zxr10IPv6ACLDestAddr  OBJECT-TYPE
        SYNTAX   DisplayString
        MAX-ACCESS  read-only
        STATUS  current
        DESCRIPTION
            "<X:X::X:X>  Destination address"
        ::= { zxr10IPv6ACLEntry 8 } 
        
    zxr10IPv6ACLDestWildcard  OBJECT-TYPE
        SYNTAX   INTEGER(0..128)
        MAX-ACCESS  read-only
        STATUS  current
        DESCRIPTION
            "<0-128>  Destination Wildcard"
        ::= { zxr10IPv6ACLEntry 9 }
           
    zxr10IPv6ACLDestAny  OBJECT-TYPE 
        SYNTAX   INTEGER{invalid(0),valid(1)}
        MAX-ACCESS  read-only
        STATUS  current
        DESCRIPTION
            "Any destination address"
        ::= { zxr10IPv6ACLEntry 10 } 
  
        
    zxr10IPv6ACLProtocol  OBJECT-TYPE
        SYNTAX   INTEGER{igmp(2),tcp(6),udp(17),gre(47),icmp(58),ospf(89),
                 pim(103),vrrp(112)}
        MAX-ACCESS  read-only
        STATUS  current
        DESCRIPTION
            " <0-255>  An IP protocol number
              gre      Generic Routing Encapsulation (47)
              icmp     Internet Control Message Protocol(58)
              igmp     Internet Group Management Protocol (2)
              ip       Any internet protocol
              ospf     Open Shortest Path First Protocol (89)
              pim      Protocol Independent Multicast (103)
              tcp      Transmission Control Protocol(6)
              udp      User Datagram Protocol(17)
              vrrp     Virtual Router Redundancy Protocol (112)"
        ::= { zxr10IPv6ACLEntry 11 }
            
    zxr10IPv6ACLSrcOpr  OBJECT-TYPE
        SYNTAX   INTEGER{oprTypeInvalid(0),eq(1),ge(2),le(3),range(7)}
        MAX-ACCESS  read-only
        STATUS  current
        DESCRIPTION
            "eq       (Optional)Match only packets on a given port number                                                                                
            ge       (Optional)Match only packets with a no lower port number                                                                           
            le       (Optional)Match only packets with a no greater port number                                                                         
            range    (Optional)Match only packet on a given port range "
        ::= { zxr10IPv6ACLEntry 12 }    
       
    zxr10IPv6ACLSrcPort  OBJECT-TYPE
        SYNTAX   INTEGER{ftp(21),telnet(23),smtp(25),domain(53),bootps(67),
                 bootpc(68),tftp(69),finger(79), www(80),pop2(109),pop3(110),
                 ntp(123),snmp(161), snmptrap(162),bgp(179),pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv6ACLEntry 13 }    
        
    zxr10IPv6ACLSrcPort2  OBJECT-TYPE
        SYNTAX   INTEGER{ftp(21),telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv6ACLEntry 14 }    
        
    zxr10IPv6ACLDestOpr  OBJECT-TYPE
        SYNTAX   INTEGER{oprTypeInvalid(0),eq(1),ge(2),le(3),range(7)}
        MAX-ACCESS  read-only
        STATUS  current
        DESCRIPTION
            "eq       (Optional)Match only packets on a given port number                                                                                
            ge       (Optional)Match only packets with a no lower port number                                                                           
            le       (Optional)Match only packets with a no greater port number                                                                         
            range    (Optional)Match only packet on a given port range "
        ::= { zxr10IPv6ACLEntry 15 }    
        
    zxr10IPv6ACLDestPort  OBJECT-TYPE
        SYNTAX   INTEGER{ftp(21),telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                         
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv6ACLEntry 16 }    
       
    zxr10IPv6ACLDestPort2  OBJECT-TYPE
        SYNTAX   INTEGER{ftp(21), telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv6ACLEntry 17 }   
          
    zxr10IPv6ACLTCPEstablish  OBJECT-TYPE
        SYNTAX    INTEGER{true(1),false(0)}
        MAX-ACCESS  read-only
        STATUS  current
        DESCRIPTION
            "(Optional)Match established connections"
        ::= { zxr10IPv6ACLEntry 18 }  
     
    zxr10IPv6ACLTcpFlagOprBitMap  OBJECT-TYPE
        SYNTAX   INTEGER(0..63)
        MAX-ACCESS  read-only
        STATUS  current
        DESCRIPTION
            "Match on the specify TCP flag bit.  
            1 means + , and 0 means -.
            Bit from low to high represents:
            first     :  ack
            second    :  fin
            third     :  psh
            fourth    :  rst
            fifth     :  syn
            sixth     :  urg"
        ::= { zxr10IPv6ACLEntry 19 }
        
     zxr10IPv6ACLTcpFlagVlaBitMap  OBJECT-TYPE
        SYNTAX   INTEGER(0..63)
        MAX-ACCESS  read-only
        STATUS  current
        DESCRIPTION
            "Match when the TCP flag set or not. 
            1 means setted , and 0 means not.
            Bit from low to high represents:
            first     :  ack
            second    :  fin
            third     :  psh
            fourth    :  rst
            fifth     :  syn
            sixth     :  urg"
        ::= { zxr10IPv6ACLEntry 20 }      
        
     zxr10IPv6ACLHeaderOptionBitMap  OBJECT-TYPE
        SYNTAX   INTEGER(0..63)
        MAX-ACCESS  read-only
        STATUS  current
        DESCRIPTION
            "Matches if the specify IPv6 header is present.
            1 means setted , and 0 means not.
            Bit from low to high represents:
            first     :  hop-by-hop   
            second    :  destopts 
            third     :  routing        
            fourth    :  fragments
            fifth     :  authen 
            sixth     :  esp"  
        ::= { zxr10IPv6ACLEntry 21 }
     
        
    zxr10IPv6ACLICMPType  OBJECT-TYPE
        SYNTAX   INTEGER(0..256)
        MAX-ACCESS  read-only
        STATUS  current
        DESCRIPTION
            "0-254|256               ICMP type
            255                      Any ICMP type
            destination-unreachable  Destination unreachable (1)
            echo-reply               Echo reply (129)
            echo-request             Echo request (ping, 128)
            mld-query                Multicast Listener Discovery Query (130)
            mld-reduction            Multicast Listener Discovery Reduction 
                                     (132)
            mld-report               Multicast Listener Discovery Report (131)
            nd-na                    Neighbor discovery neighbor advertisments 
                                     (136)
            nd-ns                    Neighbor discovery neighbor solicitations 
                                     (135)
            packet-too-big           Packet too big (2)
            parameter-problem        All parameter problems (4)
            redirect                 Neighbor redirect (137)
            router-advertisment      Neighbor discovery router advertisments 
                                     (134)
            router-renumbering       All router renumbering (138)
            router-solicitation      Neighbor discovery router solicitations 
                                     (133)
            time-exceeded            Time exceeded (3)"
        ::= { zxr10IPv6ACLEntry 22 }    
        
    zxr10IPv6ACLICMPCode  OBJECT-TYPE
        SYNTAX   INTEGER(0..256)
        MAX-ACCESS  read-only
        STATUS  current
        DESCRIPTION
            "0-254|256            ICMP code
            255                   Any ICMP code"
        ::= { zxr10IPv6ACLEntry 23 }    
        
             
    zxr10IPv6ACLDSCP  OBJECT-TYPE
        SYNTAX   Integer32(0..63)
        MAX-ACCESS  read-only
        STATUS  current
        DESCRIPTION
            "<0-63>  DSCP value"
        ::= { zxr10IPv6ACLEntry 24 }
    
    zxr10IPv6ACLStateFlag  OBJECT-TYPE
        SYNTAX   INTEGER {active(0),inactive(1)}
        MAX-ACCESS  read-only
        STATUS  current
        DESCRIPTION
            "Timerange enable or disable flag"
        ::= { zxr10IPv6ACLEntry 25 }     
               
            
    zxr10IPv6ACLTimerangeName  OBJECT-TYPE
        SYNTAX   DisplayString
        MAX-ACCESS  read-only
        STATUS  current
        DESCRIPTION
             "time-range  (Optional)Configure time range"
        ::= { zxr10IPv6ACLEntry 26 }  
              
    zxr10IPv6ACLRowStatus   OBJECT-TYPE  
        SYNTAX   RowStatus
        MAX-ACCESS  read-only
        STATUS  current
        DESCRIPTION
       "createAndGo(4)  Configure IPv6 ACL or rule
        destroy(6)  Delete IPv6 ACL or rule"        
        ::= { zxr10IPv6ACLEntry 27 }  
        
     zxr10IPv6ACLIpBitMap  OBJECT-TYPE
        SYNTAX   INTEGER(0..127)
        MAX-ACCESS  read-only
        STATUS  current
        DESCRIPTION
            "Match on the specify ip flag bit. 
            1 means setted , and 0 means not.
            Bit from low to high represents:
            first     :  DSCP
            second    :              (reserved, default value 0)
            third     :              (reserved, default value 0)
            fourth    :  ICMPCode
            fifth     :  ICMPType
            sixth     :  FlowLabel
            seventh   :  ipv6protocol"
        ::= { zxr10IPv6ACLEntry 28 }         
        
 
  
    --- link ACL

    zxr10LinkACLTable  OBJECT-TYPE
        SYNTAX  SEQUENCE OF Zxr10LinkACLEntry
        MAX-ACCESS  not-accessible
        STATUS  current
        DESCRIPTION
            "Link ACL"
        ::= { zxr10ACL 3 }

    zxr10LinkACLEntry  OBJECT-TYPE
        SYNTAX  Zxr10LinkACLEntry
        MAX-ACCESS  not-accessible
        STATUS  current
        DESCRIPTION
            "Link ACL"
        INDEX  { zxr10LinkACLName,
                 zxr10LinkACLRuleID }
        ::= { zxr10LinkACLTable 1 }
        
    Zxr10LinkACLEntry ::=
        SEQUENCE {
                      
            zxr10LinkACLName
                DisplayString,               
            zxr10LinkACLRuleID
                Integer32,
            zxr10LinkACLPermitDeny
                INTEGER,
            zxr10LinkACLProtocol
                Integer32,
            zxr10LinkACLSourceMAC 
               DisplayString, 
            zxr10LinkACLSourceMACWildcard
                DisplayString,   
            zxr10LinkACLSourceMACAny
                INTEGER,   
            zxr10LinkACLDestinationMAC 
                DisplayString,
            zxr10LinkACLDestinationMACWildCard
                DisplayString,
            zxr10LinkACLDestinationMACAny
                INTEGER,   
            zxr10LinkACLIncos
                Integer32, 
            zxr10LinkACLOutCos
                Integer32,  
            zxr10LinkACLInVlanIDBegin
                Integer32,
            zxr10LinkACLOutVlanIDBegin
               Integer32,                 
            zxr10LinkACLStateFlag
                INTEGER, 
            zxr10LinkACLTimerangeName
                DisplayString,          
            zxr10LinkACLRowStatus
                RowStatus,
            zxr10LinkACLLinkBitMap
                INTEGER,
            zxr10LinkACLInVlanIDEnd
                Integer32,
            zxr10LinkACLOutVlanIDEnd
                Integer32             
       }
    
        
    zxr10LinkACLName  OBJECT-TYPE
        SYNTAX   DisplayString
        MAX-ACCESS  read-only
        STATUS  current
        DESCRIPTION
            "link-access-list
             WORD  Name of an link access-list (1-31 characters)"
        ::= { zxr10LinkACLEntry 1 } 
            
    zxr10LinkACLRuleID  OBJECT-TYPE
        SYNTAX   Integer32(1..2147483644)
        MAX-ACCESS  read-only
        STATUS  current
        DESCRIPTION
            "rule
            <1-2147483644>  (Optional)ID of this rule"
        ::= { zxr10LinkACLEntry 2 }    

    zxr10LinkACLPermitDeny  OBJECT-TYPE
        SYNTAX   INTEGER{deny(0),permit(1)}
        MAX-ACCESS  read-only
        STATUS  current
        DESCRIPTION
            "deny    Specify packets to reject
             permit  Specify packets to forward"
        ::= { zxr10LinkACLEntry 3 }    

    zxr10LinkACLProtocol  OBJECT-TYPE
        SYNTAX   Integer32(0..65535)   
        MAX-ACCESS  read-only
        STATUS  current
        DESCRIPTION
            "<0-65535>  Link protocal "
        ::= { zxr10LinkACLEntry 4 } 
    
    zxr10LinkACLSourceMAC  OBJECT-TYPE
        SYNTAX   DisplayString
        MAX-ACCESS  read-only
        STATUS  current
        DESCRIPTION
            "<xxxx.xxxx.xxxx>  Source MAC address"
        ::= { zxr10LinkACLEntry 5 }
    
    zxr10LinkACLSourceMACWildcard  OBJECT-TYPE
        SYNTAX   DisplayString
        MAX-ACCESS  read-only
        STATUS  current
        DESCRIPTION
            "<xxxx.xxxx.xxxx>  Source MAC wildcard"
        ::= { zxr10LinkACLEntry 6 } 
    
    zxr10LinkACLSourceMACAny  OBJECT-TYPE 
        SYNTAX   INTEGER{invalid(0),valid(1)}
        MAX-ACCESS  read-only
        STATUS  current
        DESCRIPTION
            "any               Any source MAC address"
        ::= { zxr10LinkACLEntry 7 }
    
    zxr10LinkACLDestinationMAC  OBJECT-TYPE
        SYNTAX   DisplayString
        MAX-ACCESS  read-only
        STATUS  current
        DESCRIPTION
            "<xxxx.xxxx.xxxx>  Destination MAC address"
        ::= { zxr10LinkACLEntry 8 } 
        
     zxr10LinkACLDestinationMACWildCard  OBJECT-TYPE
        SYNTAX   DisplayString
        MAX-ACCESS  read-only
        STATUS  current
        DESCRIPTION
            "<xxxx.xxxx.xxxx>  Destination MAC wildcard"
        ::= { zxr10LinkACLEntry 9 } 
        
     zxr10LinkACLDestinationMACAny    OBJECT-TYPE 
        SYNTAX   INTEGER{invalid(0),valid(1)}
        MAX-ACCESS  read-only
        STATUS  current
        DESCRIPTION
            "any               Any destination MAC address"
        ::= { zxr10LinkACLEntry 10 }
     
     
     zxr10LinkACLIncos     OBJECT-TYPE
        SYNTAX   Integer32(0..7)
        MAX-ACCESS  read-only
        STATUS  current
        DESCRIPTION
            "<0-7>  Value of inner cos"
        ::= { zxr10LinkACLEntry 11 }     
        
     zxr10LinkACLOutCos   OBJECT-TYPE
        SYNTAX   Integer32(0..7)
        MAX-ACCESS  read-only
        STATUS  current
        DESCRIPTION
            "<0-7>  Value of outer cos"
        ::= { zxr10LinkACLEntry 12 }
             
    zxr10LinkACLInVlanIDBegin  OBJECT-TYPE
        SYNTAX   Integer32(1..4094)
        MAX-ACCESS  read-only
        STATUS  current
        DESCRIPTION
            "<1-4094>  Value of inner vlan"
        ::= { zxr10LinkACLEntry 13 } 
        
    zxr10LinkACLOutVlanIDBegin   OBJECT-TYPE
        SYNTAX   Integer32(1..4094)
        MAX-ACCESS  read-only
        STATUS  current
        DESCRIPTION
            "<1-4094>  Value of outer vlan"
        ::= { zxr10LinkACLEntry 14 } 
                                
    zxr10LinkACLStateFlag  OBJECT-TYPE
        SYNTAX   INTEGER {active(0),inactive(1)}
        MAX-ACCESS  read-only
        STATUS  current
        DESCRIPTION
            "Timerange enable or disable flag"
        ::= { zxr10LinkACLEntry 15 } 
        
    zxr10LinkACLTimerangeName  OBJECT-TYPE
        SYNTAX   DisplayString
        MAX-ACCESS  read-only
        STATUS  current
        DESCRIPTION
            "time-range  (Optional)Configure time range
              WORD  Time range name (1-31 characters)"
        ::= { zxr10LinkACLEntry 16 }           

    zxr10LinkACLRowStatus   OBJECT-TYPE
        SYNTAX   RowStatus
        MAX-ACCESS  read-only
        STATUS  current
        DESCRIPTION
        "createAndGo(4)  Configure ACL or rule
        destroy(6)  Delete ACL or rule"
        ::= { zxr10LinkACLEntry 17 } 
        
     zxr10LinkACLLinkBitMap  OBJECT-TYPE
        SYNTAX   INTEGER(0..63)
        MAX-ACCESS  read-only
        STATUS  current
        DESCRIPTION
            "Match on the specify limk flag bit. 
            1 means setted , and 0 means not.
            Bit from low to high represents:
            first     :  in cos
            second    :  out cos
            third     :  in vlan
            fourth    :  out vlan
            fifth     :  linkprotocol"
        ::= { zxr10LinkACLEntry 18 }
  
      zxr10LinkACLInVlanIDEnd  OBJECT-TYPE
        SYNTAX   Integer32(1..4094)
        MAX-ACCESS  read-only
        STATUS  current
        DESCRIPTION
            "<1-4094>  Value of inner vlan"
        ::= { zxr10LinkACLEntry 19 } 
        
     zxr10LinkACLOutVlanIDEnd   OBJECT-TYPE
        SYNTAX   Integer32(1..4094)
        MAX-ACCESS  read-only
        STATUS  current
        DESCRIPTION
            "<1-4094>  Value of outer vlan"
        ::= { zxr10LinkACLEntry 20 } 
  
  --- IPv4 Mixexd ACL 

    zxr10IPv4MixedACLTable  OBJECT-TYPE
        SYNTAX  SEQUENCE OF Zxr10IPv4MixedACLEntry
        MAX-ACCESS  not-accessible
        STATUS  current
        DESCRIPTION
            "IPv4 Mixed ACL Table"
        ::= { zxr10ACL 4 }

    zxr10IPv4MixedACLEntry  OBJECT-TYPE
        SYNTAX  Zxr10IPv4MixedACLEntry
        MAX-ACCESS  not-accessible
        STATUS  current
        DESCRIPTION
            "IPv4Mixed ACL"
        INDEX  { zxr10IPv4MixedACLName,
                 zxr10IPv4MixedACLRuleID }
        ::= { zxr10IPv4MixedACLTable 1 }
        
    Zxr10IPv4MixedACLEntry ::=
        SEQUENCE {
            zxr10IPv4MixedACLName
                DisplayString,            
            zxr10IPv4MixedACLRuleID
                Integer32,
            zxr10IPv4MixedACLPermitDeny
                INTEGER,
            zxr10IPv4MixedACLLinkProtocol
                Integer32,
            zxr10IPv4MixedACLSourceMAC 
                DisplayString, 
            zxr10IPv4MixedACLSourceMACWildcard
                DisplayString,   
            zxr10IPv4MixedACLSourceMACAny
                INTEGER,   
            zxr10IPv4MixedACLDestinationMAC 
                DisplayString,
            zxr10IPv4MixedACLDestinationMACWildCard
                DisplayString,
            zxr10IPv4MixedACLDestinationMACAny
                INTEGER,   
            zxr10IPv4MixedACLIncos
                Integer32, 
            zxr10IPv4MixedACLOutCos
                Integer32,  
            zxr10IPv4MixedACLInVlanIDBegin
                Integer32,
            zxr10IPv4MixedACLOutVlanIDBegin
                Integer32,       
            zxr10IPv4MixedACLSrcAddr
                IpAddress,
            zxr10IPv4MixedACLSrcWildcard
                IpAddress,         
            zxr10IPv4MixedACLSrcAny
                INTEGER,
            zxr10IPv4MixedACLDestAddr
                IpAddress,
            zxr10IPv4MixedACLDestWildcard
                IpAddress,         
            zxr10IPv4MixedACLDestAny
                INTEGER,
            zxr10IPv4MixedACLProtocol
                INTEGER,
            zxr10IPv4MixedACLSrcOpr 
                INTEGER,
            zxr10IPv4MixedACLSrcPort
                INTEGER,
            zxr10IPv4MixedACLSrcPort2
                INTEGER,
            zxr10IPv4MixedACLDestOpr
                INTEGER,
            zxr10IPv4MixedACLDestPort
                INTEGER,
            zxr10IPv4MixedACLDestPort2
                INTEGER,
            zxr10IPv4MixedACLTCPEstablish 
                INTEGER, 
            zxr10IPv4MixedACLICMPType
                INTEGER,  
            zxr10IPv4MixedACLICMPCode
                INTEGER,                
            zxr10IPv4MixedACLPrecedence
                Integer32,                
            zxr10IPv4MixedACLTOS
                Integer32,                
            zxr10IPv4MixedACLDSCP
                Integer32,
            zxr10IPv4MixedACLStateFlag
                INTEGER,
            zxr10IPv4MixedACLTimerangeName
                DisplayString,
            zxr10IPv4MixedACLRowStatus
                RowStatus,
            zxr10IPv4MixedACLIpBitMap
                INTEGER,
            zxr10IPv4MixedACLLinkBitMap
                INTEGER,
            zxr10IPv4MixedACLInVlanIDEnd
                Integer32,
            zxr10IPv4MixedACLOutVlanIDEnd
                Integer32,
            zxr10IPv4MixedACLFragment
                INTEGER                                                                       
    }
    
           
    zxr10IPv4MixedACLName  OBJECT-TYPE
        SYNTAX   DisplayString
        MAX-ACCESS  read-only
        STATUS  current
        DESCRIPTION
            "IPv4Mixed-access-list
             WORD  Name of an IPv4 mixed access-list (1-31 characters)"
        ::= { zxr10IPv4MixedACLEntry 1 } 
        
            
    zxr10IPv4MixedACLRuleID  OBJECT-TYPE
        SYNTAX   Integer32(1..2147483644)
        MAX-ACCESS  read-only
        STATUS  current
        DESCRIPTION
            "rule
            <1-2147483644>  (Optional)ID of this rule"
        ::= { zxr10IPv4MixedACLEntry 2 }    

    zxr10IPv4MixedACLPermitDeny  OBJECT-TYPE
        SYNTAX   INTEGER{deny(0),permit(1)}
        MAX-ACCESS  read-only
        STATUS  current
        DESCRIPTION
            "deny    Specify packets to reject
             permit  Specify packets to forward"
        ::= { zxr10IPv4MixedACLEntry 3 } 
    
    zxr10IPv4MixedACLLinkProtocol  OBJECT-TYPE
        SYNTAX   Integer32(0..65535)   
        MAX-ACCESS  read-only
        STATUS  current
        DESCRIPTION
            "<0-65535>  Link protocal "
        ::= { zxr10IPv4MixedACLEntry 4 } 
    
    zxr10IPv4MixedACLSourceMAC  OBJECT-TYPE
        SYNTAX   DisplayString
        MAX-ACCESS  read-only
        STATUS  current
        DESCRIPTION
            "<xxxx.xxxx.xxxx>  Source MAC address"
        ::= { zxr10IPv4MixedACLEntry 5 }
    
    zxr10IPv4MixedACLSourceMACWildcard  OBJECT-TYPE
        SYNTAX   DisplayString
        MAX-ACCESS  read-only
        STATUS  current
        DESCRIPTION
            "<xxxx.xxxx.xxxx>  Source MAC wildcard"
        ::= { zxr10IPv4MixedACLEntry 6 } 
    
    zxr10IPv4MixedACLSourceMACAny  OBJECT-TYPE 
        SYNTAX   INTEGER{invalid(0),valid(1)}
        MAX-ACCESS  read-only
        STATUS  current
        DESCRIPTION
            "any               Any source MAC address"
        ::= { zxr10IPv4MixedACLEntry 7 }
    
    zxr10IPv4MixedACLDestinationMAC  OBJECT-TYPE
        SYNTAX   DisplayString
        MAX-ACCESS  read-only
        STATUS  current
        DESCRIPTION
            "<xxxx.xxxx.xxxx>  Destination MAC address"
        ::= { zxr10IPv4MixedACLEntry 8 } 
        
     zxr10IPv4MixedACLDestinationMACWildCard  OBJECT-TYPE
        SYNTAX   DisplayString
        MAX-ACCESS  read-only
        STATUS  current
        DESCRIPTION
            "<xxxx.xxxx.xxxx>  Destination MAC wildcard"
        ::= { zxr10IPv4MixedACLEntry 9 } 
        
     zxr10IPv4MixedACLDestinationMACAny    OBJECT-TYPE 
        SYNTAX   INTEGER{invalid(0),valid(1)}
        MAX-ACCESS  read-only
        STATUS  current
        DESCRIPTION
            "any               Any destination MAC address"
        ::= { zxr10IPv4MixedACLEntry 10 }
     
     
     zxr10IPv4MixedACLIncos     OBJECT-TYPE
        SYNTAX   Integer32(0..7)
        MAX-ACCESS  read-only
        STATUS  current
        DESCRIPTION
            "<0-7>  Value of inner cos"
        ::= { zxr10IPv4MixedACLEntry 11 }     
        
     zxr10IPv4MixedACLOutCos   OBJECT-TYPE
        SYNTAX   Integer32(0..7)
        MAX-ACCESS  read-only
        STATUS  current
        DESCRIPTION
            "<0-7>  Value of outer cos"
        ::= { zxr10IPv4MixedACLEntry 12 }
             
    zxr10IPv4MixedACLInVlanIDBegin  OBJECT-TYPE
        SYNTAX   Integer32(1..4094)
        MAX-ACCESS  read-only
        STATUS  current
        DESCRIPTION
            "<1-4094>  Value of inner vlan"
        ::= { zxr10IPv4MixedACLEntry 13 } 
        
    zxr10IPv4MixedACLOutVlanIDBegin   OBJECT-TYPE
        SYNTAX   Integer32(1..4094)
        MAX-ACCESS  read-only
        STATUS  current
        DESCRIPTION
            "<1-4094>  Value of outer vlan"
        ::= { zxr10IPv4MixedACLEntry 14 }
    
    zxr10IPv4MixedACLSrcAddr  OBJECT-TYPE
        SYNTAX   IpAddress
        MAX-ACCESS  read-only
        STATUS  current
        DESCRIPTION
            "A.B.C.D  Source address"
        ::= { zxr10IPv4MixedACLEntry 15 }    

    zxr10IPv4MixedACLSrcWildcard  OBJECT-TYPE
        SYNTAX   IpAddress
        MAX-ACCESS  read-only
        STATUS  current
        DESCRIPTION
            "A.B.C.D  Wildcard bits"
        ::= { zxr10IPv4MixedACLEntry 16 } 
        
    zxr10IPv4MixedACLSrcAny  OBJECT-TYPE 
        SYNTAX   INTEGER{invalid(0),valid(1)}
        MAX-ACCESS  read-only
        STATUS  current
        DESCRIPTION
            "Any source address"
        ::= { zxr10IPv4MixedACLEntry 17 } 
        
    zxr10IPv4MixedACLDestAddr  OBJECT-TYPE
        SYNTAX   IpAddress
        MAX-ACCESS  read-only
        STATUS  current
        DESCRIPTION
            "A.B.C.D  Destination address"
        ::= { zxr10IPv4MixedACLEntry 18 } 
           
    zxr10IPv4MixedACLDestWildcard  OBJECT-TYPE
        SYNTAX   IpAddress
        MAX-ACCESS  read-only
        STATUS  current
        DESCRIPTION
            "A.B.C.D  Destination wildcard bits"
        ::= { zxr10IPv4MixedACLEntry 19 } 
        
    zxr10IPv4MixedACLDestAny  OBJECT-TYPE 
        SYNTAX   INTEGER{invalid(0),valid(1)}
        MAX-ACCESS  read-only
        STATUS  current
        DESCRIPTION
            "Any destination address"
        ::= { zxr10IPv4MixedACLEntry 20 } 
  
         
    zxr10IPv4MixedACLProtocol  OBJECT-TYPE
        SYNTAX   INTEGER{icmp(1),igmp(2),tcp(6),udp(17),gre(47),ospf(89),
                 pim(103),vrrp(112)}
        MAX-ACCESS  read-only
        STATUS  current
        DESCRIPTION
            " <0-255>  An IP protocol number
              gre      Generic Routing Encapsulation (47)
              icmp     Internet Control Message Protocol(1)
              igmp     Internet Group Management Protocol (2)
              ip       Any internet protocol
              ospf     Open Shortest Path First Protocol (89)
              pim      Protocol Independent Multicast (103)
              tcp      Transmission Control Protocol(6)
              udp      User Datagram Protocol(17)
              vrrp     Virtual Router Redundancy Protocol (112)"
        ::= { zxr10IPv4MixedACLEntry 21 }
            
    zxr10IPv4MixedACLSrcOpr  OBJECT-TYPE
        SYNTAX   INTEGER{oprTypeInvalid(0),eq(1),ge(2),le(3),range(7)}
        MAX-ACCESS  read-only
        STATUS  current
        DESCRIPTION
            "eq       (Optional)Match only packets on a given port number                                                                                
            ge       (Optional)Match only packets with a no lower port number                                                                           
            le       (Optional)Match only packets with a no greater port number                                                                         
            range    (Optional)Match only packet on a given port range "
        ::= { zxr10IPv4MixedACLEntry 22 }    
        
    zxr10IPv4MixedACLSrcPort  OBJECT-TYPE
        SYNTAX   INTEGER{ftp(21),telnet(23),smtp(25),domain(53),bootps(67),
                 bootpc(68),tftp(69),finger(79), www(80),pop2(109),pop3(110),
                 ntp(123),snmp(161), snmptrap(162),bgp(179), pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv4MixedACLEntry 23 }    
        
    zxr10IPv4MixedACLSrcPort2  OBJECT-TYPE
        SYNTAX   INTEGER{ftp(21),telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
          ::= { zxr10IPv4MixedACLEntry 24 }    
       
    zxr10IPv4MixedACLDestOpr  OBJECT-TYPE
        SYNTAX   INTEGER{oprTypeInvalid(0),eq(1),ge(2),le(3),range(7)}
        MAX-ACCESS  read-only
        STATUS  current
        DESCRIPTION
            "eq       (Optional)Match only packets on a given port number                                                                                
            ge       (Optional)Match only packets with a no lower port number                                                                           
            le       (Optional)Match only packets with a no greater port number                                                                         
            range    (Optional)Match only packet on a given port range "
        ::= { zxr10IPv4MixedACLEntry 25 }    
        
    zxr10IPv4MixedACLDestPort  OBJECT-TYPE
        SYNTAX   INTEGER{ftp(21),telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                         
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv4MixedACLEntry 26 }    
         
    zxr10IPv4MixedACLDestPort2  OBJECT-TYPE
        SYNTAX   INTEGER{ftp(21), telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv4MixedACLEntry 27 }   
         
    zxr10IPv4MixedACLTCPEstablish  OBJECT-TYPE
        SYNTAX    INTEGER{true(1),false(0)}
        MAX-ACCESS  read-only
        STATUS  current
        DESCRIPTION
            "(Optional)Match established connections"
        ::= { zxr10IPv4MixedACLEntry 28 }  
     
        
    zxr10IPv4MixedACLICMPType  OBJECT-TYPE
        SYNTAX   INTEGER(0..256)
        MAX-ACCESS  read-only
        STATUS  current
        DESCRIPTION
            "0-254|256            ICMP type
            255                   Any ICMP type
            alternate-address     Alternate address (6)
            echo                  Echo (ping, 8)
            echo-reply            Echo reply (0)
            information-reply     Information replies (16)
            information-request   Information requests (15)
            mask-request          Mask requests (17)
            mask-reply            Mask replies (18)
            parameter-problem     All parameter problems (12)
            redirect              All redirects (5)
            router-advertisement  Router discovery advertisements (9)
            router-solicitation   Router discovery solicitations (10)
            source-quench         Source quenches (4)
            time-exceeded         All time exceededs (11)
            timestamp-reply       Timestamp replies (14)
            timestamp-request     Timestamp requests (13)
            traceroute            Traceroute (30)
            unreachable           All unreachables (3)"
        ::= { zxr10IPv4MixedACLEntry 29 }    
        
    zxr10IPv4MixedACLICMPCode  OBJECT-TYPE
        SYNTAX   INTEGER(0..256)
        MAX-ACCESS  read-only
        STATUS  current
        DESCRIPTION
            "0-254|256            ICMP code
            255                   Any ICMP code"
        ::= { zxr10IPv4MixedACLEntry 30 }    
        
    zxr10IPv4MixedACLPrecedence  OBJECT-TYPE
        SYNTAX   Integer32(0..7)
        MAX-ACCESS  read-only
        STATUS  current
        DESCRIPTION
            "<0-7>  Precedence level"
        ::= { zxr10IPv4MixedACLEntry 31 }    
        
    zxr10IPv4MixedACLTOS  OBJECT-TYPE
        SYNTAX   Integer32(0..15)
        MAX-ACCESS  read-only
        STATUS  current
        DESCRIPTION
            "<0-15>  Type of service(ToS)"
        ::= { zxr10IPv4MixedACLEntry 32 }  
          
    zxr10IPv4MixedACLDSCP  OBJECT-TYPE
        SYNTAX   Integer32(0..63)
        MAX-ACCESS  read-only
        STATUS  current
        DESCRIPTION
            "<0-63>  DSCP value"
        ::= { zxr10IPv4MixedACLEntry 33 }
    
    zxr10IPv4MixedACLStateFlag  OBJECT-TYPE
        SYNTAX   INTEGER {active(0),inactive(1)}
        MAX-ACCESS  read-only
        STATUS  current
        DESCRIPTION
            "Timerange enable or disable flag"
        ::= { zxr10IPv4MixedACLEntry 34 }    
               
            
    zxr10IPv4MixedACLTimerangeName  OBJECT-TYPE
        SYNTAX   DisplayString
        MAX-ACCESS  read-only
        STATUS  current
        DESCRIPTION
             "time-range  (Optional)Configure time range"
        ::= { zxr10IPv4MixedACLEntry 35 }  
              
    zxr10IPv4MixedACLRowStatus   OBJECT-TYPE  
        SYNTAX   RowStatus
        MAX-ACCESS  read-only
        STATUS  current
        DESCRIPTION
       "createAndGo(4)  Configure IPv4 Mixed ACL or rule
        destroy(6)  Delete IPv4 Mixed ACL or rule"        
        ::= { zxr10IPv4MixedACLEntry 36 }  
        
     zxr10IPv4MixedACLIpBitMap  OBJECT-TYPE
        SYNTAX   INTEGER(0..127)
        MAX-ACCESS  read-only
        STATUS  current
        DESCRIPTION
            "Match on the specify ip flag bit. 
            1 means setted , and 0 means not.
            Bit from low to high represents:
            first     :  DSCP
            second    :  TOS
            third     :  Precedence
            fourth    :  ICMPCode
            fifth     :  ICMPType
            sixth     :  ipprotocol
            seventh   :  fragment    (obsolete, default value 1)"
        ::= { zxr10IPv4MixedACLEntry 37 }        
        
     zxr10IPv4MixedACLLinkBitMap  OBJECT-TYPE
        SYNTAX   INTEGER(0..63)
        MAX-ACCESS  read-only
        STATUS  current
        DESCRIPTION
            "Match on the specify limk flag bit. 
            1 means setted , and 0 means not.
            Bit from low to high represents:
            first     :  in cos
            second    :  out cos
            third     :  in vlan
            fourth    :  out vlan
            fifth     :  linkprotocol"
        ::= { zxr10IPv4MixedACLEntry 38 }           
        
    zxr10IPv4MixedACLInVlanIDEnd  OBJECT-TYPE
        SYNTAX   Integer32(1..4094)
        MAX-ACCESS  read-only
        STATUS  current
        DESCRIPTION
            "<1-4094>  Value of inner vlan"
        ::= { zxr10IPv4MixedACLEntry 39 } 
        
    zxr10IPv4MixedACLOutVlanIDEnd   OBJECT-TYPE
        SYNTAX   Integer32(1..4094)
        MAX-ACCESS  read-only
        STATUS  current
        DESCRIPTION
            "<1-4094>  Value of outer vlan"
        ::= { zxr10IPv4MixedACLEntry 40 }        
        
    zxr10IPv4MixedACLFragment  OBJECT-TYPE
        SYNTAX     INTEGER {match_unfragment(0), match_fragment(1)}
        MAX-ACCESS  read-only        
        STATUS  current
        DESCRIPTION
           "Fragment enable or disable flag"
        ::= { zxr10IPv4MixedACLEntry 41 }     

        
    --- IPv6 Mixexd ACL 

    zxr10IPv6MixedACLTable  OBJECT-TYPE
        SYNTAX  SEQUENCE OF Zxr10IPv6MixedACLEntry
        MAX-ACCESS  not-accessible
        STATUS  current
        DESCRIPTION
            "IPv6 Mixed ACL Table"
        ::= { zxr10ACL 5 }

    zxr10IPv6MixedACLEntry  OBJECT-TYPE
        SYNTAX  Zxr10IPv6MixedACLEntry
        MAX-ACCESS  not-accessible
        STATUS  current
        DESCRIPTION
            "IPv6 Mixed ACL"
        INDEX  { zxr10IPv6MixedACLName,
                 zxr10IPv6MixedACLRuleID }
        ::= { zxr10IPv6MixedACLTable 1 }
        
    Zxr10IPv6MixedACLEntry ::=
        SEQUENCE {
            zxr10IPv6MixedACLName
                DisplayString,            
            zxr10IPv6MixedACLRuleID
                Integer32,
            zxr10IPv6MixedACLPermitDeny
                INTEGER,
            zxr10IPv6MixedACLLinkProtocol
                Integer32,
            zxr10IPv6MixedACLSourceMAC 
                DisplayString, 
            zxr10IPv6MixedACLSourceMACWildcard
                DisplayString,   
            zxr10IPv6MixedACLSourceMACAny
                INTEGER,   
            zxr10IPv6MixedACLDestinationMAC 
                DisplayString,
            zxr10IPv6MixedACLDestinationMACWildCard
                DisplayString,
            zxr10IPv6MixedACLDestinationMACAny
                INTEGER,   
            zxr10IPv6MixedACLIncos
                Integer32, 
            zxr10IPv6MixedACLOutCos
                Integer32,  
            zxr10IPv6MixedACLInVlanIDBegin
                Integer32,
            zxr10IPv6MixedACLOutVlanIDBegin
                Integer32,
            zxr10IPv6MixedACLflowlabel
                Integer32,  
            zxr10IPv6MixedACLSrcAddr
                DisplayString, 
            zxr10IPv6MixedACLSrcWildcard 
                INTEGER, 
            zxr10IPv6MixedACLSrcAny
                INTEGER,  
            zxr10IPv6MixedACLDestAddr 
                DisplayString,
            zxr10IPv6MixedACLDestWildcard
                INTEGER,  
            zxr10IPv6MixedACLDestAny
                INTEGER,
            zxr10IPv6MixedACLProtocol
                INTEGER, 
            zxr10IPv6MixedACLSrcOpr 
                INTEGER, 
            zxr10IPv6MixedACLSrcPort 
                INTEGER, 
            zxr10IPv6MixedACLSrcPort2 
                INTEGER, 
            zxr10IPv6MixedACLDestOpr   
                INTEGER,  
            zxr10IPv6MixedACLDestPort
                INTEGER, 
            zxr10IPv6MixedACLDestPort2
                INTEGER,  
            zxr10IPv6MixedACLTCPEstablish 
                INTEGER,
            zxr10IPv6MixedACLTcpFlagOprBitMap 
                INTEGER,
            zxr10IPv6MixedACLTcpFlagVlaBitMap
                INTEGER, 
            zxr10IPv6MixedACLHeaderOptionBitMap 
                INTEGER, 
            zxr10IPv6MixedACLICMPType  
                INTEGER, 
            zxr10IPv6MixedACLICMPCode 
                INTEGER, 
            zxr10IPv6MixedACLDSCP
                Integer32,  
            zxr10IPv6MixedACLStateFlag
                INTEGER,
            zxr10IPv6MixedACLTimerangeName  
                DisplayString, 
            zxr10IPv6MixedACLRowStatus 
                RowStatus,
            zxr10IPv6MixedACLIpBitMap
                INTEGER,
            zxr10IPv6MixedACLLinkBitMap
                INTEGER,
            zxr10IPv6MixedACLInVlanIDEnd
                Integer32,
            zxr10IPv6MixedACLOutVlanIDEnd
                Integer32
         } 
  
  
  
    zxr10IPv6MixedACLName  OBJECT-TYPE
        SYNTAX   DisplayString
        MAX-ACCESS  read-only
        STATUS  current
        DESCRIPTION
            "IPv6Mixed-access-list
             WORD  Name of an IPv6 Mixed access-list (1-31 characters)"
        ::= { zxr10IPv6MixedACLEntry 1 } 
        
            
    zxr10IPv6MixedACLRuleID  OBJECT-TYPE
        SYNTAX   Integer32(1..2147483644)
        MAX-ACCESS  read-only
        STATUS  current
        DESCRIPTION
            "rule
            <1-2147483644>  (Optional)ID of this rule"
        ::= { zxr10IPv6MixedACLEntry 2 }    

    zxr10IPv6MixedACLPermitDeny  OBJECT-TYPE
        SYNTAX   INTEGER{deny(0),permit(1)}
        MAX-ACCESS  read-only
        STATUS  current
        DESCRIPTION
            "deny    Specify packets to reject
             permit  Specify packets to forward"
        ::= { zxr10IPv6MixedACLEntry 3 } 
    
    zxr10IPv6MixedACLLinkProtocol  OBJECT-TYPE
        SYNTAX   Integer32(0..65535)   
        MAX-ACCESS  read-only
        STATUS  current
        DESCRIPTION
            "<0-65535>  Link protocal "
        ::= { zxr10IPv6MixedACLEntry 4 } 
    
    zxr10IPv6MixedACLSourceMAC  OBJECT-TYPE
        SYNTAX   DisplayString
        MAX-ACCESS  read-only
        STATUS  current
        DESCRIPTION
            "<xxxx.xxxx.xxxx>  Source MAC address"
        ::= { zxr10IPv6MixedACLEntry 5 }
    
    zxr10IPv6MixedACLSourceMACWildcard  OBJECT-TYPE
        SYNTAX   DisplayString
        MAX-ACCESS  read-only
        STATUS  current
        DESCRIPTION
            "<xxxx.xxxx.xxxx>  Source MAC wildcard"
        ::= { zxr10IPv6MixedACLEntry 6 } 
    
    zxr10IPv6MixedACLSourceMACAny  OBJECT-TYPE 
        SYNTAX   INTEGER{invalid(0),valid(1)}
        MAX-ACCESS  read-only
        STATUS  current
        DESCRIPTION
            "any               Any source MAC address"
        ::= { zxr10IPv6MixedACLEntry 7 }
    
    zxr10IPv6MixedACLDestinationMAC  OBJECT-TYPE
        SYNTAX   DisplayString
        MAX-ACCESS  read-only
        STATUS  current
        DESCRIPTION
            "<xxxx.xxxx.xxxx>  Destination MAC address"
        ::= { zxr10IPv6MixedACLEntry 8 } 
        
     zxr10IPv6MixedACLDestinationMACWildCard  OBJECT-TYPE
        SYNTAX   DisplayString
        MAX-ACCESS  read-only
        STATUS  current
        DESCRIPTION
            "<xxxx.xxxx.xxxx>  Destination MAC wildcard"
        ::= { zxr10IPv6MixedACLEntry 9 } 
        
     zxr10IPv6MixedACLDestinationMACAny    OBJECT-TYPE 
        SYNTAX   INTEGER{invalid(0),valid(1)}
        MAX-ACCESS  read-only
        STATUS  current
        DESCRIPTION
            "any               Any destination MAC address"
        ::= { zxr10IPv6MixedACLEntry 10 }
     
     
     zxr10IPv6MixedACLIncos     OBJECT-TYPE
        SYNTAX   Integer32(0..7)
        MAX-ACCESS  read-only
        STATUS  current
        DESCRIPTION
            "<0-7>  Value of inner cos"
        ::= { zxr10IPv6MixedACLEntry 11 }     
        
     zxr10IPv6MixedACLOutCos   OBJECT-TYPE
        SYNTAX   Integer32(0..7)
        MAX-ACCESS  read-only
        STATUS  current
        DESCRIPTION
            "<0-7>  Value of outer cos"
        ::= { zxr10IPv6MixedACLEntry 12 }
             
    zxr10IPv6MixedACLInVlanIDBegin  OBJECT-TYPE
        SYNTAX   Integer32(1..4094)
        MAX-ACCESS  read-only
        STATUS  current
        DESCRIPTION
            "<1-4094>  Value of inner vlan"
        ::= { zxr10IPv6MixedACLEntry 13 } 
        
    zxr10IPv6MixedACLOutVlanIDBegin   OBJECT-TYPE
        SYNTAX   Integer32(1..4094)
        MAX-ACCESS  read-only
        STATUS  current
        DESCRIPTION
            "<1-4094>  Value of outer vlan"
        ::= { zxr10IPv6MixedACLEntry 14 }
    
    zxr10IPv6MixedACLflowlabel  OBJECT-TYPE
        SYNTAX   Integer32(0..1048575)
        MAX-ACCESS  read-only
        STATUS  current
        DESCRIPTION
            "<0-1048575>  Flowlabel value"
        ::= { zxr10IPv6MixedACLEntry 15 }   

    zxr10IPv6MixedACLSrcAddr  OBJECT-TYPE
        SYNTAX   DisplayString
        MAX-ACCESS  read-only
        STATUS  current
        DESCRIPTION
            "X:X::X:X  Source address"
        ::= { zxr10IPv6MixedACLEntry 16 } 
    
    zxr10IPv6MixedACLSrcWildcard  OBJECT-TYPE
        SYNTAX   INTEGER(0..128)
        MAX-ACCESS  read-only
        STATUS  current
        DESCRIPTION
            "<0-128>  Source Wildcard"
        ::= { zxr10IPv6MixedACLEntry 17 }    

     
    zxr10IPv6MixedACLSrcAny  OBJECT-TYPE 
        SYNTAX   INTEGER{invalid(0),valid(1)}
        MAX-ACCESS  read-only
        STATUS  current
        DESCRIPTION
            "Any source address"
        ::= { zxr10IPv6MixedACLEntry 18 } 
        
    zxr10IPv6MixedACLDestAddr  OBJECT-TYPE
        SYNTAX   DisplayString
        MAX-ACCESS  read-only
        STATUS  current
        DESCRIPTION
            "X:X::X:X  Destination address"
        ::= { zxr10IPv6MixedACLEntry 19 } 
        
    zxr10IPv6MixedACLDestWildcard  OBJECT-TYPE
        SYNTAX   INTEGER(0..128)
        MAX-ACCESS  read-only
        STATUS  current
        DESCRIPTION
            "<0-128>  Destination Wildcard"
        ::= { zxr10IPv6MixedACLEntry 20 }
           
    zxr10IPv6MixedACLDestAny  OBJECT-TYPE 
        SYNTAX   INTEGER{invalid(0),valid(1)}
        MAX-ACCESS  read-only
        STATUS  current
        DESCRIPTION
            "Any destination address"
        ::= { zxr10IPv6MixedACLEntry 21 } 
  
         
    zxr10IPv6MixedACLProtocol  OBJECT-TYPE
        SYNTAX   INTEGER{igmp(2),tcp(6),udp(17),gre(47),icmp(58),ospf(89),
                 pim(103),vrrp(112)}
        MAX-ACCESS  read-only
        STATUS  current
        DESCRIPTION
            " <0-255>  An IP protocol number
              gre      Generic Routing Encapsulation (47)
              icmp     Internet Control Message Protocol(58)
              igmp     Internet Group Management Protocol (2)
              ip       Any internet protocol
              ospf     Open Shortest Path First Protocol (89)
              pim      Protocol Independent Multicast (103)
              tcp      Transmission Control Protocol(6)
              udp      User Datagram Protocol(17)
              vrrp     Virtual Router Redundancy Protocol (112)"
        ::= { zxr10IPv6MixedACLEntry 22 }
            
    zxr10IPv6MixedACLSrcOpr  OBJECT-TYPE
        SYNTAX   INTEGER{oprTypeInvalid(0),eq(1),ge(2),le(3),range(7)}
        MAX-ACCESS  read-only
        STATUS  current
        DESCRIPTION
            "eq       (Optional)Match only packets on a given port number                                                                                
            ge       (Optional)Match only packets with a no lower port number                                                                           
            le       (Optional)Match only packets with a no greater port number                                                                         
            range    (Optional)Match only packet on a given port range "
        ::= { zxr10IPv6MixedACLEntry 23 }    
         
    zxr10IPv6MixedACLSrcPort  OBJECT-TYPE
        SYNTAX   INTEGER{ftp(21),telnet(23),smtp(25),domain(53),bootps(67),
                 bootpc(68),tftp(69),finger(79), www(80),pop2(109),pop3(110),
                 ntp(123),snmp(161), snmptrap(162),bgp(179), pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv6MixedACLEntry 24 }    
       
    zxr10IPv6MixedACLSrcPort2  OBJECT-TYPE
        SYNTAX   INTEGER{ftp(21),telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
          ::= { zxr10IPv6MixedACLEntry 25 }    
        
    zxr10IPv6MixedACLDestOpr  OBJECT-TYPE
        SYNTAX   INTEGER{oprTypeInvalid(0),eq(1),ge(2),le(3),range(7)}
        MAX-ACCESS  read-only
        STATUS  current
        DESCRIPTION
            "eq       (Optional)Match only packets on a given port number                                                                                
            ge       (Optional)Match only packets with a no lower port number                                                                           
            le       (Optional)Match only packets with a no greater port number                                                                         
            range    (Optional)Match only packet on a given port range "
        ::= { zxr10IPv6MixedACLEntry 26 }    
        
    zxr10IPv6MixedACLDestPort  OBJECT-TYPE
        SYNTAX   INTEGER{ftp(21),telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                         
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv6MixedACLEntry 27 }    
        
    zxr10IPv6MixedACLDestPort2  OBJECT-TYPE
        SYNTAX   INTEGER{ftp(21), telnet(23),smtp(25),domain(53),bootps(67),
                 bootpc(68),tftp(69),finger(79), www(80),pop2(109),pop3(110),
                 ntp(123),snmp(161),snmptrap(162),bgp(179), pim_auto_rp(496),
                 login(513),rip(520)}
        MAX-ACCESS  read-only
        STATUS  current
        DESCRIPTION
            "<0-65535>   Port number                                                                                                          
            bootpc       Bootstrap protocol (BOOTP) client (68)                                                                               
            bootps       Bootstrap protocol (BOOTP) server (67)                                                                               
            domain       Domain name service (DNS, 53)                                                                                        
            ntp          Network time protocol (123)                                                                                          
            pim-auto-rp  PIM auto-RP (496)                                                                                                    
            rip          Routing information protocol (router, in.routed, 520)                                                                
            snmp         Simple network management protocol (161)                                                                             
            snmptrap     SNMP traps (162)                                                                                                     
            tftp         Trivial file transfer protocol (69)"
        ::= { zxr10IPv6MixedACLEntry 28 }   
         
    zxr10IPv6MixedACLTCPEstablish  OBJECT-TYPE
        SYNTAX    INTEGER{true(1),false(0)}
        MAX-ACCESS  read-only
        STATUS  current
        DESCRIPTION
            "(Optional)Match established connections"
        ::= { zxr10IPv6MixedACLEntry 29 }  
     
    zxr10IPv6MixedACLTcpFlagOprBitMap  OBJECT-TYPE
        SYNTAX   INTEGER(0..63)
        MAX-ACCESS  read-only
        STATUS  current
        DESCRIPTION
            "Match on the specify TCP flag bit.  
            1 means + , and 0 means -.
            Bit from low to high represents:
            first     :  ack
            second    :  fin
            third     :  psh
            fourth    :  rst
            fifth     :  syn
            sixth     :  urg"
        ::= { zxr10IPv6MixedACLEntry 30 }
        
     zxr10IPv6MixedACLTcpFlagVlaBitMap  OBJECT-TYPE
        SYNTAX   INTEGER(0..63)
        MAX-ACCESS  read-only
        STATUS  current
        DESCRIPTION
            "Match when the TCP flag set or not. 
            1 means setted , and 0 means not.
            Bit from low to high represents:
            first     :  ack
            second    :  fin
            third     :  psh
            fourth    :  rst
            fifth     :  syn
            sixth     :  urg"
        ::= { zxr10IPv6MixedACLEntry 31 }      
        
     zxr10IPv6MixedACLHeaderOptionBitMap  OBJECT-TYPE
        SYNTAX   INTEGER(0..63)
        MAX-ACCESS  read-only
        STATUS  current
        DESCRIPTION
            "Matches if the specify IPv6 header is present.
            1 means setted , and 0 means not.
            Bit from low to high represents:
            first     :  hop-by-hop   
            second    :  destopts 
            third     :  routing        
            fourth    :  fragments
            fifth     :  authen 
            sixth     :  esp"  
        ::= { zxr10IPv6MixedACLEntry 32 }
     
        
    zxr10IPv6MixedACLICMPType  OBJECT-TYPE
        SYNTAX   INTEGER(0..256)
        MAX-ACCESS  read-only
        STATUS  current
        DESCRIPTION
            "0-254|256               ICMP type
            255                      Any ICMP type
            destination-unreachable  Destination unreachable (1)
            echo-reply               Echo reply (129)
            echo-request             Echo request (ping, 128)
            mld-query                Multicast Listener Discovery Query (130)
            mld-reduction            Multicast Listener Discovery Reduction 
                                     (132)
            mld-report               Multicast Listener Discovery Report (131)
            nd-na                    Neighbor discovery neighbor advertisments 
                                     (136)
            nd-ns                    Neighbor discovery neighbor solicitations 
                                     (135)
            packet-too-big           Packet too big (2)
            parameter-problem        All parameter problems (4)
            redirect                 Neighbor redirect (137)
            router-advertisment      Neighbor discovery router advertisments 
                                     (134)
            router-renumbering       All router renumbering (138)
            router-solicitation      Neighbor discovery router solicitations 
                                     (133)
            time-exceeded            Time exceeded (3)"                        
        ::= { zxr10IPv6MixedACLEntry 33 }    
        
    zxr10IPv6MixedACLICMPCode  OBJECT-TYPE
        SYNTAX   INTEGER(0..256)
        MAX-ACCESS  read-only
        STATUS  current
        DESCRIPTION
            "0-254|256               ICMP code
            255                      Any ICMP code"
        ::= { zxr10IPv6MixedACLEntry 34 }    
        
             
    zxr10IPv6MixedACLDSCP  OBJECT-TYPE
        SYNTAX   Integer32(0..63)
        MAX-ACCESS  read-only
        STATUS  current
        DESCRIPTION
            "<0-63>  DSCP value"
        ::= { zxr10IPv6MixedACLEntry 35 }
    
    zxr10IPv6MixedACLStateFlag  OBJECT-TYPE
        SYNTAX   INTEGER {active(0),inactive(1)}
        MAX-ACCESS  read-only
        STATUS  current
        DESCRIPTION
            "Timerange enable or disable flag"
        ::= { zxr10IPv6MixedACLEntry 36 }     
               
            
    zxr10IPv6MixedACLTimerangeName  OBJECT-TYPE
        SYNTAX   DisplayString
        MAX-ACCESS  read-only
        STATUS  current
        DESCRIPTION
             "time-range  (Optional)Configure time range"
        ::= { zxr10IPv6MixedACLEntry 37 }  
              
    zxr10IPv6MixedACLRowStatus   OBJECT-TYPE  
        SYNTAX   RowStatus
        MAX-ACCESS  read-only
        STATUS  current
        DESCRIPTION
       "createAndGo(4)  Configure IPv6 Mixed ACL or rule
        destroy(6)  Delete IPv6 Mixed ACL or rule"        
        ::= { zxr10IPv6MixedACLEntry 38 }  
    
     zxr10IPv6MixedACLIpBitMap  OBJECT-TYPE
        SYNTAX   INTEGER(0..127)
        MAX-ACCESS  read-only
        STATUS  current
        DESCRIPTION
            "Match on the specify ip flag bit. 
            1 means setted , and 0 means not.
            Bit from low to high represents:
            first     :  DSCP
            second    :              (reserved, default value 0)
            third     :              (reserved, default value 0)
            fourth    :  ICMPCode
            fifth     :  ICMPType
            sixth     :  FlowLabel
            seventh   :  ipv6protocol"
        ::= { zxr10IPv6MixedACLEntry 39 }        
        
     zxr10IPv6MixedACLLinkBitMap  OBJECT-TYPE
        SYNTAX   INTEGER(0..63)
        MAX-ACCESS  read-only
        STATUS  current
        DESCRIPTION
            "Match on the specify limk flag bit. 
            1 means setted , and 0 means not.
            Bit from low to high represents:
            first     :  in cos
            second    :  out cos
            third     :  in vlan
            fourth    :  out vlan
            fifth     :  linkprotocol"
        ::= { zxr10IPv6MixedACLEntry 40 }      
        
    zxr10IPv6MixedACLInVlanIDEnd  OBJECT-TYPE
        SYNTAX   Integer32(1..4094)
        MAX-ACCESS  read-only
        STATUS  current
        DESCRIPTION
            "<1-4094>  Value of inner vlan"
        ::= { zxr10IPv6MixedACLEntry 41 } 
        
    zxr10IPv6MixedACLOutVlanIDEnd   OBJECT-TYPE
        SYNTAX   Integer32(1..4094)
        MAX-ACCESS  read-only
        STATUS  current
        DESCRIPTION
            "<1-4094>  Value of outer vlan"
        ::= { zxr10IPv6MixedACLEntry 42 }        
        
       END
