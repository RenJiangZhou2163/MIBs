MR6-MIB DEFINITIONS ::= BEGIN

IMPORTS
        MODULE-IDENTITY, OBJECT-TYPE,
        enterprises, Unsigned32, Counter64, IpAddress
                FROM SNMPv2-SMI
        DisplayString, RowStatus
                FROM SNMPv2-TC
        Ipv6Address
                FROM IPV6-TC;

zxr10mr6Instance MODULE-IDENTITY
        LAST-UPDATED "201812111500Z"
        ORGANIZATION "ZTE Corporation."
        CONTACT-INFO
               "Xu benchong
               Tel: 025-698109
               E-Mail:xu.benchong@zte.com.cn"
        DESCRIPTION
                "The MIB module to describe the MR6 protocol."
        REVISION "201812111500Z"                
        DESCRIPTION
                "add: zxr10mr6InstanceMulAddrRFC7371."
        REVISION "201811151500Z"
        DESCRIPTION
                "add: zxr10Mr6SmdmTable"
        REVISION "201706051500Z" 
        DESCRIPTION
                "add: zxr10mr6InstanceNeverSwitchAcl"
        REVISION "201704241000Z"
        DESCRIPTION
                "add: zxr10pimsm6IntfAssertDisable"
        REVISION "201702281500Z" 
        DESCRIPTION
                "add: zxr10mr6InstanceSwitchThreshold
                      zxr10mr6InstanceSwitchThresholdAcl"
        REVISION "201701061000Z"
        DESCRIPTION
                "add: zxr10pimsm6IntfHelloTrackSupport"
        REVISION "201612021000Z"
        DESCRIPTION
                "add: zxr10mr6InstanceSwitchInterval"
        REVISION "201603181500Z"
        DESCRIPTION
                "add: zxr10pimsm6InstStatisticsAclName"
        REVISION "201512181500Z" 
        DESCRIPTION
                "add: zxr10mstatic6RouteIncMask
                      zxr10mstatic6RouteCount"
        REVISION "201512111500Z"
        DESCRIPTION
            "add: zxr10nexthop6Table"        
        REVISION "201511201400Z"
        DESCRIPTION
            "add: zxr10mr6InstanceMroute6LimitInst"
        REVISION "201510261000Z"
        DESCRIPTION
            "add: zxr10pimsm6InstMofrrAclName
                  zxr10pimsm6InterfaceFrrEn"
        REVISION "201509231000Z"
        DESCRIPTION
            "add: zxr10pimsm6InstPimdmReg"
        REVISION "201508281100Z"
        DESCRIPTION
                "add: zxr10mstatic6RoutePermanent,
                      zxr10mstatic6RouteSlaveIifName,
                      zxr10mstatic6RouteTrackName,
                      zxr10mstatic6RouteSlaveTrackName,
                      zxr10mstatic6FrrTable"
        REVISION "201507071100Z"
        DESCRIPTION
                "modify: the ranges of zxr10mstatic6LimitXgLimit 
                 and zxr10mstatic6LimitSgLimit are both 0-2048,
                 the max values get from performance parameter."
        REVISION "201506241000Z"
        DESCRIPTION
                "modify:zxr10mldGroupTable is obsolete
                add:zxr10mldStaticGroupTable "
        REVISION "201506201400Z"
        DESCRIPTION
            "add: zxr10pimsm6IntfHelloDrAddr"
        REVISION "201506011000Z" 
        DESCRIPTION
                "add: zxr10pimsm6InstCbsrHoldtime,
                      zxr10pimsm6InstCbsrInterval,
                      zxr10pimsm6CrpHoldtime"
        REVISION "201505121400Z"
        DESCRIPTION
            "add: zxr10mr6InstanceAccessScope"
        REVISION "201503201000Z"        
        DESCRIPTION                
                "add:zxr10pimsm6InstJpSpeed 
                     zxr10pimsm6InstKeepAlivePeriod
                     zxr10pimsm6InstAssertHoldTime
                     zxr10pimsm6InstGraftTime
                     zxr10pimsm6IntfPropagationDelay
                     zxr10pimsm6IntfOverrideInterval
                     zxr10pimsm6IntfJpMaxpktLen"        
        REVISION "201502121500Z"
        DESCRIPTION
                "modify: the status of zxr10mstatic6OifindexVlanMin and zxr10mstatic6OifindexVlanMax is obsolete"
        REVISION "201409011400Z"
        DESCRIPTION
            "modify: range of zxr10mr6InstanceMultipathSghash is 
                {none(0),sbased(1),sgbasic(2),sgnexthopbased(3),sgbalance(4)}"
        REVISION "201407221100Z"
        DESCRIPTION
                "modify: the status of zxr10pimsm6InstSsmEnable is obsolete"
        REVISION "201406181600Z" 
        DESCRIPTION
            "modify: range of zxr10mr6InstanceTosValue is (0..63|255),
                     DESCRIPTION of zxr10pimsm6BsrHashLen,
                     DESCRIPTION of zxr10mr6InstanceVrfName,
                     range of zxr10pimsm6BsrHashLen is (0..128)"
        REVISION "201402211400Z" 
        DESCRIPTION
            "modify: DESCRIPTION of some nodes
                     range of some nodes"
        REVISION "201401141400Z"
        DESCRIPTION
                "add: zxr10pimsm6InstSsmEnable
                 modify: range of zxr10pimsm6InstJpInterval is (10..6000),
                         range of zxr10mldInstVersion is (version1(1),version2(2)),
                         range of zxr10mldIntfVersion is (version1(1),version2(2)),
                         range of zxr10mldSsmmapDefault is (0..1),
                         range of zxr10mldIntfImmediateAll is (0..1)"
        REVISION "201312031700Z"
        DESCRIPTION
                "add: zxr10mvpn6InstTable
                      zxr10mvpn6InstEntry
                      zxr10mvpn6InstVrfName
                      zxr10mvpn6InstProviderTunnel"
        REVISION "201310121400Z"
        DESCRIPTION
                "add: zxr10pimsm6InstJpInterval 
                      zxr10pimsm6InstRegHoldtime"
        REVISION "201308011600Z"
        DESCRIPTION
                "add: zxr10mldGroupLimitTable"
        REVISION "201307181600Z"
        DESCRIPTION
                "add: zxr10mr6ForwordingPolicyVrfName
                      zxr10mr6ForwordingPolicyAcl
                      zxr10mr6ForwordingPolicyType"
        REVISION "201307161400Z"
        DESCRIPTION
                "modify:range of zxr10mr6InstanceMroute6Limit is (0..131070),
                range of zxr10mr6InstanceMultipathSghash is 
                {none(0),sbased(1),sgbasic(2),sgnexthopbased(3)}              
                " 
        REVISION "201305211400Z"
        DESCRIPTION
                "modify:the data type of enumeration is converted from Unsigned32 
                 to INTEGER, including of zxr10mr6InstanceMultipathSghash
                        zxr10mldInstVersion
                        zxr10mldIntfVersion
                        zxr10mldGroupStaticFlag
                        zxr10mldGroupFilterMode"
        REVISION "201102090000Z"
        DESCRIPTION
                "Initial version of this MIB module."
        ::= { zxr10mr6InstanceMIBs 1 }

    zte OBJECT IDENTIFIER ::= { enterprises 3902 }

    zxr10 OBJECT IDENTIFIER ::= { zte 3}

    zxr10RosngMIB OBJECT IDENTIFIER ::= { zxr10 6000}

    zxr10mr6InstanceMIBs OBJECT IDENTIFIER ::= { zxr10RosngMIB 166}

        
zxr10mr6InstanceMIB OBJECT IDENTIFIER ::= { zxr10mr6Instance 1 }

zxr10mr6InstanceTable OBJECT-TYPE
        SYNTAX  SEQUENCE OF Zxr10mr6InstanceEntry
        MAX-ACCESS  not-accessible
        STATUS  current
        DESCRIPTION
            "A table to mr6 instance"
        ::= { zxr10mr6InstanceMIB 1 }

zxr10mr6InstanceEntry OBJECT-TYPE
        SYNTAX Zxr10mr6InstanceEntry
        MAX-ACCESS  not-accessible
        STATUS  current
        DESCRIPTION
            "An entry to mr6 instance"
        INDEX  { zxr10mr6InstanceVrfName }
        ::= { zxr10mr6InstanceTable 1 }
            
Zxr10mr6InstanceEntry ::=
        SEQUENCE {
            zxr10mr6InstanceVrfName
                DisplayString,
            zxr10mr6InstanceMroute6Limit
                Unsigned32,
            zxr10mr6InstanceTosValue
                Unsigned32,
            zxr10mr6InstanceNsfTime
                Unsigned32,
            zxr10mr6InstanceMultipathSghash
                INTEGER,
            zxr10mr6InstanceDampingEnable
                Unsigned32,
            zxr10mr6InstanceDampingThreshold
                Unsigned32,
            zxr10mr6InstanceAccessScope
                INTEGER,
            zxr10mr6InstanceMroute6LimitInst
                Unsigned32,
            zxr10mr6InstanceSwitchInterval
                Unsigned32,
            zxr10mr6InstanceSwitchThreshold
                Unsigned32,
            zxr10mr6InstanceSwitchThresholdAcl
                DisplayString,
            zxr10mr6InstanceNeverSwitchAcl
                DisplayString,
            zxr10mr6InstanceMulAddrRFC7371
                Unsigned32
        }

zxr10mr6InstanceVrfName OBJECT-TYPE
        SYNTAX DisplayString (SIZE (0..32))
        MAX-ACCESS  read-only
        STATUS  current
        DESCRIPTION
            "vrf name"
        ::= { zxr10mr6InstanceEntry 1 }

zxr10mr6InstanceMroute6Limit OBJECT-TYPE
        SYNTAX Unsigned32 (0..131072)
        MAX-ACCESS  read-only
        STATUS  current
        DESCRIPTION
            "IPv6 mroute limit"
        ::= { zxr10mr6InstanceEntry 2 }
        
zxr10mr6InstanceTosValue OBJECT-TYPE
        SYNTAX Unsigned32 (0..63|255)
        MAX-ACCESS  read-only
        STATUS  current
        DESCRIPTION
            "tos value of multicast protocol packet"
        ::= { zxr10mr6InstanceEntry 3 }
        
zxr10mr6InstanceNsfTime OBJECT-TYPE
        SYNTAX Unsigned32 (30..1800)
        MAX-ACCESS  read-only
        STATUS  current
        DESCRIPTION
            "nsf time"
        ::= { zxr10mr6InstanceEntry 4 }
        
zxr10mr6InstanceMultipathSghash OBJECT-TYPE
        SYNTAX INTEGER {none(0),sbased(1),sgbasic(2),sgnexthopbased(3),sgbalance(4)}     
        MAX-ACCESS  read-only
        STATUS  current
        DESCRIPTION
            "multipath based sg-hash"
        ::= { zxr10mr6InstanceEntry 5 }
        
zxr10mr6InstanceDampingEnable OBJECT-TYPE
        SYNTAX Unsigned32 (0..1)
        MAX-ACCESS  read-only
        STATUS  current
        DESCRIPTION
            "damping enable"
        ::= { zxr10mr6InstanceEntry 6 }
        
zxr10mr6InstanceDampingThreshold OBJECT-TYPE
        SYNTAX Unsigned32 (2..100)
        MAX-ACCESS  read-only
        STATUS  current
        DESCRIPTION
            "damping threshold"
        ::= { zxr10mr6InstanceEntry 7 }

zxr10mr6InstanceAccessScope OBJECT-TYPE
        SYNTAX INTEGER {none(255),ffx0(1)}
        MAX-ACCESS  read-only
        STATUS  current
        DESCRIPTION
            "access multicast address scope"
        ::= { zxr10mr6InstanceEntry 8 }

zxr10mr6InstanceMroute6LimitInst OBJECT-TYPE
        SYNTAX Unsigned32 (0..131072)
        MAX-ACCESS  read-only
        STATUS  current
        DESCRIPTION
            "IPv6 mroute limit for instance, the max value gets
            from performance parameter"
        ::= { zxr10mr6InstanceEntry 9 }

zxr10mr6InstanceSwitchInterval OBJECT-TYPE
        SYNTAX Unsigned32 (3..65535)
        UNITS   "seconds"
        MAX-ACCESS  read-only
        STATUS  current
        DESCRIPTION
            "MVPN tunnel switchover interval."
        ::= { zxr10mr6InstanceEntry 10 }

zxr10mr6InstanceSwitchThreshold OBJECT-TYPE
        SYNTAX Unsigned32 (1..4294967295)
        UNITS   "Kbps"
        MAX-ACCESS  read-only
        STATUS  current
        DESCRIPTION
            "MVPN tunnel switchover threshold."
        ::= { zxr10mr6InstanceEntry 11 }

zxr10mr6InstanceSwitchThresholdAcl OBJECT-TYPE
        SYNTAX DisplayString (SIZE (0..31))
        MAX-ACCESS  read-only
        STATUS  current
        DESCRIPTION
            "ACL for MVPN tunnel switchover"
        ::= { zxr10mr6InstanceEntry 12 }

zxr10mr6InstanceNeverSwitchAcl OBJECT-TYPE
        SYNTAX DisplayString (SIZE (0..31))
        MAX-ACCESS  read-only
        STATUS  current
        DESCRIPTION
            "ACL for MVPN tunnel never switch to data tree"
        ::= { zxr10mr6InstanceEntry 13 }
        
zxr10mr6InstanceMulAddrRFC7371 OBJECT-TYPE
        SYNTAX Unsigned32 (0..1)
        MAX-ACCESS  read-only
        STATUS  current
        DESCRIPTION
            "Multicast address compatible with RFC7371,
            add FFBX/12 to SSM default group address range,
            add FFFX/12 to embedded RP address range"
        ::= { zxr10mr6InstanceEntry 14 }

zxr10mstatic6InstMIB OBJECT IDENTIFIER ::= { zxr10mr6InstanceMIB 2 }

zxr10mstatic6InstTable OBJECT-TYPE
        SYNTAX  SEQUENCE OF Zxr10mstatic6InstEntry
        MAX-ACCESS  not-accessible
        STATUS  current
        DESCRIPTION
            "A table to IPv6 mstatic instance"
        ::= { zxr10mstatic6InstMIB 1 }

zxr10mstatic6InstEntry OBJECT-TYPE
        SYNTAX Zxr10mstatic6InstEntry
        MAX-ACCESS  not-accessible
        STATUS  current
        DESCRIPTION
            "An entry to IPv6 mstatic instance"
        INDEX  { zxr10mstatic6InstVrfName }
        ::= { zxr10mstatic6InstTable 1 }
            
Zxr10mstatic6InstEntry ::=
        SEQUENCE {
            zxr10mstatic6InstVrfName
                DisplayString,
            zxr10mstatic6InstMstaticFlag
                Unsigned32
        }

zxr10mstatic6InstVrfName OBJECT-TYPE
        SYNTAX DisplayString (SIZE (0..32))
        MAX-ACCESS  read-only
        STATUS  current
        DESCRIPTION
            "vrf name"
        ::= { zxr10mstatic6InstEntry 1 }

zxr10mstatic6InstMstaticFlag OBJECT-TYPE
        SYNTAX Unsigned32 (0..1)
        MAX-ACCESS  read-only
        STATUS  current
        DESCRIPTION
            "enable IPv6 mstatic flag"
        ::= { zxr10mstatic6InstEntry 2 }



zxr10mstatic6OifindexTable OBJECT-TYPE
        SYNTAX  SEQUENCE OF Zxr10mstatic6OifindexEntry
        MAX-ACCESS  not-accessible
        STATUS  current
        DESCRIPTION
            "A table to IPv6 mstatic oif index"
        ::= { zxr10mstatic6InstMIB 2 }

zxr10mstatic6OifindexEntry OBJECT-TYPE
        SYNTAX Zxr10mstatic6OifindexEntry
        MAX-ACCESS  not-accessible
        STATUS  current
        DESCRIPTION
            "An entry to IPv6 mstatic oif index"
        INDEX  { zxr10mstatic6OifindexVrfName,
             zxr10mstatic6OifindexIntfName,zxr10mstatic6OifindexOifIndex }
        ::= { zxr10mstatic6OifindexTable 1 }
            
Zxr10mstatic6OifindexEntry ::=
        SEQUENCE {
            zxr10mstatic6OifindexVrfName
                DisplayString,
            zxr10mstatic6OifindexIntfName
                DisplayString,
            zxr10mstatic6OifindexOifIndex
                Unsigned32,
            zxr10mstatic6OifindexVlanMin
                Unsigned32,
            zxr10mstatic6OifindexVlanMax
                Unsigned32
        }

zxr10mstatic6OifindexVrfName OBJECT-TYPE
        SYNTAX DisplayString (SIZE (0..32))
        MAX-ACCESS  read-only
        STATUS  current
        DESCRIPTION
            "vrf name"
        ::= { zxr10mstatic6OifindexEntry 1 }

zxr10mstatic6OifindexIntfName OBJECT-TYPE
        SYNTAX DisplayString (SIZE (0..32))
        MAX-ACCESS  read-only
        STATUS  current
        DESCRIPTION
            "interface name"
        ::= { zxr10mstatic6OifindexEntry 2 }

zxr10mstatic6OifindexOifIndex OBJECT-TYPE
        SYNTAX Unsigned32 (0..100)
        MAX-ACCESS  read-only
        STATUS  current
        DESCRIPTION
            "oif index"
        ::= { zxr10mstatic6OifindexEntry 3 }

zxr10mstatic6OifindexVlanMin OBJECT-TYPE
        SYNTAX Unsigned32 (0..65536)
        MAX-ACCESS  read-only
        STATUS  obsolete
        DESCRIPTION
            "vlan min"
        ::= { zxr10mstatic6OifindexEntry 4 }

zxr10mstatic6OifindexVlanMax OBJECT-TYPE
        SYNTAX Unsigned32 (0..65536)
        MAX-ACCESS  read-only
        STATUS  obsolete
        DESCRIPTION
            "vlan max"
        ::= { zxr10mstatic6OifindexEntry 5 }


zxr10mstatic6LimitMIB OBJECT IDENTIFIER ::= { zxr10mstatic6InstMIB 3 }

zxr10mstatic6LimitTable OBJECT-TYPE
        SYNTAX  SEQUENCE OF Zxr10mstatic6LimitEntry
        MAX-ACCESS  not-accessible
        STATUS  current
        DESCRIPTION
            "A table to IPv6 mstatic limit"
        ::= { zxr10mstatic6LimitMIB 1 }

zxr10mstatic6LimitEntry OBJECT-TYPE
        SYNTAX Zxr10mstatic6LimitEntry
        MAX-ACCESS  not-accessible
        STATUS  current
        DESCRIPTION
            "An entry to IPv6 mstatic limit"
        INDEX  { zxr10mstatic6LimitVrfname }
        ::= { zxr10mstatic6LimitTable 1 }
            
Zxr10mstatic6LimitEntry ::=
        SEQUENCE {
            zxr10mstatic6LimitVrfname
                DisplayString,
            zxr10mstatic6LimitXgLimit
                INTEGER,
            zxr10mstatic6LimitSgLimit
                INTEGER
        }

zxr10mstatic6LimitVrfname OBJECT-TYPE
        SYNTAX DisplayString (SIZE (0..32))
        MAX-ACCESS  read-only
        STATUS  current
        DESCRIPTION
            "vrf name"
        ::= { zxr10mstatic6LimitEntry 1 }

zxr10mstatic6LimitXgLimit OBJECT-TYPE
        SYNTAX INTEGER (0..2048)
        MAX-ACCESS  read-only
        STATUS  current
        DESCRIPTION
            "xg number limit, the max value gets from performance parameter."
        ::= { zxr10mstatic6LimitEntry 2 }

zxr10mstatic6LimitSgLimit OBJECT-TYPE
        SYNTAX INTEGER (0..2048)
        MAX-ACCESS  read-only
        STATUS  current
        DESCRIPTION
            "sg number limit, the max value gets from performance parameter."
        ::= { zxr10mstatic6LimitEntry 3 }

zxr10mstatic6RouteTable OBJECT-TYPE
        SYNTAX  SEQUENCE OF Zxr10mstatic6RouteEntry
        MAX-ACCESS  not-accessible
        STATUS  current
        DESCRIPTION
            "A table to IPv6 mstatic route"
        ::= { zxr10mstatic6LimitMIB 2 }

zxr10mstatic6RouteEntry OBJECT-TYPE
        SYNTAX Zxr10mstatic6RouteEntry
        MAX-ACCESS  not-accessible
        STATUS  current
        DESCRIPTION
            "An entry to IPv6 mstatic route"
        INDEX  { zxr10mstatic6RouteVrfName,
        zxr10mstatic6RouteMstaticGroupAddr,
        zxr10mstatic6RouteMstaticSourceAddr }
        ::= { zxr10mstatic6RouteTable 1 }
            
Zxr10mstatic6RouteEntry ::=
        SEQUENCE {
            zxr10mstatic6RouteVrfName
                DisplayString,
            zxr10mstatic6RouteMstaticGroupAddr
                DisplayString,
            zxr10mstatic6RouteMstaticSourceAddr
                DisplayString,
            zxr10mstatic6RouteIifIntfname
                DisplayString,
            zxr10mstatic6RouteOifIndex
                Unsigned32,
            zxr10mstatic6RoutePermanent
                INTEGER,
            zxr10mstatic6RouteSlaveIifName
                DisplayString,
            zxr10mstatic6RouteTrackName
                DisplayString,
            zxr10mstatic6RouteSlaveTrackName
                DisplayString,
            zxr10mstatic6RouteIncMask
                Ipv6Address,
            zxr10mstatic6RouteCount
                Unsigned32                
        }

zxr10mstatic6RouteVrfName OBJECT-TYPE
        SYNTAX DisplayString (SIZE (0..32))
        MAX-ACCESS  read-only
        STATUS  current
        DESCRIPTION
            "vrf name"
        ::= { zxr10mstatic6RouteEntry 1 }

zxr10mstatic6RouteMstaticGroupAddr OBJECT-TYPE
        SYNTAX DisplayString (SIZE (0..16))
        MAX-ACCESS  read-only
        STATUS  current
        DESCRIPTION
            "group address"
        ::= { zxr10mstatic6RouteEntry 2 }

zxr10mstatic6RouteMstaticSourceAddr OBJECT-TYPE
        SYNTAX DisplayString (SIZE (0..16))
        MAX-ACCESS  read-only
        STATUS  current
        DESCRIPTION
            "source address"
        ::= { zxr10mstatic6RouteEntry 3 }

zxr10mstatic6RouteIifIntfname OBJECT-TYPE
        SYNTAX DisplayString (SIZE (0..32))
        MAX-ACCESS  read-only
        STATUS  current
        DESCRIPTION
            "iif interface name"
        ::= { zxr10mstatic6RouteEntry 4 }

zxr10mstatic6RouteOifIndex OBJECT-TYPE
        SYNTAX Unsigned32 (0..100)
        MAX-ACCESS  read-only
        STATUS  current
        DESCRIPTION
            "oif index"
        ::= { zxr10mstatic6RouteEntry 5 }

zxr10mstatic6RoutePermanent OBJECT-TYPE
        SYNTAX INTEGER {false(255),true(1)}
        MAX-ACCESS  read-only
        STATUS  current
        DESCRIPTION
            "permanent"
        ::= { zxr10mstatic6RouteEntry 6 }

zxr10mstatic6RouteSlaveIifName OBJECT-TYPE
        SYNTAX DisplayString (SIZE (0..32))
        MAX-ACCESS  read-only
        STATUS  current
        DESCRIPTION
            "slave iif interface name"
        ::= { zxr10mstatic6RouteEntry 7 }

zxr10mstatic6RouteTrackName OBJECT-TYPE
        SYNTAX DisplayString (SIZE (0..31))
        MAX-ACCESS  read-only
        STATUS  current
        DESCRIPTION
            "track name"
        ::= { zxr10mstatic6RouteEntry 8 }

zxr10mstatic6RouteSlaveTrackName OBJECT-TYPE
        SYNTAX DisplayString (SIZE (0..31))
        MAX-ACCESS  read-only
        STATUS  current
        DESCRIPTION
            "slave track name"
        ::= { zxr10mstatic6RouteEntry 9 }

zxr10mstatic6RouteIncMask OBJECT-TYPE
        SYNTAX Ipv6Address
        MAX-ACCESS  read-only
        STATUS  current
        DESCRIPTION
            "Increment mask of IPv6 MSTATIC group address"
        ::= { zxr10mstatic6RouteEntry 10 }
        
zxr10mstatic6RouteCount OBJECT-TYPE
        SYNTAX Unsigned32 (0..512)
        MAX-ACCESS  read-only
        STATUS  current
        DESCRIPTION
            "The number of IPv6 MSTATIC group addresses"
        ::= { zxr10mstatic6RouteEntry 11 }        

zxr10mstatic6FrrTable OBJECT-TYPE
        SYNTAX  SEQUENCE OF Zxr10mstatic6FrrEntry
        MAX-ACCESS  not-accessible
        STATUS  current
        DESCRIPTION
            "A table to IPv6 mstatic fast reroute"
        ::= { zxr10mstatic6InstMIB 4 }

zxr10mstatic6FrrEntry OBJECT-TYPE
        SYNTAX Zxr10mstatic6FrrEntry
        MAX-ACCESS  not-accessible
        STATUS  current
        DESCRIPTION
            "An entry to IPv6 mstatic fast reroute"
        INDEX  { zxr10mstatic6FrrVrfName }
        ::= { zxr10mstatic6FrrTable 1 }
            
Zxr10mstatic6FrrEntry ::=
        SEQUENCE {
            zxr10mstatic6FrrVrfName
                DisplayString,
            zxr10mstatic6FrrWtr
                Unsigned32
        }

zxr10mstatic6FrrVrfName OBJECT-TYPE
        SYNTAX DisplayString (SIZE (0..32))
        MAX-ACCESS  not-accessible
        STATUS  current
        DESCRIPTION
            "vrf name"
        ::= { zxr10mstatic6FrrEntry 1 }

zxr10mstatic6FrrWtr OBJECT-TYPE
        SYNTAX Unsigned32 (0..12)
        MAX-ACCESS  read-only
        STATUS  current
        DESCRIPTION
            "wait to restore"
        ::= { zxr10mstatic6FrrEntry 2 }

zxr10pimsm6InstMIB OBJECT IDENTIFIER ::= { zxr10mr6InstanceMIB 3 }

zxr10pimsm6InstTable OBJECT-TYPE
        SYNTAX  SEQUENCE OF Zxr10pimsm6InstEntry
        MAX-ACCESS  not-accessible
        STATUS  current
        DESCRIPTION
            "A table to PIMSM6 instance"
        ::= { zxr10pimsm6InstMIB 1 }

zxr10pimsm6InstEntry OBJECT-TYPE
        SYNTAX Zxr10pimsm6InstEntry
        MAX-ACCESS  not-accessible
        STATUS  current
        DESCRIPTION
            "An entry to PIMSM6 instance"
        INDEX  { zxr10pimsm6InstVrfName }
        ::= { zxr10pimsm6InstTable 1 }
            
Zxr10pimsm6InstEntry ::=
        SEQUENCE {
            zxr10pimsm6InstVrfName
                DisplayString,
            zxr10pimsm6InstRouterPimsm
                Unsigned32,
            zxr10pimsm6InstErpDisable
                Unsigned32,
            zxr10pimsm6InstSptThreshold
                Unsigned32,
            zxr10pimsm6InstSsmDefault
                Unsigned32,
            zxr10pimsm6InstSsmDataAclName
                DisplayString,
            zxr10pimsm6InstSptThresholdAcl
                DisplayString,
            zxr10pimsm6InstAcceptRpAclName
                DisplayString,
            zxr10pimsm6InstRegFilterAclName
                DisplayString,
            zxr10pimsm6InstArpLocalAddr
                DisplayString,
            zxr10pimsm6InstRegProbeInterval
                Unsigned32,
            zxr10pimsm6InstRegSuppressionInterval
                Unsigned32,
            zxr10pimsm6InstBsmUnicast
                Unsigned32,
            zxr10pimsm6InstSrpOverride
                Unsigned32,
            zxr10pimsm6InstDataFilterAclName
                DisplayString,
            zxr10pimsm6InstBidirPim
                INTEGER,
            zxr10pimsm6InstJpInterval
                Unsigned32,
            zxr10pimsm6InstRegHoldtime
                Unsigned32,
            zxr10pimsm6InstSsmEnable
                INTEGER,
            zxr10pimsm6InstJpSpeed
                Unsigned32,
            zxr10pimsm6InstKeepAlivePeriod
                Unsigned32,
            zxr10pimsm6InstAssertHoldTime
                Unsigned32,
            zxr10pimsm6InstGraftTime 
                Unsigned32,
            zxr10pimsm6InstCbsrHoldtime
                Unsigned32,
            zxr10pimsm6InstCbsrInterval
                Unsigned32,
            zxr10pimsm6InstPimdmReg
                INTEGER,
            zxr10pimsm6InstMofrrAclName
                DisplayString,
            zxr10pimsm6InstStatisticsAclName
                DisplayString
        }

zxr10pimsm6InstVrfName OBJECT-TYPE
        SYNTAX DisplayString (SIZE (0..32))
        MAX-ACCESS  read-only
        STATUS  current
        DESCRIPTION
            "vrf name"
        ::= { zxr10pimsm6InstEntry 1 }

zxr10pimsm6InstRouterPimsm OBJECT-TYPE
        SYNTAX Unsigned32 (0..1)
        MAX-ACCESS  read-only
        STATUS  current
        DESCRIPTION
            "enable PIMSM6"
        ::= { zxr10pimsm6InstEntry 2 }

zxr10pimsm6InstErpDisable OBJECT-TYPE
        SYNTAX Unsigned32 (0..1)
        MAX-ACCESS  read-only
        STATUS  current
        DESCRIPTION
            "disable embedded-RP"
        ::= { zxr10pimsm6InstEntry 3 }

zxr10pimsm6InstSptThreshold OBJECT-TYPE
        SYNTAX Unsigned32 (0..1)
        MAX-ACCESS  read-only
        STATUS  current
        DESCRIPTION
            "SPT threshold"
        ::= { zxr10pimsm6InstEntry 4 }

zxr10pimsm6InstSsmDefault OBJECT-TYPE
        SYNTAX Unsigned32 (0..1)
        MAX-ACCESS  read-only
        STATUS  current
        DESCRIPTION
            "ssm default"
        ::= { zxr10pimsm6InstEntry 5 }

zxr10pimsm6InstSsmDataAclName OBJECT-TYPE
        SYNTAX DisplayString (SIZE (0..31))
        MAX-ACCESS  read-only
        STATUS  current
        DESCRIPTION
            "ssm data ACL name"
        ::= { zxr10pimsm6InstEntry 6 }

zxr10pimsm6InstSptThresholdAcl OBJECT-TYPE
        SYNTAX DisplayString (SIZE (0..31))
        MAX-ACCESS  read-only
        STATUS  current
        DESCRIPTION
            "SPT threshold ACL name"
        ::= { zxr10pimsm6InstEntry 7 }

zxr10pimsm6InstAcceptRpAclName OBJECT-TYPE
        SYNTAX DisplayString (SIZE (0..31))
        MAX-ACCESS  read-only
        STATUS  current
        DESCRIPTION
            "accept RP ACL name"
        ::= { zxr10pimsm6InstEntry 8 }

zxr10pimsm6InstRegFilterAclName OBJECT-TYPE
        SYNTAX DisplayString (SIZE (0..31))
        MAX-ACCESS  read-only
        STATUS  current
        DESCRIPTION
            "register filter ACL name"
        ::= { zxr10pimsm6InstEntry 9 }

zxr10pimsm6InstArpLocalAddr OBJECT-TYPE
        SYNTAX DisplayString (SIZE (0..16))
        MAX-ACCESS  read-only
        STATUS  current
        DESCRIPTION
            "anycast-RP local address"
        ::= { zxr10pimsm6InstEntry 10 }

zxr10pimsm6InstRegProbeInterval OBJECT-TYPE
        SYNTAX Unsigned32 (1..210)
        MAX-ACCESS  read-only
        STATUS  current
        DESCRIPTION
            "register probe interval"
        ::= { zxr10pimsm6InstEntry 11 }

zxr10pimsm6InstRegSuppressionInterval OBJECT-TYPE
        SYNTAX Unsigned32 (60..3600)
        MAX-ACCESS  read-only
        STATUS  current
        DESCRIPTION
            "register suppression interval"
        ::= { zxr10pimsm6InstEntry 12 }
        
zxr10pimsm6InstBsmUnicast OBJECT-TYPE
        SYNTAX Unsigned32 (0..1)
        MAX-ACCESS  read-only
        STATUS  current
        DESCRIPTION
            "bsm unicast"
        ::= { zxr10pimsm6InstEntry 13 }
        
zxr10pimsm6InstSrpOverride OBJECT-TYPE
        SYNTAX Unsigned32 (0..1)
        MAX-ACCESS  read-only
        STATUS  current
        DESCRIPTION
            "enable static RP override"
        ::= { zxr10pimsm6InstEntry 14 }

zxr10pimsm6InstDataFilterAclName OBJECT-TYPE
        SYNTAX DisplayString (SIZE (0..31))
        MAX-ACCESS  read-only
        STATUS  current
        DESCRIPTION
            "IPv6 PIM source filter ACL name"
        ::= { zxr10pimsm6InstEntry 15 }

zxr10pimsm6InstBidirPim OBJECT-TYPE
        SYNTAX INTEGER {false(255),true(1)}
        MAX-ACCESS  read-only
        STATUS  current
        DESCRIPTION
            "IPv6 bidir PIM"
        ::= { zxr10pimsm6InstEntry 16 }

zxr10pimsm6InstJpInterval OBJECT-TYPE
        SYNTAX Unsigned32 (10..6000)
        MAX-ACCESS  read-only
        STATUS  current
        DESCRIPTION
            "J/P packet interval"
        ::= { zxr10pimsm6InstEntry 17 }

zxr10pimsm6InstRegHoldtime OBJECT-TYPE
        SYNTAX Unsigned32 (1..600)
        MAX-ACCESS  read-only
        STATUS  current
        DESCRIPTION
            "Register hold time without receiving register stop packet"
        ::= { zxr10pimsm6InstEntry 18 }
 
 zxr10pimsm6InstSsmEnable OBJECT-TYPE
        SYNTAX INTEGER {false(255),true(1)}
        MAX-ACCESS  read-only
        STATUS  obsolete
        DESCRIPTION
            "enable SSM"
        ::= { zxr10pimsm6InstEntry 19 }

zxr10pimsm6InstJpSpeed OBJECT-TYPE        
        SYNTAX Unsigned32 (1000..50000) 
        MAX-ACCESS  read-only  
        STATUS  current  
        DESCRIPTION           
            "Join/Prune Speed"    
        ::= { zxr10pimsm6InstEntry 20 } 
        
zxr10pimsm6InstKeepAlivePeriod OBJECT-TYPE 
        SYNTAX Unsigned32 (60..65535)  
        MAX-ACCESS  read-only    
        STATUS  current     
        DESCRIPTION            
            "Keepalive Period"    
        ::= { zxr10pimsm6InstEntry 21 }  

zxr10pimsm6InstAssertHoldTime OBJECT-TYPE  
        SYNTAX Unsigned32 (60..65535)  
        MAX-ACCESS  read-only 
        STATUS  current    
        DESCRIPTION      
            "Assert HoldTime"  
        ::= { zxr10pimsm6InstEntry 22 } 
        
zxr10pimsm6InstGraftTime OBJECT-TYPE
        SYNTAX Unsigned32 (1..65535)  
        MAX-ACCESS  read-only      
        STATUS  current       
        DESCRIPTION            
            "Graft Time" 
        ::= { zxr10pimsm6InstEntry 23 }

zxr10pimsm6InstCbsrHoldtime OBJECT-TYPE
        SYNTAX Unsigned32 (130..65535)
        MAX-ACCESS  read-only
        STATUS  current
        DESCRIPTION
            "C-BSR holdtime"
        ::= { zxr10pimsm6InstEntry 24 }
        
zxr10pimsm6InstCbsrInterval OBJECT-TYPE
        SYNTAX Unsigned32 (10..65535)
        MAX-ACCESS  read-only
        STATUS  current
        DESCRIPTION
            "C-BSR interval"
        ::= { zxr10pimsm6InstEntry 25 }

zxr10pimsm6InstPimdmReg OBJECT-TYPE
        SYNTAX INTEGER {false(255),true(1)}
        MAX-ACCESS  read-only
        STATUS  current
        DESCRIPTION
            "Send register packets when the PIM-DM interface receives
             indirectly connected stream"
        ::= { zxr10pimsm6InstEntry 26 }
        
zxr10pimsm6InstMofrrAclName OBJECT-TYPE
        SYNTAX DisplayString (SIZE (0..31))
        MAX-ACCESS  read-only
        STATUS  current
        DESCRIPTION
            "MoFRR ACL name"
        ::= { zxr10pimsm6InstEntry 27 }

zxr10pimsm6InstStatisticsAclName OBJECT-TYPE
        SYNTAX DisplayString (SIZE (0..31))
        MAX-ACCESS  read-only
        STATUS  current
        DESCRIPTION
            "IPv6 PIM packet statistics ACL name"
        ::= { zxr10pimsm6InstEntry 28 }

zxr10pimsm6IntfTable OBJECT-TYPE
        SYNTAX  SEQUENCE OF Zxr10pimsm6IntfEntry
        MAX-ACCESS  not-accessible
        STATUS  current
        DESCRIPTION
            "A table to PIMSM6 interface"
        ::= { zxr10pimsm6InstMIB 2 } 
    

zxr10pimsm6IntfEntry OBJECT-TYPE
        SYNTAX Zxr10pimsm6IntfEntry
        MAX-ACCESS  not-accessible
        STATUS  current
        DESCRIPTION
            "An entry to PIMSM6 interface"
        INDEX  { zxr10pimsm6IntfVrfName,zxr10pimsm6IntfName }
        ::= { zxr10pimsm6IntfTable 1 }
            
Zxr10pimsm6IntfEntry ::=
        SEQUENCE {
            zxr10pimsm6IntfVrfName
                DisplayString,
            zxr10pimsm6IntfName
                DisplayString,
            zxr10pimsm6IntfPimsm
                Unsigned32,
            zxr10pimsm6IntfBsrBorder
                Unsigned32,
            zxr10pimsm6IntfHelloInterval
                Unsigned32,
            zxr10pimsm6IntfDrPriority
                Unsigned32,
            zxr10pimsm6IntfNbrFilterAclName
                DisplayString,
            zxr10pimsm6IntfSilent
                Unsigned32,
            zxr10pimsm6IntfBfdEnable
                Unsigned32,
            zxr10pimsm6IntfPimDm
                Unsigned32,
            zxr10pimsm6IntfPropagationDelay 
                Unsigned32, 
            zxr10pimsm6IntfOverrideInterval 
                Unsigned32,   
            zxr10pimsm6IntfJpMaxpktLen
                Unsigned32,
            zxr10pimsm6IntfHelloDrAddr
                INTEGER,
            zxr10pimsm6InterfaceFrrEn
                INTEGER,
            zxr10pimsm6IntfHelloTrackSupport
                INTEGER,
            zxr10pimsm6IntfAssertDisable
                INTEGER
        }

zxr10pimsm6IntfVrfName OBJECT-TYPE
        SYNTAX DisplayString (SIZE (0..32))
        MAX-ACCESS  read-only
        STATUS  current
        DESCRIPTION
            "vrf name"
        ::= { zxr10pimsm6IntfEntry 1 }

zxr10pimsm6IntfName OBJECT-TYPE
        SYNTAX DisplayString (SIZE (0..32))
        MAX-ACCESS  read-only
        STATUS  current
        DESCRIPTION
            "interface name"
        ::= { zxr10pimsm6IntfEntry 2 }

zxr10pimsm6IntfPimsm OBJECT-TYPE
        SYNTAX Unsigned32 (0..1)
        MAX-ACCESS  read-only
        STATUS  current
        DESCRIPTION
            "enable PIMSM"
        ::= { zxr10pimsm6IntfEntry 3 }

zxr10pimsm6IntfBsrBorder OBJECT-TYPE
        SYNTAX Unsigned32 (0..1)
        MAX-ACCESS  read-only
        STATUS  current
        DESCRIPTION
            "BSR border"
        ::= { zxr10pimsm6IntfEntry 4 }

zxr10pimsm6IntfHelloInterval OBJECT-TYPE
        SYNTAX Unsigned32 (1..65535)
        MAX-ACCESS  read-only
        STATUS  current
        DESCRIPTION
            "hello packet interval"
        ::= { zxr10pimsm6IntfEntry 5 }

zxr10pimsm6IntfDrPriority OBJECT-TYPE
        SYNTAX Unsigned32 (0..4294967295)
        MAX-ACCESS  read-only
        STATUS  current
        DESCRIPTION
            "DR priority"
        ::= { zxr10pimsm6IntfEntry 6 }

zxr10pimsm6IntfNbrFilterAclName OBJECT-TYPE
        SYNTAX DisplayString (SIZE (0..31))
        MAX-ACCESS  read-only
        STATUS  current
        DESCRIPTION
            "PIM neighbour filter ACL name"
        ::= { zxr10pimsm6IntfEntry 7 }

zxr10pimsm6IntfSilent OBJECT-TYPE
        SYNTAX Unsigned32 (0..1)
        MAX-ACCESS  read-only
        STATUS  current
        DESCRIPTION
            "PIM silent"
        ::= { zxr10pimsm6IntfEntry 8 }

zxr10pimsm6IntfBfdEnable OBJECT-TYPE
        SYNTAX Unsigned32 (0..1)
        MAX-ACCESS  read-only
        STATUS  current
        DESCRIPTION
            "enable BFD"
        ::= { zxr10pimsm6IntfEntry 9 }
        
zxr10pimsm6IntfPimDm OBJECT-TYPE
        SYNTAX Unsigned32 (0..1)
        MAX-ACCESS  read-only
        STATUS  current
        DESCRIPTION
            "enable pimdm"
        ::= { zxr10pimsm6IntfEntry 10 }

zxr10pimsm6IntfPropagationDelay OBJECT-TYPE
        SYNTAX Unsigned32 (1..100) 
        MAX-ACCESS  read-only 
        STATUS  current 
        DESCRIPTION            
            "propagation delay"
        ::= { zxr10pimsm6IntfEntry 11 }

zxr10pimsm6IntfOverrideInterval OBJECT-TYPE
        SYNTAX Unsigned32 (1..600) 
        MAX-ACCESS  read-only   
        STATUS  current
        DESCRIPTION  
            "override interval" 
        ::= { zxr10pimsm6IntfEntry 12 }

zxr10pimsm6IntfJpMaxpktLen OBJECT-TYPE  
        SYNTAX Unsigned32 (100..8100)
        MAX-ACCESS  read-only     
        STATUS  current    
        DESCRIPTION     
            "max length of PIM Join/Prune packet"
        ::= { zxr10pimsm6IntfEntry 13 }

zxr10pimsm6IntfHelloDrAddr OBJECT-TYPE
        SYNTAX INTEGER {false(255),true(1)}
        MAX-ACCESS  read-only
        STATUS  current
        DESCRIPTION
            "PIM hello packet sent with hello DR address"
        ::= { zxr10pimsm6IntfEntry 14 }

zxr10pimsm6InterfaceFrrEn OBJECT-TYPE
        SYNTAX INTEGER {false(255),true(1)}
        MAX-ACCESS  read-only
        STATUS  current
        DESCRIPTION
            "PIM FRR enable"
        ::= { zxr10pimsm6IntfEntry 15 }

zxr10pimsm6IntfHelloTrackSupport OBJECT-TYPE
        SYNTAX INTEGER {false(255),true(1)}
        MAX-ACCESS  read-only
        STATUS  current
        DESCRIPTION
            "PIM hello tracking support enable"
        ::= { zxr10pimsm6IntfEntry 16 }

zxr10pimsm6IntfAssertDisable OBJECT-TYPE
        SYNTAX INTEGER {false(255),true(1)}
        MAX-ACCESS  read-only
        STATUS  current
        DESCRIPTION
            "PIM assert disable"
        ::= { zxr10pimsm6IntfEntry 17 }

zxr10pimsm6CrpTable OBJECT-TYPE
        SYNTAX  SEQUENCE OF Zxr10pimsm6CrpEntry
        MAX-ACCESS  not-accessible
        STATUS  current
        DESCRIPTION
            "A table to pimsm6 candidate RP"
        ::= { zxr10pimsm6InstMIB 3 }

zxr10pimsm6CrpEntry OBJECT-TYPE
        SYNTAX Zxr10pimsm6CrpEntry
        MAX-ACCESS  not-accessible
        STATUS  current
        DESCRIPTION
            "An entry to pimsm6 candidate RP"
        INDEX  { zxr10pimsm6CrpVrfName,zxr10pimsm6CrpIpv6Addr }
        ::= { zxr10pimsm6CrpTable 1 }
            
Zxr10pimsm6CrpEntry ::=
        SEQUENCE {
            zxr10pimsm6CrpVrfName
                DisplayString,
            zxr10pimsm6CrpIpv6Addr
                DisplayString,
            zxr10pimsm6CrpPrefixList
                DisplayString,
            zxr10pimsm6CrpPriority
                Unsigned32,
            zxr10pimsm6CrpBidirPim
                INTEGER,
            zxr10pimsm6CrpHoldtime
                Unsigned32
        }

zxr10pimsm6CrpVrfName OBJECT-TYPE
        SYNTAX DisplayString (SIZE (0..32))
        MAX-ACCESS  read-only
        STATUS  current
        DESCRIPTION
            "vrf name"
        ::= { zxr10pimsm6CrpEntry 1 }

zxr10pimsm6CrpIpv6Addr OBJECT-TYPE
        SYNTAX DisplayString (SIZE (0..16))
        MAX-ACCESS  read-only
        STATUS  current
        DESCRIPTION
            "candidate RP address "
        ::= { zxr10pimsm6CrpEntry 2 }

zxr10pimsm6CrpPrefixList OBJECT-TYPE         
        SYNTAX DisplayString (SIZE (0..31))
        MAX-ACCESS  read-only
        STATUS  current
        DESCRIPTION
            "candidate RP prefix list"
        ::= { zxr10pimsm6CrpEntry 3 }

zxr10pimsm6CrpPriority OBJECT-TYPE
        SYNTAX Unsigned32 (0..255)
        MAX-ACCESS  read-only
        STATUS  current
        DESCRIPTION
            "candidate RP priority"
        ::= { zxr10pimsm6CrpEntry 4 }

zxr10pimsm6CrpBidirPim OBJECT-TYPE
        SYNTAX INTEGER {false(255),true(1)}
        MAX-ACCESS  read-only
        STATUS  current
        DESCRIPTION
            "candidate RP bidir"
        ::= { zxr10pimsm6CrpEntry 5 }

zxr10pimsm6CrpHoldtime OBJECT-TYPE
        SYNTAX Unsigned32 (150..65535)
        MAX-ACCESS  read-only
        STATUS  current
        DESCRIPTION
            "candidate RP holdtime"
        ::= { zxr10pimsm6CrpEntry 6 }

zxr10pimsm6SrpTable OBJECT-TYPE
        SYNTAX  SEQUENCE OF Zxr10pimsm6SrpEntry
        MAX-ACCESS  not-accessible
        STATUS  current
        DESCRIPTION
            "A table to pimsm6 static RP"
        ::= { zxr10pimsm6InstMIB 4 }

zxr10pimsm6SrpEntry OBJECT-TYPE
        SYNTAX Zxr10pimsm6SrpEntry
        MAX-ACCESS  not-accessible
        STATUS  current
        DESCRIPTION
            "An entry to pimsm6 static RP"
        INDEX  { zxr10pimsm6SrpVrfName,zxr10pimsm6SrpIpv6Addr }
        ::= { zxr10pimsm6SrpTable 1 }
            
Zxr10pimsm6SrpEntry ::=
        SEQUENCE {
            zxr10pimsm6SrpVrfName
                DisplayString,
            zxr10pimsm6SrpIpv6Addr
                DisplayString,
            zxr10pimsm6SrpPrefixList
                DisplayString,
            zxr10pimsm6SrpPriority
                Unsigned32,
            zxr10pimsm6SrpBidirPim
                INTEGER
        }

zxr10pimsm6SrpVrfName OBJECT-TYPE
        SYNTAX DisplayString (SIZE (0..32))
        MAX-ACCESS  read-only
        STATUS  current
        DESCRIPTION
            "vrf name"
        ::= { zxr10pimsm6SrpEntry 1 }

zxr10pimsm6SrpIpv6Addr OBJECT-TYPE
        SYNTAX DisplayString (SIZE (0..16))
        MAX-ACCESS  read-only
        STATUS  current
        DESCRIPTION
            "static RP address"
        ::= { zxr10pimsm6SrpEntry 2 }

zxr10pimsm6SrpPrefixList OBJECT-TYPE
        SYNTAX DisplayString (SIZE (0..31))
        MAX-ACCESS  read-only
        STATUS  current
        DESCRIPTION
            "static RP prefix list"
        ::= { zxr10pimsm6SrpEntry 3 }

zxr10pimsm6SrpPriority OBJECT-TYPE
        SYNTAX Unsigned32 (0..255)
        MAX-ACCESS  read-only
        STATUS  current
        DESCRIPTION
            "static RP priority"
        ::= { zxr10pimsm6SrpEntry 4 }

zxr10pimsm6SrpBidirPim OBJECT-TYPE
        SYNTAX INTEGER {false(255),true(1)}
        MAX-ACCESS  read-only
        STATUS  current
        DESCRIPTION
            "static RP bidir"
        ::= { zxr10pimsm6SrpEntry 5 }


zxr10pimsm6ArpPeerTable OBJECT-TYPE
        SYNTAX  SEQUENCE OF Zxr10pimsm6ArpPeerEntry
        MAX-ACCESS  not-accessible
        STATUS  current
        DESCRIPTION
            "A table to anycast-RP peer"
        ::= { zxr10pimsm6InstMIB 5 }

zxr10pimsm6ArpPeerEntry OBJECT-TYPE
        SYNTAX Zxr10pimsm6ArpPeerEntry
        MAX-ACCESS  not-accessible
        STATUS  current
        DESCRIPTION
            "An entry to anycast-RP peer"
        INDEX  { zxr10pimsm6ArpPeerVrfName,zxr10pimsm6ArpPeerIpv6Addr }
        ::= { zxr10pimsm6ArpPeerTable 1 }
            
Zxr10pimsm6ArpPeerEntry ::=
        SEQUENCE {
            zxr10pimsm6ArpPeerVrfName
                DisplayString,
            zxr10pimsm6ArpPeerIpv6Addr
                DisplayString
        }

zxr10pimsm6ArpPeerVrfName OBJECT-TYPE
        SYNTAX DisplayString (SIZE (0..32))
        MAX-ACCESS  read-only
        STATUS  current
        DESCRIPTION
            "vrf name"
        ::= { zxr10pimsm6ArpPeerEntry 1 }

zxr10pimsm6ArpPeerIpv6Addr OBJECT-TYPE
        SYNTAX DisplayString (SIZE (0..16))
        MAX-ACCESS  read-only
        STATUS  current
        DESCRIPTION
            "peer address"
        ::= { zxr10pimsm6ArpPeerEntry 2 }



zxr10pimsm6BsrTable OBJECT-TYPE
        SYNTAX  SEQUENCE OF Zxr10pimsm6BsrEntry
        MAX-ACCESS  not-accessible
        STATUS  current
        DESCRIPTION
            "A table to pimsm6 BSR"
        ::= { zxr10pimsm6InstMIB 6 }

zxr10pimsm6BsrEntry OBJECT-TYPE
        SYNTAX Zxr10pimsm6BsrEntry
        MAX-ACCESS  not-accessible
        STATUS  current
        DESCRIPTION
            "An entry to pimsm6 BSR"
        INDEX  { zxr10pimsm6BsrVrfName }
        ::= { zxr10pimsm6BsrTable 1 }
            
Zxr10pimsm6BsrEntry ::=
        SEQUENCE {
            zxr10pimsm6BsrVrfName
                DisplayString,
            zxr10pimsm6BsrIpv6Addr
                DisplayString,
            zxr10pimsm6BsrPriority
                Unsigned32,
            zxr10pimsm6BsrHashLen
                Unsigned32
        }

zxr10pimsm6BsrVrfName OBJECT-TYPE
        SYNTAX DisplayString (SIZE (0..32))
        MAX-ACCESS  read-only
        STATUS  current
        DESCRIPTION
            "vrf name"
        ::= { zxr10pimsm6BsrEntry 1 }

zxr10pimsm6BsrIpv6Addr OBJECT-TYPE
        SYNTAX DisplayString (SIZE (0..16))
        MAX-ACCESS  read-only
        STATUS  current
        DESCRIPTION
            "BSR address"
        ::= { zxr10pimsm6BsrEntry 2 }

zxr10pimsm6BsrPriority OBJECT-TYPE
        SYNTAX Unsigned32 (0..255)
        MAX-ACCESS  read-only
        STATUS  current
        DESCRIPTION
            "BSR priority"
        ::= { zxr10pimsm6BsrEntry 3 }

zxr10pimsm6BsrHashLen OBJECT-TYPE
        SYNTAX Unsigned32 (0..128)
        MAX-ACCESS  read-only
        STATUS  current
        DESCRIPTION
            "BSR hash mask length"
        ::= { zxr10pimsm6BsrEntry 4 }
        
 zxr10pimsm6RegSourceTable OBJECT-TYPE
        SYNTAX  SEQUENCE OF Zxr10pimsm6RegSourceEntry
        MAX-ACCESS  not-accessible
        STATUS  current
        DESCRIPTION
            "A table to register source"
        ::= { zxr10pimsm6InstMIB 7 }

zxr10pimsm6RegSourceEntry OBJECT-TYPE
        SYNTAX Zxr10pimsm6RegSourceEntry
        MAX-ACCESS  not-accessible
        STATUS  current
        DESCRIPTION
            "An entry to register source"
        INDEX  { zxr10pimsm6RegSourceVrfName }
        ::= { zxr10pimsm6RegSourceTable 1 }
            
Zxr10pimsm6RegSourceEntry ::=
        SEQUENCE {
            zxr10pimsm6RegSourceVrfName
                DisplayString,
            zxr10pimsm6RegSourceIntfName
                DisplayString            
        }

zxr10pimsm6RegSourceVrfName OBJECT-TYPE
        SYNTAX DisplayString (SIZE (0..32))
        MAX-ACCESS  read-only
        STATUS  current
        DESCRIPTION
            "vrf name"
        ::= { zxr10pimsm6RegSourceEntry 1 }

zxr10pimsm6RegSourceIntfName OBJECT-TYPE
        SYNTAX DisplayString (SIZE (0..32))
        MAX-ACCESS  read-only
        STATUS  current
        DESCRIPTION
            "register source interface name"
        ::= { zxr10pimsm6RegSourceEntry 2 }       


zxr10mldInstMIB OBJECT IDENTIFIER ::= { zxr10mr6InstanceMIB 5 }

zxr10mldInstTable OBJECT-TYPE
        SYNTAX  SEQUENCE OF Zxr10mldInstEntry
        MAX-ACCESS  not-accessible
        STATUS  current
        DESCRIPTION
            "A table to MLD"
        ::= { zxr10mldInstMIB 1 }

zxr10mldInstEntry OBJECT-TYPE
        SYNTAX Zxr10mldInstEntry
        MAX-ACCESS  not-accessible
        STATUS  current
        DESCRIPTION
            "An entry to MLD"
        INDEX  { zxr10mldInstVrfName }
        ::= { zxr10mldInstTable 1 }
            
Zxr10mldInstEntry ::=
        SEQUENCE {
            zxr10mldInstVrfName
                DisplayString,
            zxr10mldInstShapingPacketsNumber
                Unsigned32,
            zxr10mldInstLastMemberQuery
                Unsigned32,
            zxr10mldInstQuerierTimeout
                Unsigned32,
            zxr10mldInstQueryInterval
                Unsigned32,
            zxr10mldInstQueryMaxResponse
                Unsigned32,
            zxr10mldInstRobustnessVariable
                Unsigned32,
            zxr10mldInstVersion
                INTEGER,
            zxr10mldInstRequireAlertOptions
                Unsigned32
        }

zxr10mldInstVrfName OBJECT-TYPE
        SYNTAX DisplayString (SIZE (0..32))
        MAX-ACCESS  read-only
        STATUS  current
        DESCRIPTION
            "vrf name"
        ::= { zxr10mldInstEntry 1 }

zxr10mldInstShapingPacketsNumber OBJECT-TYPE
        SYNTAX Unsigned32 (0..1)
        MAX-ACCESS  read-only
        STATUS  current
        DESCRIPTION
            "shaping packets number"
        ::= { zxr10mldInstEntry 3 }

zxr10mldInstLastMemberQuery OBJECT-TYPE
        SYNTAX Unsigned32 (1..25)
        MAX-ACCESS  read-only
        STATUS  current
        DESCRIPTION
            "last member query"
        ::= { zxr10mldInstEntry 4 }

zxr10mldInstQuerierTimeout OBJECT-TYPE
        SYNTAX Unsigned32 (60..300)
        MAX-ACCESS  read-only
        STATUS  current
        DESCRIPTION
            "querier timeout"
        ::= { zxr10mldInstEntry 5 }

zxr10mldInstQueryInterval OBJECT-TYPE
        SYNTAX Unsigned32 (1..65535)
        MAX-ACCESS  read-only
        STATUS  current
        DESCRIPTION
            "query interval"
        ::= { zxr10mldInstEntry 6 }

zxr10mldInstQueryMaxResponse OBJECT-TYPE
        SYNTAX Unsigned32 (1..25)
        MAX-ACCESS  read-only
        STATUS  current
        DESCRIPTION
            "query max response"
        ::= { zxr10mldInstEntry 7 }

zxr10mldInstRobustnessVariable OBJECT-TYPE
        SYNTAX Unsigned32 (2..7)
        MAX-ACCESS  read-only
        STATUS  current
        DESCRIPTION
            "robustness variable"
        ::= { zxr10mldInstEntry 8 }

zxr10mldInstVersion OBJECT-TYPE
        SYNTAX INTEGER {version1(1),version2(2)}
        MAX-ACCESS  read-only
        STATUS  current
        DESCRIPTION
            "MLD version"
        ::= { zxr10mldInstEntry 9 }
        
zxr10mldInstRequireAlertOptions OBJECT-TYPE
        SYNTAX Unsigned32 (0..1)
        MAX-ACCESS  read-only
        STATUS  current
        DESCRIPTION
            "require MLD router alert options"
        ::= { zxr10mldInstEntry 10 }        

zxr10mldSsmmapTable OBJECT-TYPE
        SYNTAX  SEQUENCE OF Zxr10mldSsmmapEntry
        MAX-ACCESS  not-accessible
        STATUS  current
        DESCRIPTION
            "A table to MLD SSM map"
        ::= { zxr10mldInstMIB 2 }

zxr10mldSsmmapEntry OBJECT-TYPE
        SYNTAX Zxr10mldSsmmapEntry
        MAX-ACCESS  not-accessible
        STATUS  current
        DESCRIPTION
            "An entry to MLD SSM map"
        INDEX  { zxr10mldSsmmapVrfName,zxr10mldSsmmapAclName,
              zxr10mldSsmmapSrcAddr,zxr10mldSsmmapDefault }
        ::= { zxr10mldSsmmapTable 1 }
            
Zxr10mldSsmmapEntry ::=
        SEQUENCE {
            zxr10mldSsmmapVrfName
                DisplayString,
            zxr10mldSsmmapAclName
                DisplayString,
            zxr10mldSsmmapSrcAddr
                DisplayString,
            zxr10mldSsmmapDefault
                Unsigned32
        }

zxr10mldSsmmapVrfName OBJECT-TYPE
        SYNTAX DisplayString (SIZE (0..32))
        MAX-ACCESS  read-only
        STATUS  current
        DESCRIPTION
            "vrf name"
        ::= { zxr10mldSsmmapEntry 1 }

zxr10mldSsmmapAclName OBJECT-TYPE
        SYNTAX DisplayString (SIZE (0..31))
        MAX-ACCESS  read-only
        STATUS  current
        DESCRIPTION
            "ACL name"
        ::= { zxr10mldSsmmapEntry 2 }

zxr10mldSsmmapSrcAddr OBJECT-TYPE
        SYNTAX DisplayString (SIZE (0..16))
        MAX-ACCESS  read-only
        STATUS  current
        DESCRIPTION
            "ssm map source address"
        ::= { zxr10mldSsmmapEntry 3 }

zxr10mldSsmmapDefault OBJECT-TYPE
        SYNTAX Unsigned32 (0..1)
        MAX-ACCESS  read-only
        STATUS  current
        DESCRIPTION
            "ssm map default"
        ::= { zxr10mldSsmmapEntry 4 }


zxr10mldIntfMIB OBJECT IDENTIFIER ::= { zxr10mldInstMIB 3 }

zxr10mldIntfTable OBJECT-TYPE
        SYNTAX  SEQUENCE OF Zxr10mldIntfEntry
        MAX-ACCESS  not-accessible
        STATUS  current
        DESCRIPTION
            "A table to MLD interface"
        ::= { zxr10mldIntfMIB 1 }

zxr10mldIntfEntry OBJECT-TYPE
        SYNTAX Zxr10mldIntfEntry
        MAX-ACCESS  not-accessible
        STATUS  current
        DESCRIPTION
            "An entry to MLD interface"
        INDEX  { zxr10mldIntfVrfName,zxr10mldIntfName }
        ::= { zxr10mldIntfTable 1 }
            
Zxr10mldIntfEntry ::=
        SEQUENCE {
            zxr10mldIntfVrfName
                DisplayString,
            zxr10mldIntfName
                DisplayString,
            zxr10mldIntfAccessGroup
                DisplayString,
            zxr10mldIntfImmediateAcl
                DisplayString,
            zxr10mldIntfLastMemberQueryInterval
                Unsigned32,
            zxr10mldIntfMaximumJoins
                Unsigned32,
            zxr10mldIntfQuerierTimeout
                Unsigned32,
            zxr10mldIntfQueryInterval
                Unsigned32,
            zxr10mldIntfQueryMaxResponseTime
                Unsigned32,
            zxr10mldIntfRobustnessCount
                Unsigned32,
            zxr10mldIntfShapingPacketsNumber
                Unsigned32,
            zxr10mldIntfVersion
                INTEGER,
            zxr10mldIntfImmediateAll
                Unsigned32,
            zxr10mldIntfQuerierElectionDisable
                Unsigned32
        }

zxr10mldIntfVrfName OBJECT-TYPE
        SYNTAX DisplayString (SIZE (0..32))
        MAX-ACCESS  read-only
        STATUS  current
        DESCRIPTION
            "vrf name"
        ::= { zxr10mldIntfEntry 1 }

zxr10mldIntfName OBJECT-TYPE
        SYNTAX DisplayString (SIZE (0..32))
        MAX-ACCESS  read-only
        STATUS  current
        DESCRIPTION
            "interface name"
        ::= { zxr10mldIntfEntry 2 }

zxr10mldIntfAccessGroup OBJECT-TYPE
        SYNTAX DisplayString (SIZE (0..31))
        MAX-ACCESS  read-only
        STATUS  current
        DESCRIPTION
            "access group"
        ::= { zxr10mldIntfEntry 3 }

zxr10mldIntfImmediateAcl OBJECT-TYPE
        SYNTAX DisplayString (SIZE (0..31))
        MAX-ACCESS  read-only
        STATUS  current
        DESCRIPTION
            "immediate leave ACL"
        ::= { zxr10mldIntfEntry 4 }

zxr10mldIntfLastMemberQueryInterval OBJECT-TYPE
        SYNTAX Unsigned32 (1..25)
        MAX-ACCESS  read-only
        STATUS  current
        DESCRIPTION
            "last member query interval"
        ::= { zxr10mldIntfEntry 5 }

zxr10mldIntfMaximumJoins OBJECT-TYPE
        SYNTAX Unsigned32 (0..40000)
        MAX-ACCESS  read-only
        STATUS  current
        DESCRIPTION
            "maximum joins number"
        ::= { zxr10mldIntfEntry 6 }

zxr10mldIntfQuerierTimeout OBJECT-TYPE
        SYNTAX Unsigned32 (60..300)
        MAX-ACCESS  read-only
        STATUS  current
        DESCRIPTION
            "querier timeout"
        ::= { zxr10mldIntfEntry 7 }

zxr10mldIntfQueryInterval OBJECT-TYPE
        SYNTAX Unsigned32 (1..65535)
        MAX-ACCESS  read-only
        STATUS  current
        DESCRIPTION
            "query interval"
        ::= { zxr10mldIntfEntry 8 }

zxr10mldIntfQueryMaxResponseTime OBJECT-TYPE
        SYNTAX Unsigned32 (1..25)
        MAX-ACCESS  read-only
        STATUS  current
        DESCRIPTION
            "query max response time"
        ::= { zxr10mldIntfEntry 9 }

zxr10mldIntfRobustnessCount OBJECT-TYPE
        SYNTAX Unsigned32 (2..7)
        MAX-ACCESS  read-only
        STATUS  current
        DESCRIPTION
            "robustness count"
        ::= { zxr10mldIntfEntry 10 }

zxr10mldIntfShapingPacketsNumber OBJECT-TYPE
        SYNTAX Unsigned32 (0..1)
        MAX-ACCESS  read-only
        STATUS  current
        DESCRIPTION
            "shaping packets number"
        ::= { zxr10mldIntfEntry 11 }

zxr10mldIntfVersion OBJECT-TYPE
        SYNTAX INTEGER {version1(1),version2(2)}
        MAX-ACCESS  read-only
        STATUS  current
        DESCRIPTION
            "MLD version"
        ::= { zxr10mldIntfEntry 12 }

zxr10mldIntfImmediateAll OBJECT-TYPE
        SYNTAX Unsigned32 (0..1)
        MAX-ACCESS  read-only
        STATUS  current
        DESCRIPTION
            "immediate leave all"
        ::= { zxr10mldIntfEntry 13 }

zxr10mldIntfQuerierElectionDisable OBJECT-TYPE
        SYNTAX Unsigned32 (0..1)
        MAX-ACCESS  read-only
        STATUS  current
        DESCRIPTION
            "querier election disable"
        ::= { zxr10mldIntfEntry 14 }


zxr10mldStaticGroupTable OBJECT-TYPE
        SYNTAX  SEQUENCE OF Zxr10mldStaticGroupEntry
        MAX-ACCESS  not-accessible
        STATUS  current
        DESCRIPTION
            "A table to static group"
        ::= { zxr10mldIntfMIB 2 }

zxr10mldStaticGroupEntry OBJECT-TYPE
        SYNTAX Zxr10mldStaticGroupEntry
        MAX-ACCESS  not-accessible
        STATUS  current
        DESCRIPTION
            "An entry to static group"
        INDEX  { zxr10mldStaticGroupVrfName,zxr10mldStaticGroupIfName,
                 zxr10mldStaticGroupGroup,zxr10mldStaticGroupSource,
                 zxr10mldStaticGroupSsmMap,zxr10mldStaticGroupStaticFlag,
                 zxr10mldStaticGroupIncMask}
        ::= { zxr10mldStaticGroupTable 1 }
            
Zxr10mldStaticGroupEntry ::=
        SEQUENCE {
            zxr10mldStaticGroupVrfName
                DisplayString,
            zxr10mldStaticGroupIfName
                DisplayString,
            zxr10mldStaticGroupGroup
                Ipv6Address,
            zxr10mldStaticGroupSource
                Ipv6Address,
            zxr10mldStaticGroupSsmMap
                Unsigned32,
            zxr10mldStaticGroupStaticFlag
                INTEGER,
            zxr10mldStaticGroupIncMask
                Ipv6Address,
            zxr10mldStaticGroupFilterMode
                INTEGER,
            zxr10mldStaticGroupCount
                Unsigned32
        }

zxr10mldStaticGroupVrfName OBJECT-TYPE
        SYNTAX DisplayString (SIZE (0..32))
        MAX-ACCESS  not-accessible
        STATUS  current
        DESCRIPTION
            "vrf name"
        ::= { zxr10mldStaticGroupEntry 1 }

zxr10mldStaticGroupIfName OBJECT-TYPE
        SYNTAX DisplayString (SIZE (0..32))
        MAX-ACCESS  not-accessible
        STATUS  current
        DESCRIPTION
            "interface name"
        ::= { zxr10mldStaticGroupEntry 2 }

zxr10mldStaticGroupGroup OBJECT-TYPE
        SYNTAX Ipv6Address
        MAX-ACCESS  not-accessible
        STATUS  current
        DESCRIPTION
            "group address"
        ::= { zxr10mldStaticGroupEntry 3 }

zxr10mldStaticGroupSource OBJECT-TYPE
        SYNTAX Ipv6Address
        MAX-ACCESS  not-accessible
        STATUS  current
        DESCRIPTION
            "source address"
        ::= { zxr10mldStaticGroupEntry 4 }

zxr10mldStaticGroupSsmMap OBJECT-TYPE
        SYNTAX Unsigned32 (0..1)
        MAX-ACCESS  not-accessible
        STATUS  current
        DESCRIPTION
            "ssm map"
        ::= { zxr10mldStaticGroupEntry 5 }

zxr10mldStaticGroupStaticFlag OBJECT-TYPE          
        SYNTAX INTEGER {staticGroup(1),joinGroup(2)}
        MAX-ACCESS  not-accessible
        STATUS  current
        DESCRIPTION
            "static flag"
        ::= { zxr10mldStaticGroupEntry 6 }

zxr10mldStaticGroupIncMask OBJECT-TYPE
        SYNTAX Ipv6Address
        MAX-ACCESS  not-accessible
        STATUS  current
        DESCRIPTION
            "increment mask for group address"
        ::= { zxr10mldStaticGroupEntry 7 }
zxr10mldStaticGroupFilterMode OBJECT-TYPE
        SYNTAX INTEGER {none(255),include(3),exclude(4)}
        MAX-ACCESS  read-only
        STATUS  current
        DESCRIPTION
            "source filter mode"
        ::= { zxr10mldStaticGroupEntry 8 }

zxr10mldStaticGroupCount OBJECT-TYPE
        SYNTAX Unsigned32 (0..512)
        MAX-ACCESS  read-only
        STATUS  current
        DESCRIPTION
            "number of group addresses to join"
        ::= { zxr10mldStaticGroupEntry 9 }

zxr10mldGroupTable OBJECT-TYPE
        SYNTAX  SEQUENCE OF Zxr10mldGroupEntry
        MAX-ACCESS  not-accessible
        STATUS  obsolete
        DESCRIPTION
            "A table to static group"
        ::= { zxr10mldIntfMIB 3 }

zxr10mldGroupEntry OBJECT-TYPE
        SYNTAX Zxr10mldGroupEntry
        MAX-ACCESS  not-accessible
        STATUS  obsolete
        DESCRIPTION
            "An entry to static group"
        INDEX  { zxr10mldGroupVrfName,zxr10mldGroupIfName,
                 zxr10mldGroupGroup,zxr10mldGroupSource,
                 zxr10mldGroupSsmMap,zxr10mldGroupStaticFlag }
        ::= { zxr10mldGroupTable 1 }
            
Zxr10mldGroupEntry ::=
        SEQUENCE {
            zxr10mldGroupVrfName
                DisplayString,
            zxr10mldGroupIfName
                DisplayString,
            zxr10mldGroupGroup
                DisplayString,
            zxr10mldGroupSource
                DisplayString,
            zxr10mldGroupSsmMap
                Unsigned32,
            zxr10mldGroupStaticFlag
                INTEGER,
            zxr10mldGroupFilterMode
                INTEGER
        }

zxr10mldGroupVrfName OBJECT-TYPE
        SYNTAX DisplayString (SIZE (0..32))
        MAX-ACCESS  read-only
        STATUS  obsolete
        DESCRIPTION
            "vrf name"
        ::= { zxr10mldGroupEntry 1 }

zxr10mldGroupIfName OBJECT-TYPE
        SYNTAX DisplayString (SIZE (0..32))
        MAX-ACCESS  read-only
        STATUS  obsolete
        DESCRIPTION
            "interface name"
        ::= { zxr10mldGroupEntry 2 }

zxr10mldGroupGroup OBJECT-TYPE
        SYNTAX DisplayString (SIZE (0..16))
        MAX-ACCESS  read-only
        STATUS  obsolete
        DESCRIPTION
            "group address"
        ::= { zxr10mldGroupEntry 3 }

zxr10mldGroupSource OBJECT-TYPE
        SYNTAX DisplayString (SIZE (0..16))
        MAX-ACCESS  read-only
        STATUS  obsolete
        DESCRIPTION
            "source address"
        ::= { zxr10mldGroupEntry 4 }

zxr10mldGroupSsmMap OBJECT-TYPE
        SYNTAX Unsigned32 (0..1)
        MAX-ACCESS  read-only
        STATUS  obsolete
        DESCRIPTION
            "ssm map"
        ::= { zxr10mldGroupEntry 5 }

zxr10mldGroupStaticFlag OBJECT-TYPE          
        SYNTAX INTEGER {staticGroup(1),joinGroup(2)}
        MAX-ACCESS  read-only
        STATUS  obsolete
        DESCRIPTION
            "static flag"
        ::= { zxr10mldGroupEntry 6 }
        
zxr10mldGroupFilterMode OBJECT-TYPE
        SYNTAX INTEGER {none(0),include(3),exclude(4)}
        MAX-ACCESS  read-only
        STATUS  obsolete
        DESCRIPTION
            "source filter mode"
        ::= { zxr10mldGroupEntry 7 }

zxr10mldGroupLimitTable OBJECT-TYPE
        SYNTAX  SEQUENCE OF Zxr10mldGroupLimitEntry
        MAX-ACCESS  not-accessible
        STATUS  current
        DESCRIPTION
            "A table to MLD group limit"
        ::= { zxr10mldInstMIB 4 }

zxr10mldGroupLimitEntry OBJECT-TYPE
        SYNTAX Zxr10mldGroupLimitEntry
        MAX-ACCESS  not-accessible
        STATUS  current
        DESCRIPTION
            "An entry to MLD group limit"
        INDEX  { zxr10mldGroupLimitVrfName,zxr10mldGroupLimitGroupAddr}
        ::= { zxr10mldGroupLimitTable 1 }
            
Zxr10mldGroupLimitEntry ::=
        SEQUENCE {
            zxr10mldGroupLimitVrfName
                DisplayString,
            zxr10mldGroupLimitGroupAddr
                DisplayString,
            zxr10mldGroupLimitNum
                Unsigned32
        }

zxr10mldGroupLimitVrfName OBJECT-TYPE
        SYNTAX DisplayString (SIZE (0..32))
        MAX-ACCESS  not-accessible
        STATUS  current
        DESCRIPTION
            "vrf name"
        ::= { zxr10mldGroupLimitEntry 1 }

zxr10mldGroupLimitGroupAddr OBJECT-TYPE
        SYNTAX DisplayString (SIZE (0..16))
        MAX-ACCESS  not-accessible
        STATUS  current
        DESCRIPTION
            "group address"
        ::= { zxr10mldGroupLimitEntry 2 }

zxr10mldGroupLimitNum OBJECT-TYPE
        SYNTAX Unsigned32 (1..64)
        MAX-ACCESS  read-only
        STATUS  current
        DESCRIPTION
            "limit number"
        ::= { zxr10mldGroupLimitEntry 3 }

zxr10mr6ForwordingPolicyTable OBJECT-TYPE
        SYNTAX  SEQUENCE OF Zxr10mr6ForwordingPolicyEntry
        MAX-ACCESS  not-accessible
        STATUS  current
        DESCRIPTION
            "A table to forwording policy"
        ::= { zxr10mr6InstanceMIB 6 }

zxr10mr6ForwordingPolicyEntry OBJECT-TYPE
        SYNTAX Zxr10mr6ForwordingPolicyEntry
        MAX-ACCESS  not-accessible
        STATUS  current
        DESCRIPTION
            "An entry to forwarding policy"
        INDEX  { zxr10mr6ForwordingPolicyVrfName}
        ::= { zxr10mr6ForwordingPolicyTable 1 }

Zxr10mr6ForwordingPolicyEntry ::=
        SEQUENCE {
            zxr10mr6ForwordingPolicyVrfName
                DisplayString,            
            zxr10mr6ForwordingPolicyAcl
                DisplayString,            
            zxr10mr6ForwordingPolicyType
                INTEGER
        }

zxr10mr6ForwordingPolicyVrfName OBJECT-TYPE
        SYNTAX DisplayString (SIZE (0..32))
        MAX-ACCESS  not-accessible
        STATUS  current
        DESCRIPTION
            "vrf name"
        ::= { zxr10mr6ForwordingPolicyEntry 1 }
        
zxr10mr6ForwordingPolicyAcl OBJECT-TYPE
        SYNTAX DisplayString (SIZE (0..31))
        MAX-ACCESS  read-only
        STATUS  current
        DESCRIPTION
            "ACL name"
        ::= { zxr10mr6ForwordingPolicyEntry 2 }
        
zxr10mr6ForwordingPolicyType OBJECT-TYPE
        SYNTAX INTEGER {perpacket(1),peruser(2),perstream(3)}
        MAX-ACCESS  read-only
        STATUS  current
        DESCRIPTION
            "forwording policy type"
        ::= { zxr10mr6ForwordingPolicyEntry 3 }

zxr10mvpn6InstTable OBJECT-TYPE
        SYNTAX  SEQUENCE OF Zxr10mvpn6InstEntry
        MAX-ACCESS  not-accessible
        STATUS  current
        DESCRIPTION
            "A table to MVPN6"
        ::= { zxr10mr6InstanceMIB 7 }

zxr10mvpn6InstEntry OBJECT-TYPE
        SYNTAX Zxr10mvpn6InstEntry
        MAX-ACCESS  not-accessible
        STATUS  current
        DESCRIPTION
            "An entry to MVPN6"
        INDEX  { zxr10mvpn6InstVrfName }
        ::= { zxr10mvpn6InstTable 1 }
            
Zxr10mvpn6InstEntry ::=
        SEQUENCE {
            zxr10mvpn6InstVrfName
                DisplayString,
            zxr10mvpn6InstProviderTunnel
                INTEGER            
        }

zxr10mvpn6InstVrfName OBJECT-TYPE
        SYNTAX DisplayString (SIZE (0..32))
        MAX-ACCESS  not-accessible
        STATUS  current
        DESCRIPTION
            "vrf name"
        ::= { zxr10mvpn6InstEntry 1 }

zxr10mvpn6InstProviderTunnel OBJECT-TYPE
        SYNTAX INTEGER {rsvpte(1),mldpp2mp(2),pimssm(3),pimsm(4),
             pimbidir(5),ingressrpl(6),mldpmp2mp(7),pimmdt(8)}
        MAX-ACCESS  read-only
        STATUS  current
        DESCRIPTION
            "provider tunnel"
        ::= { zxr10mvpn6InstEntry 2 }
        
        
zxr10nexthop6Table OBJECT-TYPE
        SYNTAX  SEQUENCE OF Zxr10nexthop6Entry
        MAX-ACCESS  not-accessible
        STATUS  current
        DESCRIPTION
            "A table to multicast nexthop"
        ::= { zxr10mr6InstanceMIB 8 }

zxr10nexthop6Entry OBJECT-TYPE
        SYNTAX Zxr10nexthop6Entry
        MAX-ACCESS  not-accessible
        STATUS  current
        DESCRIPTION
            "An entry to multicast nexthop"
        INDEX  { zxr10nexthop6VrfName,
        zxr10nexthop6IntfName,
        zxr10nexthop6IpAddr,
        zxr10nexthop6NextHopAddr,
        zxr10nexthop6PrefixLength }
        ::= { zxr10nexthop6Table 1 }

Zxr10nexthop6Entry ::=
        SEQUENCE {
            zxr10nexthop6VrfName
                DisplayString,
            zxr10nexthop6IntfName
                DisplayString,
            zxr10nexthop6IpAddr
                Ipv6Address,
            zxr10nexthop6NextHopAddr
                Ipv6Address,
            zxr10nexthop6PrefixLength
                Unsigned32,
            zxr10nexthop6NextHopSlave
                INTEGER,
            zxr10nexthop6FallbackGlobal
                INTEGER,
            zxr10nexthop6FallbackVrfName
                DisplayString
        }

zxr10nexthop6VrfName OBJECT-TYPE
        SYNTAX DisplayString (SIZE (0..32))
        MAX-ACCESS  not-accessible
        STATUS  current
        DESCRIPTION
            "VRF name"
        ::= { zxr10nexthop6Entry 1 }

zxr10nexthop6IntfName OBJECT-TYPE
        SYNTAX DisplayString (SIZE (0..32))
        MAX-ACCESS  not-accessible
        STATUS  current
        DESCRIPTION
            "interface name"
        ::= { zxr10nexthop6Entry 2 }

zxr10nexthop6IpAddr OBJECT-TYPE
        SYNTAX Ipv6Address
        MAX-ACCESS  not-accessible
        STATUS  current
        DESCRIPTION
            "IPv6 address"
        ::= { zxr10nexthop6Entry 3 }

zxr10nexthop6NextHopAddr OBJECT-TYPE
        SYNTAX Ipv6Address
        MAX-ACCESS  not-accessible
        STATUS  current
        DESCRIPTION
            "nexthop address"
        ::= { zxr10nexthop6Entry 4 }
        
zxr10nexthop6PrefixLength OBJECT-TYPE
        SYNTAX Unsigned32 (1..128)
        MAX-ACCESS  not-accessible
        STATUS  current
        DESCRIPTION
            "IPv6 address prefix length"
        ::= { zxr10nexthop6Entry 5 }

zxr10nexthop6NextHopSlave OBJECT-TYPE
        SYNTAX  INTEGER {false(255),true(1)}
        MAX-ACCESS  read-only
        STATUS  current
        DESCRIPTION
            "nexthop slave"
        ::= { zxr10nexthop6Entry 6 }

zxr10nexthop6FallbackGlobal OBJECT-TYPE
        SYNTAX  INTEGER {false(255),true(1)}
        MAX-ACCESS  read-only
        STATUS  current
        DESCRIPTION
            "the global instance of nexthop fallback"
        ::= { zxr10nexthop6Entry 7 }

zxr10nexthop6FallbackVrfName OBJECT-TYPE
        SYNTAX DisplayString (SIZE (0..32))
        MAX-ACCESS  read-only
        STATUS  current
        DESCRIPTION
            "the VRF name of nexthop fallback"
        ::= { zxr10nexthop6Entry 8 }        

--
--  IPv6 Mroute SMDM Table
--        
zxr10Mr6SmdmTable OBJECT-TYPE
        SYNTAX  SEQUENCE OF Zxr10Mr6SmdmEntry
        MAX-ACCESS  not-accessible
        STATUS  current
        DESCRIPTION
            "A table to IPv6 mroute SMDM hybrid"
        ::= { zxr10mr6InstanceMIB 9 }

zxr10Mr6SmdmEntry OBJECT-TYPE
        SYNTAX Zxr10Mr6SmdmEntry
        MAX-ACCESS  not-accessible
        STATUS  current
        DESCRIPTION
            "An entry to IPv6 mroute SMDM hybrid"
        INDEX  { zxr10Mr6SmdmIntfName }
        ::= { zxr10Mr6SmdmTable 1 }
            
Zxr10Mr6SmdmEntry ::=
        SEQUENCE {
            zxr10Mr6SmdmIntfName
                DisplayString,
            zxr10Mr6SmdmRowStatus
                RowStatus
        }

zxr10Mr6SmdmIntfName OBJECT-TYPE
        SYNTAX DisplayString (SIZE (0..32))
        MAX-ACCESS  not-accessible
        STATUS  current
        DESCRIPTION
            "Interface name"
        ::= { zxr10Mr6SmdmEntry 1 }

zxr10Mr6SmdmRowStatus OBJECT-TYPE
        SYNTAX      RowStatus
        MAX-ACCESS  read-create
        STATUS      current
        DESCRIPTION
            "Row status."
        ::= { zxr10Mr6SmdmEntry 100 }

END
