--  ************************************************
--  $Id: zxr10ping.mib 8 2005-07-28 12:17:08Z zhanglh $
--
--  zxr10ping.mib: ZXR10 Ping MIB file
--
--  JUL. 2005, Zhang lihui
--
--  Copyright(c) 2005 by ZTE Corporaton
--  All rights reservered
--
--  ************************************************

ZXR10-PING-MIB DEFINITIONS ::= BEGIN

IMPORTS
    MODULE-IDENTITY,
    OBJECT-TYPE,
    NOTIFICATION-TYPE,
    Integer32,
    Unsigned32,
    IpAddress
        FROM SNMPv2-SMI
    TruthValue, DisplayString
        FROM SNMPv2-TC
    zxr10L2vpn
        FROM ZXR10-SMI;

zxr10PingMIB MODULE-IDENTITY
    LAST-UPDATED    "201606291510Z"
    ORGANIZATION    "ZTE Corporation."
    CONTACT-INFO
        "       Zhao yanhua
        Tel:    +86-25-52870000
        E-Mail: zhao.yanhua3@zte.com.cn
        "
    DESCRIPTION
        "ZTE PING MIB
        "
    REVISION        "201606291510Z"
    DESCRIPTION
        "modify:    max value of zxr10PingCommonDataLen.
        "
    REVISION        "201305141430Z"
    DESCRIPTION
        "modify:    default value of zxr10PingCommonTrapOncompletion
                    size of zxr10PingCommonPatternString
                    description of some nodes.
         add:       default value for some nodes
                    description of some nodes
        "
    REVISION        "201303191130Z"
    DESCRIPTION
        "modify:    zxr10PingTimeout
         add:       zxr10PingCommonDcn
                    zxr10PingCommonDomainName
                    zxr10PingCommonPktSendMode
                    zxr10PingCommonLimitNumber
                    zxr10PingCommonInterval
                    zxr10PingCommonInterface
                    zxr10PingCommonPatternString
        "
    REVISION        "200901070000Z"
    DESCRIPTION
        "Initial version of this MIB module.
        "
    ::= { zxr10L2vpn 2 }

    zxr10PingTable  OBJECT-TYPE
        SYNTAX  SEQUENCE OF Zxr10PingEntry
        MAX-ACCESS  not-accessible
        STATUS  current
        DESCRIPTION
            "ping information table."
        ::= { zxr10PingMIB 1 }

    zxr10PingEntry  OBJECT-TYPE
        SYNTAX  Zxr10PingEntry
        MAX-ACCESS  not-accessible
        STATUS  current
        DESCRIPTION
            "ping information entry."
        INDEX  { zxr10PingCommonSerial }
        ::= { zxr10PingTable 1 }

    Zxr10PingEntry ::=
        SEQUENCE {
            zxr10PingCommonSerial
                Integer32,
            zxr10PingCommonPingType
                INTEGER,
            zxr10PingCommonDestAddr
                IpAddress,
            zxr10PingCommonVrfName
                DisplayString,
            zxr10PingCommonIfOption
                INTEGER,
            zxr10PingCommonPacketCount
                Integer32,
            zxr10PingCommonTimeOut
                Integer32,
            zxr10PingCommonDataLen
                Integer32,
            zxr10PingCommonIfExtOption
                INTEGER,
            zxr10PingCommonExtSourceAddr
                IpAddress,
            zxr10PingCommonExtTos
                Integer32,
            zxr10PingCommonExtTTL
                Integer32,
            zxr10PingCommonExtFragement
                Integer32,
            zxr10PingCommonExtOpType
                INTEGER,
            zxr10PingCommonExtOpIpAddr1
                IpAddress,
            zxr10PingCommonExtOpIpAddr2
                IpAddress,
            zxr10PingCommonExtOpIpAddr3
                IpAddress,
            zxr10PingCommonExtOpIpAddr4
                IpAddress,
            zxr10PingCommonExtOpIpAddr5
                IpAddress,
            zxr10PingCommonExtOpIpAddr6
                IpAddress,
            zxr10PingCommonExtOpIpAddr7
                IpAddress,
            zxr10PingCommonExtOpIpAddr8
                IpAddress,
            zxr10PingCommonExtOpIpAddr9
                IpAddress,
            zxr10PingCommonExtOpRecordNum
                Integer32,
            zxr10PingCommonExtOpTimestampNum
                Integer32,
            zxr10PingCommonRosStatus
                INTEGER,
            zxr10PingCommonEntryOwner
                DisplayString,
            zxr10PingCommonTrapOncompletion
                TruthValue,
            zxr10PingCommonDcn
                TruthValue,
            zxr10PingCommonDomainName
                DisplayString,
            zxr10PingCommonPktSendMode
                INTEGER,
            zxr10PingCommonLimitNumber
                Integer32,
            zxr10PingCommonInterval
                Integer32,
            zxr10PingCommonInterface
                DisplayString,
            zxr10PingCommonPatternString
                DisplayString
    }

    zxr10PingCommonSerial  OBJECT-TYPE
        SYNTAX  Integer32
        MAX-ACCESS  read-only
        STATUS  current
        DESCRIPTION
            "serial number"
        ::= { zxr10PingEntry 1 }

    zxr10PingCommonPingType  OBJECT-TYPE
        SYNTAX   INTEGER{common(0),vrf(1)}
        MAX-ACCESS  read-write
        STATUS  current
        DESCRIPTION
            "ping type,default:common
              0: uses zxr10PingCommonDestAddr
              1: uses zxr10PingCommonVrfName"
        DEFVAL      { common }
        ::= { zxr10PingEntry 2 }

    zxr10PingCommonDestAddr OBJECT-TYPE
        SYNTAX  IpAddress
        MAX-ACCESS  read-write
        STATUS  current
        DESCRIPTION
            "target IP address "
        ::= { zxr10PingEntry 3 }

    zxr10PingCommonVrfName OBJECT-TYPE
        SYNTAX  DisplayString(SIZE(0..32))
        MAX-ACCESS  read-write
        STATUS  current
        DESCRIPTION
            "vrf name  "
        ::= { zxr10PingEntry 4 }

    zxr10PingCommonIfOption OBJECT-TYPE
        SYNTAX  INTEGER{none(0),option(1)}
        MAX-ACCESS  read-write
        STATUS  current
        DESCRIPTION
            "option,default:none  "
        DEFVAL      { none }
        ::= { zxr10PingEntry 5 }

    zxr10PingCommonPacketCount OBJECT-TYPE
        SYNTAX    Integer32 (1..2147483647)
        MAX-ACCESS  read-write
        STATUS  current
        DESCRIPTION
            "repeat count,default:5    "
        DEFVAL      { 5 }
        ::= { zxr10PingEntry 6 }

    zxr10PingCommonTimeOut OBJECT-TYPE
        SYNTAX      Integer32 (1..60)
        MAX-ACCESS  read-write
        STATUS  current
        DESCRIPTION
            "timeout in seconds,default:2   "
        DEFVAL      { 2 }
        ::= { zxr10PingEntry 7 }

    zxr10PingCommonDataLen OBJECT-TYPE
        SYNTAX   Integer32 (36..65507)
        MAX-ACCESS  read-write
        STATUS  current
        DESCRIPTION
            "datagram size,default:  100"
        DEFVAL      { 100 }
        ::= { zxr10PingEntry 8 }

    zxr10PingCommonIfExtOption OBJECT-TYPE
        SYNTAX   INTEGER{none(0),extcom(1)}
        MAX-ACCESS  read-write
        STATUS  current
        DESCRIPTION
            "extended commands,default:none  "
        DEFVAL      { none }
        ::= { zxr10PingEntry 9 }

    zxr10PingCommonExtSourceAddr OBJECT-TYPE
        SYNTAX   IpAddress
        MAX-ACCESS  read-write
        STATUS  current
        DESCRIPTION
            "source address   "
        ::= { zxr10PingEntry 10 }

    zxr10PingCommonExtTos OBJECT-TYPE
        SYNTAX   Integer32 (0..255)
        MAX-ACCESS  read-write
        STATUS  current
        DESCRIPTION
            "type of service,default:0   "
        DEFVAL      { 0 }
        ::= { zxr10PingEntry 11 }

    zxr10PingCommonExtTTL OBJECT-TYPE
        SYNTAX   Integer32 (1..255)
        MAX-ACCESS  read-write
        STATUS  current
        DESCRIPTION
            "time to live,default:255    "
        DEFVAL      { 255 }
        ::= { zxr10PingEntry 12 }

    zxr10PingCommonExtFragement OBJECT-TYPE
        SYNTAX   Integer32 (0..1)
        MAX-ACCESS  read-write
        STATUS  current
        DESCRIPTION
            "set DONT FRAG(0--may frag,1--don't frag)  "
        DEFVAL      { 0 }
        ::= { zxr10PingEntry 13 }

    zxr10PingCommonExtOpType OBJECT-TYPE
        SYNTAX      INTEGER {
                        none(0),
                        loose(1),
                        record(2),
                        strict(3),
                        timestamp(4)
                    }
        MAX-ACCESS  read-write
        STATUS  current
        DESCRIPTION
            "extended commands  "
        DEFVAL      { none }
        ::= { zxr10PingEntry 14 }

    zxr10PingCommonExtOpIpAddr1 OBJECT-TYPE
        SYNTAX   IpAddress
        MAX-ACCESS  read-write
        STATUS  current
        DESCRIPTION
            " ip address   "
        ::= { zxr10PingEntry 15 }

    zxr10PingCommonExtOpIpAddr2 OBJECT-TYPE
        SYNTAX   IpAddress
        MAX-ACCESS  read-write
        STATUS  current
        DESCRIPTION
            " ip address   "
        ::= { zxr10PingEntry 16 }

    zxr10PingCommonExtOpIpAddr3 OBJECT-TYPE
        SYNTAX   IpAddress
        MAX-ACCESS  read-write
        STATUS  current
        DESCRIPTION
            " ip address   "
        ::= { zxr10PingEntry 17 }

    zxr10PingCommonExtOpIpAddr4 OBJECT-TYPE
        SYNTAX   IpAddress
        MAX-ACCESS  read-write
        STATUS  current
        DESCRIPTION
            " ip address   "
        ::= { zxr10PingEntry 18 }

    zxr10PingCommonExtOpIpAddr5 OBJECT-TYPE
        SYNTAX   IpAddress
        MAX-ACCESS  read-write
        STATUS  current
        DESCRIPTION
            " ip address   "
        ::= { zxr10PingEntry 19 }

    zxr10PingCommonExtOpIpAddr6 OBJECT-TYPE
        SYNTAX   IpAddress
        MAX-ACCESS  read-write
        STATUS  current
        DESCRIPTION
            " ip address   "
        ::= { zxr10PingEntry 20 }

    zxr10PingCommonExtOpIpAddr7 OBJECT-TYPE
        SYNTAX   IpAddress
        MAX-ACCESS  read-write
        STATUS  current
        DESCRIPTION
            " ip address   "
        ::= { zxr10PingEntry 21 }

    zxr10PingCommonExtOpIpAddr8 OBJECT-TYPE
        SYNTAX   IpAddress
        MAX-ACCESS  read-write
        STATUS  current
        DESCRIPTION
            " ip address   "
        ::= { zxr10PingEntry 22 }

    zxr10PingCommonExtOpIpAddr9 OBJECT-TYPE
        SYNTAX   IpAddress
        MAX-ACCESS  read-write
        STATUS  current
        DESCRIPTION
            " ip address   "
        ::= { zxr10PingEntry 23 }

    zxr10PingCommonExtOpRecordNum OBJECT-TYPE
        SYNTAX   Integer32 (1..9)
        MAX-ACCESS  read-write
        STATUS  current
        DESCRIPTION
            "number of hops"
        ::= { zxr10PingEntry 24 }

    zxr10PingCommonExtOpTimestampNum OBJECT-TYPE
        SYNTAX   Integer32 (1..9)
        MAX-ACCESS  read-write
        STATUS  current
        DESCRIPTION
            "number of timestamps"
        ::= { zxr10PingEntry 25 }

    zxr10PingCommonRosStatus OBJECT-TYPE
        SYNTAX      INTEGER {
                        notActive(1),
                        startPing(2),
                        pingProcessing(3),
                        pingCompleted(4)
                    }
        MAX-ACCESS  read-write
        STATUS  current
        DESCRIPTION
            "This object allows to start ping or destroy entries
            in the zxr10PingTable."
        ::= { zxr10PingEntry 26 }

    zxr10PingCommonEntryOwner OBJECT-TYPE
        SYNTAX   DisplayString (SIZE(0..255))
        MAX-ACCESS  read-write
        STATUS  current
        DESCRIPTION
            "entry owner"
        ::= { zxr10PingEntry 27 }

    zxr10PingCommonTrapOncompletion OBJECT-TYPE
        SYNTAX   TruthValue
        MAX-ACCESS  read-write
        STATUS  current
        DESCRIPTION
            "The value of this object determines when and whether to
             generate a notification for this entry"
        DEFVAL       { false }
        ::= { zxr10PingEntry 28 }

    zxr10PingCommonDcn OBJECT-TYPE
        SYNTAX      TruthValue
        MAX-ACCESS  read-write
        STATUS      current
        DESCRIPTION
            "Controls whether the vrf is a DCN or not:
               1: means the vrf name is ?_dcn
               2: uses zxr10PingCommonVrfName"
        DEFVAL      { false }
        ::= { zxr10PingEntry 29 }

    zxr10PingCommonDomainName OBJECT-TYPE
        SYNTAX      DisplayString (SIZE(0..128))
        MAX-ACCESS  read-write
        STATUS      current
        DESCRIPTION
            "Domain name"
        ::= { zxr10PingEntry 30 }

    zxr10PingCommonPktSendMode OBJECT-TYPE
        SYNTAX      INTEGER { limit(1), interval(2) }
        MAX-ACCESS  read-write
        STATUS      current
        DESCRIPTION
            "Specify the mode of sending packets,
              1: limit mode, control the sending packets number per second.
              2: interval mode, control time interval between packets."
        DEFVAL      { limit }
        ::= { zxr10PingEntry 31 }

    zxr10PingCommonLimitNumber OBJECT-TYPE
        SYNTAX      Integer32(0..100)
        MAX-ACCESS  read-write
        STATUS      current
        DESCRIPTION
            "Controls how many packets will be sent per second, 0 means
            absolute mode with no limitation."
        DEFVAL      { 10 }
        ::= { zxr10PingEntry 32 }

    zxr10PingCommonInterval OBJECT-TYPE
        SYNTAX      Integer32(2..10)
        MAX-ACCESS  read-write
        STATUS      current
        DESCRIPTION
            "Controls the time between two sending packets."
        DEFVAL      { 2 }
        ::= { zxr10PingEntry 33 }

    zxr10PingCommonInterface OBJECT-TYPE
        SYNTAX      DisplayString (SIZE(0..32))
        MAX-ACCESS  read-write
        STATUS      current
        DESCRIPTION
            "Controls which interface the packet will be sent out."
        ::= { zxr10PingEntry 34 }

    zxr10PingCommonPatternString OBJECT-TYPE
        SYNTAX      DisplayString (SIZE(0|4))
        MAX-ACCESS  read-write
        STATUS      current
        DESCRIPTION
            "Specify the pattern string."
        ::= { zxr10PingEntry 35 }

--- common ping result

    zxr10PingResultTable  OBJECT-TYPE
        SYNTAX  SEQUENCE OF Zxr10PingResultEntry
        MAX-ACCESS  not-accessible
        STATUS  current
        DESCRIPTION
            "ping result table."
        ::= { zxr10PingMIB 2 }

    zxr10PingResultEntry  OBJECT-TYPE
        SYNTAX  Zxr10PingResultEntry
        MAX-ACCESS  not-accessible
        STATUS  current
        DESCRIPTION
            "ping result entry."
        INDEX  { zxr10PingCommResultSerial }
        ::= { zxr10PingResultTable 1 }

    Zxr10PingResultEntry ::=
        SEQUENCE {
            zxr10PingCommResultSerial
                Integer32,
            zxr10PingCommResultSentPkts
                Unsigned32,
            zxr10PingCommResultRcvPkts
                Unsigned32,
            zxr10PingCommResultRoundTripMinTime
                Integer32,
            zxr10PingCommResultRoundTripMaxTime
                Integer32,
            zxr10PingCommResultRoundTripAvgTime
                Integer32,
            zxr10PingCommExtResultTimeStampInfo
                DisplayString,
            zxr10PingCommExtResultIpAddrInfo
                DisplayString,
            zxr10PingCommResultEntryOwner
                DisplayString,
            zxr10PingCommResultRoundWobbleMinTime
                Integer32,
            zxr10PingCommResultRoundWobbleMaxTime
                Integer32,
            zxr10PingCommResultRoundWobbleAvgTime
                Integer32
    }

     zxr10PingCommResultSerial  OBJECT-TYPE
        SYNTAX  Integer32
        MAX-ACCESS  read-only
        STATUS  current
        DESCRIPTION
            "serial number"
        ::= { zxr10PingResultEntry 1 }

     zxr10PingCommResultSentPkts  OBJECT-TYPE
        SYNTAX  Unsigned32
        MAX-ACCESS  read-only
        STATUS  current
        DESCRIPTION
            "send packet"
        ::= { zxr10PingResultEntry 2 }

     zxr10PingCommResultRcvPkts  OBJECT-TYPE
        SYNTAX  Unsigned32
        MAX-ACCESS  read-only
        STATUS  current
        DESCRIPTION
            "receive packet"
        ::= { zxr10PingResultEntry 3 }

     zxr10PingCommResultRoundTripMinTime  OBJECT-TYPE
        SYNTAX  Integer32
        MAX-ACCESS  read-only
        STATUS  current
        DESCRIPTION
            "min RTT"
        ::= { zxr10PingResultEntry 4 }

     zxr10PingCommResultRoundTripMaxTime  OBJECT-TYPE
        SYNTAX  Integer32
        MAX-ACCESS  read-only
        STATUS  current
        DESCRIPTION
            "max RTT"
        ::= { zxr10PingResultEntry 5 }

     zxr10PingCommResultRoundTripAvgTime  OBJECT-TYPE
        SYNTAX  Integer32
        MAX-ACCESS  read-only
        STATUS  current
        DESCRIPTION
            "average RTT"
        ::= { zxr10PingResultEntry 6 }

     zxr10PingCommExtResultTimeStampInfo  OBJECT-TYPE
        SYNTAX  DisplayString
        MAX-ACCESS  read-only
        STATUS  current
        DESCRIPTION
            "timestamp"
        ::= { zxr10PingResultEntry 7 }

     zxr10PingCommExtResultIpAddrInfo  OBJECT-TYPE
        SYNTAX  DisplayString
        MAX-ACCESS  read-only
        STATUS  current
        DESCRIPTION
            "ip address"
        ::= { zxr10PingResultEntry 8 }

     zxr10PingCommResultEntryOwner  OBJECT-TYPE
        SYNTAX  DisplayString
        MAX-ACCESS  read-only
        STATUS  current
        DESCRIPTION
            "entry owner"
        ::= { zxr10PingResultEntry 9 }

     zxr10PingCommResultRoundWobbleMinTime  OBJECT-TYPE
        SYNTAX  Integer32
        MAX-ACCESS  read-only
        STATUS  current
        DESCRIPTION
            "min wobble time"
        ::= { zxr10PingResultEntry 10 }   
     
     zxr10PingCommResultRoundWobbleMaxTime  OBJECT-TYPE
        SYNTAX  Integer32
        MAX-ACCESS  read-only
        STATUS  current
        DESCRIPTION
            "max wobble time"
        ::= { zxr10PingResultEntry 11 }
        
     zxr10PingCommResultRoundWobbleAvgTime  OBJECT-TYPE
        SYNTAX  Integer32
        MAX-ACCESS  read-only
        STATUS  current
        DESCRIPTION
            "average wobble time"
        ::= { zxr10PingResultEntry 12 }  

 -- *******************************************************************
--   Trap Definitions
-- *******************************************************************

 pingNotifications   OBJECT IDENTIFIER ::= { zxr10PingMIB 3 }

 pingTrapResult NOTIFICATION-TYPE
        OBJECTS {
            zxr10PingCommResultSerial,
                    zxr10PingCommResultSentPkts,
                    zxr10PingCommResultRcvPkts,
                    zxr10PingCommResultRoundTripMinTime,
                    zxr10PingCommResultRoundTripMaxTime,
                    zxr10PingCommResultRoundTripAvgTime
        }
     STATUS       current
     DESCRIPTION
         "The newMaster trap indicates that the sending agent
         has transitioned to 'Master' state."
     ::= { pingNotifications 1 }

  END
