--  ******************************************************
--  $Id: ZXR10-ROUTE-MAP-MIB.mib  
--  
--  ZXR10-ROUTE-MAP-MIB
--  
--  Mar. 2013, Qian Yi 
--  
--  Copyright(c) 2010 by ZTE Corporaton
--  All rights reservered
--  ******************************************************

ZXR10-ROUTE-MAP-MIB DEFINITIONS ::= BEGIN

IMPORTS
    MODULE-IDENTITY, OBJECT-TYPE, NOTIFICATION-TYPE,
    Integer32, Unsigned32, Counter32,enterprises, IpAddress 
        FROM SNMPv2-SMI
    MODULE-COMPLIANCE, OBJECT-GROUP, NOTIFICATION-GROUP
        FROM SNMPv2-CONF
    DisplayString, MacAddress, TEXTUAL-CONVENTION, RowStatus,TruthValue
        FROM SNMPv2-TC 
        Ipv6Address
        FROM IPV6-TC
    zxr10,zxr10RosngMIB
        FROM ZXR10-SMI;

zxr10RMAPMIB MODULE-IDENTITY
    LAST-UPDATED "201812191400Z"
    ORGANIZATION "ZTE Corporation"
    CONTACT-INFO
        "       Hu Jun
        Tel:    +86-25-52870000
        E-Mail: hu.jun11@zte.com.cn "
    DESCRIPTION
        "The MIB module to describe the RMAP protocol."

    REVISION "201812191400Z"
    DESCRIPTION 
        "Add attribute zxr10RMAPSetLocalPreAct"

    REVISION "201812041400Z"
    DESCRIPTION 
        "Add zxr10RMAPMatchIpPeerTable,
         Add zxr10RMAPMatchIpv6PeerTable,
         Add zxr10RMAPSetL2EquVniLabelTable,
         Add zxr10RMAPSetL3EquVniLabelTable,
         Add zxr10RMAPSetSHScopeTable."    

    REVISION "201811271400Z"
    DESCRIPTION 
        "Add zxr10RMAPDescriptionTable"

    REVISION "201811151400Z"
    DESCRIPTION 
        "Add zxr10RMAPSetDistanceTable"

    REVISION "201802091400Z"
    DESCRIPTION 
        "Add attribute zxr10RMAPAspathMatchName,
         Add index zxr10RMAPAspathMatchName,
         Modify the range of zxr10RMAPAspathNo."

    REVISION "201711201400Z"
    DESCRIPTION 
        "Add zxr10RMAPSetCommunityNameTable, 
         Add attribute zxr10RMAPExtCommunityMatchName,
         Add index zxr10RMAPExtCommunityMatchName,
         Modify the range of zxr10RMAPCommunityNo,
         Modify the range of zxr10RMAPCommunityMatchName,
         Modify the range of zxr10RMAPExtCommunityNo."

    REVISION "201707251400Z"
    DESCRIPTION 
        "Add attributes zxr10RMAPCommunityMatchName in table zxr10RMAPMatchCommunityTable."

    REVISION "201707041400Z"
    DESCRIPTION 
        "Modify the description of zxr10RMAPMatchRouteType"
        
    REVISION "201704281400Z"
    DESCRIPTION 
        "Add zxr10RMAPMatchPlyRtIdTable, zxr10RMAPMatchIpv6PlyRtIdTable,
         zxr10RMAPSetPlyRtIdTable, zxr10RMAPSetMonitorGroupIdTable,
         zxr10RMAPLoadShareTable, zxr10RMAPContinueTable, zxr10RMAPTimeRangeTable"

    REVISION "201703201400Z"
    DESCRIPTION 
        "Add zxr10RMAPMatchL3VniLabelTable,zxr10RMAPMatchL2VniLabelTable
        and modify the range of zxr10RMAPMatchRouteType"

    REVISION "201703081400Z"
    DESCRIPTION 
        "Add zxr10RMAPSetL3vniLabelTable"

    REVISION "201612051400Z"
    DESCRIPTION 
        "Modify the range of zxr10RMAPMatchEvpn"

    REVISION "201611171400Z"
    DESCRIPTION 
        "Add zxr10RMAPSetVxlanTunnelSrcTable,zxr10RMAPSetEvpnMacIntfTable 
        and zxr10RMAPSetL2vniLabelTable"

    REVISION "201608051400Z"
    DESCRIPTION 
        "Add zxr10RMAPStrictPolicyTable,zxr10RMAPSetPathListTable 
        and zxr10RMAPSetPathList6Table"

    REVISION "201607221400Z"
    DESCRIPTION 
        "Add zxr10RMAPBlackHoleRouteTable and zxr10RMAPDefaultRouteTable"

    REVISION "201606241000Z"
    DESCRIPTION 
        "Add zxr10RMAPMatchEvpnTable"        
    
   REVISION "201412251400Z"
    DESCRIPTION 
        "Add zxr10RMAPSetAspathPrepOrRep node"
     

    REVISION "201410091400Z"
    DESCRIPTION 
        "Add zxr10RMAPSetNextHopPeerAddrTable and zxr10RMAPSetIpv6NHorPeerAddTable"
    
    REVISION "201409011400Z"
    DESCRIPTION 
        "Discard zxr10RMAPMatchIpv6AddressTable and 
        add zxr10RMAPMatchIpv6AddrPflTable"

    REVISION "201408131400Z"
    DESCRIPTION 
        "Add zxr10RMAPMatchAsLenTable,zxr10RMAPMatchAsUnqLenTable,zxr10RMAPMatchIpSourceAclTable,
        zxr10RMAPMatchIpSourcePflTable,zxr10RMAPMatchLocalPrefTable,zxr10RMAPMatchOriginTable,
        zxr10RMAPSetPathSelTable,zxr10RMAPSetPolicyPrioTable,zxr10RMAPMatchIpAlgMetricTable,
        zxr10RMAPMatchIpv6AlgMetricTable,zxr10RMAPSetTraffIdxTable."

    REVISION "201402101400Z"
    DESCRIPTION 
        "Modify name of zxr10RMAPSetGlobalIp to zxr10RMAPSetGlobalIPAddr.
         Add attributes zxr10RMAPSetGlobalIpConst and zxr10RMAPSetGlobalNextHopConst
         in table zxr10RMAPSetGlobalTable.
         Add attributes zxr10RMAPSetVrfIpConst and zxr10RMAPSetVrfNextHopConst
         in table zxr10RMAPSetVrfTable." 
        
    REVISION "201401221400Z"
    DESCRIPTION 
        "Modify the size of DisplayString"  
        
    REVISION "201311221400Z"
    DESCRIPTION 
        "add:   zxr10RMAPMIB
        Initial version of this MIB module."
    ::= { zxr10RosngMIB 604 }

---------------------------------------------------------------------------
---------------------------------------------------------------------------
-- Groups in the ZXR10-ROUTE-MAP-MIB MIB Module
---------------------------------------------------------------------------
-- Following objects are defined.

zxr10RMAPGlobalObjects  OBJECT IDENTIFIER ::= { zxr10RMAPMIB 1}
zxr10RMAPObjects        OBJECT IDENTIFIER ::= { zxr10RMAPMIB 2}
zxr10RMAPNotifications  OBJECT IDENTIFIER ::= { zxr10RMAPMIB 3}
zxr10RMAPConformance    OBJECT IDENTIFIER ::= { zxr10RMAPMIB 4}

zxr10RMAPRuleObjects    OBJECT IDENTIFIER ::= { zxr10RMAPObjects 1}

--------------------------------------------------------------
--------------------------------------------------------------
-- Textual conventions
--------------------------------------------------------------
--The follow part defined some data types which will be used in this 
--mib file later
--

RmapPermitDeny ::= TEXTUAL-CONVENTION
    STATUS       current
    DESCRIPTION
            "permit = 0,deny = 1."
    SYNTAX       INTEGER{permit(1),deny(2)}
      
RmapPrependReplace ::= TEXTUAL-CONVENTION
    STATUS       current
    DESCRIPTION
            "prepend = 1,replace = 2."
    SYNTAX       INTEGER{prepend(1),replace(2)}
    
RmapSetMetricAct ::= TEXTUAL-CONVENTION
    STATUS       current
    DESCRIPTION
            "plus(+) = 1,minus(-) = 2."
    SYNTAX       INTEGER{plus(1),minus(2)}

RmapSetMetricType ::= TEXTUAL-CONVENTION
    STATUS       current
    DESCRIPTION
            "external  IS-IS external metric
             internal  IS-IS internal metric
             type-1    OSPF external type 1 metric
             type-2    OSPF external type 2 metric"
    SYNTAX       INTEGER{internal(1),external(2),type_1(3),type_2(4)}

RmapSetLevel ::= TEXTUAL-CONVENTION
    STATUS       current
    DESCRIPTION
            " level-1    Import into a level-1 area
              level-1-2  Import into level-1 and level-2
              level-2    Import into level-2 sub-domain"
    SYNTAX       INTEGER{level_1(1),level_2(2),level_1_2(3)}

RmapSetOrigin ::= TEXTUAL-CONVENTION
    STATUS       current
    DESCRIPTION
            " egp(1)         Remote EGP
              igp(0)         Local IGP
              incomplete(2)  Unknown heritage"
    SYNTAX       INTEGER{igp(1),egp(2),incomplete(3)} 
    
RmapMatchRouteType ::= TEXTUAL-CONVENTION
    STATUS       current
    DESCRIPTION
            "local       Locally generated route.Value is 1.
             internal    Internal route (including OSPF intra/inter area).Value is 2.
             level-1     IS-IS level-1 route.Value is 3.
             level-2     IS-IS level-2 route.Value is 4.
             external    External route (OSPF type 1/2).Value is 5.
             type-1      OSPF external type 1 route.Value is 6.
             type-2      OSPF external type 2 route.Value is 7.
             ebgp        External border gateway protocol(EBGP) route.Value is 8.
             ibgp        Internal border gateway protocol(IBGP) route.Value is 9.
             static      Static route.Value is 10.
             bgp-agg     BGP aggregate route.Value is 11."
    SYNTAX       INTEGER{local(1),internal(2),level_1(3),level_2(4),external(5),
                         type_1(6),type_2(7),ebgp(8),ibgp(9),static(10),bgp_agg(11)} 
    
RmapSetComm ::= TEXTUAL-CONVENTION
    STATUS       current
    DESCRIPTION
            "additive             Add to the existing community. Value is 5.
             internet             Internet(Well known community). Value is 4.
             no-advertise         Do not advertise to any peer. Value is 2.
             no-export            Do not export to next AS. Value is 1.
             no-export-subconfed  Do not send outside local AS. Value is 3.
             none                 No community attribute. Value is 6."
    SYNTAX       INTEGER{no_export(1),no_advertise(2),no_export_subconfed(3),
                        internet(4),additive(5),none(6)} 
    
RmapSetRt ::= TEXTUAL-CONVENTION
    STATUS       current
    DESCRIPTION
            "additive  Add to the existing extcommunity.Value is 6.
             remove    Remove the existing extcommunity.Value is 7."
    SYNTAX       INTEGER{additive(6),remove(7)}  
    
RmapSetPrec ::= TEXTUAL-CONVENTION
    STATUS       current
    DESCRIPTION
            "critical        Set critical precedence (6)
             flash           Set flash precedence (4)
             flash-override  Set flash override precedence (5)
             immediate       Set immediate precedence (3)
             internet        Set internetwork control precedence (7)
             network         Set network control precedence (8)
             priority        Set priority precedence (2)
             routine         Set routine precedence (1)"
    SYNTAX       INTEGER{routine(1),priority(2),immediate(3),
                        flash(4),flash_override(5),critical(6),internet(7),network(8)}

RmapSetTos ::= TEXTUAL-CONVENTION
    STATUS       current
    DESCRIPTION
            "max-reliability    Set max reliable TOS (3)
             max-throughput     Set max throughput TOS (4)
             min-delay          Set min delay TOS (5)
             min-monetary-cost  Set min monetary cost TOS (2)
             normal             Set normal TOS (1)"
    SYNTAX       INTEGER{normal(1),min_monetary_cost(2),max_reliability(3),max_throughput(4),min_delay(5)}   
    
RmapSetGlobalIpConst ::= TEXTUAL-CONVENTION
    STATUS       current
    DESCRIPTION
            "The Value is 3."
    SYNTAX       INTEGER{ipconst(3)}  
    
RmapSetGlobalNextHopConst ::= TEXTUAL-CONVENTION
    STATUS       current
    DESCRIPTION
            "The Value is 1."
    SYNTAX       INTEGER{nexthopconst(1)}   
    
RmapSetVrfIpConst ::= TEXTUAL-CONVENTION
    STATUS       current
    DESCRIPTION
            "The Value is 1."
    SYNTAX       INTEGER{vrfipconst(1)} 
    
RmapSetVrfNextHopConst ::= TEXTUAL-CONVENTION
    STATUS       current
    DESCRIPTION
            "The Value is 2."
    SYNTAX       INTEGER{vrfnexthopconst(2)}  

RmapMatchAlg ::= TEXTUAL-CONVENTION
    STATUS       current
    DESCRIPTION
            "eq = 1,ge = 2,le = 3."
    SYNTAX       INTEGER{eq(1),ge(2),le(3)}  
    
RmapSetPath ::= TEXTUAL-CONVENTION
    STATUS       current
    DESCRIPTION
            "all         Path for imitating iBGP full-mesh
             backup      Path for rapid convergence
             best-path   Path for load sharing
             group-best  Path for elimination of routing oscillation"
    SYNTAX       INTEGER{all(1),backup(2),best_path(3),group_best(4)}

RmapSetPathInstall ::= TEXTUAL-CONVENTION
    STATUS       current
    DESCRIPTION
            "The Value is 1."
    SYNTAX       INTEGER{install(1)} 
    
RmapSetPathMulpro ::= TEXTUAL-CONVENTION
    STATUS       current
    DESCRIPTION
            "The Value is 2."
    SYNTAX       INTEGER{multipath_protect(2)}

RmapSetPathAdvertise ::= TEXTUAL-CONVENTION
    STATUS       current
    DESCRIPTION
            "The Value is 3."
    SYNTAX       INTEGER{advertise(3)}

RmapSetLocalPreAct ::= TEXTUAL-CONVENTION
    STATUS       current
    DESCRIPTION
            "plus(+) = 1,minus(-) = 2."
    SYNTAX       INTEGER{plus(1),minus(2)}

--------------------------------------------------------------
--------------------------------------------------------------
--Table Define
-- 

--------------------------------------------------------------
--------------------------------------------------------------
--zxr10RMAPRuleObjects
--------------------------------------------------------------
--1  zxr10RMAPNameTable
--2  zxr10RMAPMatchAspathTable
--3  zxr10RMAPMatchCommunityTable
--4  zxr10RMAPMatchExtCommunityTable
--5  zxr10RMAPMatchInterfaceTable
--6  zxr10RMAPMatchIpAddressAclTable
--7  zxr10RMAPMatchIpAddressPflTable
--8  zxr10RMAPMatchIpMetricTable
--9  zxr10RMAPMatchIpNextHopTable
--10 zxr10RMAPMatchIpTagTable
--11 zxr10RMAPMatchIpv6AddressTable
--12 zxr10RMAPMatchIpv6MetricTable
--13 zxr10RMAPMatchIpv6NextHopTable
--14 zxr10RMAPMatchIpv6TagTable
--15 zxr10RMAPMatchRdTable
--16 zxr10RMAPMatchRouteTypeTable
--17 zxr10RMAPSetAspathTable
--18 zxr10RMAPSetCommunityConstTable
--19 zxr10RMAPSetCommunityAsnnTable
--20 zxr10RMAPSetCommunityUintTable
--21 zxr10RMAPSetDampeningTable
--22 zxr10RMAPSetDscpTable
--23 zxr10RMAPSetRtTable
--24 zxr10RMAPSetSooTable
--25 zxr10RMAPSetGlobalTable
--26 zxr10RMAPSetInterfaceTable
--27 zxr10RMAPSetIpMetricTable
--28 zxr10RMAPSetIpMetricTypeTable
--29 zxr10RMAPSetIpNextHopTable
--30 zxr10RMAPSetIpPathTable
--31 zxr10RMAPSetIpPrecTable
--32 zxr10RMAPSetIpTagTable
--33 zxr10RMAPSetIpTosTable
--34 zxr10RMAPSetIpv6MetricTable
--35 zxr10RMAPSetIpv6MetricTypeTable
--36 zxr10RMAPSetIpv6NextHopTable
--37 zxr10RMAPSetIpv6PathTable
--38 zxr10RMAPSetIpv6PrecTable
--39 zxr10RMAPSetIpv6TagTable
--40 zxr10RMAPSetIpv6TrafficTable
--41 zxr10RMAPSetLevelTable
--42 zxr10RMAPSetLocalPreTable
--43 zxr10RMAPSetMplsTable
--44 zxr10RMAPSetNextHopTable
--45 zxr10RMAPSetOriginTable
--46 zxr10RMAPSetQosIdTable
--47 zxr10RMAPSetVrfTable 
--48 zxr10RMAPMatchAsLenTable 
--49 zxr10RMAPMatchAsUnqLenTable  
--50 zxr10RMAPMatchIpSourceAclTable 
--51 zxr10RMAPMatchIpSourcePflTable 
--52 zxr10RMAPMatchLocalPrefTable 
--53 zxr10RMAPMatchOriginTable
--54 zxr10RMAPSetPathSelTable
--55 zxr10RMAPSetPolicyPrioTable 
--56 zxr10RMAPMatchIpAlgMetricTable  
--57 zxr10RMAPMatchIpv6AlgMetricTable
--58 zxr10RMAPSetTraffIdxTable
--59 zxr10RMAPSetTraffIdxTable
--60 zxr10RMAPSetNextHopPeerAddrTable
--61 zxr10RMAPSetIpv6NHorPeerAddTable
--62 zxr10RMAPMatchEvpnTable
--63 zxr10RMAPBlackHoleRouteTable
--64 zxr10RMAPDefaultRouteTable
--65 zxr10RMAPStrictPolicyTable
--66 zxr10RMAPSetPathListTable
--67 zxr10RMAPSetPathList6Table
--68 zxr10RMAPSetVxlanTunnelSrcTable
--69 zxr10RMAPSetEvpnMacIntfTable
--70 zxr10RMAPSetL2vniLabelTable
--71 zxr10RMAPSetL3vniLabelTable
--72 zxr10RMAPMatchL3VniLabelTable
--73 zxr10RMAPMatchL2VniLabelTable
--74 zxr10RMAPMatchPlyRtIdTable
--75 zxr10RMAPMatchIpv6PlyRtIdTable
--76 zxr10RMAPSetPlyRtIdTable
--77 zxr10RMAPSetMonitorGroupIdTable
--78 zxr10RMAPLoadShareTable
--79 zxr10RMAPContinueTable
--80 zxr10RMAPTimeRangeTable
--81 zxr10RMAPSetCommunityNameTable
--82 zxr10RMAPSetDistanceTable
--83 zxr10RMAPDescriptionTable
--84 zxr10RMAPMatchIpPeerTable
--85 zxr10RMAPMatchIpv6PeerTable
--86 zxr10RMAPSetL2EquVniLabelTable
--87 zxr10RMAPSetL3EquVniLabelTable
--88 zxr10RMAPSetSHScopeTable
--------------------------------------------------------------
--------------------------------------------------------------
--zxr10RMAPNameTable
--------------------------------------------------------------
zxr10RMAPNameTable  OBJECT-TYPE
    SYNTAX  SEQUENCE OF Zxr10RMAPNameEntry
    MAX-ACCESS  not-accessible
    STATUS  current
    DESCRIPTION
        "Route-map Name Table"
    ::= { zxr10RMAPRuleObjects 1 }

zxr10RMAPNameEntry  OBJECT-TYPE
    SYNTAX  Zxr10RMAPNameEntry
    MAX-ACCESS  not-accessible
    STATUS  current
    DESCRIPTION
        "Route-map Name"
    INDEX  { zxr10RMAPName,  zxr10RMAPSequence}
    ::= { zxr10RMAPNameTable 1 }

Zxr10RMAPNameEntry ::=SEQUENCE {
        zxr10RMAPName                  DisplayString,
        zxr10RMAPSequence              Integer32,
        zxr10RMAPAction                RmapPermitDeny,
        zxr10RMAPRowStatus             RowStatus
    }

zxr10RMAPName  OBJECT-TYPE
    SYNTAX   DisplayString(SIZE(1..31))
    MAX-ACCESS  not-accessible
    STATUS  current
    DESCRIPTION
        "Name of Route-map (1-31 characters)"
    ::= { zxr10RMAPNameEntry 1 } 

zxr10RMAPSequence  OBJECT-TYPE
    SYNTAX   Integer32
    MAX-ACCESS  not-accessible
    STATUS  current
    DESCRIPTION
        "The sequence of a route-map.
         The range of config is 0 to 65535.
         Each name of route-map has 100 sequences at most."
    ::= { zxr10RMAPNameEntry 2 } 

zxr10RMAPAction  OBJECT-TYPE
    SYNTAX   RmapPermitDeny
    MAX-ACCESS  read-create
    STATUS  current
    DESCRIPTION
        "permit:Match success
         deny  :Match failed"
    ::= { zxr10RMAPNameEntry 3 } 

zxr10RMAPRowStatus  OBJECT-TYPE
    SYNTAX   RowStatus
    MAX-ACCESS  read-create
    STATUS  current
    DESCRIPTION
        "RowStatus"
    ::= { zxr10RMAPNameEntry 100 } 

--------------------------------------------------------------
--------------------------------------------------------------
--zxr10RMAPMatchAspathTable
--------------------------------------------------------------
zxr10RMAPMatchAspathTable  OBJECT-TYPE
    SYNTAX  SEQUENCE OF Zxr10RMAPMatchAspathEntry
    MAX-ACCESS  not-accessible
    STATUS  current
    DESCRIPTION
        "Route-map Match Aspath Table"
    ::= { zxr10RMAPRuleObjects 2 }

zxr10RMAPMatchAspathEntry  OBJECT-TYPE
    SYNTAX  Zxr10RMAPMatchAspathEntry
    MAX-ACCESS  not-accessible
    STATUS  current
    DESCRIPTION          
       "Match BGP as-path list"
    INDEX  { zxr10RMAPName,  zxr10RMAPSequence, zxr10RMAPAspathNo, zxr10RMAPAspathMatchName}
    ::= { zxr10RMAPMatchAspathTable 1 }
    
Zxr10RMAPMatchAspathEntry ::=SEQUENCE {
        zxr10RMAPAspathName            DisplayString,
        zxr10RMAPAspathSequence        Integer32,
        zxr10RMAPAspathNo              Integer32,
        zxr10RMAPAspathMatchName       DisplayString,
        zxr10RMAPAspathRowStatus       RowStatus
    }

zxr10RMAPAspathName  OBJECT-TYPE
    SYNTAX   DisplayString(SIZE(1..31))
    MAX-ACCESS  not-accessible
    STATUS  current
    DESCRIPTION
        "Name of Route-map (1-31 characters)"
    ::= { zxr10RMAPMatchAspathEntry 1 } 
        
zxr10RMAPAspathSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchAspathEntry 2 }    

zxr10RMAPAspathNo  OBJECT-TYPE
    SYNTAX   Integer32
    MAX-ACCESS  not-accessible
    STATUS  current
    DESCRIPTION
        "Aspath List Number.
         The range of config is 0 to 199.
         Each sequence has 10 match aspath items at most"
    ::= { zxr10RMAPMatchAspathEntry 3 }  

zxr10RMAPAspathMatchName  OBJECT-TYPE
    SYNTAX   DisplayString(SIZE(0..31))
    MAX-ACCESS  not-accessible
    STATUS  current
    DESCRIPTION
    "Name of Aspath (0-31 characters)"
    ::= { zxr10RMAPMatchAspathEntry 4 }

zxr10RMAPAspathRowStatus  OBJECT-TYPE
    SYNTAX   RowStatus
    MAX-ACCESS  read-create
    STATUS  current
    DESCRIPTION
        "RowStatus"
    ::= { zxr10RMAPMatchAspathEntry 100 } 
--------------------------------------------------------------
--------------------------------------------------------------
--zxr10RMAPMatchCommunityTable
--------------------------------------------------------------
zxr10RMAPMatchCommunityTable  OBJECT-TYPE
    SYNTAX  SEQUENCE OF Zxr10RMAPMatchCommunityEntry
    MAX-ACCESS  not-accessible
    STATUS  current
    DESCRIPTION
        "Route-map Match Community Table"
    ::= { zxr10RMAPRuleObjects 3 }

zxr10RMAPMatchCommunityEntry  OBJECT-TYPE
    SYNTAX  Zxr10RMAPMatchCommunityEntry
    MAX-ACCESS  not-accessible
    STATUS  current
    DESCRIPTION          
       "Match BGP community list"
    INDEX  { zxr10RMAPName,  zxr10RMAPSequence, zxr10RMAPCommunityNo, zxr10RMAPCommunityMatchName}
    ::= { zxr10RMAPMatchCommunityTable 1 }
    
Zxr10RMAPMatchCommunityEntry ::=SEQUENCE {
        zxr10RMAPCommunityName         DisplayString,
        zxr10RMAPCommunitySequence     Integer32,
        zxr10RMAPCommunityNo           Integer32,
        zxr10RMAPCommunityMatchName    DisplayString,
        zxr10RMAPCommunityRowStatus    RowStatus
    }

zxr10RMAPCommunityName  OBJECT-TYPE
    SYNTAX   DisplayString(SIZE(1..31))
    MAX-ACCESS  not-accessible
    STATUS  current
    DESCRIPTION
        "Name of Route-map (1-31 characters)"
    ::= { zxr10RMAPMatchCommunityEntry 1 } 
        
zxr10RMAPCommunitySequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchCommunityEntry 2 }    

zxr10RMAPCommunityNo  OBJECT-TYPE
    SYNTAX   Integer32
    MAX-ACCESS  not-accessible
    STATUS  current
    DESCRIPTION
        "Community list number.
         The range of config is 0 to 499.
         Each sequence has 10 match community items at most."
    ::= { zxr10RMAPMatchCommunityEntry 3 } 

zxr10RMAPCommunityMatchName  OBJECT-TYPE
    SYNTAX   DisplayString(SIZE(0..31))
    MAX-ACCESS  not-accessible
    STATUS  current
    DESCRIPTION
    "Name of Community (0-31 characters)"
    ::= { zxr10RMAPMatchCommunityEntry 4 }

zxr10RMAPCommunityRowStatus  OBJECT-TYPE
    SYNTAX   RowStatus
    MAX-ACCESS  read-create
    STATUS  current
    DESCRIPTION
        "RowStatus"
    ::= { zxr10RMAPMatchCommunityEntry 100 } 
--------------------------------------------------------------
--------------------------------------------------------------
--zxr10RMAPMatchExtCommunityTable
--------------------------------------------------------------
zxr10RMAPMatchExtCommunityTable  OBJECT-TYPE
    SYNTAX  SEQUENCE OF Zxr10RMAPMatchExtCommunityEntry
    MAX-ACCESS  not-accessible
    STATUS  current
    DESCRIPTION
        "Route-map Match ExtCommunity Table"
    ::= { zxr10RMAPRuleObjects 4 }

zxr10RMAPMatchExtCommunityEntry  OBJECT-TYPE
    SYNTAX  Zxr10RMAPMatchExtCommunityEntry
    MAX-ACCESS  not-accessible
    STATUS  current
    DESCRIPTION          
       "Match BGP extcommunity list"
    INDEX  { zxr10RMAPName,  
             zxr10RMAPSequence, 
             zxr10RMAPExtCommunityNo, 
             zxr10RMAPExtCommunityMatchName}
    ::= { zxr10RMAPMatchExtCommunityTable 1 }
    
Zxr10RMAPMatchExtCommunityEntry ::=SEQUENCE {
        zxr10RMAPExtCommunityName      DisplayString,
        zxr10RMAPExtCommunitySequence  Integer32,
        zxr10RMAPExtCommunityNo        Integer32,
        zxr10RMAPExtCommunityMatchName DisplayString,
        zxr10RMAPExtCommunityRowStatus RowStatus
    }

zxr10RMAPExtCommunityName  OBJECT-TYPE
    SYNTAX   DisplayString(SIZE(1..31))
    MAX-ACCESS  not-accessible
    STATUS  current
    DESCRIPTION
        "Name of Route-map (1-31 characters)"
    ::= { zxr10RMAPMatchExtCommunityEntry 1 } 
        
zxr10RMAPExtCommunitySequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchExtCommunityEntry 2 }    

zxr10RMAPExtCommunityNo  OBJECT-TYPE
    SYNTAX   Integer32
    MAX-ACCESS  not-accessible
    STATUS  current
    DESCRIPTION
        "ExtCommunity list number.
         The range of config is 0 to 500.
         Each sequence has 10 match extcommunity items at most."
    ::= { zxr10RMAPMatchExtCommunityEntry 3 } 

zxr10RMAPExtCommunityMatchName  OBJECT-TYPE
    SYNTAX   DisplayString(SIZE(0..31))
    MAX-ACCESS  not-accessible
    STATUS  current
    DESCRIPTION
    "Name of ExtCommunity (0-31 characters)"
    ::= { zxr10RMAPMatchExtCommunityEntry 4 }

zxr10RMAPExtCommunityRowStatus  OBJECT-TYPE
    SYNTAX   RowStatus
    MAX-ACCESS  read-create
    STATUS  current
    DESCRIPTION
        "RowStatus"
    ::= { zxr10RMAPMatchExtCommunityEntry 100 }
--------------------------------------------------------------
--------------------------------------------------------------
--zxr10RMAPMatchInterfaceTable
--------------------------------------------------------------
zxr10RMAPMatchInterfaceTable  OBJECT-TYPE
    SYNTAX  SEQUENCE OF Zxr10RMAPMatchInterfaceEntry
    MAX-ACCESS  not-accessible
    STATUS  current
    DESCRIPTION
        "Route-map Match Interface Table"
    ::= { zxr10RMAPRuleObjects 5 }

zxr10RMAPMatchInterfaceEntry  OBJECT-TYPE
    SYNTAX  Zxr10RMAPMatchInterfaceEntry
    MAX-ACCESS  not-accessible
    STATUS  current
    DESCRIPTION          
       "Match first hop interface of route"
    INDEX  { zxr10RMAPName,  zxr10RMAPSequence, zxr10RMAPInterface}
    ::= { zxr10RMAPMatchInterfaceTable 1 }
    
Zxr10RMAPMatchInterfaceEntry ::=SEQUENCE {
        zxr10RMAPInterfaceName         DisplayString,
        zxr10RMAPInterfaceSequence     Integer32,
        zxr10RMAPInterface             DisplayString,
        zxr10RMAPInterfaceRowStatus    RowStatus
    }

zxr10RMAPInterfaceName  OBJECT-TYPE
    SYNTAX   DisplayString(SIZE(1..31))
    MAX-ACCESS  not-accessible
    STATUS  current
    DESCRIPTION
        "Name of Route-map (1-31 characters)"
    ::= { zxr10RMAPMatchInterfaceEntry 1 } 
        
zxr10RMAPInterfaceSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchInterfaceEntry 2 }    

zxr10RMAPInterface  OBJECT-TYPE
    SYNTAX   DisplayString(SIZE(1..31))
    MAX-ACCESS  not-accessible
    STATUS  current
    DESCRIPTION
        "Interface Name(1-31 characters).
         Each sequence has 10 match interface items at most.
         This match item supports these types of interface:
         [PORT_CLASS_FEI,          PORT_CLASS_GEI_END]
         [PORT_CLASS_OC,               PORT_TYPE_OC48]
         [PORT_TYPE_OC192,          PORT_CLASS_E1_END]
         [PORT_CLASS_E1_C_CH,          PORT_TYPE_ULEI]
         [PORT_CLASS_GVI,          PORT_CLASS_GVI_END]
         [PORT_CLASS_QX,            PORT_CLASS_QX_END]
         [PORT_TYPE_MANAGE,          PORT_TYPE_MANAGE]
         [PORT_CLASS_DSL,          PORT_CLASS_DSL_END]
         [PORT_CLASS_SPECIAL,     PORT_TYPE_SUPERQINQ]
         [PORT_TYPE_TE_TUNNEL, PORT_TYPE_IPSEC_TUNNEL]
         [PORT_TYPE_CIP,           PORT_TYPE_QX_LOGIC]."
    ::= { zxr10RMAPMatchInterfaceEntry 3 }  

zxr10RMAPInterfaceRowStatus  OBJECT-TYPE
    SYNTAX   RowStatus
    MAX-ACCESS  read-create
    STATUS  current
    DESCRIPTION
        "RowStatus"
    ::= { zxr10RMAPMatchInterfaceEntry 100 }
--------------------------------------------------------------
--------------------------------------------------------------
--zxr10RMAPMatchIpAddressAclTable
--------------------------------------------------------------
zxr10RMAPMatchIpAddressAclTable  OBJECT-TYPE
    SYNTAX  SEQUENCE OF Zxr10RMAPMatchIpAddressAclEntry
    MAX-ACCESS  not-accessible
    STATUS  current
    DESCRIPTION
        "Route-map Match IpAddress Table(match ip address by acl)."
    ::= { zxr10RMAPRuleObjects 6 }

zxr10RMAPMatchIpAddressAclEntry  OBJECT-TYPE
    SYNTAX  Zxr10RMAPMatchIpAddressAclEntry
    MAX-ACCESS  not-accessible
    STATUS  current
    DESCRIPTION          
       "Match address of route or match packet.
        This match item sets the route-map name with ipv4 type.
        It conflicts with other match or set items 
        which set the route-map name with ipv6 type.
        Otherwise, It conflicts with the item that match ip address by pfl.
        If zxr10RMAPIsConfigAcl is true,it expresses that this config is match ip address by acl."
    INDEX  { zxr10RMAPName,  zxr10RMAPSequence, zxr10RMAPAclName, zxr10RMAPIsConfigAcl}
    ::= { zxr10RMAPMatchIpAddressAclTable 1 }
    
Zxr10RMAPMatchIpAddressAclEntry ::=SEQUENCE {
        zxr10RMAPMatchAclName               DisplayString,
        zxr10RMAPMatchAclSequence           Integer32,
        zxr10RMAPAclName                    DisplayString,
        zxr10RMAPIsConfigAcl                TruthValue,
        zxr10RMAPMatchAclRowStatus          RowStatus
    }

zxr10RMAPMatchAclName  OBJECT-TYPE
    SYNTAX   DisplayString(SIZE(1..31))
    MAX-ACCESS  not-accessible
    STATUS  current
    DESCRIPTION
        "Name of Route-map (1-31 characters)"
    ::= { zxr10RMAPMatchIpAddressAclEntry 1 } 
        
zxr10RMAPMatchAclSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpAddressAclEntry 2 }  
    
 zxr10RMAPAclName  OBJECT-TYPE
    SYNTAX   DisplayString(SIZE(1..31))
    MAX-ACCESS  not-accessible
    STATUS  current
    DESCRIPTION
        "Name of an access-list(1-31 characters).
         Each sequence has 10 match ip address items at most."
    ::= { zxr10RMAPMatchIpAddressAclEntry 3 }
  

zxr10RMAPIsConfigAcl  OBJECT-TYPE
    SYNTAX   TruthValue
    MAX-ACCESS  not-accessible
    STATUS  current
    DESCRIPTION
        "It expresses that this config is match ip address by acl."
    ::= { zxr10RMAPMatchIpAddressAclEntry 4 }

zxr10RMAPMatchAclRowStatus  OBJECT-TYPE
    SYNTAX   RowStatus
    MAX-ACCESS  read-create
    STATUS  current
    DESCRIPTION
        "RowStatus"
    ::= { zxr10RMAPMatchIpAddressAclEntry 100 }

--------------------------------------------------------------
--------------------------------------------------------------
--zxr10RMAPMatchIpAddressPflTable
--------------------------------------------------------------
zxr10RMAPMatchIpAddressPflTable  OBJECT-TYPE
    SYNTAX  SEQUENCE OF Zxr10RMAPMatchIpAddressPflEntry
    MAX-ACCESS  not-accessible
    STATUS  current
    DESCRIPTION
        "Route-map Match IpAddress Table(match ip address by pfl)"
    ::= { zxr10RMAPRuleObjects 7 }

zxr10RMAPMatchIpAddressPflEntry  OBJECT-TYPE
    SYNTAX  Zxr10RMAPMatchIpAddressPflEntry
    MAX-ACCESS  not-accessible
    STATUS  current
    DESCRIPTION          
       "Match address of route or match packet.
        This match item sets the route-map name with ipv4 type.
        It conflicts with other match or set items 
        which set the route-map name with ipv6 type.
        Otherwise, It conflicts with the item that match ip address by acl."
    INDEX  { zxr10RMAPName,  zxr10RMAPSequence, zxr10RMAPPflName, zxr10RMAPIsConfigPfl}
    ::= { zxr10RMAPMatchIpAddressPflTable 1 }
    
Zxr10RMAPMatchIpAddressPflEntry ::=SEQUENCE {
        zxr10RMAPMatchPflName               DisplayString,
        zxr10RMAPMatchPflSequence           Integer32, 
        zxr10RMAPPflName                    DisplayString, 
        zxr10RMAPIsConfigPfl                TruthValue,
        zxr10RMAPMatchPflRowStatus          RowStatus
    }

zxr10RMAPMatchPflName  OBJECT-TYPE
    SYNTAX   DisplayString(SIZE(1..31))
    MAX-ACCESS  not-accessible
    STATUS  current
    DESCRIPTION
        "Name of Route-map (1-31 characters)"
    ::= { zxr10RMAPMatchIpAddressPflEntry 1 } 
        
zxr10RMAPMatchPflSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpAddressPflEntry 2 }    

zxr10RMAPPflName  OBJECT-TYPE
    SYNTAX   DisplayString(SIZE(1..31))
    MAX-ACCESS  not-accessible
    STATUS  current
    DESCRIPTION
        "Name of a prefix list (1-31 characters).
         Each sequence has 10 match ip address items at most."
    ::= { zxr10RMAPMatchIpAddressPflEntry 3 }  
    
zxr10RMAPIsConfigPfl  OBJECT-TYPE
    SYNTAX   TruthValue
    MAX-ACCESS  not-accessible
    STATUS  current
    DESCRIPTION
        "It expresses that this config is match ip address by pfl."
    ::= { zxr10RMAPMatchIpAddressPflEntry 4 }

zxr10RMAPMatchPflRowStatus  OBJECT-TYPE
    SYNTAX   RowStatus
    MAX-ACCESS  read-create
    STATUS  current
    DESCRIPTION
        "RowStatus"
    ::= { zxr10RMAPMatchIpAddressPflEntry 100 }


--------------------------------------------------------------
--------------------------------------------------------------
--zxr10RMAPMatchIpMetricTable
--------------------------------------------------------------
zxr10RMAPMatchIpMetricTable  OBJECT-TYPE
    SYNTAX  SEQUENCE OF Zxr10RMAPMatchIpMetricEntry
    MAX-ACCESS  not-accessible
    STATUS  current
    DESCRIPTION
        "Route-map Match IpMetric Table"
    ::= { zxr10RMAPRuleObjects 8 }

zxr10RMAPMatchIpMetricEntry  OBJECT-TYPE
    SYNTAX  Zxr10RMAPMatchIpMetricEntry
    MAX-ACCESS  not-accessible
    STATUS  current
    DESCRIPTION          
       "Match metric of route.
        This match item sets the route-map name with ipv4 type.
        It conflicts with other match or set items 
        which set the route-map name with ipv6 type."
    INDEX  { zxr10RMAPName,  zxr10RMAPSequence, zxr10RMAPIpMetric}
    ::= { zxr10RMAPMatchIpMetricTable 1 }
    
Zxr10RMAPMatchIpMetricEntry ::=SEQUENCE {
        zxr10RMAPIpMetricName          DisplayString,
        zxr10RMAPIpMetricSequence      Integer32, 
        zxr10RMAPIpMetric              Unsigned32,
        zxr10RMAPIpMetricRowStatus     RowStatus
    }

zxr10RMAPIpMetricName  OBJECT-TYPE
    SYNTAX   DisplayString(SIZE(1..31))
    MAX-ACCESS  not-accessible
    STATUS  current
    DESCRIPTION
        "Name of Route-map (1-31 characters)"
    ::= { zxr10RMAPMatchIpMetricEntry 1 } 
        
zxr10RMAPIpMetricSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpMetricEntry 2 }    

zxr10RMAPIpMetric  OBJECT-TYPE
    SYNTAX   Unsigned32
    MAX-ACCESS  not-accessible
    STATUS  current
    DESCRIPTION
        " Metric Value.
          The range of config is 0 to 4294967295.
          Each sequence has 10 match ip metric items at most."
    ::= { zxr10RMAPMatchIpMetricEntry 3 }

zxr10RMAPIpMetricRowStatus  OBJECT-TYPE
    SYNTAX   RowStatus
    MAX-ACCESS  read-create
    STATUS  current
    DESCRIPTION
        "RowStatus"
    ::= { zxr10RMAPMatchIpMetricEntry 100 }

--------------------------------------------------------------
--------------------------------------------------------------
--zxr10RMAPMatchIpNextHopTable
--------------------------------------------------------------
zxr10RMAPMatchIpNextHopTable  OBJECT-TYPE
    SYNTAX  SEQUENCE OF Zxr10RMAPMatchIpNextHopEntry
    MAX-ACCESS  not-accessible
    STATUS  current
    DESCRIPTION
        "Route-map Match IpNextHop Table"
    ::= { zxr10RMAPRuleObjects 9 }

zxr10RMAPMatchIpNextHopEntry  OBJECT-TYPE
    SYNTAX  Zxr10RMAPMatchIpNextHopEntry
    MAX-ACCESS  not-accessible
    STATUS  current
    DESCRIPTION          
       "Match next-hop address of route.
        This match item sets the route-map name with ipv4 type.
        It conflicts with other match or set items 
        which set the route-map name with ipv6 type."
    INDEX  { zxr10RMAPName,  zxr10RMAPSequence, zxr10RMAPIpNextHop}
    ::= { zxr10RMAPMatchIpNextHopTable 1 }
    
Zxr10RMAPMatchIpNextHopEntry ::=SEQUENCE {
        zxr10RMAPIpNextHopName         DisplayString,
        zxr10RMAPIpNextHopSequence     Integer32,
        zxr10RMAPIpNextHop             DisplayString,
        zxr10RMAPIpNextHopRowStatus    RowStatus
    }

zxr10RMAPIpNextHopName  OBJECT-TYPE
    SYNTAX   DisplayString(SIZE(1..31))
    MAX-ACCESS  not-accessible
    STATUS  current
    DESCRIPTION
        "Name of Route-map (1-31 characters)"
    ::= { zxr10RMAPMatchIpNextHopEntry 1 } 
        
zxr10RMAPIpNextHopSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpNextHopEntry 2 }    

zxr10RMAPIpNextHop  OBJECT-TYPE
    SYNTAX   DisplayString(SIZE(1..31))
    MAX-ACCESS  not-accessible
    STATUS  current
    DESCRIPTION
        "Name of an access-list(1-31 characters).
         Each sequence has 10 match ip next-hop items at most."
    ::= { zxr10RMAPMatchIpNextHopEntry 3 }

zxr10RMAPIpNextHopRowStatus  OBJECT-TYPE
    SYNTAX   RowStatus
    MAX-ACCESS  read-create
    STATUS  current
    DESCRIPTION
        "RowStatus"
    ::= { zxr10RMAPMatchIpNextHopEntry 100 }

--------------------------------------------------------------
--------------------------------------------------------------
--zxr10RMAPMatchIpTagTable
--------------------------------------------------------------
zxr10RMAPMatchIpTagTable  OBJECT-TYPE
    SYNTAX  SEQUENCE OF Zxr10RMAPMatchIpTagEntry
    MAX-ACCESS  not-accessible
    STATUS  current
    DESCRIPTION
        "Route-map Match IpTag Table"
    ::= { zxr10RMAPRuleObjects 10 }

zxr10RMAPMatchIpTagEntry  OBJECT-TYPE
    SYNTAX  Zxr10RMAPMatchIpTagEntry
    MAX-ACCESS  not-accessible
    STATUS  current
    DESCRIPTION          
       "Match tag of route.
        This match item sets the route-map name with ipv4 type.
        It conflicts with other match or set items 
        which set the route-map name with ipv6 type."
    INDEX  { zxr10RMAPName,  zxr10RMAPSequence, zxr10RMAPIpTag}
    ::= { zxr10RMAPMatchIpTagTable 1 }
    
Zxr10RMAPMatchIpTagEntry ::=SEQUENCE {
        zxr10RMAPIpTagName             DisplayString,
        zxr10RMAPIpTagSequence         Integer32, 
        zxr10RMAPIpTag                 Unsigned32,
        zxr10RMAPIpTagRowStatus        RowStatus
    }

zxr10RMAPIpTagName  OBJECT-TYPE
    SYNTAX   DisplayString(SIZE(1..31))
    MAX-ACCESS  not-accessible
    STATUS  current
    DESCRIPTION
        "Name of Route-map (1-31 characters)"
    ::= { zxr10RMAPMatchIpTagEntry 1 } 
        
zxr10RMAPIpTagSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpTagEntry 2 }    

zxr10RMAPIpTag  OBJECT-TYPE
    SYNTAX   Unsigned32
    MAX-ACCESS  not-accessible
    STATUS  current
    DESCRIPTION
        "Tag Value.
         The range of config is 0 to 4294967295.
         Each sequence has 10 match ip tag items at most."
    ::= { zxr10RMAPMatchIpTagEntry 3 }

zxr10RMAPIpTagRowStatus  OBJECT-TYPE
    SYNTAX   RowStatus
    MAX-ACCESS  read-create
    STATUS  current
    DESCRIPTION
        "RowStatus"
    ::= { zxr10RMAPMatchIpTagEntry 100 }

--------------------------------------------------------------
--------------------------------------------------------------
--zxr10RMAPMatchIpv6AddressTable
--------------------------------------------------------------
zxr10RMAPMatchIpv6AddressTable  OBJECT-TYPE
    SYNTAX  SEQUENCE OF Zxr10RMAPMatchIpv6AddressEntry
    MAX-ACCESS  not-accessible
    STATUS  obsolete
    DESCRIPTION
        "Route-map Match Ipv6Address Table"
    ::= { zxr10RMAPRuleObjects 11 }

zxr10RMAPMatchIpv6AddressEntry  OBJECT-TYPE
    SYNTAX  Zxr10RMAPMatchIpv6AddressEntry
    MAX-ACCESS  not-accessible
    STATUS  obsolete
    DESCRIPTION          
       "Match address of route or match packet.
        This match item sets the route-map name with ipv6 type.
        It conflicts with other match or set items 
        which set the route-map name with ipv4 type."
    INDEX  { zxr10RMAPName,  zxr10RMAPSequence, zxr10RMAPIpv6Address}
    ::= { zxr10RMAPMatchIpv6AddressTable 1 }
    
Zxr10RMAPMatchIpv6AddressEntry ::=SEQUENCE {
        zxr10RMAPIpv6AddressName       DisplayString,
        zxr10RMAPIpv6AddressSequence   Integer32,
        zxr10RMAPIpv6Address           DisplayString,        
        zxr10RMAPIpv6AddressRowStatus  RowStatus
    }

zxr10RMAPIpv6AddressName  OBJECT-TYPE
    SYNTAX   DisplayString(SIZE(1..31))
    MAX-ACCESS  not-accessible
    STATUS  obsolete
    DESCRIPTION
        "Name of Route-map (1-31 characters)"
    ::= { zxr10RMAPMatchIpv6AddressEntry 1 } 
        
zxr10RMAPIpv6AddressSequence  OBJECT-TYPE
    SYNTAX   Integer32
    MAX-ACCESS  not-accessible
    STATUS  obsolete
    DESCRIPTION
        "The sequence of a route-map.
         The range of config is 0 to 65535.
         Each name of route-map has 100 sequences at most."
    ::= { zxr10RMAPMatchIpv6AddressEntry 2 }    

zxr10RMAPIpv6Address  OBJECT-TYPE
    SYNTAX   DisplayString(SIZE(1..31))
    MAX-ACCESS  not-accessible
    STATUS  obsolete
    DESCRIPTION
        "Name of an access-list(1-31 characters).
         Each sequence has 10 match ipv6 address items at most."
    ::= { zxr10RMAPMatchIpv6AddressEntry 3 }

zxr10RMAPIpv6AddressRowStatus  OBJECT-TYPE
    SYNTAX   RowStatus
    MAX-ACCESS  read-create
    STATUS  obsolete
    DESCRIPTION
        "RowStatus"
    ::= { zxr10RMAPMatchIpv6AddressEntry 100 }

--------------------------------------------------------------
--------------------------------------------------------------
--zxr10RMAPMatchIpv6AddrPflTable
--------------------------------------------------------------
zxr10RMAPMatchIpv6AddrPflTable  OBJECT-TYPE
    SYNTAX  SEQUENCE OF Zxr10RMAPMatchIpv6AddrPflEntry
    MAX-ACCESS  not-accessible
    STATUS  current
    DESCRIPTION
        "Route-map Match Ipv6Address pfl Table"
    ::= { zxr10RMAPRuleObjects 59 }

zxr10RMAPMatchIpv6AddrPflEntry  OBJECT-TYPE
    SYNTAX  Zxr10RMAPMatchIpv6AddrPflEntry
    MAX-ACCESS  not-accessible
    STATUS  current
    DESCRIPTION          
       "Match address of route or match packet.
        This match item sets the route-map name with ipv6 type.
        It conflicts with other match or set items 
        which set the route-map name with ipv4 type."
    INDEX  { zxr10RMAPName,  zxr10RMAPSequence, zxr10RMAPIpv6AddrPfl, 
    zxr10RMAPIpv6IsConfigPfl}
    ::= { zxr10RMAPMatchIpv6AddrPflTable 1 }
    
Zxr10RMAPMatchIpv6AddrPflEntry ::=SEQUENCE {
        zxr10RMAPIpv6AddrPflName       DisplayString,
        zxr10RMAPIpv6AddrPflSequence   Integer32,
        zxr10RMAPIpv6AddrPfl           DisplayString,
        zxr10RMAPIpv6IsConfigPfl       TruthValue,
        zxr10RMAPIpv6AddrPflRowStatus  RowStatus
    }

zxr10RMAPIpv6AddrPflName  OBJECT-TYPE
    SYNTAX   DisplayString(SIZE(1..31))
    MAX-ACCESS  not-accessible
    STATUS  current
    DESCRIPTION
        "Name of Route-map (1-31 characters)"
    ::= { zxr10RMAPMatchIpv6AddrPflEntry 1 } 
        
zxr10RMAPIpv6AddrPflSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpv6AddrPflEntry 2 }    

zxr10RMAPIpv6AddrPfl  OBJECT-TYPE
    SYNTAX   DisplayString(SIZE(1..31))
    MAX-ACCESS  not-accessible
    STATUS  current
    DESCRIPTION
        "Name of an access-list(1-31 characters).
         Each sequence has 10 match ipv6 address items at most."
    ::= { zxr10RMAPMatchIpv6AddrPflEntry 3 }  
      
zxr10RMAPIpv6IsConfigPfl  OBJECT-TYPE
    SYNTAX   TruthValue
    MAX-ACCESS  not-accessible
    STATUS  current
    DESCRIPTION
        "It expresses that this config is match ipv6 address by pfl."
    ::= { zxr10RMAPMatchIpv6AddrPflEntry 4 }  

zxr10RMAPIpv6AddrPflRowStatus  OBJECT-TYPE
    SYNTAX   RowStatus
    MAX-ACCESS  read-create
    STATUS  current
    DESCRIPTION
        "RowStatus"
    ::= { zxr10RMAPMatchIpv6AddrPflEntry 100 }



--------------------------------------------------------------
--------------------------------------------------------------
--zxr10RMAPMatchIpv6MetricTable
--------------------------------------------------------------
zxr10RMAPMatchIpv6MetricTable  OBJECT-TYPE
    SYNTAX  SEQUENCE OF Zxr10RMAPMatchIpv6MetricEntry
    MAX-ACCESS  not-accessible
    STATUS  current
    DESCRIPTION
        "Route-map Match Ipv6Metric Table"
    ::= { zxr10RMAPRuleObjects 12 }

zxr10RMAPMatchIpv6MetricEntry  OBJECT-TYPE
    SYNTAX  Zxr10RMAPMatchIpv6MetricEntry
    MAX-ACCESS  not-accessible
    STATUS  current
    DESCRIPTION          
       "Match metric of route.
        This match item sets the route-map name with ipv6 type.
        It conflicts with other match or set items 
        which set the route-map name with ipv4 type."
    INDEX  { zxr10RMAPName,  zxr10RMAPSequence, zxr10RMAPIpv6Metric}
    ::= { zxr10RMAPMatchIpv6MetricTable 1 }
    
Zxr10RMAPMatchIpv6MetricEntry ::=SEQUENCE {
        zxr10RMAPIpv6MetricName        DisplayString,
        zxr10RMAPIpv6MetricSequence    Integer32, 
        zxr10RMAPIpv6Metric            Unsigned32,
        zxr10RMAPIpv6MetricRowStatus   RowStatus
    }

zxr10RMAPIpv6MetricName  OBJECT-TYPE
    SYNTAX   DisplayString(SIZE(1..31))
    MAX-ACCESS  not-accessible
    STATUS  current
    DESCRIPTION
        "Name of Route-map (1-31 characters)"
    ::= { zxr10RMAPMatchIpv6MetricEntry 1 } 
        
zxr10RMAPIpv6MetricSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpv6MetricEntry 2 }    

zxr10RMAPIpv6Metric  OBJECT-TYPE
    SYNTAX   Unsigned32
    MAX-ACCESS  not-accessible
    STATUS  current
    DESCRIPTION
        " Metric Value.
          The range of config is 0 to 4294967295.
          Each sequence has 10 match ipv6 metric items at most."
    ::= { zxr10RMAPMatchIpv6MetricEntry 3 }

zxr10RMAPIpv6MetricRowStatus  OBJECT-TYPE
    SYNTAX   RowStatus
    MAX-ACCESS  read-create
    STATUS  current
    DESCRIPTION
        "RowStatus"
    ::= { zxr10RMAPMatchIpv6MetricEntry 100 }

--------------------------------------------------------------
--------------------------------------------------------------
--zxr10RMAPMatchIpv6NextHopTable
--------------------------------------------------------------
zxr10RMAPMatchIpv6NextHopTable  OBJECT-TYPE
    SYNTAX  SEQUENCE OF Zxr10RMAPMatchIpv6NextHopEntry
    MAX-ACCESS  not-accessible
    STATUS  current
    DESCRIPTION
        "Route-map Match Ipv6NextHop Table"
    ::= { zxr10RMAPRuleObjects 13 }

zxr10RMAPMatchIpv6NextHopEntry  OBJECT-TYPE
    SYNTAX  Zxr10RMAPMatchIpv6NextHopEntry
    MAX-ACCESS  not-accessible
    STATUS  current
    DESCRIPTION          
       "Match next-hop address of route.       
        This match item sets the route-map name with ipv6 type.
        It conflicts with other match or set items 
        which set the route-map name with ipv4 type."
    INDEX  { zxr10RMAPName,  zxr10RMAPSequence, zxr10RMAPIpv6NextHop}
    ::= { zxr10RMAPMatchIpv6NextHopTable 1 }
    
Zxr10RMAPMatchIpv6NextHopEntry ::=SEQUENCE {
        zxr10RMAPIpv6NextHopName       DisplayString,
        zxr10RMAPIpv6NextHopSequence   Integer32,
        zxr10RMAPIpv6NextHop           DisplayString,
        zxr10RMAPIpv6NextHopRowStatus  RowStatus
    }

zxr10RMAPIpv6NextHopName  OBJECT-TYPE
    SYNTAX   DisplayString(SIZE(1..31))
    MAX-ACCESS  not-accessible
    STATUS  current
    DESCRIPTION
        "Name of Route-map (1-31 characters)"
    ::= { zxr10RMAPMatchIpv6NextHopEntry 1 } 
        
zxr10RMAPIpv6NextHopSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpv6NextHopEntry 2 }    

zxr10RMAPIpv6NextHop   OBJECT-TYPE
    SYNTAX   DisplayString(SIZE(1..31))
    MAX-ACCESS  not-accessible
    STATUS  current
    DESCRIPTION
        "Name of an access-list(1-31 characters).
         Each sequence has 10 match ipv6 next-hop items at most."
    ::= { zxr10RMAPMatchIpv6NextHopEntry 3 }

zxr10RMAPIpv6NextHopRowStatus  OBJECT-TYPE
    SYNTAX   RowStatus
    MAX-ACCESS  read-create
    STATUS  current
    DESCRIPTION
        "RowStatus"
    ::= { zxr10RMAPMatchIpv6NextHopEntry 100 }

--------------------------------------------------------------
--------------------------------------------------------------
--zxr10RMAPMatchIpv6TagTable
--------------------------------------------------------------
zxr10RMAPMatchIpv6TagTable  OBJECT-TYPE
    SYNTAX  SEQUENCE OF Zxr10RMAPMatchIpv6TagEntry
    MAX-ACCESS  not-accessible
    STATUS  current
    DESCRIPTION
        "Route-map Match Ipv6Tag Table"
    ::= { zxr10RMAPRuleObjects 14 }

zxr10RMAPMatchIpv6TagEntry  OBJECT-TYPE
    SYNTAX  Zxr10RMAPMatchIpv6TagEntry
    MAX-ACCESS  not-accessible
    STATUS  current
    DESCRIPTION          
       "Match tag of route.       
        This match item sets the route-map name with ipv6 type.
        It conflicts with other match or set items 
        which set the route-map name with ipv4 type."
    INDEX  { zxr10RMAPName,  zxr10RMAPSequence, zxr10RMAPIpv6Tag}
    ::= { zxr10RMAPMatchIpv6TagTable 1 }
    
Zxr10RMAPMatchIpv6TagEntry ::=SEQUENCE {
        zxr10RMAPIpv6TagName           DisplayString,
        zxr10RMAPIpv6TagSequence       Integer32,  
        zxr10RMAPIpv6Tag               Unsigned32,
        zxr10RMAPIpv6TagRowStatus      RowStatus
    }

zxr10RMAPIpv6TagName  OBJECT-TYPE
    SYNTAX   DisplayString(SIZE(1..31))
    MAX-ACCESS  not-accessible
    STATUS  current
    DESCRIPTION
        "Name of Route-map (1-31 characters)"
    ::= { zxr10RMAPMatchIpv6TagEntry 1 } 
        
zxr10RMAPIpv6TagSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpv6TagEntry 2 }    

zxr10RMAPIpv6Tag  OBJECT-TYPE
    SYNTAX   Unsigned32
    MAX-ACCESS  not-accessible
    STATUS  current
    DESCRIPTION
        "Tag Value.
         The range of config is 0 to 4294967295.
         Each sequence has 10 match ipv6 tag items at most."
    ::= { zxr10RMAPMatchIpv6TagEntry 3 }

zxr10RMAPIpv6TagRowStatus  OBJECT-TYPE
    SYNTAX   RowStatus
    MAX-ACCESS  read-create
    STATUS  current
    DESCRIPTION
        "RowStatus"
    ::= { zxr10RMAPMatchIpv6TagEntry 100 }

--------------------------------------------------------------
--------------------------------------------------------------
--zxr10RMAPMatchRdTable
--------------------------------------------------------------
zxr10RMAPMatchRdTable  OBJECT-TYPE
    SYNTAX  SEQUENCE OF Zxr10RMAPMatchRdEntry
    MAX-ACCESS  not-accessible
    STATUS  current
    DESCRIPTION
        "Route-map Match Rd Table"
    ::= { zxr10RMAPRuleObjects 15 }

zxr10RMAPMatchRdEntry  OBJECT-TYPE
    SYNTAX  Zxr10RMAPMatchRdEntry
    MAX-ACCESS  not-accessible
    STATUS  current
    DESCRIPTION          
       "Match BGP/VPN rd list"
    INDEX  { zxr10RMAPName,  zxr10RMAPSequence, zxr10RMAPMatchRd}
    ::= { zxr10RMAPMatchRdTable 1 }
    
Zxr10RMAPMatchRdEntry ::=SEQUENCE {
        zxr10RMAPMatchRdName           DisplayString,
        zxr10RMAPMatchRdSequence       Integer32,
        zxr10RMAPMatchRd               Integer32,
        zxr10RMAPMatchRdRowStatus      RowStatus
    }

zxr10RMAPMatchRdName  OBJECT-TYPE
    SYNTAX   DisplayString(SIZE(1..31))
    MAX-ACCESS  not-accessible
    STATUS  current
    DESCRIPTION
        "Name of Route-map (1-31 characters)"
    ::= { zxr10RMAPMatchRdEntry 1 } 
        
zxr10RMAPMatchRdSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchRdEntry 2 }    

zxr10RMAPMatchRd  OBJECT-TYPE
    SYNTAX   Integer32
    MAX-ACCESS  not-accessible
    STATUS  current
    DESCRIPTION
        "Rd-list number.
         The range of config is 1 to 500. 0 is invalid value.
         Each sequence has 10 match rd-list items at most."
    ::= { zxr10RMAPMatchRdEntry 3 }

zxr10RMAPMatchRdRowStatus  OBJECT-TYPE
    SYNTAX   RowStatus
    MAX-ACCESS  read-create
    STATUS  current
    DESCRIPTION
        "RowStatus"
    ::= { zxr10RMAPMatchRdEntry 100 }

--------------------------------------------------------------
--------------------------------------------------------------
--zxr10RMAPMatchRouteTypeTable
--------------------------------------------------------------
zxr10RMAPMatchRouteTypeTable  OBJECT-TYPE
    SYNTAX  SEQUENCE OF Zxr10RMAPMatchRouteTypeEntry
    MAX-ACCESS  not-accessible
    STATUS  current
    DESCRIPTION
        "Route-map Match RouteType Table"
    ::= { zxr10RMAPRuleObjects 16 }

zxr10RMAPMatchRouteTypeEntry  OBJECT-TYPE
    SYNTAX  Zxr10RMAPMatchRouteTypeEntry
    MAX-ACCESS  not-accessible
    STATUS  current
    DESCRIPTION          
       "Match route-type of route"
    INDEX  { zxr10RMAPName,  zxr10RMAPSequence, zxr10RMAPMatchRouteType, zxr10RMAPMatchExternType}
    ::= { zxr10RMAPMatchRouteTypeTable 1 }
    
Zxr10RMAPMatchRouteTypeEntry ::=SEQUENCE {
        zxr10RMAPMatchRouteTypeName      DisplayString,
        zxr10RMAPMatchRouteTypeSequence  Integer32,
        zxr10RMAPMatchRouteType          RmapMatchRouteType,
        zxr10RMAPMatchExternType         RmapMatchRouteType,
        zxr10RMAPMatchRouteTypeRowStatus RowStatus
    }

zxr10RMAPMatchRouteTypeName  OBJECT-TYPE
    SYNTAX   DisplayString(SIZE(1..31))
    MAX-ACCESS  not-accessible
    STATUS  current
    DESCRIPTION
        "Name of Route-map (1-31 characters)"
    ::= { zxr10RMAPMatchRouteTypeEntry 1 } 
        
zxr10RMAPMatchRouteTypeSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchRouteTypeEntry 2 }    

zxr10RMAPMatchRouteType  OBJECT-TYPE
    SYNTAX   RmapMatchRouteType
    MAX-ACCESS  not-accessible
    STATUS  current
    DESCRIPTION
        "local       Locally generated route.Value is 1.
         internal    Internal route (including OSPF intra/inter area).Value is 2.
         level-1     IS-IS level-1 route.Value is 3.
         level-2     IS-IS level-2 route.Value is 4.
         external    External route (OSPF type 1/2).Value is 5.
         ebgp        External border gateway protocol(EBGP) route.Value is 8.
         ibgp        Internal border gateway protocol(IBGP) route.Value is 9.
         static      Static route.Value is 10.
         bgp-agg     BGP aggregate route.Value is 11."
    ::= { zxr10RMAPMatchRouteTypeEntry 3 }

zxr10RMAPMatchExternType  OBJECT-TYPE
    SYNTAX   RmapMatchRouteType
    MAX-ACCESS  not-accessible
    STATUS  current
    DESCRIPTION
        "type-1      OSPF external type 1 route.Value is 6.
         type-2      OSPF external type 2 route.Value is 7."
    ::= { zxr10RMAPMatchRouteTypeEntry 4 }

zxr10RMAPMatchRouteTypeRowStatus  OBJECT-TYPE
    SYNTAX   RowStatus
    MAX-ACCESS  read-create
    STATUS  current
    DESCRIPTION
        "RowStatus"
    ::= { zxr10RMAPMatchRouteTypeEntry 100 }

--------------------------------------------------------------
--------------------------------------------------------------
--zxr10RMAPSetAspathTable
--------------------------------------------------------------
zxr10RMAPSetAspathTable  OBJECT-TYPE
    SYNTAX  SEQUENCE OF Zxr10RMAPSetAspathEntry
    MAX-ACCESS  not-accessible
    STATUS  current
    DESCRIPTION
        "Route-map Set Aspath Table"
    ::= { zxr10RMAPRuleObjects 17 }

zxr10RMAPSetAspathEntry  OBJECT-TYPE
    SYNTAX  Zxr10RMAPSetAspathEntry
    MAX-ACCESS  not-accessible
    STATUS  current
    DESCRIPTION          
       "Set prepend string for a BGP as-path attribute.
        0 is invalid value."
    INDEX  { zxr10RMAPName,  zxr10RMAPSequence}
    ::= { zxr10RMAPSetAspathTable 1 }
    
Zxr10RMAPSetAspathEntry ::=SEQUENCE {
        zxr10RMAPSetAspathName            DisplayString,
        zxr10RMAPSetAspathSequence        Integer32,
        zxr10RMAPSetAspathAsnd1           Unsigned32,
        zxr10RMAPSetAspathAsnd2           Unsigned32,
        zxr10RMAPSetAspathAsnd3           Unsigned32,
        zxr10RMAPSetAspathAsnd4           Unsigned32,
        zxr10RMAPSetAspathAsnd5           Unsigned32,
        zxr10RMAPSetAspathAsnd6           Unsigned32,
        zxr10RMAPSetAspathAsnd7           Unsigned32,
        zxr10RMAPSetAspathAsnd8           Unsigned32,
        zxr10RMAPSetAspathAsnd9           Unsigned32,
        zxr10RMAPSetAspathAsnd10          Unsigned32,
        zxr10RMAPSetAspathPrepOrRep       RmapPrependReplace,
        zxr10RMAPSetAspathRowStatus       RowStatus
    }

zxr10RMAPSetAspathName  OBJECT-TYPE
    SYNTAX   DisplayString(SIZE(1..31))
    MAX-ACCESS  not-accessible
    STATUS  current
    DESCRIPTION
        "Name of Route-map (1-31 characters)"
    ::= { zxr10RMAPSetAspathEntry 1 } 
        
zxr10RMAPSetAspathSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetAspathEntry 2 }    

zxr10RMAPSetAspathAsnd1  OBJECT-TYPE
    SYNTAX   Unsigned32
    MAX-ACCESS  read-create
    STATUS  current
    DESCRIPTION
        "AS number.
         The range of config is 1 to 4294967295."
    ::= { zxr10RMAPSetAspathEntry 3 }

zxr10RMAPSetAspathAsnd2  OBJECT-TYPE
    SYNTAX   Unsigned32
    MAX-ACCESS  read-create
    STATUS  current
    DESCRIPTION
        "AS number.
         The range of config is 1 to 4294967295."
    ::= { zxr10RMAPSetAspathEntry 4 } 
    
zxr10RMAPSetAspathAsnd3  OBJECT-TYPE
    SYNTAX   Unsigned32
    MAX-ACCESS  read-create
    STATUS  current
    DESCRIPTION
        "AS number.
         The range of config is 1 to 4294967295."
    ::= { zxr10RMAPSetAspathEntry 5 }
    
zxr10RMAPSetAspathAsnd4  OBJECT-TYPE
    SYNTAX   Unsigned32
    MAX-ACCESS  read-create
    STATUS  current
    DESCRIPTION
        "AS number.
         The range of config is 1 to 4294967295."
    ::= { zxr10RMAPSetAspathEntry 6 }
    
zxr10RMAPSetAspathAsnd5  OBJECT-TYPE
    SYNTAX   Unsigned32
    MAX-ACCESS  read-create
    STATUS  current
    DESCRIPTION
        "AS number.
         The range of config is 1 to 4294967295."
    ::= { zxr10RMAPSetAspathEntry 7 } 
    
zxr10RMAPSetAspathAsnd6  OBJECT-TYPE
    SYNTAX   Unsigned32
    MAX-ACCESS  read-create
    STATUS  current
    DESCRIPTION
        "AS number.
         The range of config is 1 to 4294967295."
    ::= { zxr10RMAPSetAspathEntry 8 }
    
zxr10RMAPSetAspathAsnd7  OBJECT-TYPE
    SYNTAX   Unsigned32
    MAX-ACCESS  read-create
    STATUS  current
    DESCRIPTION
        "AS number.
         The range of config is 1 to 4294967295."
    ::= { zxr10RMAPSetAspathEntry 9 }
    
zxr10RMAPSetAspathAsnd8  OBJECT-TYPE
    SYNTAX   Unsigned32
    MAX-ACCESS  read-create
    STATUS  current
    DESCRIPTION
        "AS number.
         The range of config is 1 to 4294967295."
    ::= { zxr10RMAPSetAspathEntry 10 }
    
zxr10RMAPSetAspathAsnd9  OBJECT-TYPE
    SYNTAX   Unsigned32
    MAX-ACCESS  read-create
    STATUS  current
    DESCRIPTION
        "AS number.
         The range of config is 1 to 4294967295."
    ::= { zxr10RMAPSetAspathEntry 11 } 
    
zxr10RMAPSetAspathAsnd10  OBJECT-TYPE
    SYNTAX   Unsigned32
    MAX-ACCESS  read-create
    STATUS  current
    DESCRIPTION
        "AS number.
         The range of config is 1 to 4294967295."
    ::= { zxr10RMAPSetAspathEntry 12 }

zxr10RMAPSetAspathPrepOrRep  OBJECT-TYPE
    SYNTAX   RmapPrependReplace
    MAX-ACCESS  read-create
    STATUS  current
    DESCRIPTION
        "Set aspath prepend or replace,prepend is 1,replace is 2"
    ::= { zxr10RMAPSetAspathEntry 13 }
   
zxr10RMAPSetAspathRowStatus  OBJECT-TYPE
    SYNTAX   RowStatus
    MAX-ACCESS  read-create
    STATUS  current
    DESCRIPTION
        "RowStatus"
    ::= { zxr10RMAPSetAspathEntry 100 }
--------------------------------------------------------------
--------------------------------------------------------------
--zxr10RMAPSetCommunityConstTable
--------------------------------------------------------------
zxr10RMAPSetCommunityConstTable  OBJECT-TYPE
    SYNTAX  SEQUENCE OF Zxr10RMAPSetCommunityConstEntry
    MAX-ACCESS  not-accessible
    STATUS  current
    DESCRIPTION
        "Route-map Set Community Table"
    ::= { zxr10RMAPRuleObjects 18 }

zxr10RMAPSetCommunityConstEntry  OBJECT-TYPE
    SYNTAX  Zxr10RMAPSetCommunityConstEntry
    MAX-ACCESS  not-accessible
    STATUS  current
    DESCRIPTION          
       "Set BGP community attribute.
        The value of config includes:
        internet             Internet(Well known community)
        no-advertise         Do not advertise to any peer
        no-export            Do not export to next AS
        no-export-subconfed  Do not send outside local AS
        none                 No community attribute.
        If set community none has been setted, other types of set community can't be setted.
        If set community has been setted with attribute addtive, 
        other configs of set community can't be setted without attribute addtive."
    INDEX  { zxr10RMAPName,  zxr10RMAPSequence, zxr10RMAPSetCommIsAddtive, zxr10RMAPSetCommConstVal}
    ::= { zxr10RMAPSetCommunityConstTable 1 }
    
Zxr10RMAPSetCommunityConstEntry ::=SEQUENCE {
        zxr10RMAPSetCommName                   DisplayString,
        zxr10RMAPSetCommSequence               Integer32,
        zxr10RMAPSetCommIsAddtive              RmapSetComm,
        zxr10RMAPSetCommConstVal               RmapSetComm,
        zxr10RMAPSetCommConstRowStatus         RowStatus  
    }

zxr10RMAPSetCommName  OBJECT-TYPE
    SYNTAX   DisplayString(SIZE(1..31))
    MAX-ACCESS  not-accessible
    STATUS  current
    DESCRIPTION
        "Name of Route-map (1-31 characters)"
    ::= { zxr10RMAPSetCommunityConstEntry 1 } 
        
zxr10RMAPSetCommSequence  OBJECT-TYPE
    SYNTAX   Integer32
    MAX-ACCESS  not-accessible
    STATUS  current
    DESCRIPTION
        "Sequence of Route-map.
         The sequence of a route-map.
         The range of config is 0 to 65535.
         Each name of route-map has 100 sequences at most."
    ::= { zxr10RMAPSetCommunityConstEntry 2 }    

zxr10RMAPSetCommIsAddtive  OBJECT-TYPE
    SYNTAX   RmapSetComm
    MAX-ACCESS  not-accessible
    STATUS  current
    DESCRIPTION
        "additive             Add to the existing community. Value is 5.
         none                 No community attribute. Value is 6."
    ::= { zxr10RMAPSetCommunityConstEntry 3 }

zxr10RMAPSetCommConstVal  OBJECT-TYPE
    SYNTAX   RmapSetComm
    MAX-ACCESS  not-accessible
    STATUS  current
    DESCRIPTION
        "internet             Internet(Well known community). Value is 4.
         no-advertise         Do not advertise to any peer. Value is 2.
         no-export            Do not export to next AS. Value is 1.
         no-export-subconfed  Do not send outside local AS. Value is 3."
    ::= { zxr10RMAPSetCommunityConstEntry 4 }

zxr10RMAPSetCommConstRowStatus  OBJECT-TYPE
    SYNTAX   RowStatus
    MAX-ACCESS  read-create
    STATUS  current
    DESCRIPTION
        "RowStatus"
    ::= { zxr10RMAPSetCommunityConstEntry 100 }

--------------------------------------------------------------
--------------------------------------------------------------
--zxr10RMAPSetCommunityAsnnTable
--------------------------------------------------------------
zxr10RMAPSetCommunityAsnnTable  OBJECT-TYPE
    SYNTAX  SEQUENCE OF Zxr10RMAPSetCommunityAsnnEntry
    MAX-ACCESS  not-accessible
    STATUS  current
    DESCRIPTION
        "Route-map Set Community Table"
    ::= { zxr10RMAPRuleObjects 19 }

zxr10RMAPSetCommunityAsnnEntry  OBJECT-TYPE
    SYNTAX  Zxr10RMAPSetCommunityAsnnEntry
    MAX-ACCESS  not-accessible
    STATUS  current
    DESCRIPTION          
       "Set BGP community attribute in aa:nn format. 
        If set community has been setted with attribute addtive, 
        other configs of set community can't be setted without attribute addtive.
        If zxr10RMAPSetCommAsnn is setted with value 0:0 , 
        the config will transform to config of set community internet.
        If zxr10RMAPSetCommAsnn is setted with value 0:X , 
        the config will transform to config of set community X in uint format.
        If zxr10RMAPSetCommUint is setted with value 65535:65281,
        the config will transform to config of set community no-export.
        If zxr10RMAPSetCommUint is setted with value 65535:65282,
        the config will transform to config of set community no-advertise.
        If zxr10RMAPSetCommUint is setted with value 65535:65283,
        the config will transform to config of set community no-export-subconfed."
    INDEX  { zxr10RMAPName,  zxr10RMAPSequence, zxr10RMAPSetCommAsnnIsAddtive, zxr10RMAPSetCommAsnn}
    ::= { zxr10RMAPSetCommunityAsnnTable 1 }
    
Zxr10RMAPSetCommunityAsnnEntry ::=SEQUENCE {
        zxr10RMAPSetCommAsnnName               DisplayString,
        zxr10RMAPSetCommAsnnSequence           Integer32,
        zxr10RMAPSetCommAsnnIsAddtive          RmapSetComm,
        zxr10RMAPSetCommAsnn                   DisplayString,
        zxr10RMAPSetCommAsnnRowStatus          RowStatus  
    }

zxr10RMAPSetCommAsnnName  OBJECT-TYPE
    SYNTAX   DisplayString(SIZE(1..31))
    MAX-ACCESS  not-accessible
    STATUS  current
    DESCRIPTION
        "Name of Route-map (1-31 characters)"
    ::= { zxr10RMAPSetCommunityAsnnEntry 1 } 
        
zxr10RMAPSetCommAsnnSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetCommunityAsnnEntry 2 }    

zxr10RMAPSetCommAsnnIsAddtive  OBJECT-TYPE
    SYNTAX   RmapSetComm
    MAX-ACCESS  not-accessible
    STATUS  current
    DESCRIPTION
        "additive Add to the existing community. Value is 5."
    ::= { zxr10RMAPSetCommunityAsnnEntry 3 }

zxr10RMAPSetCommAsnn  OBJECT-TYPE
    SYNTAX   DisplayString(SIZE(1..12))
    MAX-ACCESS  not-accessible
    STATUS  current
    DESCRIPTION
        "Community number in aa:nn format.
         The range of aa is 0 to 65535.
         The range of nn is 0 to 65535.
         The ASCII code of : is 58.
         The ASCII code from 1 to 9 is 49 to 57."
    ::= { zxr10RMAPSetCommunityAsnnEntry 4 }

zxr10RMAPSetCommAsnnRowStatus  OBJECT-TYPE
    SYNTAX   RowStatus
    MAX-ACCESS  read-create
    STATUS  current
    DESCRIPTION
        "RowStatus"
    ::= { zxr10RMAPSetCommunityAsnnEntry 100 }

--------------------------------------------------------------
--------------------------------------------------------------
--zxr10RMAPSetCommunityUintTable
--------------------------------------------------------------
zxr10RMAPSetCommunityUintTable  OBJECT-TYPE
    SYNTAX  SEQUENCE OF Zxr10RMAPSetCommunityUintEntry
    MAX-ACCESS  not-accessible
    STATUS  current
    DESCRIPTION
        "Route-map Set Community Table"
    ::= { zxr10RMAPRuleObjects 20 }

zxr10RMAPSetCommunityUintEntry  OBJECT-TYPE
    SYNTAX  Zxr10RMAPSetCommunityUintEntry
    MAX-ACCESS  not-accessible
    STATUS  current
    DESCRIPTION          
       "Set BGP community attribute in Unsigned32 format.
        If set community has been setted with addtive attribute, 
        other configs of set community can't be setted without addtive attribute. 
        If zxr10RMAPSetCommUint is setted with value which is larger than 65535,
        the config will transform to config of set community X:Y in ASNN format.
        For example,set community 65536 will transform to set community 1:1.
        If zxr10RMAPSetCommUint is setted with value 4294967041,
        the config will transform to config of set community no-export.
        If zxr10RMAPSetCommUint is setted with value 4294967042,
        the config will transform to config of set community no-advertise.
        If zxr10RMAPSetCommUint is setted with value 4294967043,
        the config will transform to config of set community no-export-subconfed."
    INDEX  { zxr10RMAPName,  zxr10RMAPSequence, zxr10RMAPSetCommUintIsAddtive, zxr10RMAPSetCommUint}
    ::= { zxr10RMAPSetCommunityUintTable 1 }
    
Zxr10RMAPSetCommunityUintEntry ::=SEQUENCE {
        zxr10RMAPSetCommUintName              DisplayString,
        zxr10RMAPSetCommUintSequence          Integer32,
        zxr10RMAPSetCommUintIsAddtive         RmapSetComm,
        zxr10RMAPSetCommUint                  Unsigned32,
        zxr10RMAPSetCommUintRowStatus         RowStatus  
    }

zxr10RMAPSetCommUintName  OBJECT-TYPE
    SYNTAX   DisplayString(SIZE(1..31))
    MAX-ACCESS  not-accessible
    STATUS  current
    DESCRIPTION
        "Name of Route-map (1-31 characters)"
    ::= { zxr10RMAPSetCommunityUintEntry 1 } 
        
zxr10RMAPSetCommUintSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetCommunityUintEntry 2 }    

zxr10RMAPSetCommUintIsAddtive  OBJECT-TYPE
    SYNTAX   RmapSetComm
    MAX-ACCESS  not-accessible
    STATUS  current
    DESCRIPTION
        "additive Add to the existing community. Value is 5."
    ::= { zxr10RMAPSetCommunityUintEntry 3 }

zxr10RMAPSetCommUint  OBJECT-TYPE
    SYNTAX   Unsigned32
    MAX-ACCESS  not-accessible
    STATUS  current
    DESCRIPTION
        "Community number in unsigned32 format.
         The range of config is 1 to 4294967295."
    ::= { zxr10RMAPSetCommunityUintEntry 4 }

zxr10RMAPSetCommUintRowStatus  OBJECT-TYPE
    SYNTAX   RowStatus
    MAX-ACCESS  read-create
    STATUS  current
    DESCRIPTION
        "RowStatus"
    ::= { zxr10RMAPSetCommunityUintEntry 100 }

--------------------------------------------------------------
--------------------------------------------------------------
--zxr10RMAPSetDampeningTable
--------------------------------------------------------------
zxr10RMAPSetDampeningTable  OBJECT-TYPE
    SYNTAX  SEQUENCE OF Zxr10RMAPSetDampeningEntry
    MAX-ACCESS  not-accessible
    STATUS  current
    DESCRIPTION
        "Route-map Set Dampening Table"
    ::= { zxr10RMAPRuleObjects 21 }

zxr10RMAPSetDampeningEntry  OBJECT-TYPE
    SYNTAX  Zxr10RMAPSetDampeningEntry
    MAX-ACCESS  not-accessible
    STATUS  current
    DESCRIPTION          
       "Set BGP route flap dampening parameters"
    INDEX  { zxr10RMAPName,  zxr10RMAPSequence}
    ::= { zxr10RMAPSetDampeningTable 1 }
    
Zxr10RMAPSetDampeningEntry ::=SEQUENCE {
        zxr10RMAPSetDampeningName             DisplayString,
        zxr10RMAPSetDampeningSequence         Integer32,
        zxr10RMAPSetDampeningHalfLife         Integer32,
        zxr10RMAPSetDampeningReuse            Integer32,
        zxr10RMAPSetDampeningSuppress         Integer32,
        zxr10RMAPSetDampeningMaxSupTime       Integer32,
        zxr10RMAPSetDampeningRowStatus        RowStatus
    }

zxr10RMAPSetDampeningName  OBJECT-TYPE
    SYNTAX   DisplayString(SIZE(1..31))
    MAX-ACCESS  not-accessible
    STATUS  current
    DESCRIPTION
        "Name of Route-map (1-31 characters)"
    ::= { zxr10RMAPSetDampeningEntry 1 } 
        
zxr10RMAPSetDampeningSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetDampeningEntry 2 }    

zxr10RMAPSetDampeningHalfLife  OBJECT-TYPE
    SYNTAX   Integer32
    MAX-ACCESS  read-create
    STATUS  current
    DESCRIPTION
        "Half-life time for the penalty.
         The range of config is 1 to 45.
         The value for half-life should be smaller than max duration to suppress."
    ::= { zxr10RMAPSetDampeningEntry 3 }

zxr10RMAPSetDampeningReuse  OBJECT-TYPE
    SYNTAX   Integer32
    MAX-ACCESS  read-create
    STATUS  current
    DESCRIPTION
        "Penalty to start reusing a route.
         The range of config is 1 to 20000.
         The value for reusing should be smaller than the value for suppressing."
    ::= { zxr10RMAPSetDampeningEntry 4 }

zxr10RMAPSetDampeningSuppress  OBJECT-TYPE
    SYNTAX   Integer32
    MAX-ACCESS  read-create
    STATUS  current
    DESCRIPTION
        "Penalty to start suppressing a route.
         The range of config is 1 to 20000.
         The value for suppressing should be larger than the value for reusing."
    ::= { zxr10RMAPSetDampeningEntry 5 }

zxr10RMAPSetDampeningMaxSupTime  OBJECT-TYPE
    SYNTAX   Integer32
    MAX-ACCESS  read-create
    STATUS  current
    DESCRIPTION
        "Maximum duration to suppress a stable route.
         The range of config is 1 to 255.
         The value for max duration to suppress should be larger than half-life."
    ::= { zxr10RMAPSetDampeningEntry 6 }

zxr10RMAPSetDampeningRowStatus  OBJECT-TYPE
    SYNTAX   RowStatus
    MAX-ACCESS  read-create
    STATUS  current
    DESCRIPTION
        "RowStatus"
    ::= { zxr10RMAPSetDampeningEntry 100 }

--------------------------------------------------------------
--------------------------------------------------------------
--zxr10RMAPSetDscpTable
--------------------------------------------------------------
zxr10RMAPSetDscpTable  OBJECT-TYPE
    SYNTAX  SEQUENCE OF Zxr10RMAPSetDscpEntry
    MAX-ACCESS  not-accessible
    STATUS  current
    DESCRIPTION
        "Route-map Set Dscp Table"
    ::= { zxr10RMAPRuleObjects 22 }

zxr10RMAPSetDscpEntry  OBJECT-TYPE
    SYNTAX  Zxr10RMAPSetDscpEntry
    MAX-ACCESS  not-accessible
    STATUS  current
    DESCRIPTION          
       "Set DSCP for PBR.
        This set item conflicts with these items below:
        set ip precedence
        set ip tos
        set ipv6 precedence
        set ipv6 traffic-class"
    INDEX  { zxr10RMAPName,  zxr10RMAPSequence}
    ::= { zxr10RMAPSetDscpTable 1 }
    
Zxr10RMAPSetDscpEntry ::=SEQUENCE {
        zxr10RMAPSetDscpName                  DisplayString,
        zxr10RMAPSetDscpSequence              Integer32,
        zxr10RMAPSetDscp                      Integer32,
        zxr10RMAPSetDscpRowStatus             RowStatus
    }

zxr10RMAPSetDscpName  OBJECT-TYPE
    SYNTAX   DisplayString(SIZE(1..31))
    MAX-ACCESS  not-accessible
    STATUS  current
    DESCRIPTION
        "Name of Route-map (1-31 characters)"
    ::= { zxr10RMAPSetDscpEntry 1 } 
        
zxr10RMAPSetDscpSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetDscpEntry 2 }    

zxr10RMAPSetDscp  OBJECT-TYPE
    SYNTAX   Integer32
    MAX-ACCESS  read-create
    STATUS  current
    DESCRIPTION
        "Type of service value.
         The range of config is 0 to 63.
         255 is invalid value."
    ::= { zxr10RMAPSetDscpEntry 3 }

zxr10RMAPSetDscpRowStatus  OBJECT-TYPE
    SYNTAX   RowStatus
    MAX-ACCESS  read-create
    STATUS  current
    DESCRIPTION
        "RowStatus"
    ::= { zxr10RMAPSetDscpEntry 100 }

--------------------------------------------------------------
--------------------------------------------------------------
--zxr10RMAPSetRtTable
--------------------------------------------------------------
zxr10RMAPSetRtTable  OBJECT-TYPE
    SYNTAX  SEQUENCE OF Zxr10RMAPSetRtEntry
    MAX-ACCESS  not-accessible
    STATUS  current
    DESCRIPTION
        "Route-map Set Rt Table"
    ::= { zxr10RMAPRuleObjects 23 }

zxr10RMAPSetRtEntry  OBJECT-TYPE
    SYNTAX  Zxr10RMAPSetRtEntry
    MAX-ACCESS  not-accessible
    STATUS  current
    DESCRIPTION          
       "Set Transitive Route Target extended community.
        If set extcommunity rt-trans remove has been setted, other types of set extcommunity can't be setted.
        If set extcommunity rt-trans has been setted with addtive attribute, 
        other configs of set extcommunity rt-trans can't be setted without addtive attribute."
    INDEX  { zxr10RMAPName,  zxr10RMAPSequence, zxr10RMAPSetRtAsnn, zxr10RMAPSetRtReOrAdd}
    ::= { zxr10RMAPSetRtTable 1 }
    
Zxr10RMAPSetRtEntry ::=SEQUENCE {
        zxr10RMAPSetRtName            DisplayString,
        zxr10RMAPSetRtSequence        Integer32,
        zxr10RMAPSetRtAsnn            DisplayString,
        zxr10RMAPSetRtReOrAdd         RmapSetRt, 
        zxr10RMAPSetRtRowStatus       RowStatus
    }

zxr10RMAPSetRtName  OBJECT-TYPE
    SYNTAX   DisplayString(SIZE(1..31))
    MAX-ACCESS  not-accessible
    STATUS  current
    DESCRIPTION
        "Name of Route-map (1-31 characters)"
    ::= { zxr10RMAPSetRtEntry 1 } 
        
zxr10RMAPSetRtSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetRtEntry 2 }    

zxr10RMAPSetRtAsnn  OBJECT-TYPE
    SYNTAX   DisplayString(SIZE(1..12))
    MAX-ACCESS  not-accessible
    STATUS  current
    DESCRIPTION
        "VPN extended community.
        This config includes 3 formats.
        1.ASNN(X:Y)
        The range of X is 0 to 65535.
        The range of X is 0 to 4294967295.
        2.ASNDot(X.Y:Z)
        The range of X is 1 to 65535.
        The range of Y is 0 to 65535.
        The range of Z is 0 to 65535.
        3.ASNIp(A.B.C.D:X)
        The range of X is 0 to 65535.
        The ASCII code of . is 46.
        The ASCII code of : is 58.
        The ASCII code from 1 to 9 is 49 to 57."
    ::= { zxr10RMAPSetRtEntry 3 }

zxr10RMAPSetRtReOrAdd  OBJECT-TYPE
    SYNTAX   RmapSetRt
    MAX-ACCESS  not-accessible
    STATUS  current
    DESCRIPTION
        "additive  Add to the existing extcommunity.Value is 6.
         remove    Remove the existing extcommunity.Value is 7."
    ::= { zxr10RMAPSetRtEntry 4 }

zxr10RMAPSetRtRowStatus  OBJECT-TYPE
    SYNTAX   RowStatus
    MAX-ACCESS  read-create
    STATUS  current
    DESCRIPTION
        "RowStatus"
    ::= { zxr10RMAPSetRtEntry 100 }

--------------------------------------------------------------
--------------------------------------------------------------
--zxr10RMAPSetSooTable
--------------------------------------------------------------
zxr10RMAPSetSooTable  OBJECT-TYPE
    SYNTAX  SEQUENCE OF Zxr10RMAPSetSooEntry
    MAX-ACCESS  not-accessible
    STATUS  current
    DESCRIPTION
        "Route-map Set Soo Table"
    ::= { zxr10RMAPRuleObjects 24 }

zxr10RMAPSetSooEntry  OBJECT-TYPE
    SYNTAX  Zxr10RMAPSetSooEntry
    MAX-ACCESS  not-accessible
    STATUS  current
    DESCRIPTION          
       "Transitive Site-of-Origin extended community.
        If set extcommunity soo-trans remove has been setted, other types of set extcommunity can't be setted.
        The ASCII code of . is 46.
        The ASCII code of : is 58.
        The ASCII code from 1 to 9 is 49 to 57."
    INDEX  { zxr10RMAPName,  zxr10RMAPSequence}
    ::= { zxr10RMAPSetSooTable 1 }
    
Zxr10RMAPSetSooEntry ::=SEQUENCE {
        zxr10RMAPSetSooName           DisplayString,
        zxr10RMAPSetSooSequence       Integer32,
        zxr10RMAPSetSooAsnn           DisplayString, 
        zxr10RMAPSetSooRemove         RmapSetRt,
        zxr10RMAPSetSooRowStatus      RowStatus 
    }

zxr10RMAPSetSooName  OBJECT-TYPE
    SYNTAX   DisplayString(SIZE(1..31))
    MAX-ACCESS  not-accessible
    STATUS  current
    DESCRIPTION
        "Name of Route-map (1-31 characters)"
    ::= { zxr10RMAPSetSooEntry 1 } 
        
zxr10RMAPSetSooSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetSooEntry 2 }    

zxr10RMAPSetSooAsnn  OBJECT-TYPE
    SYNTAX   DisplayString(SIZE(1..12))
    MAX-ACCESS  read-create
    STATUS  current
    DESCRIPTION
        "VPN extended community.
        This config includes 3 formats.
        1.ASNN(X:Y)
        The range of X is 0 to 65535.
        The range of X is 0 to 4294967295.
        2.ASNDot(X.Y:Z)
        The range of X is 1 to 65535.
        The range of Y is 0 to 65535.
        The range of Z is 0 to 65535.
        3.ASNIp(A.B.C.D:X)
        The range of X is 0 to 65535."
    ::= { zxr10RMAPSetSooEntry 3 } 

zxr10RMAPSetSooRemove  OBJECT-TYPE
    SYNTAX   RmapSetRt
    MAX-ACCESS  read-create
    STATUS  current
    DESCRIPTION
        "Remove the existing extcommunity.Value is 7"
    ::= { zxr10RMAPSetSooEntry 4 }

zxr10RMAPSetSooRowStatus  OBJECT-TYPE
    SYNTAX   RowStatus
    MAX-ACCESS  read-create
    STATUS  current
    DESCRIPTION
        "RowStatus"
    ::= { zxr10RMAPSetSooEntry 100 }

--------------------------------------------------------------
--------------------------------------------------------------
--zxr10RMAPSetGlobalTable
--------------------------------------------------------------
zxr10RMAPSetGlobalTable  OBJECT-TYPE
    SYNTAX  SEQUENCE OF Zxr10RMAPSetGlobalEntry
    MAX-ACCESS  not-accessible
    STATUS  current
    DESCRIPTION
        "Route-map Set Global Table"
    ::= { zxr10RMAPRuleObjects 25 }

zxr10RMAPSetGlobalEntry  OBJECT-TYPE
    SYNTAX  Zxr10RMAPSetGlobalEntry
    MAX-ACCESS  not-accessible
    STATUS  current
    DESCRIPTION          
       "Set global route for PBR.
        This set item sets the route-map name with ipv4 type.
        It conflicts with other match or set items 
        which set the route-map name with ipv6 type.
        It conflicts with these set items below:
        set interface
        set ip next-hop
        set ipv6 next-hop
        set next-hop
        set ip path
        set ipv6 path
        set vrf                                "
    INDEX  { zxr10RMAPName,  zxr10RMAPSequence}
    ::= { zxr10RMAPSetGlobalTable 1 }
    
Zxr10RMAPSetGlobalEntry ::=SEQUENCE {
        zxr10RMAPSetGlobalName                DisplayString,
        zxr10RMAPSetGlobalSequence            Integer32,
        zxr10RMAPSetGlobal                    TruthValue, 
        zxr10RMAPSetGlobalIPAddr              IpAddress,
        zxr10RMAPSetGlobalIpConst             RmapSetGlobalIpConst,
        zxr10RMAPSetGlobalNextHopConst        RmapSetGlobalNextHopConst,
        zxr10RMAPSetGlobalRowStatus           RowStatus
    }

zxr10RMAPSetGlobalName  OBJECT-TYPE
    SYNTAX   DisplayString(SIZE(1..31))
    MAX-ACCESS  not-accessible
    STATUS  current
    DESCRIPTION
        "Name of Route-map (1-31 characters)"
    ::= { zxr10RMAPSetGlobalEntry 1 } 
        
zxr10RMAPSetGlobalSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetGlobalEntry 2 }    

zxr10RMAPSetGlobal  OBJECT-TYPE
    SYNTAX   TruthValue
    MAX-ACCESS  read-create
    STATUS  current
    DESCRIPTION
        "It expresses that whether this config is setted or not."
    ::= { zxr10RMAPSetGlobalEntry 3 }

zxr10RMAPSetGlobalIPAddr  OBJECT-TYPE
    SYNTAX   IpAddress
    MAX-ACCESS  read-create
    STATUS  current
    DESCRIPTION
        "IP address of next hop.
         This attribut may be setted or not.
         0 is invaid value."
    ::= { zxr10RMAPSetGlobalEntry 4 }  
    
zxr10RMAPSetGlobalIpConst  OBJECT-TYPE
    SYNTAX   RmapSetGlobalIpConst
    MAX-ACCESS  read-create
    STATUS  current
    DESCRIPTION
        "If zxr10RMAPSetGlobalIPAddr is setted, this attribut should be setted
        with value 3"
    ::= { zxr10RMAPSetGlobalEntry 5 } 
    
zxr10RMAPSetGlobalNextHopConst  OBJECT-TYPE
    SYNTAX   RmapSetGlobalNextHopConst
    MAX-ACCESS  read-create
    STATUS  current
    DESCRIPTION
        "If zxr10RMAPSetGlobalIPAddr is setted, this attribut should be setted
        with value 1"
    ::= { zxr10RMAPSetGlobalEntry 6 }

zxr10RMAPSetGlobalRowStatus  OBJECT-TYPE
    SYNTAX   RowStatus
    MAX-ACCESS  read-create
    STATUS  current
    DESCRIPTION
        "RowStatus"
    ::= { zxr10RMAPSetGlobalEntry 100 }

--------------------------------------------------------------
--------------------------------------------------------------
--zxr10RMAPSetInterfaceTable
--------------------------------------------------------------
zxr10RMAPSetInterfaceTable  OBJECT-TYPE
    SYNTAX  SEQUENCE OF Zxr10RMAPSetInterfaceEntry
    MAX-ACCESS  not-accessible
    STATUS  current
    DESCRIPTION
        "Route-map Set Interface Table"
    ::= { zxr10RMAPRuleObjects 26 }

zxr10RMAPSetInterfaceEntry  OBJECT-TYPE
    SYNTAX  Zxr10RMAPSetInterfaceEntry
    MAX-ACCESS  not-accessible
    STATUS  current
    DESCRIPTION          
       "Set output interface.
        Each sequence has 10 set interface items at most.
        This set item supports these types of interface:
        [PORT_CLASS_OC, PORT_TYPE_OC48]
        [PORT_TYPE_OC192, PORT_CLASS_OC_END]
        PORT_TYPE_NULL
        PORT_TYPE_TE_TUNNEL
        PORT_TYPE_GRE_TUNNEL
        PORT_TYPE_OC3_C_E1
        PORT_TYPE_OC3_C_E1_TS
        PORT_TYPE_E1_C_TS
        [PORT_TYPE_DIALER,PORT_TYPE_DIALER].
        It conflicts with these set items below:
        set vrf
        set global                              "
    INDEX  { zxr10RMAPName,  zxr10RMAPSequence, zxr10RMAPSetInterface}
    ::= { zxr10RMAPSetInterfaceTable 1 }
    
Zxr10RMAPSetInterfaceEntry ::=SEQUENCE {
        zxr10RMAPSetInterfaceName      DisplayString,
        zxr10RMAPSetInterfaceSequence  Integer32,
        zxr10RMAPSetInterface          DisplayString,
        zxr10RMAPSetInterfaceRowStatus RowStatus
    }

zxr10RMAPSetInterfaceName  OBJECT-TYPE
    SYNTAX   DisplayString(SIZE(1..31))
    MAX-ACCESS  not-accessible
    STATUS  current
    DESCRIPTION
        "Name of Route-map (1-31 characters)"
    ::= { zxr10RMAPSetInterfaceEntry 1 } 
        
zxr10RMAPSetInterfaceSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetInterfaceEntry 2 }    

zxr10RMAPSetInterface  OBJECT-TYPE
    SYNTAX   DisplayString(SIZE(1..31))
    MAX-ACCESS  not-accessible
    STATUS  current
    DESCRIPTION
        "Interface Name.
         Each sequence has 10 set  interface items at most."
    ::= { zxr10RMAPSetInterfaceEntry 3 }

zxr10RMAPSetInterfaceRowStatus  OBJECT-TYPE
    SYNTAX   RowStatus
    MAX-ACCESS  read-create
    STATUS  current
    DESCRIPTION
        "RowStatus"
    ::= { zxr10RMAPSetInterfaceEntry 100 }

--------------------------------------------------------------
--------------------------------------------------------------
--zxr10RMAPSetIpMetricTable
--------------------------------------------------------------
zxr10RMAPSetIpMetricTable  OBJECT-TYPE
    SYNTAX  SEQUENCE OF Zxr10RMAPSetIpMetricEntry
    MAX-ACCESS  not-accessible
    STATUS  current
    DESCRIPTION
        "Route-map Set IpMetric Table"
    ::= { zxr10RMAPRuleObjects 27 }

zxr10RMAPSetIpMetricEntry  OBJECT-TYPE
    SYNTAX  Zxr10RMAPSetIpMetricEntry
    MAX-ACCESS  not-accessible
    STATUS  current
    DESCRIPTION          
       "Set metric value for destination routing protocol.        
        This set item sets the route-map name with ipv4 type.
        It conflicts with other match or set items 
        which set the route-map name with ipv6 type."
    INDEX  { zxr10RMAPName,  zxr10RMAPSequence}
    ::= { zxr10RMAPSetIpMetricTable 1 }
    
Zxr10RMAPSetIpMetricEntry ::=SEQUENCE {
        zxr10RMAPSetIpMetricName       DisplayString,
        zxr10RMAPSetIpMetricSequence   Integer32,
        zxr10RMAPSetIpMetricAct        RmapSetMetricAct,
        zxr10RMAPSetIpMetricValue      Unsigned32,
        zxr10RMAPSetIpMetricRowStatus  RowStatus
    }

zxr10RMAPSetIpMetricName  OBJECT-TYPE
    SYNTAX   DisplayString(SIZE(1..31))
    MAX-ACCESS  not-accessible
    STATUS  current
    DESCRIPTION
        "Name of Route-map (1-31 characters)"
    ::= { zxr10RMAPSetIpMetricEntry 1 } 
        
zxr10RMAPSetIpMetricSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpMetricEntry 2 }    

zxr10RMAPSetIpMetricAct  OBJECT-TYPE
    SYNTAX   RmapSetMetricAct
    MAX-ACCESS  read-create
    STATUS  current
    DESCRIPTION
        "plus :Add metric.Value is 1.
         minus:Del metric.Value is 2.
         unset:No Action.Value is 0."
    ::= { zxr10RMAPSetIpMetricEntry 3 }

zxr10RMAPSetIpMetricValue  OBJECT-TYPE
    SYNTAX   Unsigned32
    MAX-ACCESS  read-create
    STATUS  current
    DESCRIPTION
        "Metric value.
         The range of config is 0 to 4294967295"
    ::= { zxr10RMAPSetIpMetricEntry 4 }

zxr10RMAPSetIpMetricRowStatus  OBJECT-TYPE
    SYNTAX   RowStatus
    MAX-ACCESS  read-create
    STATUS  current
    DESCRIPTION
        "RowStatus"
    ::= { zxr10RMAPSetIpMetricEntry 100 }

--------------------------------------------------------------
--------------------------------------------------------------
--zxr10RMAPSetIpMetricTypeTable
--------------------------------------------------------------
zxr10RMAPSetIpMetricTypeTable  OBJECT-TYPE
    SYNTAX  SEQUENCE OF Zxr10RMAPSetIpMetricTypeEntry
    MAX-ACCESS  not-accessible
    STATUS  current
    DESCRIPTION
        "Route-map Set IpMetricType Table"
    ::= { zxr10RMAPRuleObjects 28 }

zxr10RMAPSetIpMetricTypeEntry  OBJECT-TYPE
    SYNTAX  Zxr10RMAPSetIpMetricTypeEntry
    MAX-ACCESS  not-accessible
    STATUS  current
    DESCRIPTION          
       "Set type of metric for destination routing protocol.
        This set item sets the route-map name with ipv4 type.
        It conflicts with other match or set items 
        which set the route-map name with ipv6 type."
    INDEX  { zxr10RMAPName,  zxr10RMAPSequence}
    ::= { zxr10RMAPSetIpMetricTypeTable 1 }
    
Zxr10RMAPSetIpMetricTypeEntry ::=SEQUENCE {
        zxr10RMAPSetIpMetricTypeName        DisplayString,
        zxr10RMAPSetIpMetricTypeSequence    Integer32,
        zxr10RMAPSetIpMetricType            RmapSetMetricType,
        zxr10RMAPSetIpMetricTypeRowStat     RowStatus
    }

zxr10RMAPSetIpMetricTypeName  OBJECT-TYPE
    SYNTAX   DisplayString(SIZE(1..31))
    MAX-ACCESS  not-accessible
    STATUS  current
    DESCRIPTION
        "Name of Route-map (1-31 characters)"
    ::= { zxr10RMAPSetIpMetricTypeEntry 1 } 
        
zxr10RMAPSetIpMetricTypeSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpMetricTypeEntry 2 }    

zxr10RMAPSetIpMetricType  OBJECT-TYPE
    SYNTAX   RmapSetMetricType
    MAX-ACCESS  read-create
    STATUS  current
    DESCRIPTION
        "external  IS-IS external metric.Value is 2.
         internal  IS-IS internal metric.Value is 1.
         type-1    OSPF external type 1 metric.Value is 3.
         type-2    OSPF external type 2 metric.Value is 4.
         0 is invalid value."
    ::= { zxr10RMAPSetIpMetricTypeEntry 3 }

zxr10RMAPSetIpMetricTypeRowStat  OBJECT-TYPE
    SYNTAX   RowStatus
    MAX-ACCESS  read-create
    STATUS  current
    DESCRIPTION
        "RowStatus"
    ::= { zxr10RMAPSetIpMetricTypeEntry 100 }

--------------------------------------------------------------
--------------------------------------------------------------
--zxr10RMAPSetIpNextHopTable
--------------------------------------------------------------
zxr10RMAPSetIpNextHopTable  OBJECT-TYPE
    SYNTAX  SEQUENCE OF Zxr10RMAPSetIpNextHopEntry
    MAX-ACCESS  not-accessible
    STATUS  current
    DESCRIPTION
        "Route-map Set IpNextHop Table"
    ::= { zxr10RMAPRuleObjects 29 }

zxr10RMAPSetIpNextHopEntry  OBJECT-TYPE
    SYNTAX  Zxr10RMAPSetIpNextHopEntry
    MAX-ACCESS  not-accessible
    STATUS  current
    DESCRIPTION          
       "Set Next hop address.
        This set item sets the route-map name with ipv4 type.
        It conflicts with other match or set items 
        which set the route-map name with ipv6 type.
        It conflicts with these set items below:
        set vrf
        set global"
    INDEX  { zxr10RMAPName,  zxr10RMAPSequence, zxr10RMAPSetIpNextHop}
    ::= { zxr10RMAPSetIpNextHopTable 1 }
    
Zxr10RMAPSetIpNextHopEntry ::=SEQUENCE {
        zxr10RMAPSetIpNextHopName      DisplayString,
        zxr10RMAPSetIpNextHopSequence  Integer32,
        zxr10RMAPSetIpNextHop          IpAddress,
        zxr10RMAPSetIpNextHopSqa       DisplayString,  
        zxr10RMAPSetIpNextHopRowStatus RowStatus
    }

zxr10RMAPSetIpNextHopName  OBJECT-TYPE
    SYNTAX   DisplayString(SIZE(1..31))
    MAX-ACCESS  not-accessible
    STATUS  current
    DESCRIPTION
        "Name of Route-map (1-31 characters)"
    ::= { zxr10RMAPSetIpNextHopEntry 1 } 
        
zxr10RMAPSetIpNextHopSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpNextHopEntry 2 }    

zxr10RMAPSetIpNextHop  OBJECT-TYPE
    SYNTAX   IpAddress
    MAX-ACCESS  not-accessible
    STATUS  current
    DESCRIPTION
        "IP address of next hop. 0 is invalid value.
         Each sequence has 10 set ip next-hop items at most."
    ::= { zxr10RMAPSetIpNextHopEntry 3 }   
    
zxr10RMAPSetIpNextHopSqa  OBJECT-TYPE
    SYNTAX   DisplayString(SIZE(1..31))
    MAX-ACCESS  read-create
    STATUS  current
    DESCRIPTION
        "Track name.
         This attribut may be setted or not."
    ::= { zxr10RMAPSetIpNextHopEntry 4 }

zxr10RMAPSetIpNextHopRowStatus  OBJECT-TYPE
    SYNTAX   RowStatus
    MAX-ACCESS  read-create
    STATUS  current
    DESCRIPTION
        "RowStatus"
    ::= { zxr10RMAPSetIpNextHopEntry 100 }

--------------------------------------------------------------
--------------------------------------------------------------
--zxr10RMAPSetIpPathTable
--------------------------------------------------------------
zxr10RMAPSetIpPathTable  OBJECT-TYPE
    SYNTAX  SEQUENCE OF Zxr10RMAPSetIpPathEntry
    MAX-ACCESS  not-accessible
    STATUS  current
    DESCRIPTION
        "Route-map Set IpPath Table"
    ::= { zxr10RMAPRuleObjects 30 }

zxr10RMAPSetIpPathEntry  OBJECT-TYPE
    SYNTAX  Zxr10RMAPSetIpPathEntry
    MAX-ACCESS  not-accessible
    STATUS  current
    DESCRIPTION          
       "Set output interface.
        This set item supports these types of interface:
        [PORT_CLASS_FEI,PORT_CLASS_GEI_END].
        This set item sets the route-map name with ipv4 type.
        It conflicts with other match or set items 
        which set the route-map name with ipv6 type.
        It conflicts with these set items below:
        set vrf
        set global"
    INDEX  { zxr10RMAPName,  zxr10RMAPSequence}
    ::= { zxr10RMAPSetIpPathTable 1 }
    
Zxr10RMAPSetIpPathEntry ::=SEQUENCE {
        zxr10RMAPIpPathName            DisplayString,
        zxr10RMAPIpPathSequence        Integer32,
        zxr10RMAPSetIpPathIntf         DisplayString,
        zxr10RMAPSetIpPathNextHop      IpAddress,
        zxr10RMAPSetIpPathRowStatus    RowStatus
    }

zxr10RMAPIpPathName  OBJECT-TYPE
    SYNTAX   DisplayString(SIZE(1..31))
    MAX-ACCESS  not-accessible
    STATUS  current
    DESCRIPTION
        "Name of Route-map (1-31 characters)"
    ::= { zxr10RMAPSetIpPathEntry 1 } 
        
zxr10RMAPIpPathSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpPathEntry 2 }    

zxr10RMAPSetIpPathIntf  OBJECT-TYPE
    SYNTAX   DisplayString(SIZE(1..31))
    MAX-ACCESS  read-create
    STATUS  current
    DESCRIPTION
        "Name of Interface (1-31 characters)"
    ::= { zxr10RMAPSetIpPathEntry 3 } 
        
zxr10RMAPSetIpPathNextHop  OBJECT-TYPE
    SYNTAX   IpAddress
    MAX-ACCESS  read-create
    STATUS  current
    DESCRIPTION
        "IP address of next hop.0 is invalid value."
    ::= { zxr10RMAPSetIpPathEntry 4 }

zxr10RMAPSetIpPathRowStatus  OBJECT-TYPE
    SYNTAX   RowStatus
    MAX-ACCESS  read-create
    STATUS  current
    DESCRIPTION
        "RowStatus"
    ::= { zxr10RMAPSetIpPathEntry 100 }

--------------------------------------------------------------
--------------------------------------------------------------
--zxr10RMAPSetIpPrecTable
--------------------------------------------------------------
zxr10RMAPSetIpPrecTable  OBJECT-TYPE
    SYNTAX  SEQUENCE OF Zxr10RMAPSetIpPrecEntry
    MAX-ACCESS  not-accessible
    STATUS  current
    DESCRIPTION
        "Route-map Set IpPrec Table"
    ::= { zxr10RMAPRuleObjects 31 }

zxr10RMAPSetIpPrecEntry  OBJECT-TYPE
    SYNTAX  Zxr10RMAPSetIpPrecEntry
    MAX-ACCESS  not-accessible
    STATUS  current
    DESCRIPTION          
       "Set precedence field.
        This set item sets the route-map name with ipv4 type.
        It conflicts with other match or set items 
        which set the route-map name with ipv6 type.
        It conflicts with these set items below:
        set dscp.
        If zxr10RMAPSetIpPrec is getted with value 255,
        it expresses this config is invalid."
    INDEX  { zxr10RMAPName,  zxr10RMAPSequence}
    ::= { zxr10RMAPSetIpPrecTable 1 }
    
Zxr10RMAPSetIpPrecEntry ::=SEQUENCE {
        zxr10RMAPSetIpPrecName                  DisplayString,
        zxr10RMAPSetIpPrecSequence              Integer32,
        zxr10RMAPSetIpPrec                      Integer32,
        zxr10RMAPSetIpPrecMap                   RmapSetPrec,
        zxr10RMAPSetIpPrecRowStatus             RowStatus
    }

zxr10RMAPSetIpPrecName  OBJECT-TYPE
    SYNTAX   DisplayString(SIZE(1..31))
    MAX-ACCESS  not-accessible
    STATUS  current
    DESCRIPTION
        "Name of Route-map (1-31 characters)"
    ::= { zxr10RMAPSetIpPrecEntry 1 } 
        
zxr10RMAPSetIpPrecSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpPrecEntry 2 }    

zxr10RMAPSetIpPrec  OBJECT-TYPE
    SYNTAX   Integer32
    MAX-ACCESS  read-create
    STATUS  current
    DESCRIPTION
        "Precedence value.
         The range of config is 0 to 7.
         255 is invalid value.
         If zxr10RMAPSetIpPrec is setted with valid value,
         zxr10RMAPSetIpPrecMap should be setted with 255."
    ::= { zxr10RMAPSetIpPrecEntry 3 }
       
zxr10RMAPSetIpPrecMap  OBJECT-TYPE
    SYNTAX   RmapSetPrec
    MAX-ACCESS  read-create
    STATUS  current
    DESCRIPTION
        "critical        Set critical precedence (6)
         flash           Set flash precedence (4)
         flash-override  Set flash override precedence (5)
         immediate       Set immediate precedence (3)
         internet        Set internetwork control precedence (7)
         network         Set network control precedence (8)
         priority        Set priority precedence (2)
         routine         Set routine precedence (1)
         255 is invalid value.
         If zxr10RMAPSetIpPrecMap is setted with valid value,
         zxr10RMAPSetIpPrec should be setted with 255."
    ::= { zxr10RMAPSetIpPrecEntry 4 }

zxr10RMAPSetIpPrecRowStatus  OBJECT-TYPE
    SYNTAX   RowStatus
    MAX-ACCESS  read-create
    STATUS  current
    DESCRIPTION
        "RowStatus"
    ::= { zxr10RMAPSetIpPrecEntry 100 }

--------------------------------------------------------------
--------------------------------------------------------------
--zxr10RMAPSetIpTagTable
--------------------------------------------------------------
zxr10RMAPSetIpTagTable  OBJECT-TYPE
    SYNTAX  SEQUENCE OF Zxr10RMAPSetIpTagEntry
    MAX-ACCESS  not-accessible
    STATUS  current
    DESCRIPTION
        "Route-map Set IpTag Table"
    ::= { zxr10RMAPRuleObjects 32 }

zxr10RMAPSetIpTagEntry  OBJECT-TYPE
    SYNTAX  Zxr10RMAPSetIpTagEntry
    MAX-ACCESS  not-accessible
    STATUS  current
    DESCRIPTION          
       "Set tag value for destination routing protocol.
        This set item sets the route-map name with ipv4 type.
        It conflicts with other match or set items 
        which set the route-map name with ipv6 type."
    INDEX  { zxr10RMAPName,  zxr10RMAPSequence}
    ::= { zxr10RMAPSetIpTagTable 1 }
    
Zxr10RMAPSetIpTagEntry ::=SEQUENCE {
        zxr10RMAPSetIpTagName                  DisplayString,
        zxr10RMAPSetIpTagSequence              Integer32, 
        zxr10RMAPSetIpTag                      Unsigned32,
        zxr10RMAPSetIpTagRowStatus             RowStatus
    }

zxr10RMAPSetIpTagName  OBJECT-TYPE
    SYNTAX   DisplayString(SIZE(1..31))
    MAX-ACCESS  not-accessible
    STATUS  current
    DESCRIPTION
        "Name of Route-map (1-31 characters)"
    ::= { zxr10RMAPSetIpTagEntry 1 } 
        
zxr10RMAPSetIpTagSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpTagEntry 2 } 
      
zxr10RMAPSetIpTag  OBJECT-TYPE
    SYNTAX   Unsigned32
    MAX-ACCESS  read-create
    STATUS  current
    DESCRIPTION
        "Set tag value for destination routing protocol.
         The range of config is 0 to 4294967295."
    ::= { zxr10RMAPSetIpTagEntry 3 }  

zxr10RMAPSetIpTagRowStatus  OBJECT-TYPE
    SYNTAX   RowStatus
    MAX-ACCESS  read-create
    STATUS  current
    DESCRIPTION
        "RowStatus"
    ::= { zxr10RMAPSetIpTagEntry 100 }

--------------------------------------------------------------
--------------------------------------------------------------
--zxr10RMAPSetIpTosTable
--------------------------------------------------------------
zxr10RMAPSetIpTosTable  OBJECT-TYPE
    SYNTAX  SEQUENCE OF Zxr10RMAPSetIpTosEntry
    MAX-ACCESS  not-accessible
    STATUS  current
    DESCRIPTION
        "Route-map Set IpTos Table"
    ::= { zxr10RMAPRuleObjects 33 }

zxr10RMAPSetIpTosEntry  OBJECT-TYPE
    SYNTAX  Zxr10RMAPSetIpTosEntry
    MAX-ACCESS  not-accessible
    STATUS  current
    DESCRIPTION          
       "Set type of service field.
        This set item sets the route-map name with ipv4 type.
        It conflicts with other match or set items 
        which set the route-map name with ipv6 type.
        It conflicts with these set items below:
        set dscp"
    INDEX  { zxr10RMAPName,  zxr10RMAPSequence}
    ::= { zxr10RMAPSetIpTosTable 1 }
    
Zxr10RMAPSetIpTosEntry ::=SEQUENCE {
        zxr10RMAPSetIpTosName                  DisplayString,
        zxr10RMAPSetIpTosSequence              Integer32,
        zxr10RMAPSetIpTos                      Integer32,
        zxr10RMAPSetIpTosMap                   RmapSetTos,
        zxr10RMAPSetIpTosRowStatus             RowStatus
    }

zxr10RMAPSetIpTosName  OBJECT-TYPE
    SYNTAX   DisplayString(SIZE(1..31))
    MAX-ACCESS  not-accessible
    STATUS  current
    DESCRIPTION
        "Name of Route-map (1-31 characters)"
    ::= { zxr10RMAPSetIpTosEntry 1 } 
        
zxr10RMAPSetIpTosSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpTosEntry 2 }    

zxr10RMAPSetIpTos  OBJECT-TYPE
    SYNTAX   Integer32
    MAX-ACCESS  read-create
    STATUS  current
    DESCRIPTION
        "Type of service value.
         The range of config is 0 to 15.
         255 is invalid value.
         If zxr10RMAPSetIpTos is setted with valid value,
         zxr10RMAPSetIpTosMap should be setted with 255."
    ::= { zxr10RMAPSetIpTosEntry 3 }  
    
zxr10RMAPSetIpTosMap  OBJECT-TYPE
    SYNTAX   RmapSetTos
    MAX-ACCESS  read-create
    STATUS  current
    DESCRIPTION
        "max-reliability    Set max reliable TOS (3)
         max-throughput     Set max throughput TOS (4)
         min-delay          Set min delay TOS (5)
         min-monetary-cost  Set min monetary cost TOS (2)
         normal             Set normal TOS (1)
         255 is invalid value.
         If zxr10RMAPSetIpTosMap is setted with valid value,
         zxr10RMAPSetIpTos should be setted with 255."
    ::= { zxr10RMAPSetIpTosEntry 4 }

zxr10RMAPSetIpTosRowStatus  OBJECT-TYPE
    SYNTAX   RowStatus
    MAX-ACCESS  read-create
    STATUS  current
    DESCRIPTION
        "RowStatus"
    ::= { zxr10RMAPSetIpTosEntry 100 }

--------------------------------------------------------------
--------------------------------------------------------------
--zxr10RMAPSetIpv6MetricTable
--------------------------------------------------------------
zxr10RMAPSetIpv6MetricTable  OBJECT-TYPE
    SYNTAX  SEQUENCE OF Zxr10RMAPSetIpv6MetricEntry
    MAX-ACCESS  not-accessible
    STATUS  current
    DESCRIPTION
        "Route-map Set Ipv6Metric Table"
    ::= { zxr10RMAPRuleObjects 34 }

zxr10RMAPSetIpv6MetricEntry  OBJECT-TYPE
    SYNTAX  Zxr10RMAPSetIpv6MetricEntry
    MAX-ACCESS  not-accessible
    STATUS  current
    DESCRIPTION          
       "Set metric value for destination routing protocol.
        This set item sets the route-map name with ipv6 type.
        It conflicts with other match or set items 
        which set the route-map name with ipv4 type."
    INDEX  { zxr10RMAPName,  zxr10RMAPSequence}
    ::= { zxr10RMAPSetIpv6MetricTable 1 }
    
Zxr10RMAPSetIpv6MetricEntry ::=SEQUENCE {
        zxr10RMAPSetIpv6MetricName      DisplayString,
        zxr10RMAPSetIpv6MetricSequence  Integer32,
        zxr10RMAPSetIpv6MetricAct       RmapSetMetricAct,
        zxr10RMAPSetIpv6MetricValue     Unsigned32,
        zxr10RMAPSetIpv6MetricRowStatus RowStatus
    }

zxr10RMAPSetIpv6MetricName  OBJECT-TYPE
    SYNTAX   DisplayString(SIZE(1..31))
    MAX-ACCESS  not-accessible
    STATUS  current
    DESCRIPTION
        "Name of Route-map (1-31 characters)"
    ::= { zxr10RMAPSetIpv6MetricEntry 1 } 
        
zxr10RMAPSetIpv6MetricSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpv6MetricEntry 2 }    

zxr10RMAPSetIpv6MetricAct  OBJECT-TYPE
    SYNTAX   RmapSetMetricAct
    MAX-ACCESS  read-create
    STATUS  current
    DESCRIPTION
        "plus :Add metric.Value is 1.
         minus:Del metric.Value is 2.
         unset:No Action.Value is 0."
    ::= { zxr10RMAPSetIpv6MetricEntry 3 }

zxr10RMAPSetIpv6MetricValue  OBJECT-TYPE
    SYNTAX   Unsigned32
    MAX-ACCESS  read-create
    STATUS  current
    DESCRIPTION
        "Metric value.
         The range of config is 0 to 4294967295."
    ::= { zxr10RMAPSetIpv6MetricEntry 4 }

zxr10RMAPSetIpv6MetricRowStatus  OBJECT-TYPE
    SYNTAX   RowStatus
    MAX-ACCESS  read-create
    STATUS  current
    DESCRIPTION
        "RowStatus"
    ::= { zxr10RMAPSetIpv6MetricEntry 100 }

--------------------------------------------------------------
--------------------------------------------------------------
--zxr10RMAPSetIpv6MetricTypeTable
--------------------------------------------------------------
zxr10RMAPSetIpv6MetricTypeTable  OBJECT-TYPE
    SYNTAX  SEQUENCE OF Zxr10RMAPSetIpv6MetricTypeEntry
    MAX-ACCESS  not-accessible
    STATUS  current
    DESCRIPTION
        "Route-map Set Ipv6MetricType Table"
    ::= { zxr10RMAPRuleObjects 35 }

zxr10RMAPSetIpv6MetricTypeEntry  OBJECT-TYPE
    SYNTAX  Zxr10RMAPSetIpv6MetricTypeEntry
    MAX-ACCESS  not-accessible
    STATUS  current
    DESCRIPTION          
       "Set type of metric for destination routing protocol.
        This set item sets the route-map name with ipv6 type.
        It conflicts with other match or set items 
        which set the route-map name with ipv4 type."
    INDEX  { zxr10RMAPName,  zxr10RMAPSequence}
    ::= { zxr10RMAPSetIpv6MetricTypeTable 1 }
    
Zxr10RMAPSetIpv6MetricTypeEntry ::=SEQUENCE {
        zxr10RMAPSetIpv6MetricTypeName       DisplayString,
        zxr10RMAPSetIpv6MetricTypeSeq        Integer32,
        zxr10RMAPSetIpv6MetricType           RmapSetMetricType,
        zxr10RMAPSetIpv6MetricTypeRowSta     RowStatus
    }

zxr10RMAPSetIpv6MetricTypeName  OBJECT-TYPE
    SYNTAX   DisplayString(SIZE(1..31))
    MAX-ACCESS  not-accessible
    STATUS  current
    DESCRIPTION
        "Name of Route-map (1-31 characters)"
    ::= { zxr10RMAPSetIpv6MetricTypeEntry 1 } 
        
zxr10RMAPSetIpv6MetricTypeSeq  OBJECT-TYPE
    SYNTAX   Integer32
    MAX-ACCESS  not-accessible
    STATUS  current
    DESCRIPTION
        "The sequence of a route-map.
         The range of config is 0 to 65535.
         Each name of route-map has 100 sequences at most."
    ::= { zxr10RMAPSetIpv6MetricTypeEntry 2 }    

zxr10RMAPSetIpv6MetricType  OBJECT-TYPE
    SYNTAX   RmapSetMetricType
    MAX-ACCESS  read-create
    STATUS  current
    DESCRIPTION
        "external  IS-IS external metric.Value is 2.
         internal  IS-IS internal metric.Value is 1.
         type-1    OSPF external type 1 metric.Value is 3.
         type-2    OSPF external type 2 metric.Value is 4.
         0 is invalid value"
    ::= { zxr10RMAPSetIpv6MetricTypeEntry 3 }

zxr10RMAPSetIpv6MetricTypeRowSta  OBJECT-TYPE
    SYNTAX   RowStatus
    MAX-ACCESS  read-create
    STATUS  current
    DESCRIPTION
        "RowStatus"
    ::= { zxr10RMAPSetIpv6MetricTypeEntry 100 }

--------------------------------------------------------------
--------------------------------------------------------------
--zxr10RMAPSetIpv6NextHopTable
--------------------------------------------------------------
zxr10RMAPSetIpv6NextHopTable  OBJECT-TYPE
    SYNTAX  SEQUENCE OF Zxr10RMAPSetIpv6NextHopEntry
    MAX-ACCESS  not-accessible
    STATUS  current
    DESCRIPTION
        "Route-map Set IpNextHop Table"
    ::= { zxr10RMAPRuleObjects 36 }

zxr10RMAPSetIpv6NextHopEntry  OBJECT-TYPE
    SYNTAX  Zxr10RMAPSetIpv6NextHopEntry
    MAX-ACCESS  not-accessible
    STATUS  current
    DESCRIPTION          
       "Set Next hop address.
        This set item sets the route-map name with ipv6 type.
        It conflicts with other match or set items 
        which set the route-map name with ipv4 type.
        It conflicts with these set items below:
        set vrf
        set global"
    INDEX  { zxr10RMAPName,  zxr10RMAPSequence, zxr10RMAPSetIpv6NextHop}
    ::= { zxr10RMAPSetIpv6NextHopTable 1 }
    
Zxr10RMAPSetIpv6NextHopEntry ::=SEQUENCE {
        zxr10RMAPSetIpv6NextHopName      DisplayString,
        zxr10RMAPSetIpv6NextHopSequence  Integer32,
        zxr10RMAPSetIpv6NextHop          Ipv6Address,  
        zxr10RMAPSetIpv6NextHopRowStatus RowStatus
    }

zxr10RMAPSetIpv6NextHopName  OBJECT-TYPE
    SYNTAX   DisplayString(SIZE(1..31))
    MAX-ACCESS  not-accessible
    STATUS  current
    DESCRIPTION
        "Name of Route-map (1-31 characters)"
    ::= { zxr10RMAPSetIpv6NextHopEntry 1 } 
        
zxr10RMAPSetIpv6NextHopSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpv6NextHopEntry 2 }    

zxr10RMAPSetIpv6NextHop  OBJECT-TYPE
    SYNTAX   Ipv6Address
    MAX-ACCESS  not-accessible
    STATUS  current
    DESCRIPTION
        "<X:X::X:X> IPv6 address of next hop. 0 is invalid value.
         Each sequence has 10 set ipv6 next-hop items at most."
    ::= { zxr10RMAPSetIpv6NextHopEntry 3 }

zxr10RMAPSetIpv6NextHopRowStatus  OBJECT-TYPE
    SYNTAX   RowStatus
    MAX-ACCESS  read-create
    STATUS  current
    DESCRIPTION
        "RowStatus"
    ::= { zxr10RMAPSetIpv6NextHopEntry 100 }

--------------------------------------------------------------
--------------------------------------------------------------
--zxr10RMAPSetIpv6PathTable
--------------------------------------------------------------
zxr10RMAPSetIpv6PathTable  OBJECT-TYPE
    SYNTAX  SEQUENCE OF Zxr10RMAPSetIpv6PathEntry
    MAX-ACCESS  not-accessible
    STATUS  current
    DESCRIPTION
        "Route-map Set Ipv6Path Table"
    ::= { zxr10RMAPRuleObjects 37 }

zxr10RMAPSetIpv6PathEntry  OBJECT-TYPE
    SYNTAX  Zxr10RMAPSetIpv6PathEntry
    MAX-ACCESS  not-accessible
    STATUS  current
    DESCRIPTION          
       "Set output interface.
        This set item supports these types of interface:
        [PORT_CLASS_FEI,PORT_CLASS_GEI_END].
        This set item sets the route-map name with ipv6 type.
        It conflicts with other match or set items 
        which set the route-map name with ipv4 type.
        It conflicts with these set items below:
        set vrf
        set global"
    INDEX  { zxr10RMAPName,  zxr10RMAPSequence}
    ::= { zxr10RMAPSetIpv6PathTable 1 }
    
Zxr10RMAPSetIpv6PathEntry ::=SEQUENCE {
        zxr10RMAPSetIpv6PathName       DisplayString,
        zxr10RMAPSetIpv6PathSequence   Integer32,
        zxr10RMAPSetIpv6PathIntf       DisplayString,
        zxr10RMAPSetIpv6PathNextHop    Ipv6Address,
        zxr10RMAPSetIpv6PathRowStatus  RowStatus
    }

zxr10RMAPSetIpv6PathName  OBJECT-TYPE
    SYNTAX   DisplayString(SIZE(1..31))
    MAX-ACCESS  not-accessible
    STATUS  current
    DESCRIPTION
        "Name of Route-map (1-31 characters)"
    ::= { zxr10RMAPSetIpv6PathEntry 1 } 
        
zxr10RMAPSetIpv6PathSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpv6PathEntry 2 }    

zxr10RMAPSetIpv6PathIntf  OBJECT-TYPE
    SYNTAX   DisplayString(SIZE(1..31))
    MAX-ACCESS  read-create
    STATUS  current
    DESCRIPTION
        "Name of Interface (1-31 characters)"
    ::= { zxr10RMAPSetIpv6PathEntry 3 } 
        
zxr10RMAPSetIpv6PathNextHop  OBJECT-TYPE
    SYNTAX   Ipv6Address
    MAX-ACCESS  read-create
    STATUS  current
    DESCRIPTION
        "<X:X::X:X> IPv6 address of next hop.0 is invalid value."
    ::= { zxr10RMAPSetIpv6PathEntry 4 }

zxr10RMAPSetIpv6PathRowStatus  OBJECT-TYPE
    SYNTAX   RowStatus
    MAX-ACCESS  read-create
    STATUS  current
    DESCRIPTION
        "RowStatus"
    ::= { zxr10RMAPSetIpv6PathEntry 100 }

--------------------------------------------------------------
--------------------------------------------------------------
--zxr10RMAPSetIpv6PrecTable
--------------------------------------------------------------
zxr10RMAPSetIpv6PrecTable  OBJECT-TYPE
    SYNTAX  SEQUENCE OF Zxr10RMAPSetIpv6PrecEntry
    MAX-ACCESS  not-accessible
    STATUS  current
    DESCRIPTION
        "Route-map Set Ipv6Prec Table"
    ::= { zxr10RMAPRuleObjects 38 }

zxr10RMAPSetIpv6PrecEntry  OBJECT-TYPE
    SYNTAX  Zxr10RMAPSetIpv6PrecEntry
    MAX-ACCESS  not-accessible
    STATUS  current
    DESCRIPTION          
       "Set precedence field.
        This set item sets the route-map name with ipv6 type.
        It conflicts with other match or set items 
        which set the route-map name with ipv4 type.
        It conflicts with these set items below:
        set dscp
        255 is invalid value."
    INDEX  { zxr10RMAPName,  zxr10RMAPSequence}
    ::= { zxr10RMAPSetIpv6PrecTable 1 }
    
Zxr10RMAPSetIpv6PrecEntry ::=SEQUENCE {
        zxr10RMAPSetIpv6precName       DisplayString,
        zxr10RMAPSetIpv6precSequence   Integer32,
        zxr10RMAPSetIpv6prec           Integer32,
        zxr10RMAPSetIpv6precMap        RmapSetPrec,
        zxr10RMAPSetIpv6precRowStatus  RowStatus
    }

zxr10RMAPSetIpv6precName  OBJECT-TYPE
    SYNTAX   DisplayString(SIZE(1..31))
    MAX-ACCESS  not-accessible
    STATUS  current
    DESCRIPTION
        "Name of Route-map (1-31 characters)"
    ::= { zxr10RMAPSetIpv6PrecEntry 1 } 
        
zxr10RMAPSetIpv6precSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpv6PrecEntry 2 }    

zxr10RMAPSetIpv6prec  OBJECT-TYPE
    SYNTAX   Integer32
    MAX-ACCESS  read-create
    STATUS  current
    DESCRIPTION
        "Precedence value. 255 is invalid.
         The range of config is 0 to 7.
         If zxr10RMAPSetIpv6prec is setted with valid value,
         zxr10RMAPSetIpv6precMap should be setted with 255."
    ::= { zxr10RMAPSetIpv6PrecEntry 3 }
    
zxr10RMAPSetIpv6precMap  OBJECT-TYPE
    SYNTAX   RmapSetPrec
    MAX-ACCESS  read-create
    STATUS  current
    DESCRIPTION
        "critical        Set critical precedence (6)
         flash           Set flash precedence (4)
         flash-override  Set flash override precedence (5)
         immediate       Set immediate precedence (3)
         internet        Set internetwork control precedence (7)
         network         Set network control precedence (8)
         priority        Set priority precedence (2)
         routine         Set routine precedence (1)
         255 is invalid value.
         If zxr10RMAPSetIpv6precMap is setted with valid value,
         zxr10RMAPSetIpv6prec should be setted with 255."
    ::= { zxr10RMAPSetIpv6PrecEntry 4 }
 
zxr10RMAPSetIpv6precRowStatus  OBJECT-TYPE
    SYNTAX   RowStatus
    MAX-ACCESS  read-create
    STATUS  current
    DESCRIPTION
        "RowStatus"
    ::= { zxr10RMAPSetIpv6PrecEntry 100 }

--------------------------------------------------------------
--------------------------------------------------------------
--zxr10RMAPSetIpv6TagTable
--------------------------------------------------------------
zxr10RMAPSetIpv6TagTable  OBJECT-TYPE
    SYNTAX  SEQUENCE OF Zxr10RMAPSetIpv6TagEntry
    MAX-ACCESS  not-accessible
    STATUS  current
    DESCRIPTION
        "Route-map Set Ipv6Tag Table"
    ::= { zxr10RMAPRuleObjects 39 }

zxr10RMAPSetIpv6TagEntry  OBJECT-TYPE
    SYNTAX  Zxr10RMAPSetIpv6TagEntry
    MAX-ACCESS  not-accessible
    STATUS  current
    DESCRIPTION          
       "Set tag value for destination routing protocol.
        This set item sets the route-map name with ipv6 type.
        It conflicts with other match or set items 
        which set the route-map name with ipv4 type."
    INDEX  { zxr10RMAPName,  zxr10RMAPSequence}
    ::= { zxr10RMAPSetIpv6TagTable 1 }
    
Zxr10RMAPSetIpv6TagEntry ::=SEQUENCE {
        zxr10RMAPSetIpv6TagName        DisplayString,
        zxr10RMAPSetIpv6TagSequence    Integer32,
        zxr10RMAPSetIpv6Tag            Unsigned32,
        zxr10RMAPSetIpv6TagRowStatus   RowStatus
    }

zxr10RMAPSetIpv6TagName  OBJECT-TYPE
    SYNTAX   DisplayString(SIZE(1..31))
    MAX-ACCESS  not-accessible
    STATUS  current
    DESCRIPTION
        "Name of Route-map (1-31 characters)"
    ::= { zxr10RMAPSetIpv6TagEntry 1 } 
        
zxr10RMAPSetIpv6TagSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpv6TagEntry 2 }    
    
zxr10RMAPSetIpv6Tag  OBJECT-TYPE
    SYNTAX   Unsigned32
    MAX-ACCESS  read-create
    STATUS  current
    DESCRIPTION
        "Precedence value.
         The range of config is 0 to 4294967295."
    ::= { zxr10RMAPSetIpv6TagEntry 3 }  

zxr10RMAPSetIpv6TagRowStatus  OBJECT-TYPE
    SYNTAX   RowStatus
    MAX-ACCESS  read-create
    STATUS  current
    DESCRIPTION
        "RowStatus"
    ::= { zxr10RMAPSetIpv6TagEntry 100 }

--------------------------------------------------------------
--------------------------------------------------------------
--zxr10RMAPSetIpv6TrafficTable
--------------------------------------------------------------
zxr10RMAPSetIpv6TrafficTable  OBJECT-TYPE
    SYNTAX  SEQUENCE OF Zxr10RMAPSetIpv6TrafficEntry
    MAX-ACCESS  not-accessible
    STATUS  current
    DESCRIPTION
        "Route-map Set Ipv6Traffic Table"
    ::= { zxr10RMAPRuleObjects 40 }

zxr10RMAPSetIpv6TrafficEntry  OBJECT-TYPE
    SYNTAX  Zxr10RMAPSetIpv6TrafficEntry
    MAX-ACCESS  not-accessible
    STATUS  current
    DESCRIPTION          
       "Set IPv6 traffic-class.
        This set item sets the route-map name with ipv6 type.
        It conflicts with other match or set items 
        which set the route-map name with ipv4 type.
        It conflicts with these set items below:
        set dscp"
    INDEX  { zxr10RMAPName,  zxr10RMAPSequence}
    ::= { zxr10RMAPSetIpv6TrafficTable 1 }
    
Zxr10RMAPSetIpv6TrafficEntry ::=SEQUENCE {
        zxr10RMAPSetIpv6TrafficName                  DisplayString,
        zxr10RMAPSetIpv6TrafficSequence              Integer32, 
        zxr10RMAPSetIpv6Traffic                      Integer32,
        zxr10RMAPSetIpv6TrafficRowStatus             RowStatus
    }

zxr10RMAPSetIpv6TrafficName  OBJECT-TYPE
    SYNTAX   DisplayString(SIZE(1..31))
    MAX-ACCESS  not-accessible
    STATUS  current
    DESCRIPTION
        "Name of Route-map (1-31 characters)"
    ::= { zxr10RMAPSetIpv6TrafficEntry 1 } 
        
zxr10RMAPSetIpv6TrafficSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetIpv6TrafficEntry 2 }    

zxr10RMAPSetIpv6Traffic  OBJECT-TYPE
    SYNTAX   Integer32
    MAX-ACCESS  read-create
    STATUS  current
    DESCRIPTION
        "Value of IPv6 traffic-class.
         The range of config is 0 to 255."
    ::= { zxr10RMAPSetIpv6TrafficEntry 3 }  

zxr10RMAPSetIpv6TrafficRowStatus  OBJECT-TYPE
    SYNTAX   RowStatus
    MAX-ACCESS  read-create
    STATUS  current
    DESCRIPTION
        "RowStatus"
    ::= { zxr10RMAPSetIpv6TrafficEntry 100 }

--------------------------------------------------------------
--------------------------------------------------------------
--zxr10RMAPSetLevelTable
--------------------------------------------------------------
zxr10RMAPSetLevelTable  OBJECT-TYPE
    SYNTAX  SEQUENCE OF Zxr10RMAPSetLevelEntry
    MAX-ACCESS  not-accessible
    STATUS  current
    DESCRIPTION
        "Route-map Set Level Table"
    ::= { zxr10RMAPRuleObjects 41 }

zxr10RMAPSetLevelEntry  OBJECT-TYPE
    SYNTAX  Zxr10RMAPSetLevelEntry
    MAX-ACCESS  not-accessible
    STATUS  current
    DESCRIPTION          
       "Set where to import route"
    INDEX  { zxr10RMAPName,  zxr10RMAPSequence}
    ::= { zxr10RMAPSetLevelTable 1 }
    
Zxr10RMAPSetLevelEntry ::=SEQUENCE {
        zxr10RMAPSetLevelName                  DisplayString,
        zxr10RMAPSetLevelSequence              Integer32,
        zxr10RMAPSetLevel                      RmapSetLevel,
        zxr10RMAPSetLevelRowStatus             RowStatus
    }

zxr10RMAPSetLevelName  OBJECT-TYPE
    SYNTAX   DisplayString(SIZE(1..31))
    MAX-ACCESS  not-accessible
    STATUS  current
    DESCRIPTION
        "Name of Route-map (1-31 characters)"
    ::= { zxr10RMAPSetLevelEntry 1 } 
        
zxr10RMAPSetLevelSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetLevelEntry 2 }    

zxr10RMAPSetLevel  OBJECT-TYPE
    SYNTAX   RmapSetLevel
    MAX-ACCESS  read-create
    STATUS  current
    DESCRIPTION
        "level-1    Import into a level-1 area.Value is 1.
         level-1-2  Import into level-1 and level-2.Value is 3.
         level-2    Import into level-2 sub-domain.Value is 2.
         0 is invalid value."
    ::= { zxr10RMAPSetLevelEntry 3 }  

zxr10RMAPSetLevelRowStatus  OBJECT-TYPE
    SYNTAX   RowStatus
    MAX-ACCESS  read-create
    STATUS  current
    DESCRIPTION
        "RowStatus"
    ::= { zxr10RMAPSetLevelEntry 100 }

--------------------------------------------------------------
--------------------------------------------------------------
--zxr10RMAPSetLocalPreTable
--------------------------------------------------------------
zxr10RMAPSetLocalPreTable  OBJECT-TYPE
    SYNTAX  SEQUENCE OF Zxr10RMAPSetLocalPreEntry
    MAX-ACCESS  not-accessible
    STATUS  current
    DESCRIPTION
        "Route-map Set LocalPreference Table"
    ::= { zxr10RMAPRuleObjects 42 }

zxr10RMAPSetLocalPreEntry  OBJECT-TYPE
    SYNTAX  Zxr10RMAPSetLocalPreEntry
    MAX-ACCESS  not-accessible
    STATUS  current
    DESCRIPTION          
       "Set BGP local preference path attribute."
    INDEX  { zxr10RMAPName,  zxr10RMAPSequence}
    ::= { zxr10RMAPSetLocalPreTable 1 }
    
Zxr10RMAPSetLocalPreEntry ::=SEQUENCE {
        zxr10RMAPSetLocalPreName                  DisplayString,
        zxr10RMAPSetLocalPreSequence              Integer32, 
        zxr10RMAPSetLocalPre                      Unsigned32,
        zxr10RMAPSetLocalPreAct                   RmapSetLocalPreAct,
        zxr10RMAPSetLocalPreRowStatus             RowStatus
    }

zxr10RMAPSetLocalPreName  OBJECT-TYPE
    SYNTAX   DisplayString(SIZE(1..31))
    MAX-ACCESS  not-accessible
    STATUS  current
    DESCRIPTION
        "Name of Route-map (1-31 characters)"
    ::= { zxr10RMAPSetLocalPreEntry 1 } 
        
zxr10RMAPSetLocalPreSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetLocalPreEntry 2 }    
    
zxr10RMAPSetLocalPre  OBJECT-TYPE
    SYNTAX   Unsigned32
    MAX-ACCESS  read-create
    STATUS  current
    DESCRIPTION
        "Preference value.
         The range of config is 0 to 4294967295."
    ::= { zxr10RMAPSetLocalPreEntry 3 }  

zxr10RMAPSetLocalPreAct  OBJECT-TYPE
    SYNTAX   RmapSetLocalPreAct
    MAX-ACCESS  read-create
    STATUS  current
    DESCRIPTION
        "plus :Add local preference.Value is 1.
         minus:Del local preference.Value is 2.
         unset:No Action.Value is 0."
    ::= { zxr10RMAPSetLocalPreEntry 4 }

zxr10RMAPSetLocalPreRowStatus  OBJECT-TYPE
    SYNTAX   RowStatus
    MAX-ACCESS  read-create
    STATUS  current
    DESCRIPTION
        "RowStatus"
    ::= { zxr10RMAPSetLocalPreEntry 100 }

--------------------------------------------------------------
--------------------------------------------------------------
--zxr10RMAPSetMplsTable
--------------------------------------------------------------
zxr10RMAPSetMplsTable  OBJECT-TYPE
    SYNTAX  SEQUENCE OF Zxr10RMAPSetMplsEntry
    MAX-ACCESS  not-accessible
    STATUS  current
    DESCRIPTION
        "Route-map Set Mpls-label Table"
    ::= { zxr10RMAPRuleObjects 43 }

zxr10RMAPSetMplsEntry  OBJECT-TYPE
    SYNTAX  Zxr10RMAPSetMplsEntry
    MAX-ACCESS  not-accessible
    STATUS  current
    DESCRIPTION          
       "Set MPLS label for prefix"
    INDEX  { zxr10RMAPName,  zxr10RMAPSequence}
    ::= { zxr10RMAPSetMplsTable 1 }
    
Zxr10RMAPSetMplsEntry ::=SEQUENCE {
        zxr10RMAPSetMplsName                  DisplayString,
        zxr10RMAPSetMplsSequence              Integer32,
        zxr10RMAPSetMpls                      TruthValue,
        zxr10RMAPSetMplsRowStatus             RowStatus
    }

zxr10RMAPSetMplsName  OBJECT-TYPE
    SYNTAX   DisplayString(SIZE(1..31))
    MAX-ACCESS  not-accessible
    STATUS  current
    DESCRIPTION
        "Name of Route-map (1-31 characters)"
    ::= { zxr10RMAPSetMplsEntry 1 } 
        
zxr10RMAPSetMplsSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetMplsEntry 2 }    

zxr10RMAPSetMpls  OBJECT-TYPE
    SYNTAX   TruthValue
    MAX-ACCESS  read-create
    STATUS  current
    DESCRIPTION
        "Set MPLS label for prefix.
         It expresses that  whether this config is valid or not."
    ::= { zxr10RMAPSetMplsEntry 3 } 

zxr10RMAPSetMplsRowStatus  OBJECT-TYPE
    SYNTAX   RowStatus
    MAX-ACCESS  read-create
    STATUS  current
    DESCRIPTION
        "RowStatus"
    ::= { zxr10RMAPSetMplsEntry 100 }

--------------------------------------------------------------
--------------------------------------------------------------
--zxr10RMAPSetNextHopTable
--------------------------------------------------------------
zxr10RMAPSetNextHopTable  OBJECT-TYPE
    SYNTAX  SEQUENCE OF Zxr10RMAPSetNextHopEntry
    MAX-ACCESS  not-accessible
    STATUS  current
    DESCRIPTION
        "Route-map Set NextHop Table"
    ::= { zxr10RMAPRuleObjects 44 }

zxr10RMAPSetNextHopEntry  OBJECT-TYPE
    SYNTAX  Zxr10RMAPSetNextHopEntry
    MAX-ACCESS  not-accessible
    STATUS  current
    DESCRIPTION          
       "Set IP address of next hop.
        It conflicts with these set items below:
        set vrf
        set global"
    INDEX  { zxr10RMAPName,  zxr10RMAPSequence, zxr10RMAPSetNextHop}
    ::= { zxr10RMAPSetNextHopTable 1 }
    
Zxr10RMAPSetNextHopEntry ::=SEQUENCE {
        zxr10RMAPSetNextHopName        DisplayString,
        zxr10RMAPSetNextHopSequence    Integer32,
        zxr10RMAPSetNextHop            IpAddress,  
        zxr10RMAPSetNextHopRowStatus   RowStatus
    }

zxr10RMAPSetNextHopName  OBJECT-TYPE
    SYNTAX   DisplayString(SIZE(1..31))
    MAX-ACCESS  not-accessible
    STATUS  current
    DESCRIPTION
        "Name of Route-map (1-31 characters)"
    ::= { zxr10RMAPSetNextHopEntry 1 } 
        
zxr10RMAPSetNextHopSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetNextHopEntry 2 }    

zxr10RMAPSetNextHop  OBJECT-TYPE
    SYNTAX   IpAddress
    MAX-ACCESS  not-accessible
    STATUS  current
    DESCRIPTION
        "IP address of next hop. 0 is invalid value.
         Each sequence has 10 set next-hop items at most."
    ::= { zxr10RMAPSetNextHopEntry 3 }

zxr10RMAPSetNextHopRowStatus  OBJECT-TYPE
    SYNTAX   RowStatus
    MAX-ACCESS  read-create
    STATUS  current
    DESCRIPTION
        "RowStatus"
    ::= { zxr10RMAPSetNextHopEntry 100 }

--------------------------------------------------------------
--------------------------------------------------------------
--zxr10RMAPSetOriginTable
--------------------------------------------------------------
zxr10RMAPSetOriginTable  OBJECT-TYPE
    SYNTAX  SEQUENCE OF Zxr10RMAPSetOriginEntry
    MAX-ACCESS  not-accessible
    STATUS  current
    DESCRIPTION
        "Route-map Set Origin Table"
    ::= { zxr10RMAPRuleObjects 45 }

zxr10RMAPSetOriginEntry  OBJECT-TYPE
    SYNTAX  Zxr10RMAPSetOriginEntry
    MAX-ACCESS  not-accessible
    STATUS  current
    DESCRIPTION          
       "Set BGP origin code"
    INDEX  { zxr10RMAPName,  zxr10RMAPSequence}
    ::= { zxr10RMAPSetOriginTable 1 }
    
Zxr10RMAPSetOriginEntry ::=SEQUENCE {
        zxr10RMAPSetOriginName                  DisplayString,
        zxr10RMAPSetOriginSequence              Integer32,
        zxr10RMAPSetOrigin                      RmapSetOrigin,
        zxr10RMAPSetOriginRowStatus             RowStatus
    }

zxr10RMAPSetOriginName  OBJECT-TYPE
    SYNTAX   DisplayString(SIZE(1..31))
    MAX-ACCESS  not-accessible
    STATUS  current
    DESCRIPTION
        "Name of Route-map (1-31 characters)"
    ::= { zxr10RMAPSetOriginEntry 1 } 
        
zxr10RMAPSetOriginSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetOriginEntry 2 }    

zxr10RMAPSetOrigin  OBJECT-TYPE
    SYNTAX   RmapSetOrigin
    MAX-ACCESS  read-create
    STATUS  current
    DESCRIPTION
        "egp         Remote EGP.Value is 2.
         igp         Local IGP.Value is 1.
         incomplete  Unknown heritage.Value is 3.
         0 is invalid value."
    ::= { zxr10RMAPSetOriginEntry 3 } 

zxr10RMAPSetOriginRowStatus  OBJECT-TYPE
    SYNTAX   RowStatus
    MAX-ACCESS  read-create
    STATUS  current
    DESCRIPTION
        "RowStatus"
    ::= { zxr10RMAPSetOriginEntry 100 }

--------------------------------------------------------------
--------------------------------------------------------------
--zxr10RMAPSetQosIdTable
--------------------------------------------------------------
zxr10RMAPSetQosIdTable  OBJECT-TYPE
    SYNTAX  SEQUENCE OF Zxr10RMAPSetQosIdEntry
    MAX-ACCESS  not-accessible
    STATUS  current
    DESCRIPTION
        "Route-map Set QosId Table"
    ::= { zxr10RMAPRuleObjects 46 }

zxr10RMAPSetQosIdEntry  OBJECT-TYPE
    SYNTAX  Zxr10RMAPSetQosIdEntry
    MAX-ACCESS  not-accessible
    STATUS  current
    DESCRIPTION          
       "Set QoS ID of routing"
    INDEX  { zxr10RMAPName,  zxr10RMAPSequence}
    ::= { zxr10RMAPSetQosIdTable 1 }
    
Zxr10RMAPSetQosIdEntry ::=SEQUENCE {
        zxr10RMAPSetQosIdName          DisplayString,
        zxr10RMAPSetQosIdSequence      Integer32,
        zxr10RMAPSetQosId              Integer32,
        zxr10RMAPSetQosIdRowStatus     RowStatus
    }

zxr10RMAPSetQosIdName  OBJECT-TYPE
    SYNTAX   DisplayString(SIZE(1..31))
    MAX-ACCESS  not-accessible
    STATUS  current
    DESCRIPTION
        "Name of Route-map (1-31 characters)"
    ::= { zxr10RMAPSetQosIdEntry 1 } 
        
zxr10RMAPSetQosIdSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetQosIdEntry 2 }    

zxr10RMAPSetQosId  OBJECT-TYPE
    SYNTAX   Integer32
    MAX-ACCESS  read-create
    STATUS  current
    DESCRIPTION
        "QoS ID.
         The range of config is 1 to 16000.
         0 is invalid value."
    ::= { zxr10RMAPSetQosIdEntry 3 } 

zxr10RMAPSetQosIdRowStatus  OBJECT-TYPE
    SYNTAX   RowStatus
    MAX-ACCESS  read-create
    STATUS  current
    DESCRIPTION
        "RowStatus"
    ::= { zxr10RMAPSetQosIdEntry 100 }

--------------------------------------------------------------
--------------------------------------------------------------
--zxr10RMAPSetVrfTable
--------------------------------------------------------------
zxr10RMAPSetVrfTable  OBJECT-TYPE
    SYNTAX  SEQUENCE OF Zxr10RMAPSetVrfEntry
    MAX-ACCESS  not-accessible
    STATUS  current
    DESCRIPTION
        "Route-map Set Vrf Table"
    ::= { zxr10RMAPRuleObjects 47 }

zxr10RMAPSetVrfEntry  OBJECT-TYPE
    SYNTAX  Zxr10RMAPSetVrfEntry
    MAX-ACCESS  not-accessible
    STATUS  current
    DESCRIPTION          
       "Set virtual route forwarding name.
        This set item sets the route-map name with ipv4 type.
        It conflicts with other match or set items 
        which set the route-map name with ipv6 type.
        It conflicts with these set items below:
        set interface
        set ip next-hop
        set ipv6 next-hop
        set next-hop
        set global"
    INDEX  { zxr10RMAPName,  zxr10RMAPSequence}
    ::= { zxr10RMAPSetVrfTable 1 }
    
Zxr10RMAPSetVrfEntry ::=SEQUENCE {
        zxr10RMAPSetVrfName            DisplayString,
        zxr10RMAPSetVrfSequence        Integer32,
        zxr10RMAPSetVrf                DisplayString,
        zxr10RMAPSetVrfNextHop         IpAddress, 
        zxr10RMAPSetVrfSqa             DisplayString,
        zxr10RMAPSetVrfIpConst         RmapSetVrfIpConst,
        zxr10RMAPSetVrfNextHopConst    RmapSetVrfNextHopConst,
        zxr10RMAPSetVrfRowStatus       RowStatus
    }

zxr10RMAPSetVrfName  OBJECT-TYPE
    SYNTAX   DisplayString(SIZE(1..31))
    MAX-ACCESS  not-accessible
    STATUS  current
    DESCRIPTION
        "Name of Route-map (1-31 characters)"
    ::= { zxr10RMAPSetVrfEntry 1 } 
        
zxr10RMAPSetVrfSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetVrfEntry 2 }    

zxr10RMAPSetVrf  OBJECT-TYPE
    SYNTAX   DisplayString(SIZE(1..32))
    MAX-ACCESS  read-create
    STATUS  current
    DESCRIPTION
        "Virtual route forwarding name"
    ::= { zxr10RMAPSetVrfEntry 3 } 

zxr10RMAPSetVrfNextHop  OBJECT-TYPE
    SYNTAX   IpAddress
    MAX-ACCESS  read-create
    STATUS  current
    DESCRIPTION
        "IP address of next hop. 0 is invalid value.
         This attribut may be setted or not."
    ::= { zxr10RMAPSetVrfEntry 4 } 
    
zxr10RMAPSetVrfSqa  OBJECT-TYPE
    SYNTAX   DisplayString(SIZE(1..31))
    MAX-ACCESS  read-create
    STATUS  current
    DESCRIPTION
        "Track name.
         This attribut may be setted or not."
    ::= { zxr10RMAPSetVrfEntry 5 } 
    
zxr10RMAPSetVrfIpConst  OBJECT-TYPE
    SYNTAX   RmapSetVrfIpConst
    MAX-ACCESS  read-create
    STATUS  current
    DESCRIPTION
        "If zxr10RMAPSetVrfNextHop is setted, this attribute
         should be setted with value 1."
    ::= { zxr10RMAPSetVrfEntry 6 }
    
zxr10RMAPSetVrfNextHopConst  OBJECT-TYPE
    SYNTAX   RmapSetVrfNextHopConst
    MAX-ACCESS  read-create
    STATUS  current
    DESCRIPTION
        "If zxr10RMAPSetVrfNextHop is setted, this attribute
         should be setted with value 2."
    ::= { zxr10RMAPSetVrfEntry 7 }  

zxr10RMAPSetVrfRowStatus  OBJECT-TYPE
    SYNTAX   RowStatus
    MAX-ACCESS  read-create
    STATUS  current
    DESCRIPTION
        "RowStatus"
    ::= { zxr10RMAPSetVrfEntry 100 }  
    
--------------------------------------------------------------
--------------------------------------------------------------
--zxr10RMAPMatchAsLenTable
--------------------------------------------------------------
zxr10RMAPMatchAsLenTable  OBJECT-TYPE
    SYNTAX  SEQUENCE OF Zxr10RMAPMatchAsLenEntry
    MAX-ACCESS  not-accessible
    STATUS  current
    DESCRIPTION
        "Route-map Match As-path-length Table"
    ::= { zxr10RMAPRuleObjects 48 }

zxr10RMAPMatchAsLenEntry  OBJECT-TYPE
    SYNTAX  Zxr10RMAPMatchAsLenEntry
    MAX-ACCESS  not-accessible
    STATUS  current
    DESCRIPTION          
       "Match BGP as-path-length"
    INDEX  { zxr10RMAPName,  zxr10RMAPSequence}
    ::= { zxr10RMAPMatchAsLenTable 1 }
    
Zxr10RMAPMatchAsLenEntry ::=SEQUENCE {
        zxr10RMAPMatchAsLenName         DisplayString,
        zxr10RMAPMatchAsLenSequence     Integer32, 
        zxr10RMAPMatchAsLenAlg          RmapMatchAlg,
        zxr10RMAPMatchAsLen             Integer32,
        zxr10RMAPMatchAsLenRowStatus    RowStatus
    }

zxr10RMAPMatchAsLenName  OBJECT-TYPE
    SYNTAX   DisplayString(SIZE(1..31))
    MAX-ACCESS  not-accessible
    STATUS  current
    DESCRIPTION
        "Name of Route-map (1-31 characters)"
    ::= { zxr10RMAPMatchAsLenEntry 1 } 
        
zxr10RMAPMatchAsLenSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchAsLenEntry 2 }    

zxr10RMAPMatchAsLenAlg  OBJECT-TYPE
    SYNTAX   RmapMatchAlg
    MAX-ACCESS  read-create
    STATUS  current
    DESCRIPTION
        "eq  Equal as-path length to be matched.Value is 1.
         ge  Minimum as-path length to be matched.Value is 2.
         le  Maximun as-path length to be matched.Value is 3."
    ::= { zxr10RMAPMatchAsLenEntry 3 } 

zxr10RMAPMatchAsLen  OBJECT-TYPE
    SYNTAX   Integer32(0..255)
    MAX-ACCESS  read-create
    STATUS  current
    DESCRIPTION
        "As-path length.
         The range of config is 0 to 255."
    ::= { zxr10RMAPMatchAsLenEntry 4 } 
     
zxr10RMAPMatchAsLenRowStatus  OBJECT-TYPE
    SYNTAX   RowStatus
    MAX-ACCESS  read-create
    STATUS  current
    DESCRIPTION
        "RowStatus"
    ::= { zxr10RMAPMatchAsLenEntry 100 } 
    
--------------------------------------------------------------
--------------------------------------------------------------
--zxr10RMAPMatchAsUnqLenTable
--------------------------------------------------------------
zxr10RMAPMatchAsUnqLenTable  OBJECT-TYPE
    SYNTAX  SEQUENCE OF Zxr10RMAPMatchAsUnqLenEntry
    MAX-ACCESS  not-accessible
    STATUS  current
    DESCRIPTION
        "Route-map Match As-path-unique-length Table"
    ::= { zxr10RMAPRuleObjects 49 }

zxr10RMAPMatchAsUnqLenEntry  OBJECT-TYPE
    SYNTAX  Zxr10RMAPMatchAsUnqLenEntry
    MAX-ACCESS  not-accessible
    STATUS  current
    DESCRIPTION          
       "Match BGP as-path-unique-length"
    INDEX  { zxr10RMAPName,  zxr10RMAPSequence}
    ::= { zxr10RMAPMatchAsUnqLenTable 1 }
    
Zxr10RMAPMatchAsUnqLenEntry ::=SEQUENCE {
        zxr10RMAPMatchAsUnqLenName         DisplayString,
        zxr10RMAPMatchAsUnqLenSequence     Integer32, 
        zxr10RMAPMatchAsUnqLenAlg          RmapMatchAlg,
        zxr10RMAPMatchAsUnqLen             Integer32,
        zxr10RMAPMatchAsUnqLenRowStatus    RowStatus
    }

zxr10RMAPMatchAsUnqLenName  OBJECT-TYPE
    SYNTAX   DisplayString(SIZE(1..31))
    MAX-ACCESS  not-accessible
    STATUS  current
    DESCRIPTION
        "Name of Route-map (1-31 characters)"
    ::= { zxr10RMAPMatchAsUnqLenEntry 1 } 
        
zxr10RMAPMatchAsUnqLenSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchAsUnqLenEntry 2 }    

zxr10RMAPMatchAsUnqLenAlg  OBJECT-TYPE
    SYNTAX   RmapMatchAlg
    MAX-ACCESS  read-create
    STATUS  current
    DESCRIPTION
        "eq  Equal as-path length to be matched.Value is 1.
         ge  Minimum as-path length to be matched.Value is 2.
         le  Maximun as-path length to be matched.Value is 3."
    ::= { zxr10RMAPMatchAsUnqLenEntry 3 } 

zxr10RMAPMatchAsUnqLen  OBJECT-TYPE
    SYNTAX   Integer32(0..255)
    MAX-ACCESS  read-create
    STATUS  current
    DESCRIPTION
        "As-path unique length.
         The range of config is 0 to 255."
    ::= { zxr10RMAPMatchAsUnqLenEntry 4 } 
     
zxr10RMAPMatchAsUnqLenRowStatus  OBJECT-TYPE
    SYNTAX   RowStatus
    MAX-ACCESS  read-create
    STATUS  current
    DESCRIPTION
        "RowStatus"
    ::= { zxr10RMAPMatchAsUnqLenEntry 100 }   
    
--------------------------------------------------------------
--------------------------------------------------------------
--zxr10RMAPMatchIpSourceAclTable
--------------------------------------------------------------
zxr10RMAPMatchIpSourceAclTable  OBJECT-TYPE
    SYNTAX  SEQUENCE OF Zxr10RMAPMatchIpSourceAclEntry
    MAX-ACCESS  not-accessible
    STATUS  current
    DESCRIPTION
        "Route-map Match IpSource Table(match ip source by acl)."
    ::= { zxr10RMAPRuleObjects 50 }

zxr10RMAPMatchIpSourceAclEntry  OBJECT-TYPE
    SYNTAX  Zxr10RMAPMatchIpSourceAclEntry
    MAX-ACCESS  not-accessible
    STATUS  current
    DESCRIPTION          
       "Match source ip address of route or match packet.
        This match item sets the route-map name with ipv4 type.
        It conflicts with other match or set items 
        which set the route-map name with ipv6 type.
        Otherwise, It conflicts with the item that match ip source by pfl.
        If zxr10RMAPsourceIsConfigAcl is true,it expresses that this config 
        is match ip source by acl."
    INDEX  { zxr10RMAPName,  zxr10RMAPSequence, zxr10RMAPSourceAclName, zxr10RMAPSourceIsConfigAcl}
    ::= { zxr10RMAPMatchIpSourceAclTable 1 }
    
Zxr10RMAPMatchIpSourceAclEntry ::=SEQUENCE {
        zxr10RMAPMatchSourceAclName               DisplayString,
        zxr10RMAPMatchSourceAclSequence           Integer32,
        zxr10RMAPSourceAclName                    DisplayString,
        zxr10RMAPSourceIsConfigAcl                TruthValue,
        zxr10RMAPMatchSourceAclRowStatus          RowStatus
    }

zxr10RMAPMatchSourceAclName  OBJECT-TYPE
    SYNTAX   DisplayString(SIZE(1..31))
    MAX-ACCESS  not-accessible
    STATUS  current
    DESCRIPTION
        "Name of Route-map (1-31 characters)"
    ::= { zxr10RMAPMatchIpSourceAclEntry 1 } 
        
zxr10RMAPMatchSourceAclSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchIpSourceAclEntry 2 }  
    
 zxr10RMAPSourceAclName  OBJECT-TYPE
    SYNTAX   DisplayString(SIZE(1..31))
    MAX-ACCESS  not-accessible
    STATUS  current
    DESCRIPTION
        "Name of an access-list(1-31 characters).
         Each sequence has 10 match ip source items at most."
    ::= { zxr10RMAPMatchIpSourceAclEntry 3 }
  

zxr10RMAPSourceIsConfigAcl  OBJECT-TYPE
    SYNTAX   TruthValue
    MAX-ACCESS  not-accessible
    STATUS  current
    DESCRIPTION
        "It expresses that this config is match ip source by acl."
    ::= { zxr10RMAPMatchIpSourceAclEntry 4 }

zxr10RMAPMatchSourceAclRowStatus  OBJECT-TYPE
    SYNTAX   RowStatus
    MAX-ACCESS  read-create
    STATUS  current
    DESCRIPTION
        "RowStatus"
    ::= { zxr10RMAPMatchIpSourceAclEntry 100 }

--------------------------------------------------------------
--------------------------------------------------------------
--zxr10RMAPMatchIpSourcePflTable
-------------------------------------------------------------- 
 zxr10RMAPMatchIpSourcePflTable  OBJECT-TYPE
    SYNTAX  SEQUENCE OF Zxr10RMAPMatchIpSourcePflEntry
    MAX-ACCESS  not-accessible
    STATUS  current
    DESCRIPTION
        "Route-map Match IpSource Table(match ip source by pfl)"
    ::= { zxr10RMAPRuleObjects 51 }

zxr10RMAPMatchIpSourcePflEntry  OBJECT-TYPE
    SYNTAX  Zxr10RMAPMatchIpSourcePflEntry
    MAX-ACCESS  not-accessible
    STATUS  current
    DESCRIPTION          
       "Match Source ip address of route or match packet.
        This match item sets the route-map name with ipv4 type.
        It conflicts with other match or set items 
        which set the route-map name with ipv6 type.
        Otherwise, It conflicts with the item that match ip source by acl."
    INDEX  { zxr10RMAPName,  zxr10RMAPSequence, zxr10RMAPSourcePflName, zxr10RMAPSourceIsConfigPfl}
    ::= { zxr10RMAPMatchIpSourcePflTable 1 }
    
Zxr10RMAPMatchIpSourcePflEntry ::=SEQUENCE {
        zxr10RMAPMatchSourcePflName               DisplayString,
        zxr10RMAPMatchSourcePflSequence           Integer32, 
        zxr10RMAPSourcePflName                    DisplayString, 
        zxr10RMAPSourceIsConfigPfl                TruthValue,
        zxr10RMAPMatchSourcePflRowStatus          RowStatus
    }

zxr10RMAPMatchSourcePflName  OBJECT-TYPE
    SYNTAX   DisplayString(SIZE(1..31))
    MAX-ACCESS  not-accessible
    STATUS  current
    DESCRIPTION
        "Name of Route-map (1-31 characters)"
    ::= { zxr10RMAPMatchIpSourcePflEntry 1 } 
        
zxr10RMAPMatchSourcePflSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchIpSourcePflEntry 2 }    

zxr10RMAPSourcePflName  OBJECT-TYPE
    SYNTAX   DisplayString(SIZE(1..31))
    MAX-ACCESS  not-accessible
    STATUS  current
    DESCRIPTION
        "Name of a prefix list (1-31 characters).
         Each sequence has 10 match ip source items at most."
    ::= { zxr10RMAPMatchIpSourcePflEntry 3 }  
    
zxr10RMAPSourceIsConfigPfl  OBJECT-TYPE
    SYNTAX   TruthValue
    MAX-ACCESS  not-accessible
    STATUS  current
    DESCRIPTION
        "It expresses that this config is match ip source by pfl."
    ::= { zxr10RMAPMatchIpSourcePflEntry 4 }

zxr10RMAPMatchSourcePflRowStatus  OBJECT-TYPE
    SYNTAX   RowStatus
    MAX-ACCESS  read-create
    STATUS  current
    DESCRIPTION
        "RowStatus"
    ::= { zxr10RMAPMatchIpSourcePflEntry 100 }

--------------------------------------------------------------
--------------------------------------------------------------
--zxr10RMAPMatchLocalPrefTable
--------------------------------------------------------------
zxr10RMAPMatchLocalPrefTable  OBJECT-TYPE
    SYNTAX  SEQUENCE OF Zxr10RMAPMatchLocalPrefEntry
    MAX-ACCESS  not-accessible
    STATUS  current
    DESCRIPTION
        "Route-map Match local-preference Table"
    ::= { zxr10RMAPRuleObjects 52 }

zxr10RMAPMatchLocalPrefEntry  OBJECT-TYPE
    SYNTAX  Zxr10RMAPMatchLocalPrefEntry
    MAX-ACCESS  not-accessible
    STATUS  current
    DESCRIPTION          
       "Match BGP local preference path attribute"
    INDEX  { zxr10RMAPName,  zxr10RMAPSequence}
    ::= { zxr10RMAPMatchLocalPrefTable 1 }
    
Zxr10RMAPMatchLocalPrefEntry ::=SEQUENCE {
        zxr10RMAPMatchLocalPrefName         DisplayString,
        zxr10RMAPMatchLocalPrefSequence     Integer32, 
        zxr10RMAPMatchLocalPrefAlg          RmapMatchAlg,
        zxr10RMAPMatchLocalPref             Unsigned32,
        zxr10RMAPMatchLocalPrefRowStatus    RowStatus
    }

zxr10RMAPMatchLocalPrefName  OBJECT-TYPE
    SYNTAX   DisplayString(SIZE(1..31))
    MAX-ACCESS  not-accessible
    STATUS  current
    DESCRIPTION
        "Name of Route-map (1-31 characters)"
    ::= { zxr10RMAPMatchLocalPrefEntry 1 } 
        
zxr10RMAPMatchLocalPrefSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchLocalPrefEntry 2 }    

zxr10RMAPMatchLocalPrefAlg  OBJECT-TYPE
    SYNTAX   RmapMatchAlg
    MAX-ACCESS  read-create
    STATUS  current
    DESCRIPTION
        "eq  Equal as-path length to be matched.Value is 1.
         ge  Minimum as-path length to be matched.Value is 2.
         le  Maximun as-path length to be matched.Value is 3."
    ::= { zxr10RMAPMatchLocalPrefEntry 3 } 

zxr10RMAPMatchLocalPref  OBJECT-TYPE
    SYNTAX   Unsigned32(0..4294967295)
    MAX-ACCESS  read-create
    STATUS  current
    DESCRIPTION
        "Preference value.
         The range of config is 0 to 4294967295."
    ::= { zxr10RMAPMatchLocalPrefEntry 4 } 
     
zxr10RMAPMatchLocalPrefRowStatus  OBJECT-TYPE
    SYNTAX   RowStatus
    MAX-ACCESS  read-create
    STATUS  current
    DESCRIPTION
        "RowStatus"
    ::= { zxr10RMAPMatchLocalPrefEntry 100 } 

--------------------------------------------------------------
--------------------------------------------------------------
--zxr10RMAPMatchOriginTable
--------------------------------------------------------------
zxr10RMAPMatchOriginTable  OBJECT-TYPE
    SYNTAX  SEQUENCE OF Zxr10RMAPMatchOriginEntry
    MAX-ACCESS  not-accessible
    STATUS  current
    DESCRIPTION
        "Route-map Match Origin Table"
    ::= { zxr10RMAPRuleObjects 53 }

zxr10RMAPMatchOriginEntry  OBJECT-TYPE
    SYNTAX  Zxr10RMAPMatchOriginEntry
    MAX-ACCESS  not-accessible
    STATUS  current
    DESCRIPTION          
       "Match BGP origin code"
    INDEX  { zxr10RMAPName,  zxr10RMAPSequence}
    ::= { zxr10RMAPMatchOriginTable 1 }
    
Zxr10RMAPMatchOriginEntry ::=SEQUENCE {
        zxr10RMAPMatchOriginName                  DisplayString,
        zxr10RMAPMatchOriginSequence              Integer32,
        zxr10RMAPMatchOrigin                      RmapSetOrigin,
        zxr10RMAPMatchOriginRowStatus             RowStatus
    }

zxr10RMAPMatchOriginName  OBJECT-TYPE
    SYNTAX   DisplayString(SIZE(1..31))
    MAX-ACCESS  not-accessible
    STATUS  current
    DESCRIPTION
        "Name of Route-map (1-31 characters)"
    ::= { zxr10RMAPMatchOriginEntry 1 } 
        
zxr10RMAPMatchOriginSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchOriginEntry 2 }    

zxr10RMAPMatchOrigin  OBJECT-TYPE
    SYNTAX   RmapSetOrigin
    MAX-ACCESS  read-create
    STATUS  current
    DESCRIPTION
        "egp         Remote EGP.Value is 2.
         igp         Local IGP.Value is 1.
         incomplete  Unknown heritage.Value is 3.
         0 is invalid value."
    ::= { zxr10RMAPMatchOriginEntry 3 } 

zxr10RMAPMatchOriginRowStatus  OBJECT-TYPE
    SYNTAX   RowStatus
    MAX-ACCESS  read-create
    STATUS  current
    DESCRIPTION
        "RowStatus"
    ::= { zxr10RMAPMatchOriginEntry 100 } 
    
--------------------------------------------------------------
--------------------------------------------------------------
--zxr10RMAPSetPathSelTable
--------------------------------------------------------------
zxr10RMAPSetPathSelTable  OBJECT-TYPE
    SYNTAX  SEQUENCE OF Zxr10RMAPSetPathSelEntry
    MAX-ACCESS  not-accessible
    STATUS  current
    DESCRIPTION
        "Route-map Set Path-selection Table"
    ::= { zxr10RMAPRuleObjects 54 }

zxr10RMAPSetPathSelEntry  OBJECT-TYPE
    SYNTAX  Zxr10RMAPSetPathSelEntry
    MAX-ACCESS  not-accessible
    STATUS  current
    DESCRIPTION          
       "Set BGP path-selection"
    INDEX  { zxr10RMAPName,  zxr10RMAPSequence}
    ::= { zxr10RMAPSetPathSelTable 1 }
    
Zxr10RMAPSetPathSelEntry ::=SEQUENCE {
        zxr10RMAPSetPathSelName                  DisplayString,
        zxr10RMAPSetPathSelSequence              Integer32,
        zxr10RMAPSetPathSelPath                  RmapSetPath,
        zxr10RMAPSetPathSelNum                   Integer32,
        zxr10RMAPSetPathSelInstall               RmapSetPathInstall,
        zxr10RMAPSetPathSelMulpro                RmapSetPathMulpro, 
        zxr10RMAPSetPathSelAdvertise             RmapSetPathAdvertise, 
        zxr10RMAPSetPathSelRowStatus             RowStatus
    }

zxr10RMAPSetPathSelName  OBJECT-TYPE
    SYNTAX   DisplayString(SIZE(1..31))
    MAX-ACCESS  not-accessible
    STATUS  current
    DESCRIPTION
        "Name of Route-map (1-31 characters)"
    ::= { zxr10RMAPSetPathSelEntry 1 } 
        
zxr10RMAPSetPathSelSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetPathSelEntry 2 }    

zxr10RMAPSetPathSelPath  OBJECT-TYPE
    SYNTAX   RmapSetPath
    MAX-ACCESS  read-create
    STATUS  current
    DESCRIPTION
        "all         Path for imitating iBGP full-mesh.Value is 1.
         backup      Path for rapid convergence.Value is 2.
         best-path   Path for load sharing.Value is 3.
         group-best  Path for elimination of routing oscillation.Value is 4."
    ::= { zxr10RMAPSetPathSelEntry 3 } 
    
zxr10RMAPSetPathSelNum  OBJECT-TYPE
    SYNTAX   Integer32(1..32)
    MAX-ACCESS  read-create
    STATUS  current
    DESCRIPTION
        "Path numbers.
         The range of config is 1 to 32."
    ::= { zxr10RMAPSetPathSelEntry 4 } 
    
zxr10RMAPSetPathSelInstall  OBJECT-TYPE
    SYNTAX   RmapSetPathInstall
    MAX-ACCESS  read-create
    STATUS  current
    DESCRIPTION
        "Manner of sending to forwarding table."
    ::= { zxr10RMAPSetPathSelEntry 5 } 
    
zxr10RMAPSetPathSelMulpro  OBJECT-TYPE
    SYNTAX   RmapSetPathMulpro
    MAX-ACCESS  read-create
    STATUS  current
    DESCRIPTION
        "Manner of sending to forwarding table."
    ::= { zxr10RMAPSetPathSelEntry 6 } 
    
zxr10RMAPSetPathSelAdvertise  OBJECT-TYPE
    SYNTAX   RmapSetPathAdvertise
    MAX-ACCESS  read-create
    STATUS  current
    DESCRIPTION
        "Advertising the path selected outward."
    ::= { zxr10RMAPSetPathSelEntry 7 }

zxr10RMAPSetPathSelRowStatus  OBJECT-TYPE
    SYNTAX   RowStatus
    MAX-ACCESS  read-create
    STATUS  current
    DESCRIPTION
        "RowStatus"
    ::= { zxr10RMAPSetPathSelEntry 100 } 
    
--------------------------------------------------------------
--------------------------------------------------------------
--zxr10RMAPSetPolicyPrioTable
--------------------------------------------------------------
zxr10RMAPSetPolicyPrioTable  OBJECT-TYPE
    SYNTAX  SEQUENCE OF Zxr10RMAPSetPolicyPrioEntry
    MAX-ACCESS  not-accessible
    STATUS  current
    DESCRIPTION
        "Route-map Set Policy-priority Table"
    ::= { zxr10RMAPRuleObjects 55 }

zxr10RMAPSetPolicyPrioEntry  OBJECT-TYPE
    SYNTAX  Zxr10RMAPSetPolicyPrioEntry
    MAX-ACCESS  not-accessible
    STATUS  current
    DESCRIPTION          
       "Set policy priority for PBR"
    INDEX  { zxr10RMAPName,  zxr10RMAPSequence}
    ::= { zxr10RMAPSetPolicyPrioTable 1 }
    
Zxr10RMAPSetPolicyPrioEntry ::=SEQUENCE {
        zxr10RMAPSetPolicyPrioName                  DisplayString,
        zxr10RMAPSetPolicyPrioSequence              Integer32,
        zxr10RMAPSetPolicyPrio                      Integer32,
        zxr10RMAPSetPolicyPrioRowStatus             RowStatus
    }

zxr10RMAPSetPolicyPrioName  OBJECT-TYPE
    SYNTAX   DisplayString(SIZE(1..31))
    MAX-ACCESS  not-accessible
    STATUS  current
    DESCRIPTION
        "Name of Route-map (1-31 characters)"
    ::= { zxr10RMAPSetPolicyPrioEntry 1 } 
        
zxr10RMAPSetPolicyPrioSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetPolicyPrioEntry 2 }    

zxr10RMAPSetPolicyPrio  OBJECT-TYPE
    SYNTAX   Integer32(0..7)
    MAX-ACCESS  read-create
    STATUS  current
    DESCRIPTION
        "Value of policy priority.
         The range of config is 0 to 7."
    ::= { zxr10RMAPSetPolicyPrioEntry 3 } 
    
zxr10RMAPSetPolicyPrioRowStatus  OBJECT-TYPE
    SYNTAX   RowStatus
    MAX-ACCESS  read-create
    STATUS  current
    DESCRIPTION
        "RowStatus"
    ::= { zxr10RMAPSetPolicyPrioEntry 100 } 
    
--------------------------------------------------------------
--------------------------------------------------------------
--zxr10RMAPMatchIpAlgMetricTable
--------------------------------------------------------------
zxr10RMAPMatchIpAlgMetricTable  OBJECT-TYPE
    SYNTAX  SEQUENCE OF Zxr10RMAPMatchIpAlgMetricEntry
    MAX-ACCESS  not-accessible
    STATUS  current
    DESCRIPTION
        "Route-map Match Ip Metric Table"
    ::= { zxr10RMAPRuleObjects 56 }

zxr10RMAPMatchIpAlgMetricEntry  OBJECT-TYPE
    SYNTAX  Zxr10RMAPMatchIpAlgMetricEntry
    MAX-ACCESS  not-accessible
    STATUS  current
    DESCRIPTION          
       "Match address of route or match packet.
This match item sets the route-map with ipv4 type.
It conflicts with other match or set items which set the route-map name with ipv6 type."
    INDEX  { zxr10RMAPName,  zxr10RMAPSequence}
    ::= { zxr10RMAPMatchIpAlgMetricTable 1 }
    
Zxr10RMAPMatchIpAlgMetricEntry ::=SEQUENCE {
        zxr10RMAPMatchIpAlgMetricName         DisplayString,
        zxr10RMAPMatchIpAlgMetricSeq          Integer32, 
        zxr10RMAPMatchIpAlgMetricAlg          RmapMatchAlg,
        zxr10RMAPMatchIpAlgMetric             Unsigned32,
        zxr10RMAPIpAlgMetricRowStatus         RowStatus
    }

zxr10RMAPMatchIpAlgMetricName  OBJECT-TYPE
    SYNTAX   DisplayString(SIZE(1..31))
    MAX-ACCESS  not-accessible
    STATUS  current
    DESCRIPTION
        "Name of Route-map (1-31 characters)"
    ::= { zxr10RMAPMatchIpAlgMetricEntry 1 } 
        
zxr10RMAPMatchIpAlgMetricSeq  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchIpAlgMetricEntry 2 }    

zxr10RMAPMatchIpAlgMetricAlg  OBJECT-TYPE
    SYNTAX   RmapMatchAlg
    MAX-ACCESS  read-create
    STATUS  current
    DESCRIPTION
        "eq  Equal matric length to be matched.Value is 1.
         ge  Minimum matric length to be matched.Value is 2.
         le  Maximun matric length to be matched.Value is 3."
    ::= { zxr10RMAPMatchIpAlgMetricEntry 3 } 

zxr10RMAPMatchIpAlgMetric  OBJECT-TYPE
    SYNTAX   Unsigned32(0..4294967295)
    MAX-ACCESS  read-create
    STATUS  current
    DESCRIPTION
        "Metric value.
         The range of config is 0 to 4294967295."
    ::= { zxr10RMAPMatchIpAlgMetricEntry 4 } 
     
zxr10RMAPIpAlgMetricRowStatus  OBJECT-TYPE
    SYNTAX   RowStatus
    MAX-ACCESS  read-create
    STATUS  current
    DESCRIPTION
        "RowStatus"
    ::= { zxr10RMAPMatchIpAlgMetricEntry 100 } 

--------------------------------------------------------------
--------------------------------------------------------------
--zxr10RMAPMatchIpv6AlgMetricTable
--------------------------------------------------------------
zxr10RMAPMatchIpv6AlgMetricTable  OBJECT-TYPE
    SYNTAX  SEQUENCE OF Zxr10RMAPMatchIpv6AlgMetricEntry
    MAX-ACCESS  not-accessible
    STATUS  current
    DESCRIPTION
        "Route-map Match Ipv6 Metric Table"
    ::= { zxr10RMAPRuleObjects 57 }

zxr10RMAPMatchIpv6AlgMetricEntry  OBJECT-TYPE
    SYNTAX  Zxr10RMAPMatchIpv6AlgMetricEntry
    MAX-ACCESS  not-accessible
    STATUS  current
    DESCRIPTION          
       "Match address of route or match packet.
This match item sets the route-map with ipv6 type.
It conflicts with other match or set items which set the route-map name with ipv4 type."
    INDEX  { zxr10RMAPName,  zxr10RMAPSequence}
    ::= { zxr10RMAPMatchIpv6AlgMetricTable 1 }
    
Zxr10RMAPMatchIpv6AlgMetricEntry ::=SEQUENCE {
        zxr10RMAPMatchIpv6AlgMetricName         DisplayString,
        zxr10RMAPMatchIpv6AlgMetricSeq          Integer32, 
        zxr10RMAPMatchIpv6AlgMetricAlg          RmapMatchAlg,
        zxr10RMAPMatchIpv6AlgMetric             Unsigned32,
        zxr10RMAPIpv6AlgMetricRowStatus         RowStatus
    }

zxr10RMAPMatchIpv6AlgMetricName  OBJECT-TYPE
    SYNTAX   DisplayString(SIZE(1..31))
    MAX-ACCESS  not-accessible
    STATUS  current
    DESCRIPTION
        "Name of Route-map (1-31 characters)"
    ::= { zxr10RMAPMatchIpv6AlgMetricEntry 1 } 
        
zxr10RMAPMatchIpv6AlgMetricSeq  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchIpv6AlgMetricEntry 2 }    

zxr10RMAPMatchIpv6AlgMetricAlg  OBJECT-TYPE
    SYNTAX   RmapMatchAlg
    MAX-ACCESS  read-create
    STATUS  current
    DESCRIPTION
        "eq  Equal matric length to be matched.Value is 1.
         ge  Minimum matric length to be matched.Value is 2.
         le  Maximun matric length to be matched.Value is 3."
    ::= { zxr10RMAPMatchIpv6AlgMetricEntry 3 } 

zxr10RMAPMatchIpv6AlgMetric  OBJECT-TYPE
    SYNTAX   Unsigned32(0..4294967295)
    MAX-ACCESS  read-create
    STATUS  current
    DESCRIPTION
        "Metric value.
         The range of config is 0 to 4294967295."
    ::= { zxr10RMAPMatchIpv6AlgMetricEntry 4 } 
     
zxr10RMAPIpv6AlgMetricRowStatus  OBJECT-TYPE
    SYNTAX   RowStatus
    MAX-ACCESS  read-create
    STATUS  current
    DESCRIPTION
        "RowStatus"
    ::= { zxr10RMAPMatchIpv6AlgMetricEntry 100 } 
    
 
--------------------------------------------------------------
--------------------------------------------------------------
--zxr10RMAPSetTraffIdxTable
--------------------------------------------------------------
zxr10RMAPSetTraffIdxTable  OBJECT-TYPE
    SYNTAX  SEQUENCE OF Zxr10RMAPSetTraffIdxEntry
    MAX-ACCESS  not-accessible
    STATUS  current
    DESCRIPTION
        "Route-map Set Traffic-index Table"
    ::= { zxr10RMAPRuleObjects 58 }

zxr10RMAPSetTraffIdxEntry  OBJECT-TYPE
    SYNTAX  Zxr10RMAPSetTraffIdxEntry
    MAX-ACCESS  not-accessible
    STATUS  current
    DESCRIPTION          
       "Set BGP traffic index"
    INDEX  { zxr10RMAPName,  zxr10RMAPSequence}
    ::= { zxr10RMAPSetTraffIdxTable 1 }
    
Zxr10RMAPSetTraffIdxEntry ::=SEQUENCE {
        zxr10RMAPSetTraffIdxName          DisplayString,
        zxr10RMAPSetTraffIdxSequence      Integer32,
        zxr10RMAPSetTraffIdx              Integer32,
        zxr10RMAPSetTraffIdxRowStatus     RowStatus
    }

zxr10RMAPSetTraffIdxName  OBJECT-TYPE
    SYNTAX   DisplayString(SIZE(1..31))
    MAX-ACCESS  not-accessible
    STATUS  current
    DESCRIPTION
        "Name of Route-map (1-31 characters)"
    ::= { zxr10RMAPSetTraffIdxEntry 1 } 
        
zxr10RMAPSetTraffIdxSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetTraffIdxEntry 2 }    

zxr10RMAPSetTraffIdx  OBJECT-TYPE
    SYNTAX   Integer32(1..32)
    MAX-ACCESS  read-create
    STATUS  current
    DESCRIPTION
        "Traffic-index number.
         The range of config is 1 to 63."
    ::= { zxr10RMAPSetTraffIdxEntry 3 } 

zxr10RMAPSetTraffIdxRowStatus  OBJECT-TYPE
    SYNTAX   RowStatus
    MAX-ACCESS  read-create
    STATUS  current
    DESCRIPTION
        "RowStatus"
    ::= { zxr10RMAPSetTraffIdxEntry 100 }

--------------------------------------------------------------
--------------------------------------------------------------
--zxr10RMAPSetNextHopPeerAddrTable
--------------------------------------------------------------
zxr10RMAPSetNextHopPeerAddrTable  OBJECT-TYPE
    SYNTAX  SEQUENCE OF Zxr10RMAPSetNextHopPeerAddrEntry
    MAX-ACCESS  not-accessible
    STATUS  current
    DESCRIPTION
        "Route-map Set NextHop Table"
    ::= { zxr10RMAPRuleObjects 60 }

zxr10RMAPSetNextHopPeerAddrEntry  OBJECT-TYPE
    SYNTAX  Zxr10RMAPSetNextHopPeerAddrEntry
    MAX-ACCESS  not-accessible
    STATUS  current
    DESCRIPTION          
       "Set IP address of next hop.
        It conflicts with these set items below:
        set vrf
        set global"
    INDEX  { zxr10RMAPName,  zxr10RMAPSequence, zxr10RMAPSetNextHopAddr, zxr10RMAPSetNextHopPeerAddr}
    ::= { zxr10RMAPSetNextHopPeerAddrTable 1 }
    
Zxr10RMAPSetNextHopPeerAddrEntry ::=SEQUENCE {
        zxr10RMAPSetNextHopPeerAddrName        DisplayString,
        zxr10RMAPSetNextHopPeerAddrSeq         Integer32,
        zxr10RMAPSetNextHopAddr                IpAddress,  
        zxr10RMAPSetNextHopPeerAddr            Integer32,  
        zxr10RMAPSetNHorPeerAddRowStatus       RowStatus
    }

zxr10RMAPSetNextHopPeerAddrName  OBJECT-TYPE
    SYNTAX   DisplayString(SIZE(1..31))
    MAX-ACCESS  not-accessible
    STATUS  current
    DESCRIPTION
        "Name of Route-map (1-31 characters)"
    ::= { zxr10RMAPSetNextHopPeerAddrEntry 1 } 
        
zxr10RMAPSetNextHopPeerAddrSeq  OBJECT-TYPE
    SYNTAX   Integer32
    MAX-ACCESS  not-accessible
    STATUS  current
    DESCRIPTION
        "The sequence of a route-map.
         The range of config is 0 to 65535.
         Each name of route-map has 100 sequences at most."
    ::= { zxr10RMAPSetNextHopPeerAddrEntry 2 }
    
zxr10RMAPSetNextHopAddr  OBJECT-TYPE
    SYNTAX   IpAddress
    MAX-ACCESS  not-accessible
    STATUS  current
    DESCRIPTION
        "IP address of next hop. 0 is invalid value.
         Each sequence has 10 set next-hop items at most."
    ::= { zxr10RMAPSetNextHopPeerAddrEntry 3 }

zxr10RMAPSetNextHopPeerAddr  OBJECT-TYPE
    SYNTAX   Integer32
    MAX-ACCESS  not-accessible
    STATUS  current
    DESCRIPTION
        "Peer address for BGP."
    ::= { zxr10RMAPSetNextHopPeerAddrEntry 4 }

zxr10RMAPSetNHorPeerAddRowStatus  OBJECT-TYPE
    SYNTAX   RowStatus
    MAX-ACCESS  read-create
    STATUS  current
    DESCRIPTION
        "RowStatus"
    ::= { zxr10RMAPSetNextHopPeerAddrEntry 100 }

--------------------------------------------------------------
--------------------------------------------------------------
--zxr10RMAPSetIpv6NHorPeerAddTable
--------------------------------------------------------------
zxr10RMAPSetIpv6NHorPeerAddTable  OBJECT-TYPE
    SYNTAX  SEQUENCE OF Zxr10RMAPSetIpv6NHorPeerAddEntry
    MAX-ACCESS  not-accessible
    STATUS  current
    DESCRIPTION
        "Route-map Set IpNextHop Table"
    ::= { zxr10RMAPRuleObjects 61 }

zxr10RMAPSetIpv6NHorPeerAddEntry  OBJECT-TYPE
    SYNTAX  Zxr10RMAPSetIpv6NHorPeerAddEntry
    MAX-ACCESS  not-accessible
    STATUS  current
    DESCRIPTION          
       "Set Next hop address.
        This set item sets the route-map name with ipv6 type.
        It conflicts with other match or set items 
        which set the route-map name with ipv4 type.
        It conflicts with these set items below:
        set vrf
        set global"
    INDEX  { zxr10RMAPName,  zxr10RMAPSequence, zxr10RMAPSetIpv6NextHopAddr, 
             zxr10RMAPSetIpv6NextHopPeerAddr}
    ::= { zxr10RMAPSetIpv6NHorPeerAddTable 1 }
    
Zxr10RMAPSetIpv6NHorPeerAddEntry ::=SEQUENCE {
        zxr10RMAPSetIpv6NHorPeerAddName       DisplayString,
        zxr10RMAPSetIpv6NHorPeerAddSeq        Integer32,
        zxr10RMAPSetIpv6NextHopAddr           Ipv6Address,  
        zxr10RMAPSetIpv6NextHopPeerAddr       Integer32,  
        zxr10RMAPSetv6NHorPeerRowStatus       RowStatus
    }

zxr10RMAPSetIpv6NHorPeerAddName  OBJECT-TYPE
    SYNTAX   DisplayString(SIZE(1..31))
    MAX-ACCESS  not-accessible
    STATUS  current
    DESCRIPTION
        "Name of Route-map (1-31 characters)"
    ::= { zxr10RMAPSetIpv6NHorPeerAddEntry 1 } 
        
zxr10RMAPSetIpv6NHorPeerAddSeq  OBJECT-TYPE
    SYNTAX   Integer32
    MAX-ACCESS  not-accessible
    STATUS  current
    DESCRIPTION
        "The sequence of a route-map.
         The range of config is 0 to 65535.
         Each name of route-map has 100 sequences at most."
    ::= { zxr10RMAPSetIpv6NHorPeerAddEntry 2 } 

zxr10RMAPSetIpv6NextHopAddr  OBJECT-TYPE
    SYNTAX   Ipv6Address
    MAX-ACCESS  not-accessible
    STATUS  current
    DESCRIPTION
        "<X:X::X:X> IPv6 address of next hop. 0 is invalid value.
         Each sequence has 10 set ipv6 next-hop items at most."
    ::= { zxr10RMAPSetIpv6NHorPeerAddEntry 3 }

zxr10RMAPSetIpv6NextHopPeerAddr  OBJECT-TYPE
    SYNTAX   Integer32
    MAX-ACCESS  not-accessible
    STATUS  current
    DESCRIPTION
        "Peer address for BGP."
    ::= { zxr10RMAPSetIpv6NHorPeerAddEntry 4 }

zxr10RMAPSetv6NHorPeerRowStatus  OBJECT-TYPE
    SYNTAX   RowStatus
    MAX-ACCESS  read-create
    STATUS  current
    DESCRIPTION
        "RowStatus"
    ::= { zxr10RMAPSetIpv6NHorPeerAddEntry 100 }
    
--------------------------------------------------------------
--------------------------------------------------------------
--zxr10RMAPMatchEvpnTable
--------------------------------------------------------------
zxr10RMAPMatchEvpnTable  OBJECT-TYPE
    SYNTAX  SEQUENCE OF Zxr10RMAPMatchEvpnEntry
    MAX-ACCESS  not-accessible
    STATUS  current
    DESCRIPTION
        "Route-map match EVPN table"
    ::= { zxr10RMAPRuleObjects 62 }

zxr10RMAPMatchEvpnEntry  OBJECT-TYPE
    SYNTAX  Zxr10RMAPMatchEvpnEntry
    MAX-ACCESS  not-accessible
    STATUS  current
    DESCRIPTION          
       "Match BGP EVPN route"
    INDEX  { zxr10RMAPName,  zxr10RMAPSequence,  zxr10RMAPMatchEvpn}
    ::= { zxr10RMAPMatchEvpnTable 1 }
    
Zxr10RMAPMatchEvpnEntry ::=SEQUENCE {
        zxr10RMAPMatchEvpnName                  DisplayString,
        zxr10RMAPMatchEvpnSequence              Integer32,
        zxr10RMAPMatchEvpn                      Integer32,
        zxr10RMAPMatchEvpnRowStatus             RowStatus
    }

zxr10RMAPMatchEvpnName  OBJECT-TYPE
    SYNTAX   DisplayString(SIZE(1..31))
    MAX-ACCESS  not-accessible
    STATUS  current
    DESCRIPTION
        "Name of route-map (1-31 characters)"
    ::= { zxr10RMAPMatchEvpnEntry 1 } 
        
zxr10RMAPMatchEvpnSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchEvpnEntry 2 }    

zxr10RMAPMatchEvpn  OBJECT-TYPE
    SYNTAX   Integer32(1..5)
    MAX-ACCESS  not-accessible
    STATUS  current
    DESCRIPTION
        "EVPN route type.
        1: Ethernet Auto-Discovery (A-D) route;
        2: MAC/IP Advertisement route;
        3: Inclusive Multicast Ethernet Tag route;
        4: Ethernet Segment route;
        5: IP Prefix route."
    ::= { zxr10RMAPMatchEvpnEntry 3 }

zxr10RMAPMatchEvpnRowStatus  OBJECT-TYPE
    SYNTAX   RowStatus
    MAX-ACCESS  read-create
    STATUS  current
    DESCRIPTION
        "Row status"
    ::= { zxr10RMAPMatchEvpnEntry 100 }


--------------------------------------------------------------
--------------------------------------------------------------
--zxr10RMAPBlackHoleRouteTable
--------------------------------------------------------------
zxr10RMAPBlackHoleRouteTable  OBJECT-TYPE
    SYNTAX  SEQUENCE OF Zxr10RMAPBlackHoleRouteEntry
    MAX-ACCESS  not-accessible
    STATUS  current
    DESCRIPTION
        "Route-map black hole route table"
    ::= { zxr10RMAPRuleObjects 63 }

zxr10RMAPBlackHoleRouteEntry  OBJECT-TYPE
    SYNTAX  Zxr10RMAPBlackHoleRouteEntry
    MAX-ACCESS  not-accessible
    STATUS  current
    DESCRIPTION          
       "Black hole route which outcoming interface is null."
    INDEX  { zxr10RMAPName,  zxr10RMAPSequence}
    ::= { zxr10RMAPBlackHoleRouteTable 1 }
    
Zxr10RMAPBlackHoleRouteEntry ::=SEQUENCE {
        zxr10RMAPBlackHoleRouteName             DisplayString,
        zxr10RMAPBlackHoleRouteSequence         Integer32,
        zxr10RMAPBlackHoleRouteEnable           INTEGER,
        zxr10RMAPBlackHoleRouteRowStatus        RowStatus
    }

zxr10RMAPBlackHoleRouteName  OBJECT-TYPE
    SYNTAX   DisplayString(SIZE(1..31))
    MAX-ACCESS  not-accessible
    STATUS  current
    DESCRIPTION
        "Name of route-map (1-31 characters)"
    ::= { zxr10RMAPBlackHoleRouteEntry 1 } 
        
zxr10RMAPBlackHoleRouteSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPBlackHoleRouteEntry 2 }    

zxr10RMAPBlackHoleRouteEnable  OBJECT-TYPE
    SYNTAX INTEGER {false(255),true(1)}
    MAX-ACCESS  read-create
    STATUS  current
    DESCRIPTION
        "Black hole route enable."
    ::= { zxr10RMAPBlackHoleRouteEntry 3 }

zxr10RMAPBlackHoleRouteRowStatus  OBJECT-TYPE
    SYNTAX   RowStatus
    MAX-ACCESS  read-create
    STATUS  current
    DESCRIPTION
        "Row status"
    ::= { zxr10RMAPBlackHoleRouteEntry 100 }

--------------------------------------------------------------
--------------------------------------------------------------
--zxr10RMAPDefaultRouteTable
--------------------------------------------------------------
zxr10RMAPDefaultRouteTable  OBJECT-TYPE
    SYNTAX  SEQUENCE OF Zxr10RMAPDefaultRouteEntry
    MAX-ACCESS  not-accessible
    STATUS  current
    DESCRIPTION
        "Route-map default route table"
    ::= { zxr10RMAPRuleObjects 64 }

zxr10RMAPDefaultRouteEntry  OBJECT-TYPE
    SYNTAX  Zxr10RMAPDefaultRouteEntry
    MAX-ACCESS  not-accessible
    STATUS  current
    DESCRIPTION          
       "Default route"
    INDEX  { zxr10RMAPName,  zxr10RMAPSequence}
    ::= { zxr10RMAPDefaultRouteTable 1 }
    
Zxr10RMAPDefaultRouteEntry ::=SEQUENCE {
        zxr10RMAPDefaultRouteName             DisplayString,
        zxr10RMAPDefaultRouteSequence         Integer32,
        zxr10RMAPDefaultRouteEnable           INTEGER,
        zxr10RMAPDefaultRouteRowStatus        RowStatus
    }

zxr10RMAPDefaultRouteName  OBJECT-TYPE
    SYNTAX   DisplayString(SIZE(1..31))
    MAX-ACCESS  not-accessible
    STATUS  current
    DESCRIPTION
        "Name of route-map (1-31 characters)"
    ::= { zxr10RMAPDefaultRouteEntry 1 } 
        
zxr10RMAPDefaultRouteSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPDefaultRouteEntry 2 }    

zxr10RMAPDefaultRouteEnable  OBJECT-TYPE
    SYNTAX INTEGER {false(255),true(1)}
    MAX-ACCESS  read-create
    STATUS  current
    DESCRIPTION
        "Default route enable."
    ::= { zxr10RMAPDefaultRouteEntry 3 }

zxr10RMAPDefaultRouteRowStatus  OBJECT-TYPE
    SYNTAX   RowStatus
    MAX-ACCESS  read-create
    STATUS  current
    DESCRIPTION
        "Row status"
    ::= { zxr10RMAPDefaultRouteEntry 100 }    


--------------------------------------------------------------
--------------------------------------------------------------
--zxr10RMAPStrictPolicyTable
--------------------------------------------------------------
zxr10RMAPStrictPolicyTable  OBJECT-TYPE
    SYNTAX  SEQUENCE OF Zxr10RMAPStrictPolicyEntry
    MAX-ACCESS  not-accessible
    STATUS  current
    DESCRIPTION
        "Route-map strict policy table"
    ::= { zxr10RMAPRuleObjects 65 }

zxr10RMAPStrictPolicyEntry  OBJECT-TYPE
    SYNTAX  Zxr10RMAPStrictPolicyEntry
    MAX-ACCESS  not-accessible
    STATUS  current
    DESCRIPTION          
       "Strict policy"
    INDEX  { zxr10RMAPName,  zxr10RMAPSequence}
    ::= { zxr10RMAPStrictPolicyTable 1 }
    
Zxr10RMAPStrictPolicyEntry ::=SEQUENCE {
        zxr10RMAPStrictPolicyName             DisplayString,
        zxr10RMAPStrictPolicySequence         Integer32,
        zxr10RMAPStrictPolicyEnable           INTEGER,
        zxr10RMAPStrictPolicyRowStatus        RowStatus
    }

zxr10RMAPStrictPolicyName  OBJECT-TYPE
    SYNTAX   DisplayString(SIZE(1..31))
    MAX-ACCESS  not-accessible
    STATUS  current
    DESCRIPTION
        "Name of route-map (1-31 characters)"
    ::= { zxr10RMAPStrictPolicyEntry 1 } 
        
zxr10RMAPStrictPolicySequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPStrictPolicyEntry 2 }    

zxr10RMAPStrictPolicyEnable  OBJECT-TYPE
    SYNTAX INTEGER {false(255),true(1)}
    MAX-ACCESS  read-create
    STATUS  current
    DESCRIPTION
        "Strict policy enable."
    ::= { zxr10RMAPStrictPolicyEntry 3 }

zxr10RMAPStrictPolicyRowStatus  OBJECT-TYPE
    SYNTAX   RowStatus
    MAX-ACCESS  read-create
    STATUS  current
    DESCRIPTION
        "Row status"
    ::= { zxr10RMAPStrictPolicyEntry 100 }

--------------------------------------------------------------
--------------------------------------------------------------
--zxr10RMAPSetPathListTable
--------------------------------------------------------------
zxr10RMAPSetPathListTable  OBJECT-TYPE
    SYNTAX  SEQUENCE OF Zxr10RMAPSetPathListEntry
    MAX-ACCESS  not-accessible
    STATUS  current
    DESCRIPTION
        "Route-map set IPv4 path list table"
    ::= { zxr10RMAPRuleObjects 66 }

zxr10RMAPSetPathListEntry  OBJECT-TYPE
    SYNTAX  Zxr10RMAPSetPathListEntry
    MAX-ACCESS  not-accessible
    STATUS  current
    DESCRIPTION          
       "Set output interfaces.
        This set item supports these types of interface:
        [PORT_CLASS_FEI,PORT_CLASS_GEI_END].
        This set item sets the route-map name with IPv4 type.
        It conflicts with other match or set items 
        which set the route-map name with IPv6 type and
        zxr10RMAPSetIpPathListTable.
        It conflicts with these set items below:
        set vrf
        set global"
    INDEX  { zxr10RMAPName,
    zxr10RMAPSequence,
    zxr10RMAPSetPathListIntf,
    zxr10RMAPSetPathListNextHop}
    ::= { zxr10RMAPSetPathListTable 1 }
    
Zxr10RMAPSetPathListEntry ::=SEQUENCE {
        zxr10RMAPSetPathListName            DisplayString,
        zxr10RMAPSetPathListSequence        Integer32,
        zxr10RMAPSetPathListIntf            DisplayString,
        zxr10RMAPSetPathListNextHop         IpAddress,
        zxr10RMAPSetPathListRowStatus       RowStatus
    }

zxr10RMAPSetPathListName  OBJECT-TYPE
    SYNTAX   DisplayString(SIZE(1..31))
    MAX-ACCESS  not-accessible
    STATUS  current
    DESCRIPTION
        "Name of route-map (1-31 characters)"
    ::= { zxr10RMAPSetPathListEntry 1 } 
        
zxr10RMAPSetPathListSequence  OBJECT-TYPE
    SYNTAX   Integer32
    MAX-ACCESS  not-accessible
    STATUS  current
    DESCRIPTION
        "The sequence of a route-map.
         The range of config is 0 to 65535.
         Each name of route-map has 100 sequences at most."
    ::= { zxr10RMAPSetPathListEntry 2 }    

zxr10RMAPSetPathListIntf  OBJECT-TYPE
    SYNTAX   DisplayString(SIZE(1..31))
    MAX-ACCESS  not-accessible
    STATUS  current
    DESCRIPTION
        "Name of interface (1-31 characters)"
    ::= { zxr10RMAPSetPathListEntry 3 } 
        
zxr10RMAPSetPathListNextHop  OBJECT-TYPE
    SYNTAX   IpAddress
    MAX-ACCESS  not-accessible
    STATUS  current
    DESCRIPTION
        "IP address of next hop.0 is invalid value."
    ::= { zxr10RMAPSetPathListEntry 4 }

zxr10RMAPSetPathListRowStatus  OBJECT-TYPE
    SYNTAX   RowStatus
    MAX-ACCESS  read-create
    STATUS  current
    DESCRIPTION
        "Row status"
    ::= { zxr10RMAPSetPathListEntry 100 }
    
--------------------------------------------------------------
--------------------------------------------------------------
--zxr10RMAPSetPathList6Table
--------------------------------------------------------------
zxr10RMAPSetPathList6Table  OBJECT-TYPE
    SYNTAX  SEQUENCE OF Zxr10RMAPSetPathList6Entry
    MAX-ACCESS  not-accessible
    STATUS  current
    DESCRIPTION
        "Route-map set Ipv6 path list table"
    ::= { zxr10RMAPRuleObjects 67 }

zxr10RMAPSetPathList6Entry  OBJECT-TYPE
    SYNTAX  Zxr10RMAPSetPathList6Entry
    MAX-ACCESS  not-accessible
    STATUS  current
    DESCRIPTION          
       "Set output interface.
        This set item supports these types of interface:
        [PORT_CLASS_FEI,PORT_CLASS_GEI_END].
        This set item sets the route-map name with ipv6 type.
        It conflicts with other match or set items 
        which set the route-map name with ipv4 type and
        zxr10RMAPSetIpv6PathTable.
        It conflicts with these set items below:
        set vrf
        set global"
    INDEX  { zxr10RMAPName,
    zxr10RMAPSequence,
    zxr10RMAPSetPathList6Intf,
    zxr10RMAPSetPathList6NextHop}
    ::= { zxr10RMAPSetPathList6Table 1 }
    
Zxr10RMAPSetPathList6Entry ::=SEQUENCE {
        zxr10RMAPSetPathList6Name       DisplayString,
        zxr10RMAPSetPathList6Sequence   Integer32,
        zxr10RMAPSetPathList6Intf       DisplayString,
        zxr10RMAPSetPathList6NextHop    Ipv6Address,
        zxr10RMAPSetPathList6RowStatus  RowStatus
    }

zxr10RMAPSetPathList6Name  OBJECT-TYPE
    SYNTAX   DisplayString(SIZE(1..31))
    MAX-ACCESS  not-accessible
    STATUS  current
    DESCRIPTION
        "Name of route-map (1-31 characters)"
    ::= { zxr10RMAPSetPathList6Entry 1 } 
        
zxr10RMAPSetPathList6Sequence  OBJECT-TYPE
    SYNTAX   Integer32
    MAX-ACCESS  not-accessible
    STATUS  current
    DESCRIPTION
        "The sequence of a route-map.
         The range of config is 0 to 65535.
         Each name of route-map has 100 sequences at most."
    ::= { zxr10RMAPSetPathList6Entry 2 }    

zxr10RMAPSetPathList6Intf  OBJECT-TYPE
    SYNTAX   DisplayString(SIZE(1..31))
    MAX-ACCESS  not-accessible
    STATUS  current
    DESCRIPTION
        "Name of interface (1-31 characters)"
    ::= { zxr10RMAPSetPathList6Entry 3 } 
        
zxr10RMAPSetPathList6NextHop  OBJECT-TYPE
    SYNTAX   Ipv6Address
    MAX-ACCESS  not-accessible
    STATUS  current
    DESCRIPTION
        "<X:X::X:X> IPv6 address of next hop.0 is invalid value."
    ::= { zxr10RMAPSetPathList6Entry 4 }

zxr10RMAPSetPathList6RowStatus  OBJECT-TYPE
    SYNTAX   RowStatus
    MAX-ACCESS  read-create
    STATUS  current
    DESCRIPTION
        "Row status"
    ::= { zxr10RMAPSetPathList6Entry 100 }

--------------------------------------------------------------
--------------------------------------------------------------
--zxr10RMAPSetVxlanTunnelSrcTable
--------------------------------------------------------------
zxr10RMAPSetVxlanTunnelSrcTable  OBJECT-TYPE
    SYNTAX  SEQUENCE OF Zxr10RMAPSetVxlanTunnelSrcEntry
    MAX-ACCESS  not-accessible
    STATUS  current
    DESCRIPTION
        "Route-map set VXLAN tunnel source table"
    ::= { zxr10RMAPRuleObjects 68 }

zxr10RMAPSetVxlanTunnelSrcEntry  OBJECT-TYPE
    SYNTAX  Zxr10RMAPSetVxlanTunnelSrcEntry
    MAX-ACCESS  not-accessible
    STATUS  current
    DESCRIPTION          
       "Route-map set VXLAN tunnel source entry"
    INDEX  { zxr10RMAPName,  zxr10RMAPSequence}
    ::= { zxr10RMAPSetVxlanTunnelSrcTable 1 }
    
Zxr10RMAPSetVxlanTunnelSrcEntry ::=SEQUENCE {
        zxr10RMAPSetVxlanTunnelSrcName        DisplayString,
        zxr10RMAPSetVxlanTunnelSrcSeq         Integer32,
        zxr10RMAPSetVxlanTunnelSrcAddr        IpAddress,
        zxr10RMAPVxlanTunnelSrcRowStatus      RowStatus
    }

zxr10RMAPSetVxlanTunnelSrcName  OBJECT-TYPE
    SYNTAX   DisplayString(SIZE(1..31))
    MAX-ACCESS  not-accessible
    STATUS  current
    DESCRIPTION
        "Name of route-map (1-31 characters)"
    ::= { zxr10RMAPSetVxlanTunnelSrcEntry 1 } 
        
zxr10RMAPSetVxlanTunnelSrcSeq  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetVxlanTunnelSrcEntry 2 }    

zxr10RMAPSetVxlanTunnelSrcAddr  OBJECT-TYPE
    SYNTAX   IpAddress
    MAX-ACCESS  read-create
    STATUS  current
    DESCRIPTION
        "IP address of VXLAN tunnel source."
    ::= { zxr10RMAPSetVxlanTunnelSrcEntry 3 }

zxr10RMAPVxlanTunnelSrcRowStatus  OBJECT-TYPE
    SYNTAX   RowStatus
    MAX-ACCESS  read-create
    STATUS  current
    DESCRIPTION
        "Row status"
    ::= { zxr10RMAPSetVxlanTunnelSrcEntry 100 }

--------------------------------------------------------------
--------------------------------------------------------------
--zxr10RMAPSetEvpnMacIntfTable
--------------------------------------------------------------
zxr10RMAPSetEvpnMacIntfTable  OBJECT-TYPE
    SYNTAX  SEQUENCE OF Zxr10RMAPSetEvpnMacIntfEntry
    MAX-ACCESS  not-accessible
    STATUS  current
    DESCRIPTION
        "Route-map set EVPN router's MAC interface table"
    ::= { zxr10RMAPRuleObjects 69 }

zxr10RMAPSetEvpnMacIntfEntry  OBJECT-TYPE
    SYNTAX  Zxr10RMAPSetEvpnMacIntfEntry
    MAX-ACCESS  not-accessible
    STATUS  current
    DESCRIPTION          
       "Route-map set EVPN router's MAC interface entry"
    INDEX  { zxr10RMAPName,  zxr10RMAPSequence}
    ::= { zxr10RMAPSetEvpnMacIntfTable 1 }
    
Zxr10RMAPSetEvpnMacIntfEntry ::=SEQUENCE {
        zxr10RMAPSetEvpnMacIntfName        DisplayString,
        zxr10RMAPSetEvpnMacIntfSequence    Integer32,
        zxr10RMAPSetEvpnMacIntf            DisplayString,
        zxr10RMAPSetEvpnMacIntfRowStatus   RowStatus
    }

zxr10RMAPSetEvpnMacIntfName  OBJECT-TYPE
    SYNTAX   DisplayString(SIZE(1..31))
    MAX-ACCESS  not-accessible
    STATUS  current
    DESCRIPTION
        "Name of route-map (1-31 characters)"
    ::= { zxr10RMAPSetEvpnMacIntfEntry 1 } 
        
zxr10RMAPSetEvpnMacIntfSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetEvpnMacIntfEntry 2 }    

zxr10RMAPSetEvpnMacIntf  OBJECT-TYPE
    SYNTAX   DisplayString(SIZE(1..31))
    MAX-ACCESS  read-create
    STATUS  current
    DESCRIPTION
        "Name of interface (1-31 characters)"
    ::= { zxr10RMAPSetEvpnMacIntfEntry 3 }

zxr10RMAPSetEvpnMacIntfRowStatus  OBJECT-TYPE
    SYNTAX   RowStatus
    MAX-ACCESS  read-create
    STATUS  current
    DESCRIPTION
        "Row status"
    ::= { zxr10RMAPSetEvpnMacIntfEntry 100 }

--------------------------------------------------------------
--------------------------------------------------------------
--zxr10RMAPSetL2vniLabelTable
--------------------------------------------------------------
zxr10RMAPSetL2vniLabelTable  OBJECT-TYPE
    SYNTAX  SEQUENCE OF Zxr10RMAPSetL2vniLabelEntry
    MAX-ACCESS  not-accessible
    STATUS  current
    DESCRIPTION
        "Route-map set l2-vni label table"
    ::= { zxr10RMAPRuleObjects 70 }

zxr10RMAPSetL2vniLabelEntry  OBJECT-TYPE
    SYNTAX  Zxr10RMAPSetL2vniLabelEntry
    MAX-ACCESS  not-accessible
    STATUS  current
    DESCRIPTION          
       "Route-map set l2-vni label entry"
    INDEX  { zxr10RMAPName,  zxr10RMAPSequence}
    ::= { zxr10RMAPSetL2vniLabelTable 1 }
    
Zxr10RMAPSetL2vniLabelEntry ::=SEQUENCE {
        zxr10RMAPSetL2vniLabelName        DisplayString,
        zxr10RMAPSetL2vniLabelSequence    Integer32,
        zxr10RMAPSetL2vniLabel            Integer32,
        zxr10RMAPSetL2vniLabelRowStatus   RowStatus
    }

zxr10RMAPSetL2vniLabelName  OBJECT-TYPE
    SYNTAX   DisplayString(SIZE(1..31))
    MAX-ACCESS  not-accessible
    STATUS  current
    DESCRIPTION
        "Name of route-map (1-31 characters)"
    ::= { zxr10RMAPSetL2vniLabelEntry 1 } 
        
zxr10RMAPSetL2vniLabelSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetL2vniLabelEntry 2 }    

zxr10RMAPSetL2vniLabel  OBJECT-TYPE
    SYNTAX   Integer32(1..16777215)
    MAX-ACCESS  read-create
    STATUS  current
    DESCRIPTION
        "The value of l2-vni label."
    ::= { zxr10RMAPSetL2vniLabelEntry 3 }

zxr10RMAPSetL2vniLabelRowStatus  OBJECT-TYPE
    SYNTAX   RowStatus
    MAX-ACCESS  read-create
    STATUS  current
    DESCRIPTION
        "Row status"
    ::= { zxr10RMAPSetL2vniLabelEntry 100 }

--------------------------------------------------------------
--------------------------------------------------------------
--zxr10RMAPSetL3vniLabelTable
--------------------------------------------------------------
zxr10RMAPSetL3vniLabelTable  OBJECT-TYPE
    SYNTAX  SEQUENCE OF Zxr10RMAPSetL3vniLabelEntry
    MAX-ACCESS  not-accessible
    STATUS  current
    DESCRIPTION
        "Route-map set l3-vni label table"
    ::= { zxr10RMAPRuleObjects 71 }

zxr10RMAPSetL3vniLabelEntry  OBJECT-TYPE
    SYNTAX  Zxr10RMAPSetL3vniLabelEntry
    MAX-ACCESS  not-accessible
    STATUS  current
    DESCRIPTION          
       "Route-map set l3-vni label entry"
    INDEX  { zxr10RMAPName,  zxr10RMAPSequence}
    ::= { zxr10RMAPSetL3vniLabelTable 1 }
    
Zxr10RMAPSetL3vniLabelEntry ::=SEQUENCE {
        zxr10RMAPSetL3vniLabelName        DisplayString,
        zxr10RMAPSetL3vniLabelSequence    Integer32,
        zxr10RMAPSetL3vniLabel            Integer32,
        zxr10RMAPSetL3vniLabelRowStatus   RowStatus
    }

zxr10RMAPSetL3vniLabelName  OBJECT-TYPE
    SYNTAX   DisplayString(SIZE(1..31))
    MAX-ACCESS  not-accessible
    STATUS  current
    DESCRIPTION
        "Name of route-map (1-31 characters)"
    ::= { zxr10RMAPSetL3vniLabelEntry 1 } 
        
zxr10RMAPSetL3vniLabelSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetL3vniLabelEntry 2 }    

zxr10RMAPSetL3vniLabel  OBJECT-TYPE
    SYNTAX   Integer32(1..16777215)
    MAX-ACCESS  read-create
    STATUS  current
    DESCRIPTION
        "The value of l3-vni label."
    ::= { zxr10RMAPSetL3vniLabelEntry 3 }

zxr10RMAPSetL3vniLabelRowStatus  OBJECT-TYPE
    SYNTAX   RowStatus
    MAX-ACCESS  read-create
    STATUS  current
    DESCRIPTION
        "Row status"
    ::= { zxr10RMAPSetL3vniLabelEntry 100 }

--------------------------------------------------------------
--------------------------------------------------------------
--zxr10RMAPMatchL3VniLabelTable
--------------------------------------------------------------
zxr10RMAPMatchL3VniLabelTable  OBJECT-TYPE
    SYNTAX  SEQUENCE OF Zxr10RMAPMatchL3VniLabelEntry
    MAX-ACCESS  not-accessible
    STATUS  current
    DESCRIPTION
        "Route-map match l3-vni label table"
    ::= { zxr10RMAPRuleObjects 72 }

zxr10RMAPMatchL3VniLabelEntry  OBJECT-TYPE
    SYNTAX  Zxr10RMAPMatchL3VniLabelEntry
    MAX-ACCESS  not-accessible
    STATUS  current
    DESCRIPTION          
       "Route-map match l3-vni label entry"
    INDEX  { zxr10RMAPName,  zxr10RMAPSequence}
    ::= { zxr10RMAPMatchL3VniLabelTable 1 }
    
Zxr10RMAPMatchL3VniLabelEntry ::=SEQUENCE {
        zxr10RMAPMatchL3VniLabelName                  DisplayString,
        zxr10RMAPMatchL3VniLabelSequence              Integer32,
        zxr10RMAPMatchL3VniLabel                      Integer32,
        zxr10RMAPMatchL3VniLabelStatus             RowStatus
    }

zxr10RMAPMatchL3VniLabelName  OBJECT-TYPE
    SYNTAX   DisplayString(SIZE(1..31))
    MAX-ACCESS  not-accessible
    STATUS  current
    DESCRIPTION
        "Name of route-map (1-31 characters)"
    ::= { zxr10RMAPMatchL3VniLabelEntry 1 } 
        
zxr10RMAPMatchL3VniLabelSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchL3VniLabelEntry 2 }    

zxr10RMAPMatchL3VniLabel  OBJECT-TYPE
    SYNTAX   Integer32(1..16777215)
    MAX-ACCESS  read-create
    STATUS  current
    DESCRIPTION
        "The value of l3-vni label."
    ::= { zxr10RMAPMatchL3VniLabelEntry 3 }

zxr10RMAPMatchL3VniLabelStatus  OBJECT-TYPE
    SYNTAX   RowStatus
    MAX-ACCESS  read-create
    STATUS  current
    DESCRIPTION
        "Row status"
    ::= { zxr10RMAPMatchL3VniLabelEntry 100 }

--------------------------------------------------------------
--------------------------------------------------------------
--zxr10RMAPMatchL2VniLabelTable
--------------------------------------------------------------
zxr10RMAPMatchL2VniLabelTable  OBJECT-TYPE
    SYNTAX  SEQUENCE OF Zxr10RMAPMatchL2VniLabelEntry
    MAX-ACCESS  not-accessible
    STATUS  current
    DESCRIPTION
        "Route-map match l2-vni label table"
    ::= { zxr10RMAPRuleObjects 73 }

zxr10RMAPMatchL2VniLabelEntry  OBJECT-TYPE
    SYNTAX  Zxr10RMAPMatchL2VniLabelEntry
    MAX-ACCESS  not-accessible
    STATUS  current
    DESCRIPTION          
       "Route-map match l2-vni label entry"
    INDEX  { zxr10RMAPName,  zxr10RMAPSequence}
    ::= { zxr10RMAPMatchL2VniLabelTable 1 }
    
Zxr10RMAPMatchL2VniLabelEntry ::=SEQUENCE {
        zxr10RMAPMatchL2VniLabelName                  DisplayString,
        zxr10RMAPMatchL2VniLabelSequence              Integer32,
        zxr10RMAPMatchL2VniLabel                      Integer32,
        zxr10RMAPMatchL2VniLabelStatus             RowStatus
    }

zxr10RMAPMatchL2VniLabelName  OBJECT-TYPE
    SYNTAX   DisplayString(SIZE(1..31))
    MAX-ACCESS  not-accessible
    STATUS  current
    DESCRIPTION
        "Name of route-map (1-31 characters)"
    ::= { zxr10RMAPMatchL2VniLabelEntry 1 } 
        
zxr10RMAPMatchL2VniLabelSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchL2VniLabelEntry 2 }    

zxr10RMAPMatchL2VniLabel  OBJECT-TYPE
    SYNTAX   Integer32(1..16777215)
    MAX-ACCESS  read-create
    STATUS  current
    DESCRIPTION
        "The value of l2-vni label."
    ::= { zxr10RMAPMatchL2VniLabelEntry 3 }

zxr10RMAPMatchL2VniLabelStatus  OBJECT-TYPE
    SYNTAX   RowStatus
    MAX-ACCESS  read-create
    STATUS  current
    DESCRIPTION
        "Row status"
    ::= { zxr10RMAPMatchL2VniLabelEntry 100 }

--------------------------------------------------------------
--------------------------------------------------------------
--zxr10RMAPMatchPlyRtIdTable
--------------------------------------------------------------
zxr10RMAPMatchPlyRtIdTable  OBJECT-TYPE
    SYNTAX  SEQUENCE OF Zxr10RMAPMatchPlyRtIdEntry
    MAX-ACCESS  not-accessible
    STATUS  current
    DESCRIPTION
        "Route-map match policy-route-id table"
    ::= { zxr10RMAPRuleObjects 74 }

zxr10RMAPMatchPlyRtIdEntry  OBJECT-TYPE
    SYNTAX  Zxr10RMAPMatchPlyRtIdEntry
    MAX-ACCESS  not-accessible
    STATUS  current
    DESCRIPTION          
       "Route-map match policy-route-id entry"
    INDEX  { zxr10RMAPMatchPlyRtIdName,  zxr10RMAPMatchPlyRtIdSequence,
      zxr10RMAPMatchPlyRtId, zxr10RMAPMatchPlyRtIdDeriction}
    ::= { zxr10RMAPMatchPlyRtIdTable 1 }
    
Zxr10RMAPMatchPlyRtIdEntry ::=SEQUENCE {
        zxr10RMAPMatchPlyRtIdName                DisplayString,
        zxr10RMAPMatchPlyRtIdSequence            Integer32,
        zxr10RMAPMatchPlyRtId                    Integer32,
    zxr10RMAPMatchPlyRtIdDeriction           INTEGER,
        zxr10RMAPMatchPlyRtIdStatus             RowStatus
    }

zxr10RMAPMatchPlyRtIdName  OBJECT-TYPE
    SYNTAX   DisplayString(SIZE(1..31))
    MAX-ACCESS  not-accessible
    STATUS  current
    DESCRIPTION
        "Name of route-map (1-31 characters)"
    ::= { zxr10RMAPMatchPlyRtIdEntry 1 } 
        
zxr10RMAPMatchPlyRtIdSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchPlyRtIdEntry 2 }    

zxr10RMAPMatchPlyRtId  OBJECT-TYPE
    SYNTAX   Integer32(1..63)
    MAX-ACCESS  not-accessible
    STATUS  current
    DESCRIPTION
        "The value of policy-route-id."
    ::= { zxr10RMAPMatchPlyRtIdEntry 3 }
    
zxr10RMAPMatchPlyRtIdDeriction  OBJECT-TYPE
    SYNTAX     INTEGER {distination (1),
                        source (2) }
    MAX-ACCESS  not-accessible
    STATUS  current
    DESCRIPTION
        "The deriction of policy-route-id."
    ::= { zxr10RMAPMatchPlyRtIdEntry 4 }

zxr10RMAPMatchPlyRtIdStatus  OBJECT-TYPE
    SYNTAX   RowStatus
    MAX-ACCESS  read-create
    STATUS  current
    DESCRIPTION
        "Row status"
    ::= { zxr10RMAPMatchPlyRtIdEntry 100 }
    
--------------------------------------------------------------
--------------------------------------------------------------
--zxr10RMAPMatchIpv6PlyRtIdTable
--------------------------------------------------------------
zxr10RMAPMatchIpv6PlyRtIdTable  OBJECT-TYPE
    SYNTAX  SEQUENCE OF Zxr10RMAPMatchIpv6PlyRtIdEntry
    MAX-ACCESS  not-accessible
    STATUS  current
    DESCRIPTION
        "Route-map match ipv6 policy-route-id table"
    ::= { zxr10RMAPRuleObjects 75 }

zxr10RMAPMatchIpv6PlyRtIdEntry  OBJECT-TYPE
    SYNTAX  Zxr10RMAPMatchIpv6PlyRtIdEntry
    MAX-ACCESS  not-accessible
    STATUS  current
    DESCRIPTION          
       "Route-map match ipv6 policy-route-id entry"
    INDEX  { zxr10RMAPMatchIpv6PlyRtIdName,  zxr10RMAPMatchIpv6PlyRtIdSeq,
      zxr10RMAPMatchIpv6PlyRtId, zxr10RMAPMatchIpv6PlyRtIdDerict}
    ::= { zxr10RMAPMatchIpv6PlyRtIdTable 1 }
    
Zxr10RMAPMatchIpv6PlyRtIdEntry ::=SEQUENCE {
        zxr10RMAPMatchIpv6PlyRtIdName                DisplayString,
        zxr10RMAPMatchIpv6PlyRtIdSeq            Integer32,
        zxr10RMAPMatchIpv6PlyRtId                    Integer32,
        zxr10RMAPMatchIpv6PlyRtIdDerict           INTEGER,
        zxr10RMAPMatchIpv6PlyRtIdStatus             RowStatus
    }

zxr10RMAPMatchIpv6PlyRtIdName  OBJECT-TYPE
    SYNTAX   DisplayString(SIZE(1..31))
    MAX-ACCESS  not-accessible
    STATUS  current
    DESCRIPTION
        "Name of route-map (1-31 characters)"
    ::= { zxr10RMAPMatchIpv6PlyRtIdEntry 1 } 
        
zxr10RMAPMatchIpv6PlyRtIdSeq  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPMatchIpv6PlyRtIdEntry 2 }    

zxr10RMAPMatchIpv6PlyRtId  OBJECT-TYPE
    SYNTAX   Integer32(1..63)
    MAX-ACCESS  not-accessible
    STATUS  current
    DESCRIPTION
        "The value of policy-route-id."
    ::= { zxr10RMAPMatchIpv6PlyRtIdEntry 3 }
    
zxr10RMAPMatchIpv6PlyRtIdDerict  OBJECT-TYPE
    SYNTAX     INTEGER {distination (1),
                        source (2) }
    MAX-ACCESS  not-accessible
    STATUS  current
    DESCRIPTION
        "The deriction of policy-route-id."
    ::= { zxr10RMAPMatchIpv6PlyRtIdEntry 4 }

zxr10RMAPMatchIpv6PlyRtIdStatus  OBJECT-TYPE
    SYNTAX   RowStatus
    MAX-ACCESS  read-create
    STATUS  current
    DESCRIPTION
        "Row status"
    ::= { zxr10RMAPMatchIpv6PlyRtIdEntry 100 }
    
--------------------------------------------------------------
--------------------------------------------------------------
--zxr10RMAPSetPlyRtIdTable
--------------------------------------------------------------
zxr10RMAPSetPlyRtIdTable  OBJECT-TYPE
    SYNTAX  SEQUENCE OF Zxr10RMAPSetPlyRtIdEntry
    MAX-ACCESS  not-accessible
    STATUS  current
    DESCRIPTION
        "Route-map set policy-route-id table"
    ::= { zxr10RMAPRuleObjects 76 }

zxr10RMAPSetPlyRtIdEntry  OBJECT-TYPE
    SYNTAX  Zxr10RMAPSetPlyRtIdEntry
    MAX-ACCESS  not-accessible
    STATUS  current
    DESCRIPTION          
       "Route-map set policy-route-id entry"
    INDEX  { zxr10RMAPSetPlyRtIdName,  zxr10RMAPSetPlyRtIdSequence }
    ::= { zxr10RMAPSetPlyRtIdTable 1 }
    
Zxr10RMAPSetPlyRtIdEntry ::=SEQUENCE {
        zxr10RMAPSetPlyRtIdName                DisplayString,
        zxr10RMAPSetPlyRtIdSequence            Integer32,
        zxr10RMAPSetPlyRtId                    Integer32,     
        zxr10RMAPSetPlyRtIdStatus             RowStatus
    }

zxr10RMAPSetPlyRtIdName  OBJECT-TYPE
    SYNTAX   DisplayString(SIZE(1..31))
    MAX-ACCESS  not-accessible
    STATUS  current
    DESCRIPTION
        "Name of route-map (1-31 characters)"
    ::= { zxr10RMAPSetPlyRtIdEntry 1 } 
        
zxr10RMAPSetPlyRtIdSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetPlyRtIdEntry 2 }    

zxr10RMAPSetPlyRtId  OBJECT-TYPE
    SYNTAX   Integer32(1..63)
    MAX-ACCESS  read-create
    STATUS  current
    DESCRIPTION
        "The value of policy-route-id."
    ::= { zxr10RMAPSetPlyRtIdEntry 3 }

zxr10RMAPSetPlyRtIdStatus  OBJECT-TYPE
    SYNTAX   RowStatus
    MAX-ACCESS  read-create
    STATUS  current
    DESCRIPTION
        "Row status"
    ::= { zxr10RMAPSetPlyRtIdEntry 100 }
    
--------------------------------------------------------------
--------------------------------------------------------------
--zxr10RMAPSetMonitorGroupIdTable
--------------------------------------------------------------
zxr10RMAPSetMonitorGroupIdTable  OBJECT-TYPE
    SYNTAX  SEQUENCE OF Zxr10RMAPSetMonitorGroupIdEntry
    MAX-ACCESS  not-accessible
    STATUS  current
    DESCRIPTION
        "Route-map set monitor-group-id table"
    ::= { zxr10RMAPRuleObjects 77 }

zxr10RMAPSetMonitorGroupIdEntry  OBJECT-TYPE
    SYNTAX  Zxr10RMAPSetMonitorGroupIdEntry
    MAX-ACCESS  not-accessible
    STATUS  current
    DESCRIPTION          
       "Route-map set monitor-group-id entry"
    INDEX  { zxr10RMAPSetMonitorGroupIdName,  zxr10RMAPSetMonitorGroupIdSeq }
    ::= { zxr10RMAPSetMonitorGroupIdTable 1 }
    
Zxr10RMAPSetMonitorGroupIdEntry ::=SEQUENCE {
        zxr10RMAPSetMonitorGroupIdName                DisplayString,
        zxr10RMAPSetMonitorGroupIdSeq            Integer32,
        zxr10RMAPSetMonitorGroupId                    Integer32,        
        zxr10RMAPSetMonitorGroupIdStatus             RowStatus
    }

zxr10RMAPSetMonitorGroupIdName  OBJECT-TYPE
    SYNTAX   DisplayString(SIZE(1..31))
    MAX-ACCESS  not-accessible
    STATUS  current
    DESCRIPTION
        "Name of route-map (1-31 characters)"
    ::= { zxr10RMAPSetMonitorGroupIdEntry 1 } 
        
zxr10RMAPSetMonitorGroupIdSeq  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetMonitorGroupIdEntry 2 }    

zxr10RMAPSetMonitorGroupId  OBJECT-TYPE
    SYNTAX   Integer32(1..63)
    MAX-ACCESS  read-create
    STATUS  current
    DESCRIPTION
        "The value of policy-route-id."
    ::= { zxr10RMAPSetMonitorGroupIdEntry 3 }

zxr10RMAPSetMonitorGroupIdStatus  OBJECT-TYPE
    SYNTAX   RowStatus
    MAX-ACCESS  read-create
    STATUS  current
    DESCRIPTION
        "Row status"
    ::= { zxr10RMAPSetMonitorGroupIdEntry 100 }
    
--------------------------------------------------------------
--------------------------------------------------------------
--zxr10RMAPLoadShareTable
--------------------------------------------------------------
zxr10RMAPLoadShareTable  OBJECT-TYPE
    SYNTAX  SEQUENCE OF Zxr10RMAPLoadShareEntry
    MAX-ACCESS  not-accessible
    STATUS  current
    DESCRIPTION
        "Route-map load share table"
    ::= { zxr10RMAPRuleObjects 78 }

zxr10RMAPLoadShareEntry  OBJECT-TYPE
    SYNTAX  Zxr10RMAPLoadShareEntry
    MAX-ACCESS  not-accessible
    STATUS  current
    DESCRIPTION          
       "Load share"
    INDEX  { zxr10RMAPLoadShareName,  zxr10RMAPLoadShareSequence }
    ::= { zxr10RMAPLoadShareTable 1 }
    
Zxr10RMAPLoadShareEntry ::=SEQUENCE {
        zxr10RMAPLoadShareName             DisplayString,
        zxr10RMAPLoadShareSequence         Integer32,
        zxr10RMAPLoadShareEnable           Integer32,
        zxr10RMAPLoadShareStatus        RowStatus
    }

zxr10RMAPLoadShareName  OBJECT-TYPE
    SYNTAX   DisplayString(SIZE(1..31))
    MAX-ACCESS  not-accessible
    STATUS  current
    DESCRIPTION
        "Name of route-map (1-31 characters)"
    ::= { zxr10RMAPLoadShareEntry 1 } 
        
zxr10RMAPLoadShareSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPLoadShareEntry 2 }    

zxr10RMAPLoadShareEnable  OBJECT-TYPE
    SYNTAX Integer32(0..1)
    MAX-ACCESS  read-create
    STATUS  current
    DESCRIPTION
        "Load share enable."
    ::= { zxr10RMAPLoadShareEntry 3 }

zxr10RMAPLoadShareStatus  OBJECT-TYPE
    SYNTAX   RowStatus
    MAX-ACCESS  read-create
    STATUS  current
    DESCRIPTION
        "Row status"
    ::= { zxr10RMAPLoadShareEntry 100 }
    
--------------------------------------------------------------
--------------------------------------------------------------
--zxr10RMAPContinueTable
--------------------------------------------------------------
zxr10RMAPContinueTable  OBJECT-TYPE
    SYNTAX  SEQUENCE OF Zxr10RMAPContinueEntry
    MAX-ACCESS  not-accessible
    STATUS  current
    DESCRIPTION
        "Route-map continue table"
    ::= { zxr10RMAPRuleObjects 79 }

zxr10RMAPContinueEntry  OBJECT-TYPE
    SYNTAX  Zxr10RMAPContinueEntry
    MAX-ACCESS  not-accessible
    STATUS  current
    DESCRIPTION          
       "Route-map continue entry"
    INDEX  { zxr10RMAPContinueName,  zxr10RMAPContinueSequence }
    ::= { zxr10RMAPContinueTable 1 }
    
Zxr10RMAPContinueEntry ::=SEQUENCE {
        zxr10RMAPContinueName                DisplayString,
        zxr10RMAPContinueSequence            Integer32,
        zxr10RMAPContinue                    Integer32,
        zxr10RMAPContinueNext                Integer32,
        zxr10RMAPContinueStatus             RowStatus
    }

zxr10RMAPContinueName  OBJECT-TYPE
    SYNTAX   DisplayString(SIZE(1..31))
    MAX-ACCESS  not-accessible
    STATUS  current
    DESCRIPTION
        "Name of route-map (1-31 characters)"
    ::= { zxr10RMAPContinueEntry 1 } 
        
zxr10RMAPContinueSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPContinueEntry 2 }    

zxr10RMAPContinue  OBJECT-TYPE
    SYNTAX   Integer32(0..65535)
    MAX-ACCESS  read-create
    STATUS  current
    DESCRIPTION
        "The value of continue sequence."
    ::= { zxr10RMAPContinueEntry 3 }
    
zxr10RMAPContinueNext  OBJECT-TYPE
    SYNTAX     Integer32(0..1)
    MAX-ACCESS  read-create
    STATUS  current
    DESCRIPTION
        "Continue next."
    ::= { zxr10RMAPContinueEntry 4 }

zxr10RMAPContinueStatus  OBJECT-TYPE
    SYNTAX   RowStatus
    MAX-ACCESS  read-create
    STATUS  current
    DESCRIPTION
        "Row status"
    ::= { zxr10RMAPContinueEntry 100 }
    
--------------------------------------------------------------  
--------------------------------------------------------------
--zxr10RMAPTimeRangeTable
--------------------------------------------------------------
zxr10RMAPTimeRangeTable  OBJECT-TYPE
    SYNTAX  SEQUENCE OF Zxr10RMAPTimeRangeEntry
    MAX-ACCESS  not-accessible
    STATUS  current
    DESCRIPTION
        "Route-map Time Range Table"
    ::= { zxr10RMAPRuleObjects 80 }

zxr10RMAPTimeRangeEntry  OBJECT-TYPE
    SYNTAX  Zxr10RMAPTimeRangeEntry
    MAX-ACCESS  not-accessible
    STATUS  current
    DESCRIPTION          
       "Route-map time range."
    INDEX  { zxr10RMAPTimeRangeName,  zxr10RMAPTimeRangeSequence }
    ::= { zxr10RMAPTimeRangeTable 1 }
    
Zxr10RMAPTimeRangeEntry ::=SEQUENCE {
        zxr10RMAPTimeRangeName         DisplayString,
        zxr10RMAPTimeRangeSequence     Integer32,
        zxr10RMAPTimeRange             DisplayString,
        zxr10RMAPTimeRangeStatus    RowStatus
    }

zxr10RMAPTimeRangeName  OBJECT-TYPE
    SYNTAX   DisplayString(SIZE(1..31))
    MAX-ACCESS  not-accessible
    STATUS  current
    DESCRIPTION
        "Name of Route-map (1-31 characters)"
    ::= { zxr10RMAPTimeRangeEntry 1 } 
        
zxr10RMAPTimeRangeSequence  OBJECT-TYPE
    SYNTAX   Integer32
    MAX-ACCESS  not-accessible
    STATUS  current
    DESCRIPTION
        "The sequence of a route-map.
         The range of config is 0 to 65535.
         Each name of route-map has 100 sequences at most."
    ::= { zxr10RMAPTimeRangeEntry 2 }    

zxr10RMAPTimeRange  OBJECT-TYPE
    SYNTAX   DisplayString(SIZE(1..31))
    MAX-ACCESS  read-create
    STATUS  current
    DESCRIPTION
        "Name of time range(1-31 characters)."
    ::= { zxr10RMAPTimeRangeEntry 3 }

zxr10RMAPTimeRangeStatus  OBJECT-TYPE
    SYNTAX   RowStatus
    MAX-ACCESS  read-create
    STATUS  current
    DESCRIPTION
        "RowStatus"
    ::= { zxr10RMAPTimeRangeEntry 100 }

--------------------------------------------------------------
--------------------------------------------------------------
--zxr10RMAPSetCommunityNameTable
--------------------------------------------------------------
zxr10RMAPSetCommunityNameTable  OBJECT-TYPE
    SYNTAX  SEQUENCE OF Zxr10RMAPSetCommunityNameEntry
    MAX-ACCESS  not-accessible
    STATUS  current
    DESCRIPTION
        "Route-map Set Community Table"
    ::= { zxr10RMAPRuleObjects 81 }

zxr10RMAPSetCommunityNameEntry  OBJECT-TYPE
    SYNTAX  Zxr10RMAPSetCommunityNameEntry
    MAX-ACCESS  not-accessible
    STATUS  current
    DESCRIPTION          
       "Set BGP community name."
    INDEX  { zxr10RMAPSetCommunityName, 
             zxr10RMAPSetCommunitySequence, 
             zxr10RMAPSetCommunityIsAddtive, 
             zxr10RMAPSetCommunityListName}
    ::= { zxr10RMAPSetCommunityNameTable 1 }
    
Zxr10RMAPSetCommunityNameEntry ::=SEQUENCE {
        zxr10RMAPSetCommunityName              DisplayString,
        zxr10RMAPSetCommunitySequence          Integer32,
        zxr10RMAPSetCommunityIsAddtive         RmapSetComm,
        zxr10RMAPSetCommunityListName          DisplayString,
        zxr10RMAPSetCommunityRowStatus         RowStatus  
    }

zxr10RMAPSetCommunityName  OBJECT-TYPE
    SYNTAX   DisplayString(SIZE(1..31))
    MAX-ACCESS  not-accessible
    STATUS  current
    DESCRIPTION
        "Name of Route-map (1-31 characters)"
    ::= { zxr10RMAPSetCommunityNameEntry 1 } 
        
zxr10RMAPSetCommunitySequence  OBJECT-TYPE
    SYNTAX   Integer32
    MAX-ACCESS  not-accessible
    STATUS  current
    DESCRIPTION
        "The sequence of a route-map.
         The range of config is 0 to 65535.
         Each name of route-map has 100 sequences at most."
    ::= { zxr10RMAPSetCommunityNameEntry 2 }    

zxr10RMAPSetCommunityIsAddtive  OBJECT-TYPE
    SYNTAX   RmapSetComm
    MAX-ACCESS  not-accessible
    STATUS  current
    DESCRIPTION
        "additive Add to the existing community. Value is 5."
    ::= { zxr10RMAPSetCommunityNameEntry 3 }

zxr10RMAPSetCommunityListName  OBJECT-TYPE
    SYNTAX   DisplayString(SIZE(1..31))
    MAX-ACCESS  not-accessible
    STATUS  current
    DESCRIPTION
        "Community list name (1-31 characters)"
    ::= { zxr10RMAPSetCommunityNameEntry 4 } 

zxr10RMAPSetCommunityRowStatus  OBJECT-TYPE
    SYNTAX   RowStatus
    MAX-ACCESS  read-create
    STATUS  current
    DESCRIPTION
        "RowStatus"
    ::= { zxr10RMAPSetCommunityNameEntry 100 }

--------------------------------------------------------------
--------------------------------------------------------------
--zxr10RMAPSetDistanceTable
--------------------------------------------------------------
zxr10RMAPSetDistanceTable  OBJECT-TYPE
    SYNTAX  SEQUENCE OF Zxr10RMAPSetDistanceEntry
    MAX-ACCESS  not-accessible
    STATUS  current
    DESCRIPTION
        "Route-map set distance table"
    ::= { zxr10RMAPRuleObjects 82 }

zxr10RMAPSetDistanceEntry  OBJECT-TYPE
    SYNTAX  Zxr10RMAPSetDistanceEntry
    MAX-ACCESS  not-accessible
    STATUS  current
    DESCRIPTION          
       "Route-map set distance entry"
    INDEX  { zxr10RMAPSetDistanceName,  zxr10RMAPSetDistanceSequence }
    ::= { zxr10RMAPSetDistanceTable 1 }
    
Zxr10RMAPSetDistanceEntry ::=SEQUENCE {
        zxr10RMAPSetDistanceName                DisplayString,
        zxr10RMAPSetDistanceSequence            Integer32,
        zxr10RMAPSetDistance                    Integer32,     
        zxr10RMAPSetDistanceRowStatus           RowStatus
    }

zxr10RMAPSetDistanceName  OBJECT-TYPE
    SYNTAX   DisplayString(SIZE(1..31))
    MAX-ACCESS  not-accessible
    STATUS  current
    DESCRIPTION
        "Name of route-map (1-31 characters)"
    ::= { zxr10RMAPSetDistanceEntry 1 } 
        
zxr10RMAPSetDistanceSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetDistanceEntry 2 }    

zxr10RMAPSetDistance  OBJECT-TYPE
    SYNTAX   Integer32(1..255)
    MAX-ACCESS  read-create
    STATUS  current
    DESCRIPTION
        "The value of distance."
    ::= { zxr10RMAPSetDistanceEntry 3 }

zxr10RMAPSetDistanceRowStatus  OBJECT-TYPE
    SYNTAX   RowStatus
    MAX-ACCESS  read-create
    STATUS  current
    DESCRIPTION
        "Row status"
    ::= { zxr10RMAPSetDistanceEntry 100 }

--------------------------------------------------------------  
--------------------------------------------------------------
--zxr10RMAPDescriptionTable
--------------------------------------------------------------
zxr10RMAPDescriptionTable  OBJECT-TYPE
    SYNTAX  SEQUENCE OF Zxr10RMAPDescriptionEntry
    MAX-ACCESS  not-accessible
    STATUS  current
    DESCRIPTION
        "Route-map Description Table"
    ::= { zxr10RMAPRuleObjects 83 }

zxr10RMAPDescriptionEntry  OBJECT-TYPE
    SYNTAX  Zxr10RMAPDescriptionEntry
    MAX-ACCESS  not-accessible
    STATUS  current
    DESCRIPTION          
       "Route-map description."
    INDEX  { zxr10RMAPDescriptionName,  zxr10RMAPDescriptionSequence }
    ::= { zxr10RMAPDescriptionTable 1 }
    
Zxr10RMAPDescriptionEntry ::=SEQUENCE {
        zxr10RMAPDescriptionName         DisplayString,
        zxr10RMAPDescriptionSequence     Integer32,
        zxr10RMAPDescription             DisplayString,
        zxr10RMAPDescriptionStatus       RowStatus
    }

zxr10RMAPDescriptionName  OBJECT-TYPE
    SYNTAX   DisplayString(SIZE(1..31))
    MAX-ACCESS  not-accessible
    STATUS  current
    DESCRIPTION
        "Name of Route-map (1-31 characters)"
    ::= { zxr10RMAPDescriptionEntry 1 } 
        
zxr10RMAPDescriptionSequence  OBJECT-TYPE
    SYNTAX   Integer32
    MAX-ACCESS  not-accessible
    STATUS  current
    DESCRIPTION
        "The sequence of a route-map.
         The range of config is 0 to 65535.
         Each name of route-map has 100 sequences at most."
    ::= { zxr10RMAPDescriptionEntry 2 }    

zxr10RMAPDescription  OBJECT-TYPE
    SYNTAX   DisplayString(SIZE(1..199))
    MAX-ACCESS  read-create
    STATUS  current
    DESCRIPTION
        "Description of the route-map (1-199 characters)."
    ::= { zxr10RMAPDescriptionEntry 3 }

zxr10RMAPDescriptionStatus  OBJECT-TYPE
    SYNTAX   RowStatus
    MAX-ACCESS  read-create
    STATUS  current
    DESCRIPTION
        "RowStatus"
    ::= { zxr10RMAPDescriptionEntry 100 }

--------------------------------------------------------------
--------------------------------------------------------------
--zxr10RMAPMatchIpPeerTable
--------------------------------------------------------------
zxr10RMAPMatchIpPeerTable  OBJECT-TYPE
    SYNTAX  SEQUENCE OF Zxr10RMAPMatchIpPeerEntry
    MAX-ACCESS  not-accessible
    STATUS  current
    DESCRIPTION
        "The table of route-map match IPV4 peer by ACL."
    ::= { zxr10RMAPRuleObjects 84 }

zxr10RMAPMatchIpPeerEntry  OBJECT-TYPE
    SYNTAX  Zxr10RMAPMatchIpPeerEntry
    MAX-ACCESS  not-accessible
    STATUS  current
    DESCRIPTION          
       "The entry of route-map match IPV4 peer.
        This match item sets the route-map name with ipv4 type.
        It conflicts with other match or set items 
        which set the route-map name with IPV6 type.
        Otherwise, It conflicts with the item that match BGP peer by PFL.
        If zxr10RMAPMatchPeerIsConfigAcl is true, 
        it expresses that this config is match IPV4 peer by ACL."
    INDEX  { zxr10RMAPMatchIpPeerName, 
             zxr10RMAPMatchIpPeerSequence, 
             zxr10RMAPMatchIpPeerAclOrPfl, 
             zxr10RMAPMatchIpPeerIsPfl }
    ::= { zxr10RMAPMatchIpPeerTable 1 }
    
Zxr10RMAPMatchIpPeerEntry ::=SEQUENCE {
        zxr10RMAPMatchIpPeerName               DisplayString,
        zxr10RMAPMatchIpPeerSequence           Integer32,
        zxr10RMAPMatchIpPeerAclOrPfl           DisplayString,
        zxr10RMAPMatchIpPeerIsPfl              Integer32,
        zxr10RMAPMatchIpPeerRowStatus          RowStatus
    }

zxr10RMAPMatchIpPeerName  OBJECT-TYPE
    SYNTAX   DisplayString(SIZE(1..31))
    MAX-ACCESS  not-accessible
    STATUS  current
    DESCRIPTION
        "The name of route-map (1-31 characters)"
    ::= { zxr10RMAPMatchIpPeerEntry 1 } 
        
zxr10RMAPMatchIpPeerSequence  OBJECT-TYPE
    SYNTAX   Integer32
    MAX-ACCESS  not-accessible
    STATUS  current
    DESCRIPTION
        "The sequence of a route-map.
         The range of config is 0 to 65535.
         Each name of route-map has 100 sequences at most."
    ::= { zxr10RMAPMatchIpPeerEntry 2 }  
    
 zxr10RMAPMatchIpPeerAclOrPfl  OBJECT-TYPE
    SYNTAX   DisplayString(SIZE(1..31))
    MAX-ACCESS  not-accessible
    STATUS  current
    DESCRIPTION
        "The name of an access-list or prefix-list(1-31 characters).
         Each sequence has 10 match IPv4 peer items at most."
    ::= { zxr10RMAPMatchIpPeerEntry 3 }
 
zxr10RMAPMatchIpPeerIsPfl  OBJECT-TYPE
    SYNTAX   Integer32
    MAX-ACCESS  not-accessible
    STATUS  current
    DESCRIPTION
        "It expresses that this config is match IPV4 peer by PFL, 
         otherwise by ACL."
    ::= { zxr10RMAPMatchIpPeerEntry 4 }

zxr10RMAPMatchIpPeerRowStatus  OBJECT-TYPE
    SYNTAX   RowStatus
    MAX-ACCESS  read-create
    STATUS  current
    DESCRIPTION
        "RowStatus"
    ::= { zxr10RMAPMatchIpPeerEntry 100 }

--------------------------------------------------------------
--------------------------------------------------------------
--zxr10RMAPMatchIpv6PeerTable
--------------------------------------------------------------
zxr10RMAPMatchIpv6PeerTable  OBJECT-TYPE
    SYNTAX  SEQUENCE OF Zxr10RMAPMatchIpv6PeerEntry
    MAX-ACCESS  not-accessible
    STATUS  obsolete
    DESCRIPTION
        "The table of route-map match IPV6 peer"
    ::= { zxr10RMAPRuleObjects 85 }

zxr10RMAPMatchIpv6PeerEntry  OBJECT-TYPE
    SYNTAX  Zxr10RMAPMatchIpv6PeerEntry
    MAX-ACCESS  not-accessible
    STATUS  obsolete
    DESCRIPTION          
       "The entry of route-map match IPV6 peer.
        This match item sets the route-map name with IPV6 type.
        It conflicts with other match or set items 
        which set the route-map name with IPV4 type."
    INDEX  { zxr10RMAPMatchIpv6PeerName,  
             zxr10RMAPMatchIpv6PeerSequence, 
             zxr10RMAPMatchIpv6PeerAclOrPfl, 
             zxr10RMAPMatchIpv6PeerIsPfl }
    ::= { zxr10RMAPMatchIpv6PeerTable 1 }
    
Zxr10RMAPMatchIpv6PeerEntry ::=SEQUENCE {
        zxr10RMAPMatchIpv6PeerName           DisplayString,
        zxr10RMAPMatchIpv6PeerSequence       Integer32,
        zxr10RMAPMatchIpv6PeerAclOrPfl       DisplayString,
        zxr10RMAPMatchIpv6PeerIsPfl          Integer32,
        zxr10RMAPMatchIpv6PeerRowStatus      RowStatus
    }
    
zxr10RMAPMatchIpv6PeerName  OBJECT-TYPE
    SYNTAX   DisplayString(SIZE(1..31))
    MAX-ACCESS  not-accessible
    STATUS  obsolete
    DESCRIPTION
        "The name of route-map (1-31 characters)"
    ::= { zxr10RMAPMatchIpv6PeerEntry 1 } 
        
zxr10RMAPMatchIpv6PeerSequence  OBJECT-TYPE
    SYNTAX   Integer32
    MAX-ACCESS  not-accessible
    STATUS  obsolete
    DESCRIPTION
        "The sequence of a route-map.
         The range of config is 0 to 65535.
         Each name of route-map has 100 sequences at most."
    ::= { zxr10RMAPMatchIpv6PeerEntry 2 }    

zxr10RMAPMatchIpv6PeerAclOrPfl  OBJECT-TYPE
    SYNTAX   DisplayString(SIZE(1..31))
    MAX-ACCESS  not-accessible
    STATUS  obsolete
    DESCRIPTION
        "The name of an access-list or prefix-list(1-31 characters).
         Each sequence has 10 match IPV6 address items at most."
    ::= { zxr10RMAPMatchIpv6PeerEntry 3 }

zxr10RMAPMatchIpv6PeerIsPfl  OBJECT-TYPE
    SYNTAX   Integer32
    MAX-ACCESS  not-accessible
    STATUS  current
    DESCRIPTION
        "It expresses that this config is match IPV6 peer by PFL, 
         otherwise by ACL."
    ::= { zxr10RMAPMatchIpv6PeerEntry 4 }  

zxr10RMAPMatchIpv6PeerRowStatus  OBJECT-TYPE
    SYNTAX   RowStatus
    MAX-ACCESS  read-create
    STATUS  obsolete
    DESCRIPTION
        "RowStatus"
    ::= { zxr10RMAPMatchIpv6PeerEntry 100 }

--------------------------------------------------------------
--------------------------------------------------------------
--zxr10RMAPSetL2EquVniLabelTable
--------------------------------------------------------------
zxr10RMAPSetL2EquVniLabelTable  OBJECT-TYPE
    SYNTAX  SEQUENCE OF Zxr10RMAPSetL2EquVniLabelEntry
    MAX-ACCESS  not-accessible
    STATUS  current
    DESCRIPTION
        "The table of route-map set L2 equivalent VNI label"
    ::= { zxr10RMAPRuleObjects 86 }

zxr10RMAPSetL2EquVniLabelEntry  OBJECT-TYPE
    SYNTAX  Zxr10RMAPSetL2EquVniLabelEntry
    MAX-ACCESS  not-accessible
    STATUS  current
    DESCRIPTION          
       "The entry of route-map set L2 equivalent VNI label"
    INDEX  { zxr10RMAPSetL2EquVniLabelName,  
             zxr10RMAPSetL2EquVniLabelSeq}
    ::= { zxr10RMAPSetL2EquVniLabelTable 1 }
    
Zxr10RMAPSetL2EquVniLabelEntry ::=SEQUENCE {
        zxr10RMAPSetL2EquVniLabelName               DisplayString,
        zxr10RMAPSetL2EquVniLabelSeq                Integer32,
        zxr10RMAPSetL2EquVniLabel                   TruthValue,
        zxr10RMAPSetL2EquVniLabelRow                RowStatus
    }

zxr10RMAPSetL2EquVniLabelName  OBJECT-TYPE
    SYNTAX   DisplayString(SIZE(1..31))
    MAX-ACCESS  not-accessible
    STATUS  current
    DESCRIPTION
        "The name of route-map (1-31 characters)"
    ::= { zxr10RMAPSetL2EquVniLabelEntry 1 } 
        
zxr10RMAPSetL2EquVniLabelSeq  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetL2EquVniLabelEntry 2 }    

zxr10RMAPSetL2EquVniLabel  OBJECT-TYPE
    SYNTAX   TruthValue
    MAX-ACCESS  read-create
    STATUS  current
    DESCRIPTION
        "The value of L2 equivalent VNI label."
    ::= { zxr10RMAPSetL2EquVniLabelEntry 3 }

zxr10RMAPSetL2EquVniLabelRow  OBJECT-TYPE
    SYNTAX   RowStatus
    MAX-ACCESS  read-create
    STATUS  current
    DESCRIPTION
        "Row status"
    ::= { zxr10RMAPSetL2EquVniLabelEntry 100 }

--------------------------------------------------------------
--------------------------------------------------------------
--zxr10RMAPSetL3EquVniLabelTable
--------------------------------------------------------------
zxr10RMAPSetL3EquVniLabelTable  OBJECT-TYPE
    SYNTAX  SEQUENCE OF Zxr10RMAPSetL3EquVniLabelEntry
    MAX-ACCESS  not-accessible
    STATUS  current
    DESCRIPTION
        "The table of route-map set L3 equivalent VNI label"
    ::= { zxr10RMAPRuleObjects 87 }

zxr10RMAPSetL3EquVniLabelEntry  OBJECT-TYPE
    SYNTAX  Zxr10RMAPSetL3EquVniLabelEntry
    MAX-ACCESS  not-accessible
    STATUS  current
    DESCRIPTION          
       "The entry of route-map set L3 equivalent VNI label"
    INDEX  { zxr10RMAPSetL3EquVniLabelName,  
             zxr10RMAPSetL3EquVniLabelSeq}
    ::= { zxr10RMAPSetL3EquVniLabelTable 1 }
    
Zxr10RMAPSetL3EquVniLabelEntry ::=SEQUENCE {
        zxr10RMAPSetL3EquVniLabelName               DisplayString,
        zxr10RMAPSetL3EquVniLabelSeq                Integer32,
        zxr10RMAPSetL3EquVniLabel                   TruthValue,
        zxr10RMAPSetL3EquVniLabelRow                RowStatus
    }

zxr10RMAPSetL3EquVniLabelName  OBJECT-TYPE
    SYNTAX   DisplayString(SIZE(1..31))
    MAX-ACCESS  not-accessible
    STATUS  current
    DESCRIPTION
        "The name of route-map (1-31 characters)"
    ::= { zxr10RMAPSetL3EquVniLabelEntry 1 } 
        
zxr10RMAPSetL3EquVniLabelSeq  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetL3EquVniLabelEntry 2 }    

zxr10RMAPSetL3EquVniLabel  OBJECT-TYPE
    SYNTAX   TruthValue
    MAX-ACCESS  read-create
    STATUS  current
    DESCRIPTION
        "The value of L3 equivalent VNI label."
    ::= { zxr10RMAPSetL3EquVniLabelEntry 3 }

zxr10RMAPSetL3EquVniLabelRow  OBJECT-TYPE
    SYNTAX   RowStatus
    MAX-ACCESS  read-create
    STATUS  current
    DESCRIPTION
        "Row status"
    ::= { zxr10RMAPSetL3EquVniLabelEntry 100 }

--------------------------------------------------------------
--------------------------------------------------------------
--zxr10RMAPSetSHScopeTable
--------------------------------------------------------------
zxr10RMAPSetSHScopeTable  OBJECT-TYPE
    SYNTAX  SEQUENCE OF Zxr10RMAPSetSHScopeEntry
    MAX-ACCESS  not-accessible
    STATUS  current
    DESCRIPTION
        "The table of route-map set split-horizon-scope"
    ::= { zxr10RMAPRuleObjects 88 }

zxr10RMAPSetSHScopeEntry  OBJECT-TYPE
    SYNTAX  Zxr10RMAPSetSHScopeEntry
    MAX-ACCESS  not-accessible
    STATUS  current
    DESCRIPTION          
       "The entry of route-map set split-horizon-scope"
    INDEX  { zxr10RMAPSetSHScopeName,  
             zxr10RMAPSetSHScopeSequence}
    ::= { zxr10RMAPSetSHScopeTable 1 }
    
Zxr10RMAPSetSHScopeEntry ::=SEQUENCE {
        zxr10RMAPSetSHScopeName        DisplayString,
        zxr10RMAPSetSHScopeSequence    Integer32,
        zxr10RMAPSetSHScope            DisplayString,
        zxr10RMAPSetSHScopeRowStatus   RowStatus
    }

zxr10RMAPSetSHScopeName  OBJECT-TYPE
    SYNTAX   DisplayString(SIZE(1..31))
    MAX-ACCESS  not-accessible
    STATUS  current
    DESCRIPTION
        "The name of route-map (1-31 characters)"
    ::= { zxr10RMAPSetSHScopeEntry 1 } 
        
zxr10RMAPSetSHScopeSequence  OBJECT-TYPE
    SYNTAX   Integer32(0..65535)
    MAX-ACCESS  not-accessible
    STATUS  current
    DESCRIPTION
        "The sequence of a route-map.
         The range of config is 0 to 65535.
         Each name of route-map has 100 sequences at most."
    ::= { zxr10RMAPSetSHScopeEntry 2 }    

zxr10RMAPSetSHScope  OBJECT-TYPE
    SYNTAX   DisplayString(SIZE(1))
    MAX-ACCESS  read-create
    STATUS  current
    DESCRIPTION
        "The name of split-horizon-scope(<A-Z>)."
    ::= { zxr10RMAPSetSHScopeEntry 3 }

zxr10RMAPSetSHScopeRowStatus  OBJECT-TYPE
    SYNTAX   RowStatus
    MAX-ACCESS  read-create
    STATUS  current
    DESCRIPTION
        "Row status"
    ::= { zxr10RMAPSetSHScopeEntry 100 }


END
