ZXR10-ADM-MGR-MIB DEFINITIONS ::= BEGIN

IMPORTS
        MODULE-IDENTITY, OBJECT-TYPE,
        enterprises, Unsigned32, IpAddress
                FROM SNMPv2-SMI
        DisplayString, DateAndTime,TEXTUAL-CONVENTION
                FROM SNMPv2-TC
        Ipv6Address
                FROM IPV6-TC; 
    
    zxr10AdmmgrMIB MODULE-IDENTITY
        LAST-UPDATED "201807230000Z"
        ORGANIZATION "ZTE Corporation"
        CONTACT-INFO
            "Chen wenbo
             Tel: +86-25-52870000 
             E-Mail: chen.wenbo@zte.com.cn"
        
        DESCRIPTION
            "The MIB module to describe the information for 
            administrator management"

        REVISION "201807230000Z"
        DESCRIPTION
            "Add node zxr10AdmmgrAuthorWebAllowed,zxr10AdmmgrAuthorConsoleAllowed and
            zxr10AdmmgrAuthorOnlyTelnetAllow"

        REVISION "201807170000Z"
        DESCRIPTION
            "Add node zxr10AdmmgrStrongPwdMinCharSet"

        REVISION "201801310000Z"
        DESCRIPTION
            "Add node zxr10AdmmgrPwdRelatedUsrSubstChk and 
            zxr10AdmmgrPwdRelatedUsrInverChk"

        REVISION "201711250000Z"
        DESCRIPTION
            "Add node zxr10AdmmgrStrongPwdCheck"

        REVISION "201710171120Z"
        DESCRIPTION
            "Add node zxr10AdmmgrIsPwdIrreversible"

        REVISION "201508170000Z"
        DESCRIPTION
            "Add task l2protocoltunnel(2317),nhrp(2318) and 
             rpl(3084) in TEXTUAL-CONVENTION AdmmgrSysTaskName"

        REVISION "201504280000Z"
        DESCRIPTION
            "Modify word spelling error,
             Add task fcoe(1286) in TEXTUAL-CONVENTION AdmmgrSysTaskName"

        REVISION "201504200000Z"
        DESCRIPTION
            "Add task meap(3595) in TEXTUAL-CONVENTION AdmmgrSysTaskName"
             
        REVISION "201503030000Z"
        DESCRIPTION
            "Change the description of zxr10AdmmgrFailuedUserIpv4
             and zxr10AdmmgrFailuedUserIpv6"

        REVISION "201412020000Z"
        DESCRIPTION
            "Change the length range of zxr10AdmmgrAuthenAAATemplate,
             zxr10AdmmgrAuthorAAATemplate,zxr10AdmmgrCmdGroupName,
             zxr10AdmmgrUserGroupPassword,zxr10AdmmgrFailuedUser,
             zxr10AdmmgrOnlineUserIpaddr,zxr10admmgrOnlineUserOnlineTime,
             zxr10admmgrOnlineUserLoginTime,zxr10admmgrOnlineUserIdleTime,
             zxr10AdmmgrarRoleName,zxr10AdmmgrRoleDescription,
             zxr10AdmmgrriInheritRoleName,zxr10AdmmgrrtgTaskGroupName,
             zxr10AdmmgrTaskGrpDescription,zxr10AdmmgrtgiInheritGroupName.
             Change the description of zxr10AdmmgrStrongPwdNumber,
             zxr10AdmmgrStrongPwdCapital,zxr10AdmmgrStrongPwdLowercase,
             zxr10AdmmgrStrongPwdSpecial,zxr10AdmmgrUserLock,
             zxr10AdmmgrUserOncePwd"

        REVISION "201411180000Z"
        DESCRIPTION
            "Change the default value of 
            zxr10AdmmgrAccountSwitch and zxr10AdmmgrRoleBasedModel,
            Change the length range of zxr10AdmmgrAuthorDescription"

        REVISION "201406240000Z"
        DESCRIPTION
            "Add scalar node,zxr10AdmmgrRoleBasedModel,
             Add tables,zxr10AdmmgrRoleTable,zxr10AdmmgrRoleInheritTable,
             zxr10AdmmgrRoleTaskGroupTable,zxr10AdmmgrTaskGroupTable,
             zxr10AdmmgrtgInheritTable,zxr10AdmmgrTaskGroupTaskTable,
             zxr10AdmmgrAuthorRoleTable,zxr10AdmmgrUserPrivLocalTable,
             zxr10AdmmgrRolePrivCfgTable,zxr10AdmmgrRolePrivDefTable,
             zxr10AdmmgrOnlineUserInfoTable,
             Add TEXTUAL-CONVENTION AdmmgrSysTaskName"

        REVISION "201311290000Z"  -- 2013-11-29 12:00
        DESCRIPTION
            "Change the max length of 
            zxr10AdmmgrUserName,zxr10AdmmgrShowLockStateUser,
            zxr10AdmmgrFailuedUser"

        REVISION "201309180000Z"
        DESCRIPTION
                "Change the range of 
                zxr10AdmmgrAccountSwitch, zxr10AdmmgrGlobalEnableTemplate
                zxr10AdmmgrAsciiAuthenTemplate, zxr10AdmmgrAsciiAuthorTemplate, 
                zxr10AdmmgrStrongPwdMinLength, zxr10AdmmgrAuthenFailTime, 
                zxr10AdmmgrAuthenLockMinute, zxr10AdmmgrDefaultAuthenTemplate,
                zxr10AdmmgrDefaultAuthorTemplate, zxr10AdmmgrLoginBlockSeconds, 
                zxr10AdmmgrLoginBlockAttempts,zxr10AdmmgrLoginBlockWatchSec,
                zxr10AdmmgrLoginBlockFailTimes, zxr10AdmmgrUserPassword, 
                zxr10AdmmgrUserAuthenTemplate,zxr10AdmmgrUserAuthorTemplate, 
                zxr10AdmmgrUserPwdQuestion, zxr10AdmmgrUserPwdAnswer, 
                zxr10AdmmgrUserEnableTemplate,
                zxr10AdmmgrAuthenAAATemplate, zxr10AdmmgrAuthenAclV4, 
                zxr10AdmmgrAuthenAclV6,
                zxr10AdmmgrAuthenDescription,zxr10AdmmgrAuthorAAATemplate,
                zxr10AdmmgrAuthorLoginMax, zxr10AdmmgrAuthorFtpTopdir,
                zxr10AdmmgrAuthorSFtpTopdir.
                Change the value of zxr10AdmmgrAccountSwitch.
                Add node zxr10AdmmgrLogFileNone, zxr10AdmmgrFailuedSeqNum.
                Change syntax of zxr10AdmmgrFailuedTime"

        REVISION "201303051500Z"  -- 2013-03-05 15:00
        DESCRIPTION
            " Initial version of this MIB module."

        ::= { zxr10RosngMIB 51 } 
               
    zte OBJECT IDENTIFIER ::= { enterprises 3902 }
    zxr10 OBJECT IDENTIFIER ::= { zte 3}
    zxr10RosngMIB OBJECT IDENTIFIER ::= { zxr10 6000}

    zxr10AdmmgrGlobalObjects  OBJECT IDENTIFIER ::= { zxr10AdmmgrMIB 1 }
    zxr10AdmmgrObjects        OBJECT IDENTIFIER ::= { zxr10AdmmgrMIB 2 }
    zxr10AdmmgrGlobalTraps    OBJECT IDENTIFIER ::= { zxr10AdmmgrMIB 3 }
    zxr10AdmmgrConformance    OBJECT IDENTIFIER ::= { zxr10AdmmgrMIB 4 }

    AdmmgrSysTaskName ::= TEXTUAL-CONVENTION
        STATUS current
        DESCRIPTION
            "All task name."
        SYNTAX INTEGER
            {
                freedeploy(257),
                diagnostic(258),
                logicalrouter(259),
                sdn(260),
                lldp(513),
                udld(514),
                configcommon(515),
                filesystem(516),
                ftp(517),
                alarm(518),
                logging(519),
                performancestat(520),
                sftp(521),
                systime(522),
                systemuser(523),
                telnet(524),
                cwmp(525),
                http(526),
                netconf(527),
                rtelnet(528),
                snmp(529),
                ssh(530),
                web(531),
                ntp(532),
                ptp(533), 
                ssm(534),
                lspdetect(535),
                macping(536),
                ping(537),
                pingdetect(538),
                sqa(539),
                trace(540),
                twamp(541),
                ifconfig(769),
                interfaceperf(770),
                arp(771),
                framerelay(772),
                hdlc(773),
                lacp(774),
                mac(775),
                mff(776),
                ppp(777),
                qinq(778),
                stp(779),
                switchvlan(780),
                supervlan(781), 
                vlan(782),
                mppp(783),
                garp(784),
                ip(785),
                nd(786),
                sctp(787), 
                transport(788),
                urpf(789),
                timerange(790),
                groupmanagement(791),
                vxlan(792),
                eld(793),
                monitor(1025),
                netflow(1026),
                rmon(1027),
                sflow(1028),
                span(1029),
                evb(1281),
                loe(1282),
                trill(1283),
                fipsnooping(1284),
                vmm(1285),
                fcoe(1286),
                dhcp(1537),
                dns(1538),
                dpi(1539),
                ippool(1540),
                tunnelv6(1541),
                cgn(1542),
                lawfulinterception(1793),
                multicastsnooping(2049),
                igmp(2050),
                igmpsnooping(2051),
                mld(2052),
                mldsnooping(2053),
                msdp(2054),
                multicast(2055),
                multicaststatic(2056),
                multicastvpn(2057),
                pimdm(2058),
                pimsm(2059),
                pimsnooping(2060),
                pimv6(2061),
                ves(2062),
                pwe3(2305),
                ldp(2306),
                mplste(2307),
                labelmanage(2308),
                tunnelpolicy(2309),
                l2vpn(2310),
                l2vpnperf(2311),
                l3vpnperf(2312),
                vrf(2313),
                gretunnel(2314),
                vpdn(2315),
                l2tp(2316),
                l2protocoltunnel(2317),
                nhrp(2318),
                aps(2561),
                lspprotect(2562),
                sectionprotect(2563),
                tunnelprotect(2564),
                bfd(2565),
                cfm(2566),
                efm(2567),
                icbg(2568),
                mcelam(2569),
                mplsoam(2570),
                portprotect(2571),
                propagate(2572),
                protectgroup(2573),
                redundancyinterchassisgroup(2574),
                tpoam(2575),
                track(2576),
                sus(2577),
                vrrp(2578),
                dsdomain(2817),
                qospolicy(2818),
                qppb(2819),
                routemap(3073),
                bgp(3074),
                staticrouting(3075),
                isis(3076),
                ospf(3077),
                ospfv3(3078),
                pbr(3079),
                rip(3080),
                ripng(3081),
                routemanage(3082),
                trillisis(3083),
                rpl(3084),
                aaatemplate(3329),
                diameter(3330),
                radius(3331),
                tacacs(3332),
                ipsourceguard(3585),
                cps(3586),
                dhcpsnooping(3587),
                ipsec(3588),
                ndsnooping(3589),
                pki(3590),
                savi(3591),
                ssl(3592),
                tcpprotect(3593),
                securityzone(3594),
                meap(3595),
                pppoeclient(3841),
                acl(4097),
                bras(4353)
            }

    zxr10AdmmgrAccountSwitch OBJECT-TYPE 
    SYNTAX   INTEGER
              {
                 off(1),
                 on(2)
              }
    MAX-ACCESS    read-only 
    STATUS        current 
    DESCRIPTION
       "Global command account function (off(1) ,on(2))"  
    DEFVAL        {off}
    ::= { zxr10AdmmgrGlobalObjects 1 }

     zxr10AdmmgrAccountTemplate OBJECT-TYPE 
    SYNTAX        Unsigned32 (0|2001..2128)
    MAX-ACCESS    read-only 
    STATUS        current 
    DESCRIPTION
       "Bind aaa account template(2001-2128),
        0 invalid value"  
    ::= { zxr10AdmmgrGlobalObjects 2 }

     zxr10AdmmgrDefaultPrivilege OBJECT-TYPE 
    SYNTAX        Unsigned32 (0..15)
    MAX-ACCESS    read-only 
    STATUS        current 
    DESCRIPTION
       " Default privilege level(0..15)"
    ::= { zxr10AdmmgrGlobalObjects 3 }
    
     zxr10AdmmgrGlobalEnableType OBJECT-TYPE 
    SYNTAX    INTEGER
              {
                 aaa(1),
                 local(2)
              }
    MAX-ACCESS    read-only 
    STATUS        current 
    DESCRIPTION
       " Global enable authentication type (local(2), aaa(1))"  
    ::= { zxr10AdmmgrGlobalObjects 4 }    

     zxr10AdmmgrGlobalEnableTemplate OBJECT-TYPE 
    SYNTAX        Unsigned32 (0..128)
    MAX-ACCESS    read-only 
    STATUS        current 
    DESCRIPTION
       "Global enable aaa authentication bind template number(1-128),
       0 invalid value"  
    ::= { zxr10AdmmgrGlobalObjects 5 }

     zxr10AdmmgrAsciiAuthenTemplate OBJECT-TYPE 
    SYNTAX        Unsigned32 (0..128)
    MAX-ACCESS    read-only 
    STATUS        current 
    DESCRIPTION
       "ASCII authentication bind template number(1-128),
        0 invalid value"  
    ::= { zxr10AdmmgrGlobalObjects 6 }

     zxr10AdmmgrAsciiAuthorTemplate OBJECT-TYPE 
    SYNTAX        Unsigned32 (0..128)
    MAX-ACCESS    read-only 
    STATUS        current 
    DESCRIPTION
       "ASCII authortication bind template number(1-128),
        0 invalid value"  
    ::= { zxr10AdmmgrGlobalObjects 7 }

     zxr10AdmmgrStrongPwdMinLength OBJECT-TYPE 
    SYNTAX        Unsigned32 (0|6..32)
    MAX-ACCESS    read-only 
    STATUS        current 
    DESCRIPTION
       "The minimum length(6..32) of strong password,
        0 invalid value"  
    ::= { zxr10AdmmgrGlobalObjects 8 }    
    
     zxr10AdmmgrStrongPwdNumber OBJECT-TYPE 
    SYNTAX    INTEGER
              {
                 true(1),
                 false(2)         
              }
    MAX-ACCESS    read-only 
    STATUS        current 
    DESCRIPTION
       "If password must contain number, true(1), not must(2)"  
    ::= { zxr10AdmmgrGlobalObjects 9 }
 
     zxr10AdmmgrStrongPwdCapital OBJECT-TYPE 
    SYNTAX    INTEGER
              {
                 true(1),
                 false(2)         
              }
    MAX-ACCESS    read-only 
    STATUS        current 
    DESCRIPTION
       "If password must contain capital, true(1), not must(2)"  
    ::= { zxr10AdmmgrGlobalObjects 10 }    

     zxr10AdmmgrStrongPwdLowercase OBJECT-TYPE 
    SYNTAX    INTEGER
              {
                 true(1),
                 false(2)         
              }
    MAX-ACCESS    read-only 
    STATUS        current 
    DESCRIPTION
       "If password must contain lowercase, true(1), not must(2)"  
    ::= { zxr10AdmmgrGlobalObjects 11 }    

     zxr10AdmmgrStrongPwdSpecial OBJECT-TYPE 
    SYNTAX    INTEGER
              {
                 true(1),
                 false(2)         
              }
    MAX-ACCESS    read-only 
    STATUS        current 
    DESCRIPTION
       "If password must contain special character, true(1), not must(2)"  
    ::= { zxr10AdmmgrGlobalObjects 12 }    
    
    zxr10AdmmgrAuthenFailTime OBJECT-TYPE 
    SYNTAX        Unsigned32 (0|3..16)
    MAX-ACCESS    read-only 
    STATUS        current 
    DESCRIPTION
       "The user authentication restriction of continuous failure 
       times(3-16),0 invalid value"  
    ::= { zxr10AdmmgrGlobalObjects 13 }    

    zxr10AdmmgrAuthenLockMinute OBJECT-TYPE 
    SYNTAX        Unsigned32 (0..1440) 
    UNITS         "Minutes"
    MAX-ACCESS    read-only 
    STATUS        current 
    DESCRIPTION
       "The  user lock minutes(1-1440),
        0 invalid value,
        if reaching continuous authentication failure times"  
    ::= { zxr10AdmmgrGlobalObjects 14 }    
    
     zxr10AdmmgrDefaultAuthenTemplate OBJECT-TYPE 
    SYNTAX        Unsigned32 (0..128)
    MAX-ACCESS    read-only 
    STATUS        current 
    DESCRIPTION
       "Default authentication bind template number(1-128),
       0 invalid value"  
    ::= { zxr10AdmmgrGlobalObjects 15 }    

     zxr10AdmmgrDefaultAuthorTemplate OBJECT-TYPE 
    SYNTAX        Unsigned32 (0..128)
    MAX-ACCESS    read-only 
    STATUS        current 
    DESCRIPTION
       "Default authortication bind template number(1-128),
       0 invalid value"  
    ::= { zxr10AdmmgrGlobalObjects 16 }
    
     zxr10AdmmgrLoginBlockSeconds OBJECT-TYPE 
    SYNTAX        Unsigned32 (0..65535)
    UNITS         "seconds"
    MAX-ACCESS    read-only 
    STATUS        current 
    DESCRIPTION
       "Block period in second(1-65535),
       0 invalid value"  
    ::= { zxr10AdmmgrGlobalObjects 17 }    
    
     zxr10AdmmgrLoginBlockAttempts OBJECT-TYPE 
    SYNTAX        Unsigned32 (0..65535)
    MAX-ACCESS    read-only 
    STATUS        current 
    DESCRIPTION
       "The max number of continuous login failure times(1-65535),
       0 invalid value"  
    ::= { zxr10AdmmgrGlobalObjects 18 }    

    zxr10AdmmgrLoginBlockWatchSec OBJECT-TYPE 
    SYNTAX        Unsigned32 (0..65535)
    UNITS         "seconds"
    MAX-ACCESS    read-only 
    STATUS        current 
    DESCRIPTION
       "Watch period in second(1-65535),
       0 invalid value"  
    ::= { zxr10AdmmgrGlobalObjects 19 }    

    zxr10AdmmgrLoginBlockFailTimes OBJECT-TYPE 
    SYNTAX        Unsigned32 (0..100)
    MAX-ACCESS    read-only 
    STATUS        current 
    DESCRIPTION
       "Create the log or trap once reaching continuous login failure 
       times(1..100),0 invalid value"  
    ::= { zxr10AdmmgrGlobalObjects 20 }    

     zxr10AdmmgrLoginBlockV4Acl OBJECT-TYPE 
    SYNTAX        DisplayString (SIZE (0..31))
    MAX-ACCESS    read-only 
    STATUS        current 
    DESCRIPTION
       "IPv4 ACL for Filtering user connections."  
    ::= { zxr10AdmmgrGlobalObjects 21 }    

     zxr10AdmmgrLoginBlockV6Acl OBJECT-TYPE 
    SYNTAX        DisplayString (SIZE (0..31))
    MAX-ACCESS    read-only 
    STATUS        current 
    DESCRIPTION
       "IPv6 ACL for Filtering user connections"  
    ::= { zxr10AdmmgrGlobalObjects 22 }        
    
    zxr10AdmmgrRoleBasedModel OBJECT-TYPE
    SYNTAX   INTEGER
              {
                 enable(1),
                 disable(2)
              }
    MAX-ACCESS    read-only 
    STATUS        current 
    DESCRIPTION
       "Global command role-based model switch function 
       (enable(1) ,disable(2))"  
    DEFVAL        {disable}
    ::= { zxr10AdmmgrGlobalObjects 23 }
    
    zxr10AdmmgrStrongPwdCheck OBJECT-TYPE
    SYNTAX   INTEGER
              {
                 enable(1),
                 disable(2)
              }
    MAX-ACCESS    read-only
    STATUS        current 
    DESCRIPTION
       "The status of strong password check
       (enable(1),disable(2))"  
    DEFVAL        {enable}
    ::= { zxr10AdmmgrGlobalObjects 24 }

    zxr10AdmmgrPwdRelatedUsrSubstChk OBJECT-TYPE
    SYNTAX   INTEGER
              {
                 enable(1),
                 disable(2)
              }
    MAX-ACCESS    read-only
    STATUS        current 
    DESCRIPTION
       "Check the substring associated with username(case insensitive)
       (enable(1),disable(2))"
    DEFVAL        {disable}
    ::= { zxr10AdmmgrGlobalObjects 25 }

    zxr10AdmmgrPwdRelatedUsrInverChk OBJECT-TYPE
    SYNTAX   INTEGER
              {
                 enable(1),
                 disable(2)
              }
    MAX-ACCESS    read-only
    STATUS        current 
    DESCRIPTION
       "Check the inverse substring associated with username
       (enable(1),disable(2))"
    DEFVAL        {disable}
    ::= { zxr10AdmmgrGlobalObjects 26 }

     zxr10AdmmgrStrongPwdMinCharSet OBJECT-TYPE 
    SYNTAX        Unsigned32 (0|2..4)
    MAX-ACCESS    read-only 
    STATUS        current 
    DESCRIPTION
       "The number of character types that must be included in the password, 
        The character sets contains number, uppercase, lowercase and 
        sepcial characters. 
        The default value is 0.
        There is no limit on the number of character types by default."
    ::= { zxr10AdmmgrGlobalObjects 27 }

    zxr10AdmmgrUserInfo         OBJECT IDENTIFIER ::= { zxr10AdmmgrObjects 1 }
    zxr10AdmmgrUserGroupInfo    OBJECT IDENTIFIER ::= { zxr10AdmmgrObjects 2 }
    zxr10AdmmgrShowState        OBJECT IDENTIFIER ::= { zxr10AdmmgrObjects 3 }
    zxr10AdmmgrRoleInfo         OBJECT IDENTIFIER ::= { zxr10AdmmgrObjects 4 }
    zxr10AdmmgrTaskGroupInfo    OBJECT IDENTIFIER ::= { zxr10AdmmgrObjects 5 }
    
    zxr10AdmmgrUserTable OBJECT-TYPE 
        SYNTAX       SEQUENCE OF Zxr10AdmmgrUserEntry 
        MAX-ACCESS   not-accessible 
        STATUS       current
        DESCRIPTION
            "User name table" 
        ::= { zxr10AdmmgrUserInfo 1 }
    
    zxr10AdmmgrUserEntry OBJECT-TYPE 
        SYNTAX       Zxr10AdmmgrUserEntry
        MAX-ACCESS   not-accessible 
        STATUS       current
        DESCRIPTION
            "User name entry." 
        INDEX { zxr10AdmmgrUserName} 
            ::= { zxr10AdmmgrUserTable 1 }
            
        Zxr10AdmmgrUserEntry ::=  
        SEQUENCE {
            zxr10AdmmgrUserName            DisplayString,
            zxr10AdmmgrUserPassword        DisplayString,
            zxr10AdmmgrUserAuthenTemplate  Unsigned32,
            zxr10AdmmgrUserAuthorTemplate  Unsigned32,
            zxr10AdmmgrUserLock            INTEGER,
            zxr10AdmmgrUserOncePwd         INTEGER,
            zxr10AdmmgrUserPwdDuration     Unsigned32,
            zxr10AdmmgrUserPwdQuestion     DisplayString,
            zxr10AdmmgrUserPwdAnswer       DisplayString,
            zxr10AdmmgrUserEnableType      INTEGER,
            zxr10AdmmgrUserEnableTemplate  Unsigned32,
            zxr10AdmmgrIsPwdIrreversible   INTEGER
            --zxr10AdmmgrUserRowStatus       RowStatus
            }
            
     zxr10AdmmgrUserName OBJECT-TYPE 
    SYNTAX        DisplayString (SIZE (1..65))
    MAX-ACCESS    not-accessible 
    STATUS        current 
    DESCRIPTION
       "User name"  
    ::= { zxr10AdmmgrUserEntry 1 }                    
        
     zxr10AdmmgrUserPassword OBJECT-TYPE 
    SYNTAX        DisplayString (SIZE (0..64))
    MAX-ACCESS    read-only 
    STATUS        current 
    DESCRIPTION
       "Password"  
    ::= { zxr10AdmmgrUserEntry 2 }    
    
     zxr10AdmmgrUserAuthenTemplate OBJECT-TYPE 
    SYNTAX        Unsigned32 (0..128)
    MAX-ACCESS    read-only 
    STATUS        current 
    DESCRIPTION
       "Authentication bind template number(1-128)for user,
       0 invalid value"  
    ::= { zxr10AdmmgrUserEntry 3 }        
    
     zxr10AdmmgrUserAuthorTemplate OBJECT-TYPE 
    SYNTAX        Unsigned32 (0..128)
    MAX-ACCESS    read-only 
    STATUS        current 
    DESCRIPTION
       "Authorization bind template number(1-128)for user,
       0 invalid value"  
    ::= { zxr10AdmmgrUserEntry 4 }    
    
     zxr10AdmmgrUserLock OBJECT-TYPE 
    SYNTAX    INTEGER
              {
                 locked(1),
                 unlocked(2)
              }
    MAX-ACCESS    read-only 
    STATUS        current 
    DESCRIPTION
       "If user locked, (locked(1),unlocked(2))"  
    ::= { zxr10AdmmgrUserEntry 5 }    
    
     zxr10AdmmgrUserOncePwd OBJECT-TYPE 
    SYNTAX    INTEGER
              {
                 oncepassword(1),
                 nononcepassword(2)
              }
    MAX-ACCESS    read-only 
    STATUS        current 
    DESCRIPTION
       "If user need to modify password when the user first login on,
        oncepassword(1),nononcepassword(2)"
    ::= { zxr10AdmmgrUserEntry 6 }    
    
    zxr10AdmmgrUserPwdDuration OBJECT-TYPE 
    SYNTAX        Unsigned32 (0..360)
    UNITS         "days"    
    MAX-ACCESS    read-only 
    STATUS        current 
    DESCRIPTION
       "User password duration days(0..360)"  
    ::= { zxr10AdmmgrUserEntry 7 }    
    
    zxr10AdmmgrUserPwdQuestion OBJECT-TYPE 
    SYNTAX        DisplayString (SIZE (0..50))
    MAX-ACCESS    read-only 
    STATUS        current 
    DESCRIPTION
       "User password recover reminder question"  
    ::= { zxr10AdmmgrUserEntry 8 }    

    zxr10AdmmgrUserPwdAnswer OBJECT-TYPE 
    SYNTAX        DisplayString (SIZE (0..50))
    MAX-ACCESS    read-only 
    STATUS        current 
    DESCRIPTION
       "User password recover reminder answer"  
    ::= { zxr10AdmmgrUserEntry 9 }    

    zxr10AdmmgrUserEnableType OBJECT-TYPE 
    SYNTAX    INTEGER
              {
                 aaa(1),
                 local(2)
              }
    MAX-ACCESS    read-only 
    STATUS        current 
    DESCRIPTION
       "User enable authentication type local(2) or aaa(1)"  
    ::= { zxr10AdmmgrUserEntry 10 }    
    
    zxr10AdmmgrUserEnableTemplate OBJECT-TYPE 
    SYNTAX        Unsigned32 (0..128)
    MAX-ACCESS    read-only 
    STATUS        current 
    DESCRIPTION
       "User enable authentication bind template number(1-128),
       0 invalid value
        if the enable authentication type is aaa"  
    ::= { zxr10AdmmgrUserEntry 11 }        
    
     zxr10AdmmgrIsPwdIrreversible OBJECT-TYPE 
    SYNTAX    INTEGER
              {
                 irreversible(1),
                 reversible(2)
              }
    MAX-ACCESS    read-only 
    STATUS        current 
    DESCRIPTION
       "If the password is irreversible encryption,
       0 invalid value (irreversible(1),reversible(2))"  
    ::= { zxr10AdmmgrUserEntry 12 }   

   -- zxr10AdmmgrUserRowStatus OBJECT-TYPE
   --     SYNTAX        RowStatus
   --     MAX-ACCESS    read-create 
   --     STATUS        current
   --     DESCRIPTION
   --        "Row Status"
   -- ::= { zxr10AdmmgrUserEntry 100 }

    zxr10AdmmgrAuthenTable OBJECT-TYPE 
    SYNTAX       SEQUENCE OF Zxr10AdmmgrAuthenEntry 
    MAX-ACCESS   not-accessible 
    STATUS       current
    DESCRIPTION
        "User authentication table" 
    ::= { zxr10AdmmgrUserInfo 2 }
    
    zxr10AdmmgrAuthenEntry OBJECT-TYPE 
        SYNTAX       Zxr10AdmmgrAuthenEntry
        MAX-ACCESS   not-accessible 
        STATUS       current
        DESCRIPTION
            "User authentication entry." 
        INDEX { zxr10AdmmgrAuthenTemplate} 
            ::= { zxr10AdmmgrAuthenTable 1 }
            
        Zxr10AdmmgrAuthenEntry ::=  
        SEQUENCE {
            zxr10AdmmgrAuthenTemplate      Unsigned32,
            zxr10AdmmgrAuthenAAATemplate   Unsigned32,
            zxr10AdmmgrAuthenAclV4         DisplayString,
            zxr10AdmmgrAuthenAclV6         DisplayString,
            zxr10AdmmgrAuthenMethod        INTEGER,
            zxr10AdmmgrAuthenDescription   DisplayString
            --zxr10AdmmgrAuthenRowStatus     RowStatus
            }
            
    zxr10AdmmgrAuthenTemplate OBJECT-TYPE 
    SYNTAX        Unsigned32 (1..128)
    MAX-ACCESS    not-accessible 
    STATUS        current 
    DESCRIPTION
       "Authentication template number(1..128)"  
    ::= { zxr10AdmmgrAuthenEntry 1 }

    zxr10AdmmgrAuthenAAATemplate OBJECT-TYPE 
    SYNTAX        Unsigned32 (0|1..2128)
    MAX-ACCESS    read-only 
    STATUS        current 
    DESCRIPTION
       "AAA authentication template number(1..2128),
       0 invalid value"  
    ::= { zxr10AdmmgrAuthenEntry 2 }

    zxr10AdmmgrAuthenAclV4 OBJECT-TYPE 
    SYNTAX        DisplayString (SIZE (0..31))
    MAX-ACCESS    read-only 
    STATUS        current 
    DESCRIPTION
       "IPv4 ACL of the authentication template"  
    ::= { zxr10AdmmgrAuthenEntry 3 }

    zxr10AdmmgrAuthenAclV6 OBJECT-TYPE 
    SYNTAX        DisplayString (SIZE (0..31))
    MAX-ACCESS    read-only 
    STATUS        current 
    DESCRIPTION
       "IPv6 ACL of the authentication template"  
    ::= { zxr10AdmmgrAuthenEntry 4 }
    
    zxr10AdmmgrAuthenMethod OBJECT-TYPE 
    SYNTAX    INTEGER
              {
                 pap(1), 
                 chap(2)
              } 
    MAX-ACCESS    read-only 
    STATUS        current 
    DESCRIPTION
       "Authentication method (chap(2),pap(1))"  
    ::= { zxr10AdmmgrAuthenEntry 5 }

    zxr10AdmmgrAuthenDescription OBJECT-TYPE 
    SYNTAX        DisplayString (SIZE (0..127))
    MAX-ACCESS    read-only 
    STATUS        current 
    DESCRIPTION
       "The description of authentication template"  
    ::= { zxr10AdmmgrAuthenEntry 6 }

    --zxr10AdmmgrAuthenRowStatus OBJECT-TYPE
    --    SYNTAX        RowStatus
    --   MAX-ACCESS    read-create 
    --    STATUS        current
    --    DESCRIPTION
    --       "Row Status"
    --::= { zxr10AdmmgrAuthenEntry 100 }
    
    zxr10AdmmgrAuthorTable OBJECT-TYPE 
    SYNTAX       SEQUENCE OF Zxr10AdmmgrAuthorEntry 
    MAX-ACCESS   not-accessible 
    STATUS       current
    DESCRIPTION
        "User authorization table" 
    ::= { zxr10AdmmgrUserInfo 3 }
    
    zxr10AdmmgrAuthorEntry OBJECT-TYPE 
        SYNTAX       Zxr10AdmmgrAuthorEntry
        MAX-ACCESS   not-accessible 
        STATUS       current
        DESCRIPTION
            "User authorization entry." 
        INDEX { zxr10AdmmgrAuthorTemplate} 
     ::= { zxr10AdmmgrAuthorTable 1 }
            
        Zxr10AdmmgrAuthorEntry ::=  
        SEQUENCE {
            zxr10AdmmgrAuthorTemplate      Unsigned32,
            zxr10AdmmgrAuthorAAATemplate   Unsigned32,
            zxr10AdmmgrAuthorLocalPriv     Unsigned32,
            zxr10AdmmgrAuthorCmdGroupMode  INTEGER,
            zxr10AdmmgrAuthorLoginMax      Unsigned32,
            zxr10AdmmgrAuthorDescription   DisplayString,
            zxr10AdmmgrAuthorFtpTopdir     DisplayString,
            zxr10AdmmgrAuthorFtpTopdirRO   INTEGER,
            zxr10AdmmgrAuthorFtpTopdirRW   INTEGER,
            zxr10AdmmgrAuthorFtpTopdirCopy INTEGER,
            zxr10AdmmgrAuthorSFtpTopdir    DisplayString, 
            zxr10AdmmgrAuthorSFtpTopdirRO  INTEGER,
            zxr10AdmmgrAuthorSFtpTopdirRW  INTEGER,
            zxr10AdmmgrAuthorSFtpTopdirCopy      INTEGER,
            zxr10AdmmgrAuthorTelnetAllowed       INTEGER,
            zxr10AdmmgrAuthorSSHAllowed          INTEGER,
            zxr10AdmmgrAuthorFtpAllowed          INTEGER,
            zxr10AdmmgrAuthorWebAllowed          INTEGER,
            zxr10AdmmgrAuthorConsoleAllowed      INTEGER,
            zxr10AdmmgrAuthorOnlyTelnetAllow     INTEGER
            --zxr10AdmmgrAuthorRowStatus         RowStatus
            }
            
   zxr10AdmmgrAuthorTemplate OBJECT-TYPE 
    SYNTAX        Unsigned32 (1..128)
    MAX-ACCESS    not-accessible 
    STATUS        current 
    DESCRIPTION
       "Authorization template number(1..128)"  
    ::= { zxr10AdmmgrAuthorEntry 1 }

    zxr10AdmmgrAuthorAAATemplate OBJECT-TYPE 
    SYNTAX        Unsigned32 (0|1..2128)
    MAX-ACCESS    read-only 
    STATUS        current 
    DESCRIPTION
       "AAA authorization template number(1..2128),
       0 invalid value"  
    ::= { zxr10AdmmgrAuthorEntry 2 }

    zxr10AdmmgrAuthorLocalPriv OBJECT-TYPE 
    SYNTAX        Unsigned32 (0..15|255)
    MAX-ACCESS    read-only 
    STATUS        current 
    DESCRIPTION
       "Local privilege level:
        (0..15)  valid value
        255      invalid value"  
    ::= { zxr10AdmmgrAuthorEntry 3 }

    zxr10AdmmgrAuthorCmdGroupMode OBJECT-TYPE 
    SYNTAX    INTEGER
              {
                 exclusive(1), 
                 nonexclusive(2)
              }
    MAX-ACCESS    read-only 
    STATUS        current 
    DESCRIPTION
       "Set command group mode exclusive(1) or not(2)"  
    ::= { zxr10AdmmgrAuthorEntry 4 }
    
    zxr10AdmmgrAuthorLoginMax OBJECT-TYPE 
    SYNTAX        Unsigned32 (0..60)
    MAX-ACCESS    read-only 
    STATUS        current 
    DESCRIPTION
       "Set the max times(1..60) user login in the same time,
       0 invalid value"  
    ::= { zxr10AdmmgrAuthorEntry 5 }
    
    zxr10AdmmgrAuthorDescription OBJECT-TYPE 
    SYNTAX        DisplayString (SIZE (0..127))
    MAX-ACCESS    read-only 
    STATUS        current 
    DESCRIPTION
       "The description of authorization template"  
    ::= { zxr10AdmmgrAuthorEntry 6 }    

    zxr10AdmmgrAuthorFtpTopdir OBJECT-TYPE 
    SYNTAX        DisplayString (SIZE (0..159))
    MAX-ACCESS    read-only 
    STATUS        current 
    DESCRIPTION
       "The ftp top directory name"  
    ::= { zxr10AdmmgrAuthorEntry 7 }    

    zxr10AdmmgrAuthorFtpTopdirRO OBJECT-TYPE 
    SYNTAX    INTEGER
              {
                 true(1), 
                 false(2)
              }
    MAX-ACCESS    read-only 
    STATUS        current 
    DESCRIPTION
       "If ftp top directory access read only configed, true(1) or false(2)"  
    ::= { zxr10AdmmgrAuthorEntry 8 }    

    zxr10AdmmgrAuthorFtpTopdirRW OBJECT-TYPE 
    SYNTAX    INTEGER
              {
                 true(1), 
                 false(2)
              }
    MAX-ACCESS    read-only 
    STATUS        current 
    DESCRIPTION
       "If ftp top directory access read write configed, true(1) or false(2)"  
    ::= { zxr10AdmmgrAuthorEntry 9 }    

    zxr10AdmmgrAuthorFtpTopdirCopy OBJECT-TYPE 
    SYNTAX    INTEGER
              {
                 true(1), 
                 false(2)
              }
    MAX-ACCESS    read-only 
    STATUS        current 
    DESCRIPTION
       "If ftp top directory access copy configed, true(1) or false(2)"  
    ::= { zxr10AdmmgrAuthorEntry 10 }    

    zxr10AdmmgrAuthorSFtpTopdir OBJECT-TYPE 
    SYNTAX        DisplayString (SIZE (0..159))
    MAX-ACCESS    read-only 
    STATUS        current 
    DESCRIPTION
       "The sftp top directory name"  
    ::= { zxr10AdmmgrAuthorEntry 11 }    

    zxr10AdmmgrAuthorSFtpTopdirRO OBJECT-TYPE 
    SYNTAX    INTEGER
              {
                 true(1), 
                 false(2)
              }
    MAX-ACCESS    read-only 
    STATUS        current 
    DESCRIPTION
       "If sftp top directory access read only configed, true(1) or false(2)"  
    ::= { zxr10AdmmgrAuthorEntry 12 }    

    zxr10AdmmgrAuthorSFtpTopdirRW OBJECT-TYPE 
    SYNTAX    INTEGER
              {
                 true(1), 
                 false(2)
              }
    MAX-ACCESS    read-only 
    STATUS        current 
    DESCRIPTION
       "If sftp top directory access read write configed, true(1) or false(2)"
    ::= { zxr10AdmmgrAuthorEntry 13 }

    zxr10AdmmgrAuthorSFtpTopdirCopy OBJECT-TYPE 
    SYNTAX    INTEGER
              {
                 true(1), 
                 false(2)
              }
    MAX-ACCESS    read-only 
    STATUS        current 
    DESCRIPTION
       "If sftp top directory access copy configed, true(1) or false(2)"
    ::= { zxr10AdmmgrAuthorEntry 14 }

    zxr10AdmmgrAuthorTelnetAllowed OBJECT-TYPE 
    SYNTAX    INTEGER
              {
                 true(1), 
                 false(2)
              }
    MAX-ACCESS    read-only 
    STATUS        current 
    DESCRIPTION
       "Whether to allow users to login via telnet and console,
        true(1) or false(2)"
    ::= { zxr10AdmmgrAuthorEntry 15 }

    zxr10AdmmgrAuthorSSHAllowed OBJECT-TYPE 
    SYNTAX    INTEGER
              {
                 true(1), 
                 false(2)
              }
    MAX-ACCESS    read-only 
    STATUS        current 
    DESCRIPTION
       "Whether to allow users to login via SSH, true(1) or false(2)"
    ::= { zxr10AdmmgrAuthorEntry 16 }

    zxr10AdmmgrAuthorFtpAllowed OBJECT-TYPE
    SYNTAX    INTEGER
              {
                 true(1), 
                 false(2)
              }
    MAX-ACCESS    read-only 
    STATUS        current 
    DESCRIPTION
       "Whether to allow users to login via FTP, true(1) or false(2)"  
    ::= { zxr10AdmmgrAuthorEntry 17 }
    
    zxr10AdmmgrAuthorWebAllowed OBJECT-TYPE 
    SYNTAX    INTEGER
              {
                 true(1), 
                 false(2)
              }
    MAX-ACCESS    read-only 
    STATUS        current 
    DESCRIPTION
       "Whether to allow users to login via web, true(1) or false(2)"
    ::= { zxr10AdmmgrAuthorEntry 18 }

    zxr10AdmmgrAuthorConsoleAllowed OBJECT-TYPE 
    SYNTAX    INTEGER
              {
                 true(1), 
                 false(2)
              }
    MAX-ACCESS    read-only 
    STATUS        current 
    DESCRIPTION
       "Whether to allow users to login via console, true(1) or false(2)"
    ::= { zxr10AdmmgrAuthorEntry 19 }

    zxr10AdmmgrAuthorOnlyTelnetAllow OBJECT-TYPE
    SYNTAX    INTEGER
              {
                 true(1), 
                 false(2)
              }
    MAX-ACCESS    read-only 
    STATUS        current 
    DESCRIPTION
       "Whether to allow users to login via telnet, true(1) or false(2)"  
    ::= { zxr10AdmmgrAuthorEntry 20 }
    
    --zxr10AdmmgrAuthorRowStatus OBJECT-TYPE
    --    SYNTAX        RowStatus
    --    MAX-ACCESS    read-create 
    --    STATUS        current
    --    DESCRIPTION
    --      "Row Status"
    --::= { zxr10AdmmgrAuthorEntry 100 }

    zxr10AdmmgrCmdGroupTable OBJECT-TYPE 
    SYNTAX       SEQUENCE OF Zxr10AdmmgrCmdGroupEntry 
    MAX-ACCESS   not-accessible 
    STATUS       current
    DESCRIPTION
        "The command group table" 
    ::= { zxr10AdmmgrUserInfo 4 }
    
    zxr10AdmmgrCmdGroupEntry OBJECT-TYPE
        SYNTAX       Zxr10AdmmgrCmdGroupEntry
        MAX-ACCESS   not-accessible
        STATUS       current
        DESCRIPTION
            "The command group entry." 
        INDEX { zxr10AdmmgrCmdGroupTemplate, zxr10AdmmgrCmdGroupName} 
            ::= { zxr10AdmmgrCmdGroupTable 1 }
            
        Zxr10AdmmgrCmdGroupEntry ::=
        SEQUENCE {
            zxr10AdmmgrCmdGroupTemplate     Unsigned32,
            zxr10AdmmgrCmdGroupName         DisplayString
            --zxr10AdmmgrCmdGroupRowStatus  RowStatus
            }    
            
   zxr10AdmmgrCmdGroupTemplate OBJECT-TYPE
    SYNTAX        Unsigned32 (1..128)
    MAX-ACCESS    not-accessible
    STATUS        current 
    DESCRIPTION
       "Authorization template number(1..128)"
    ::= { zxr10AdmmgrCmdGroupEntry 1 }

   zxr10AdmmgrCmdGroupName OBJECT-TYPE 
    SYNTAX        DisplayString (SIZE (0..31))
    MAX-ACCESS    read-only
    STATUS        current 
    DESCRIPTION
       "The command group name"  
    ::= { zxr10AdmmgrCmdGroupEntry 2 }    
    
    --zxr10AdmmgrCmdGroupRowStatus OBJECT-TYPE
    --    SYNTAX        RowStatus
    --    MAX-ACCESS    read-create 
    --    STATUS        current
    --    DESCRIPTION
    --       "Row Status"
    --::= { zxr10AdmmgrCmdGroupEntry 100 }


    zxr10AdmmgrLogAllowedTable OBJECT-TYPE 
    SYNTAX       SEQUENCE OF Zxr10AdmmgrLogAllowedEntry
    MAX-ACCESS   not-accessible 
    STATUS       current
    DESCRIPTION
        "The log file permission table"
    ::= { zxr10AdmmgrUserInfo 5 }
    
    zxr10AdmmgrLogAllowedEntry OBJECT-TYPE 
        SYNTAX       Zxr10AdmmgrLogAllowedEntry
        MAX-ACCESS   not-accessible 
        STATUS       current
        DESCRIPTION
            "The log file permission entry." 
        INDEX { zxr10AdmmgrLogAllowedTemplate, zxr10AdmmgrLogType} 
            ::= { zxr10AdmmgrLogAllowedTable 1 }
            
        Zxr10AdmmgrLogAllowedEntry ::=  
        SEQUENCE {
            zxr10AdmmgrLogAllowedTemplate   Unsigned32,
            zxr10AdmmgrLogType              INTEGER,
            zxr10AdmmgrLogFileReadOnly      INTEGER, 
            zxr10AdmmgrLogFileReadWrite     INTEGER, 
            zxr10AdmmgrLogFileCopy          INTEGER,
            zxr10AdmmgrLogFileNone          INTEGER
            --zxr10AdmmgrLogAllowedRowStatus  RowStatus
            }    
            
   zxr10AdmmgrLogAllowedTemplate OBJECT-TYPE 
    SYNTAX        Unsigned32 (1..128)
    MAX-ACCESS    not-accessible
    STATUS        current 
    DESCRIPTION
       "Authorization template number(1..128)"
    ::= { zxr10AdmmgrLogAllowedEntry 1 }

   zxr10AdmmgrLogType OBJECT-TYPE 
    SYNTAX     INTEGER
              {
                 cmd(1), 
                 alarm(2), 
                 nat(3), 
                 li(4), 
                 service(5)
              } 
    MAX-ACCESS    not-accessible 
    STATUS        current 
    DESCRIPTION
       "Logfile type, cmd log(1), alarm log(2), 
        nat log(3), li log(4), service log(5)"  
    ::= { zxr10AdmmgrLogAllowedEntry 2 }

    zxr10AdmmgrLogFileReadOnly OBJECT-TYPE 
    SYNTAX    INTEGER
              {
                 true(1), 
                 false(2)
              }
    MAX-ACCESS    read-only 
    STATUS        current 
    DESCRIPTION
       "If logfile access read only configed, true(1) or false(2)"  
    ::= { zxr10AdmmgrLogAllowedEntry 3 }    

    zxr10AdmmgrLogFileReadWrite OBJECT-TYPE 
    SYNTAX    INTEGER
              {
                 true(1), 
                 false(2)
              }
    MAX-ACCESS    read-only 
    STATUS        current 
    DESCRIPTION
       "If logfile access read write configed, true(1) or false(2)"  
    ::= { zxr10AdmmgrLogAllowedEntry 4 }    

    zxr10AdmmgrLogFileCopy OBJECT-TYPE 
    SYNTAX    INTEGER
              {
                 true(1), 
                 false(2)
              }
    MAX-ACCESS    read-only 
    STATUS        current 
    DESCRIPTION
       "If logfile access copy configed, true(1) or false(2)"  
    ::= { zxr10AdmmgrLogAllowedEntry 5 }

    zxr10AdmmgrLogFileNone OBJECT-TYPE 
    SYNTAX    INTEGER
              {
                 true(1), 
                 false(2)
              }
    MAX-ACCESS    read-only 
    STATUS        current 
    DESCRIPTION
       "If logfile access none configed, true(1) or false(2)"  
    ::= { zxr10AdmmgrLogAllowedEntry 6 }

    --zxr10AdmmgrLogAllowedRowStatus OBJECT-TYPE
    --    SYNTAX        RowStatus
    --    MAX-ACCESS    read-create 
    --    STATUS        current
    --    DESCRIPTION
    --       "Row Status"
    --::= { zxr10AdmmgrLogAllowedEntry 100 }    

    zxr10AdmmgrAuthorRoleTable OBJECT-TYPE 
        SYNTAX       SEQUENCE OF Zxr10AdmmgrAuthorRoleEntry 
        MAX-ACCESS   not-accessible 
        STATUS       current
        DESCRIPTION
            "Roles of authorization templeate table" 
        ::= { zxr10AdmmgrUserInfo 6 }
    
    zxr10AdmmgrAuthorRoleEntry OBJECT-TYPE 
        SYNTAX       Zxr10AdmmgrAuthorRoleEntry
        MAX-ACCESS   not-accessible 
        STATUS       current
        DESCRIPTION
            "Roles of authorization templeate entry" 
        INDEX { zxr10AdmmgrarAuthorTemplate, zxr10AdmmgrarRoleName} 
            ::= { zxr10AdmmgrAuthorRoleTable 1 }
            
        Zxr10AdmmgrAuthorRoleEntry ::=  
        SEQUENCE {
            zxr10AdmmgrarAuthorTemplate       Unsigned32,
            zxr10AdmmgrarRoleName             DisplayString
            }           
            
    zxr10AdmmgrarAuthorTemplate OBJECT-TYPE 
        SYNTAX        Unsigned32 (1..128)
        MAX-ACCESS    not-accessible 
        STATUS        current 
        DESCRIPTION
           "Authorization template number(1..128)"  
        ::= { zxr10AdmmgrAuthorRoleEntry 1 }
            
    zxr10AdmmgrarRoleName OBJECT-TYPE 
        SYNTAX        DisplayString (SIZE (0..48))
        MAX-ACCESS    read-only 
        STATUS        current 
        DESCRIPTION
           "Role name"  
        ::= { zxr10AdmmgrAuthorRoleEntry 2 }

    zxr10AdmmgrUserGroupTable OBJECT-TYPE 
        SYNTAX       SEQUENCE OF Zxr10AdmmgrUserGroupEntry 
        MAX-ACCESS   not-accessible 
        STATUS       current
        DESCRIPTION
            "User group table" 
        ::= { zxr10AdmmgrUserGroupInfo 1 }
    
    zxr10AdmmgrUserGroupEntry OBJECT-TYPE 
        SYNTAX       Zxr10AdmmgrUserGroupEntry
        MAX-ACCESS   not-accessible 
        STATUS       current
        DESCRIPTION
            "User group entry." 
        INDEX {zxr10AdmmgrUserGroupName ,zxr10AdmmgrUserGroupUserName } 
            ::= { zxr10AdmmgrUserGroupTable 1 }
            
        Zxr10AdmmgrUserGroupEntry ::=  
        SEQUENCE {
            zxr10AdmmgrUserGroupName            DisplayString,
            zxr10AdmmgrUserGroupUserName        DisplayString,            
            zxr10AdmmgrUserGroupPassword        DisplayString
            --zxr10AdmmgrUserGroupRowStatus     RowStatus
            }

   zxr10AdmmgrUserGroupName OBJECT-TYPE 
    SYNTAX        DisplayString (SIZE (1..15))
    MAX-ACCESS    not-accessible 
    STATUS        current 
    DESCRIPTION
       "The user group name"  
    ::= { zxr10AdmmgrUserGroupEntry 1 }    

   zxr10AdmmgrUserGroupUserName OBJECT-TYPE 
    SYNTAX        DisplayString (SIZE (1..16))
    MAX-ACCESS    not-accessible 
    STATUS        current 
    DESCRIPTION
       "User in the group"  
    ::= { zxr10AdmmgrUserGroupEntry 2 }

   zxr10AdmmgrUserGroupPassword OBJECT-TYPE 
    SYNTAX        DisplayString (SIZE (0..64))
    MAX-ACCESS    read-only 
    STATUS        current 
    DESCRIPTION
       "The password"  
    ::= { zxr10AdmmgrUserGroupEntry 3 }

    --zxr10AdmmgrUserGroupRowStatus OBJECT-TYPE
    --    SYNTAX        RowStatus
    --    MAX-ACCESS    read-create 
    --    STATUS        current
    --    DESCRIPTION
    --       "Row Status"
    --::= { zxr10AdmmgrUserGroupEntry 100 }
    
    zxr10AdmmgrShowLockStateTable OBJECT-TYPE 
        SYNTAX       SEQUENCE OF Zxr10AdmmgrShowLockStateEntry 
        MAX-ACCESS   not-accessible 
        STATUS       current
        DESCRIPTION
            "User lock state table" 
        ::= { zxr10AdmmgrShowState 1 }
    
    zxr10AdmmgrShowLockStateEntry OBJECT-TYPE 
        SYNTAX       Zxr10AdmmgrShowLockStateEntry
        MAX-ACCESS   not-accessible 
        STATUS       current
        DESCRIPTION
            "User lock state entry." 
        INDEX {zxr10AdmmgrShowLockStateUser } 
            ::= { zxr10AdmmgrShowLockStateTable 1 }
            
        Zxr10AdmmgrShowLockStateEntry ::=  
        SEQUENCE {
            zxr10AdmmgrShowLockStateUser            DisplayString,
            zxr10AdmmgrShowFailedTimes              Unsigned32,            
            zxr10AdmmgrShowLockState                INTEGER,
            zxr10AdmmgrShowRemainMinute             Unsigned32           
            }    
            
   zxr10AdmmgrShowLockStateUser OBJECT-TYPE 
    SYNTAX        DisplayString (SIZE (1..65))
    MAX-ACCESS    not-accessible 
    STATUS        current 
    DESCRIPTION
       "The username "  
    ::= { zxr10AdmmgrShowLockStateEntry 1 }    

    zxr10AdmmgrShowFailedTimes OBJECT-TYPE
    SYNTAX        Unsigned32
    MAX-ACCESS    read-only
    STATUS        current
    DESCRIPTION
       "The failed login times"  
    ::= { zxr10AdmmgrShowLockStateEntry 2 }
    
   zxr10AdmmgrShowLockState OBJECT-TYPE 
    SYNTAX    INTEGER
              {
                 locked(1),
                 unlocked(2)
              }
    MAX-ACCESS    read-only 
    STATUS        current 
    DESCRIPTION
       "The lock state locked(1) or not(2)"
    ::= { zxr10AdmmgrShowLockStateEntry 3 }

   zxr10AdmmgrShowRemainMinute OBJECT-TYPE 
    SYNTAX        Unsigned32 
    MAX-ACCESS    read-only 
    STATUS        current 
    DESCRIPTION
       "The remain minutes of a locked user to unlock"
    ::= { zxr10AdmmgrShowLockStateEntry 4 }

    zxr10AdmmgrFailuedUserTable OBJECT-TYPE 
        SYNTAX       SEQUENCE OF Zxr10AdmmgrFailuedUserEntry
        MAX-ACCESS   not-accessible 
        STATUS       current
        DESCRIPTION
            "Login failure information table,
             recorded when login block function on"
        ::= { zxr10AdmmgrShowState 2 }
    
    zxr10AdmmgrFailuedUserEntry OBJECT-TYPE 
        SYNTAX       Zxr10AdmmgrFailuedUserEntry
        MAX-ACCESS   not-accessible 
        STATUS       current
        DESCRIPTION
            "Login failure information entry" 
        INDEX {zxr10AdmmgrFailuedLoginType,  zxr10AdmmgrFailuedSeqNum} 
            ::= { zxr10AdmmgrFailuedUserTable 1 }
            
        Zxr10AdmmgrFailuedUserEntry ::=  
        SEQUENCE {
            zxr10AdmmgrFailuedUser                   DisplayString,
            zxr10AdmmgrFailuedUserIpv4               IpAddress,            
            zxr10AdmmgrFailuedUserIpv6               Ipv6Address,
            zxr10AdmmgrFailuedLoginType              INTEGER,    
            zxr10AdmmgrFailuedTime                   DateAndTime, 
            zxr10AdmmgrFailuedSeqNum                 Unsigned32
            }

   zxr10AdmmgrFailuedUser OBJECT-TYPE 
    SYNTAX        DisplayString (SIZE (0..65))
    MAX-ACCESS    read-only 
    STATUS        current 
    DESCRIPTION
       "The username "  
    ::= { zxr10AdmmgrFailuedUserEntry 1 }    

   zxr10AdmmgrFailuedUserIpv4 OBJECT-TYPE 
    SYNTAX        IpAddress 
    MAX-ACCESS    read-only 
    STATUS        current 
    DESCRIPTION
       "The IPv4 address of the login "  
    ::= { zxr10AdmmgrFailuedUserEntry 2 }    

   zxr10AdmmgrFailuedUserIpv6 OBJECT-TYPE 
    SYNTAX        Ipv6Address 
    MAX-ACCESS    read-only 
    STATUS        current 
    DESCRIPTION
       "The IPv6 address of the login "  
    ::= { zxr10AdmmgrFailuedUserEntry 3 }    

   zxr10AdmmgrFailuedLoginType OBJECT-TYPE 
    SYNTAX    INTEGER
              {
                 telnet(1), 
                 ssh(2), 
                 ftp(3) 
              } 
    MAX-ACCESS    read-only 
    STATUS        current 
    DESCRIPTION
       "The login type "  
    ::= { zxr10AdmmgrFailuedUserEntry 4 }    

   zxr10AdmmgrFailuedTime OBJECT-TYPE 
    SYNTAX        DateAndTime 
    MAX-ACCESS    read-only 
    STATUS        current 
    DESCRIPTION
       "The login failure time"  
    ::= { zxr10AdmmgrFailuedUserEntry 5 }    

   zxr10AdmmgrFailuedSeqNum OBJECT-TYPE 
    SYNTAX        Unsigned32 
    MAX-ACCESS    not-accessible 
    STATUS        current 
    DESCRIPTION
       "The login failure sequence number"  
    ::= { zxr10AdmmgrFailuedUserEntry 6 }

    zxr10AdmmgrLoginBlockStateTable OBJECT-TYPE 
        SYNTAX       SEQUENCE OF Zxr10AdmmgrLoginBlockStateEntry 
        MAX-ACCESS   not-accessible 
        STATUS       current
        DESCRIPTION
            "Login block state table" 
        ::= { zxr10AdmmgrShowState 3 }
    
    zxr10AdmmgrLoginBlockStateEntry OBJECT-TYPE 
        SYNTAX       Zxr10AdmmgrLoginBlockStateEntry
        MAX-ACCESS   not-accessible 
        STATUS       current
        DESCRIPTION
            "Login block state entry" 
        INDEX {zxr10AdmmgrLoginBlockType } 
            ::= { zxr10AdmmgrLoginBlockStateTable 1 }
            
        Zxr10AdmmgrLoginBlockStateEntry ::=  
        SEQUENCE {
            zxr10AdmmgrLoginBlockType                INTEGER,
            zxr10AdmmgrLoginBlockMode                INTEGER,            
            zxr10AdmmgrLoginBlockRemain              Unsigned32,
            zxr10AdmmgrLoginBlockFailCount           Unsigned32                
            }
    zxr10AdmmgrLoginBlockType  OBJECT-TYPE 
    SYNTAX    INTEGER
              {
                 telnet(1), 
                 ssh(2), 
                 ftp(3) 
              }
    MAX-ACCESS    not-accessible
    STATUS        current    
    DESCRIPTION
       "Login type, telnet(1), ssh(2), or ftp(3)"
    ::= { zxr10AdmmgrLoginBlockStateEntry 1 }   
    
    zxr10AdmmgrLoginBlockMode  OBJECT-TYPE 
    SYNTAX       INTEGER
                {
                  watch_Mode(1), 
                  quiet_Mode(2),
                  normal_Mode(3)
                }
    MAX-ACCESS    read-only
    STATUS        current    
    DESCRIPTION
       "Router presently in Watch_Mode(1), Quiet_Mode(2), or Normal_Mode(3)"
    ::= { zxr10AdmmgrLoginBlockStateEntry 2 }
    
    zxr10AdmmgrLoginBlockRemain  OBJECT-TYPE 
    SYNTAX        Unsigned32
    UNITS         "seconds"
    MAX-ACCESS    read-only
    STATUS        current    
    DESCRIPTION
       "How many seconds remains in current login block mode"
    ::= { zxr10AdmmgrLoginBlockStateEntry 3 }

    zxr10AdmmgrLoginBlockFailCount  OBJECT-TYPE 
    SYNTAX        Unsigned32
    MAX-ACCESS    read-only
    STATUS        current    
    DESCRIPTION
       "Login failure count in Watch-Mode"
    ::= { zxr10AdmmgrLoginBlockStateEntry 4 }
    
    zxr10AdmmgrOnlineUserInfoTable OBJECT-TYPE 
        SYNTAX       SEQUENCE OF Zxr10AdmmgrOnlineUserInfoEntry 
        MAX-ACCESS   not-accessible 
        STATUS       current
        DESCRIPTION
            "Online user information table" 
        ::= { zxr10AdmmgrShowState 4 }  
         
     zxr10AdmmgrOnlineUserInfoEntry OBJECT-TYPE 
        SYNTAX       Zxr10AdmmgrOnlineUserInfoEntry
        MAX-ACCESS   not-accessible 
        STATUS       current
        DESCRIPTION
            "Online user information entry" 
        INDEX { zxr10AdmmgrOnlineUsername, zxr10AdmmgrOnlineUserAccessType, 
                zxr10AdmmgrOnlineUserVtyNo} 
            ::= { zxr10AdmmgrOnlineUserInfoTable 1 }
             
        Zxr10AdmmgrOnlineUserInfoEntry ::=  
        SEQUENCE {
            zxr10AdmmgrOnlineUsername                DisplayString,
            zxr10AdmmgrOnlineUserAccessType          INTEGER,            
            zxr10AdmmgrOnlineUserVtyNo               Unsigned32,
            zxr10AdmmgrOnlineUserIpaddr              DisplayString,
            zxr10admmgrOnlineUserOnlineTime          DisplayString,
            zxr10admmgrOnlineUserLoginTime           DisplayString,
            zxr10admmgrOnlineUserIdleTime            DisplayString
            }  
        
        
    zxr10AdmmgrOnlineUsername OBJECT-TYPE 
        SYNTAX        DisplayString (SIZE (1..65))
        MAX-ACCESS    not-accessible 
        STATUS        current 
        DESCRIPTION
           "Username of online user"  
        ::= { zxr10AdmmgrOnlineUserInfoEntry 1 }  
        
    zxr10AdmmgrOnlineUserAccessType OBJECT-TYPE 
        SYNTAX        INTEGER
              {
                 cli(1), 
                 snmp(2),
                 web(3),
                 netconf(4),
                 qx(5),
                 cwmp(6)                
              }
        MAX-ACCESS    not-accessible 
        STATUS        current 
        DESCRIPTION
           "Access type of online user"  
        ::= { zxr10AdmmgrOnlineUserInfoEntry 2 } 
         
    zxr10AdmmgrOnlineUserVtyNo OBJECT-TYPE 
        SYNTAX        Unsigned32 
        MAX-ACCESS    not-accessible 
        STATUS        current 
        DESCRIPTION
           "Vtyno of online user"  
        ::= { zxr10AdmmgrOnlineUserInfoEntry 3 }  
        
    zxr10AdmmgrOnlineUserIpaddr OBJECT-TYPE 
        SYNTAX        DisplayString (SIZE (0..45))
        MAX-ACCESS    read-only 
        STATUS        current 
        DESCRIPTION
           "IP address of online user"  
        ::= { zxr10AdmmgrOnlineUserInfoEntry 4 }  
        
    zxr10admmgrOnlineUserOnlineTime OBJECT-TYPE 
        SYNTAX        DisplayString (SIZE (0..32))
        MAX-ACCESS    read-only 
        STATUS        current 
        DESCRIPTION
           "Online time of online user"  
        ::= { zxr10AdmmgrOnlineUserInfoEntry 5 }  
        
    zxr10admmgrOnlineUserLoginTime OBJECT-TYPE 
        SYNTAX        DisplayString (SIZE (0..32))
        MAX-ACCESS    read-only 
        STATUS        current 
        DESCRIPTION
           "Login time of online user"  
        ::= { zxr10AdmmgrOnlineUserInfoEntry 6 }  
        
    zxr10admmgrOnlineUserIdleTime OBJECT-TYPE 
        SYNTAX        DisplayString (SIZE (0..32))
        MAX-ACCESS    read-only 
        STATUS        current 
        DESCRIPTION
           "Idle time of online user"  
        ::= { zxr10AdmmgrOnlineUserInfoEntry 7 }  
 
     zxr10AdmmgrUserPrivLocalTable OBJECT-TYPE 
        SYNTAX       SEQUENCE OF Zxr10AdmmgrUserPrivLocalEntry 
        MAX-ACCESS   not-accessible 
        STATUS       current
        DESCRIPTION
            "Local user privilege table" 
        ::= { zxr10AdmmgrShowState 5 }
    zxr10AdmmgrUserPrivLocalEntry OBJECT-TYPE 
        SYNTAX       Zxr10AdmmgrUserPrivLocalEntry
        MAX-ACCESS   not-accessible 
        STATUS       current
        DESCRIPTION
            "Local user privilege entry" 
        INDEX {zxr10AdmmgrUserPrivLocalName, zxr10AdmmgrUserPrivLocalTask} 
            ::= { zxr10AdmmgrUserPrivLocalTable 1 }
        Zxr10AdmmgrUserPrivLocalEntry ::=  
            SEQUENCE {
                zxr10AdmmgrUserPrivLocalName                DisplayString,
                zxr10AdmmgrUserPrivLocalTask                AdmmgrSysTaskName,            
                zxr10AdmmgrUserPrivLocalRead                INTEGER,
                zxr10AdmmgrUserPrivLocalWrite               INTEGER,
                zxr10AdmmgrUserPrivLocalExecute             INTEGER,
                zxr10AdmmgrUserPrivLocalDebug               INTEGER
            }
    zxr10AdmmgrUserPrivLocalName  OBJECT-TYPE 
        SYNTAX        DisplayString(SIZE (1..65))
        MAX-ACCESS    not-accessible
        STATUS        current    
        DESCRIPTION
            "Local user name(1..65)"
        ::= { zxr10AdmmgrUserPrivLocalEntry 1 }   
    zxr10AdmmgrUserPrivLocalTask  OBJECT-TYPE 
        SYNTAX        AdmmgrSysTaskName
        MAX-ACCESS    not-accessible
        STATUS        current    
        DESCRIPTION
            "Task name"
        ::= { zxr10AdmmgrUserPrivLocalEntry 2 }
    zxr10AdmmgrUserPrivLocalRead  OBJECT-TYPE 
        SYNTAX        INTEGER
                {
                  true(1), 
                  false(2)
                }
        MAX-ACCESS    read-only
        STATUS        current    
        DESCRIPTION
            "If task has read privilege, true(1) or false(2)"
        ::= { zxr10AdmmgrUserPrivLocalEntry 3 }
    zxr10AdmmgrUserPrivLocalWrite  OBJECT-TYPE 
        SYNTAX        INTEGER
                {
                  true(1), 
                  false(2)
                }
        MAX-ACCESS    read-only
        STATUS        current    
        DESCRIPTION
            "If task has write privilege, true(1) or false(2)"
        ::= { zxr10AdmmgrUserPrivLocalEntry 4 }
    zxr10AdmmgrUserPrivLocalExecute  OBJECT-TYPE 
        SYNTAX        INTEGER
                {
                  true(1), 
                  false(2)
                }
        MAX-ACCESS    read-only
        STATUS        current    
        DESCRIPTION
            "If task has execute privilege, true(1) or false(2)"
        ::= { zxr10AdmmgrUserPrivLocalEntry 5 }
    zxr10AdmmgrUserPrivLocalDebug  OBJECT-TYPE 
        SYNTAX        INTEGER
                {
                  true(1), 
                  false(2)
                }
        MAX-ACCESS    read-only
        STATUS        current    
        DESCRIPTION
            "If task has debug privilege, true(1) or false(2)"
        ::= { zxr10AdmmgrUserPrivLocalEntry 6 }
    zxr10AdmmgrRolePrivCfgTable OBJECT-TYPE 
        SYNTAX       SEQUENCE OF Zxr10AdmmgrRolePrivCfgEntry 
        MAX-ACCESS   not-accessible 
        STATUS       current
        DESCRIPTION
            "Configurated role privilege table" 
        ::= { zxr10AdmmgrShowState 6 }
    zxr10AdmmgrRolePrivCfgEntry OBJECT-TYPE 
        SYNTAX       Zxr10AdmmgrRolePrivCfgEntry
        MAX-ACCESS   not-accessible 
        STATUS       current
        DESCRIPTION
            "Configurated role privilege entry" 
        INDEX {zxr10AdmmgrRolePrivCfgName, zxr10AdmmgrRolePrivCfgTask} 
            ::= { zxr10AdmmgrRolePrivCfgTable 1 }
        Zxr10AdmmgrRolePrivCfgEntry ::=  
            SEQUENCE {
                zxr10AdmmgrRolePrivCfgName                DisplayString,
                zxr10AdmmgrRolePrivCfgTask                AdmmgrSysTaskName,            
                zxr10AdmmgrRolePrivCfgRead                INTEGER,
                zxr10AdmmgrRolePrivCfgWrite               INTEGER,
                zxr10AdmmgrRolePrivCfgExecute             INTEGER,
                zxr10AdmmgrRolePrivCfgDebug               INTEGER
            }
    zxr10AdmmgrRolePrivCfgName  OBJECT-TYPE 
        SYNTAX        DisplayString(SIZE (1..48))
        MAX-ACCESS    not-accessible
        STATUS        current    
        DESCRIPTION
            "Configurated role name(1..48)"
        ::= { zxr10AdmmgrRolePrivCfgEntry 1 }   
    zxr10AdmmgrRolePrivCfgTask  OBJECT-TYPE 
        SYNTAX        AdmmgrSysTaskName
        MAX-ACCESS    not-accessible
        STATUS        current    
        DESCRIPTION
            "Task name"
        ::= { zxr10AdmmgrRolePrivCfgEntry 2 }
    zxr10AdmmgrRolePrivCfgRead  OBJECT-TYPE 
        SYNTAX        INTEGER
                {
                  true(1), 
                  false(2)
                }
        MAX-ACCESS    read-only
        STATUS        current    
        DESCRIPTION
            "If task has read privilege, true(1) or false(2)"
        ::= { zxr10AdmmgrRolePrivCfgEntry 3 }
    zxr10AdmmgrRolePrivCfgWrite  OBJECT-TYPE 
        SYNTAX        INTEGER
                {
                  true(1), 
                  false(2)
                }
        MAX-ACCESS    read-only
        STATUS        current    
        DESCRIPTION
            "If task has write privilege, true(1) or false(2)"
        ::= { zxr10AdmmgrRolePrivCfgEntry 4 }
    zxr10AdmmgrRolePrivCfgExecute  OBJECT-TYPE 
        SYNTAX        INTEGER
                {
                  true(1), 
                  false(2)
                }
        MAX-ACCESS    read-only
        STATUS        current    
        DESCRIPTION
            "If task has execute privilege, true(1) or false(2)"
        ::= { zxr10AdmmgrRolePrivCfgEntry 5 }
    zxr10AdmmgrRolePrivCfgDebug  OBJECT-TYPE 
        SYNTAX        INTEGER
                {
                  true(1), 
                  false(2)
                }
        MAX-ACCESS    read-only
        STATUS        current    
        DESCRIPTION
            "If task has debug privilege, true(1) or false(2)"
        ::= { zxr10AdmmgrRolePrivCfgEntry 6 }
    zxr10AdmmgrRolePrivDefTable OBJECT-TYPE 
        SYNTAX       SEQUENCE OF Zxr10AdmmgrRolePrivDefEntry 
        MAX-ACCESS   not-accessible 
        STATUS       current
        DESCRIPTION
            "Default role privilege table" 
        ::= { zxr10AdmmgrShowState 7 }
    zxr10AdmmgrRolePrivDefEntry OBJECT-TYPE 
        SYNTAX       Zxr10AdmmgrRolePrivDefEntry
        MAX-ACCESS   not-accessible 
        STATUS       current
        DESCRIPTION
            "Default role privilege entry" 
        INDEX {zxr10AdmmgrRolePrivDefName, zxr10AdmmgrRolePrivDefTask} 
            ::= { zxr10AdmmgrRolePrivDefTable 1 }
        Zxr10AdmmgrRolePrivDefEntry ::=  
            SEQUENCE {
                zxr10AdmmgrRolePrivDefName                DisplayString,
                zxr10AdmmgrRolePrivDefTask                AdmmgrSysTaskName,
                zxr10AdmmgrRolePrivDefRead                INTEGER,
                zxr10AdmmgrRolePrivDefWrite               INTEGER,
                zxr10AdmmgrRolePrivDefExecute             INTEGER,
                zxr10AdmmgrRolePrivDefDebug               INTEGER
            }
    zxr10AdmmgrRolePrivDefName  OBJECT-TYPE 
        SYNTAX        DisplayString(SIZE (1..48))
        MAX-ACCESS    not-accessible
        STATUS        current    
        DESCRIPTION
           "Default role name(1..48)"
        ::= { zxr10AdmmgrRolePrivDefEntry 1 }   
    zxr10AdmmgrRolePrivDefTask  OBJECT-TYPE 
        SYNTAX        AdmmgrSysTaskName
        MAX-ACCESS    not-accessible
        STATUS        current    
        DESCRIPTION
            "Task name"
        ::= { zxr10AdmmgrRolePrivDefEntry 2 }
    zxr10AdmmgrRolePrivDefRead  OBJECT-TYPE 
        SYNTAX        INTEGER
                {
                  true(1), 
                  false(2)
                }
        MAX-ACCESS    read-only
        STATUS        current    
        DESCRIPTION
            "If task has read privilege, true(1) or false(2)"
        ::= { zxr10AdmmgrRolePrivDefEntry 3 }
    zxr10AdmmgrRolePrivDefWrite  OBJECT-TYPE 
    SYNTAX        INTEGER
                {
                  true(1), 
                  false(2)
                }
    MAX-ACCESS    read-only
    STATUS        current    
    DESCRIPTION
       "If task has write privilege, true(1) or false(2)"
    ::= { zxr10AdmmgrRolePrivDefEntry 4 }
    zxr10AdmmgrRolePrivDefExecute  OBJECT-TYPE 
        SYNTAX        INTEGER
                {
                  true(1), 
                  false(2)
                }
        MAX-ACCESS    read-only
        STATUS        current    
        DESCRIPTION
            "If task has execute privilege, true(1) or false(2)"
        ::= { zxr10AdmmgrRolePrivDefEntry 5 }
    zxr10AdmmgrRolePrivDefDebug  OBJECT-TYPE 
        SYNTAX       INTEGER
                {
                  true(1), 
                  false(2)
                }
        MAX-ACCESS    read-only
        STATUS        current    
        DESCRIPTION
       "If task has debug privilege, true(1) or false(2)"
    ::= { zxr10AdmmgrRolePrivDefEntry 6 }
-- end added by houjin for Adm-mgr mib

    zxr10AdmmgrRoleTable OBJECT-TYPE 
        SYNTAX       SEQUENCE OF Zxr10AdmmgrRoleEntry 
        MAX-ACCESS   not-accessible 
        STATUS       current
        DESCRIPTION
            "Role table" 
        ::= { zxr10AdmmgrRoleInfo 1 }
    
    zxr10AdmmgrRoleEntry OBJECT-TYPE 
        SYNTAX       Zxr10AdmmgrRoleEntry
        MAX-ACCESS   not-accessible 
        STATUS       current
        DESCRIPTION
            "Role entry" 
        INDEX { zxr10AdmmgrRoleInfoRoleName} 
            ::= { zxr10AdmmgrRoleTable 1 }
            
        Zxr10AdmmgrRoleEntry ::=  
        SEQUENCE {
            zxr10AdmmgrRoleInfoRoleName    DisplayString,
            zxr10AdmmgrRoleDescription     DisplayString
            --zxr10AdmmgrRoleRowStatus     RowStatus
            }
            
    zxr10AdmmgrRoleInfoRoleName OBJECT-TYPE 
        SYNTAX        DisplayString (SIZE (1..48))
        MAX-ACCESS    not-accessible 
        STATUS        current 
        DESCRIPTION
           "Role name"  
        ::= { zxr10AdmmgrRoleEntry 1 }

    zxr10AdmmgrRoleDescription OBJECT-TYPE 
        SYNTAX        DisplayString (SIZE (0..128))
        MAX-ACCESS    read-only 
        STATUS        current 
        DESCRIPTION
           "The description of role"  
        ::= { zxr10AdmmgrRoleEntry 2 }

    -- zxr10AdmmgrRoleRowStatus OBJECT-TYPE
    --     SYNTAX        RowStatus
    --     MAX-ACCESS    read-create 
    --     STATUS        current
    --     DESCRIPTION
    --        "Row Status"
    -- ::= { zxr10AdmmgrRoleEntry 100 }

    zxr10AdmmgrRoleInheritTable OBJECT-TYPE 
        SYNTAX       SEQUENCE OF Zxr10AdmmgrRoleInheritEntry 
        MAX-ACCESS   not-accessible 
        STATUS       current
        DESCRIPTION
            "Role inherit table" 
        ::= { zxr10AdmmgrRoleInfo 2 }
    
    zxr10AdmmgrRoleInheritEntry OBJECT-TYPE 
        SYNTAX       Zxr10AdmmgrRoleInheritEntry
        MAX-ACCESS   not-accessible 
        STATUS       current
        DESCRIPTION
            "Role inherit entry" 
        INDEX { zxr10AdmmgrriRoleName,zxr10AdmmgrriInheritRoleName} 
            ::= { zxr10AdmmgrRoleInheritTable 1 }
            
        Zxr10AdmmgrRoleInheritEntry ::=  
        SEQUENCE {
            zxr10AdmmgrriRoleName           DisplayString,
            zxr10AdmmgrriInheritRoleName    DisplayString
            --zxr10AdmmgrriRowStatus        RowStatus
            }
            
    zxr10AdmmgrriRoleName OBJECT-TYPE 
        SYNTAX        DisplayString (SIZE (1..48))
        MAX-ACCESS    not-accessible 
        STATUS        current 
        DESCRIPTION
           "Role name"  
        ::= { zxr10AdmmgrRoleInheritEntry 1 }

    zxr10AdmmgrriInheritRoleName OBJECT-TYPE 
        SYNTAX        DisplayString (SIZE (0..48))
        MAX-ACCESS    read-only 
        STATUS        current 
        DESCRIPTION
           "Inherit role name"  
        ::= { zxr10AdmmgrRoleInheritEntry 2 }

    -- zxr10AdmmgrriRowStatus OBJECT-TYPE
    --     SYNTAX        RowStatus
    --     MAX-ACCESS    read-create 
    --     STATUS        current
    --     DESCRIPTION
    --        "Row Status"
    -- ::= { zxr10AdmmgrRoleInheritEntry 100 }

    zxr10AdmmgrRoleTaskGroupTable OBJECT-TYPE 
        SYNTAX       SEQUENCE OF Zxr10AdmmgrRoleTaskGroupEntry 
        MAX-ACCESS   not-accessible 
        STATUS       current
        DESCRIPTION
            "Role-related taskgroups table" 
        ::= { zxr10AdmmgrRoleInfo 3 }
    
    zxr10AdmmgrRoleTaskGroupEntry OBJECT-TYPE 
        SYNTAX       Zxr10AdmmgrRoleTaskGroupEntry
        MAX-ACCESS   not-accessible 
        STATUS       current
        DESCRIPTION
            "Role-related taskgroups entry." 
        INDEX { zxr10AdmmgrrtgRoleName,zxr10AdmmgrrtgTaskGroupName} 
            ::= { zxr10AdmmgrRoleTaskGroupTable 1 }
            
        Zxr10AdmmgrRoleTaskGroupEntry ::=  
        SEQUENCE {
            zxr10AdmmgrrtgRoleName        DisplayString,
            zxr10AdmmgrrtgTaskGroupName   DisplayString
            --zxr10AdmmgrrtgRowStatus     RowStatus
            }
            
    zxr10AdmmgrrtgRoleName OBJECT-TYPE 
        SYNTAX        DisplayString (SIZE (1..48))
        MAX-ACCESS    not-accessible 
        STATUS        current 
        DESCRIPTION
           "Role name"  
        ::= { zxr10AdmmgrRoleTaskGroupEntry 1 }

    zxr10AdmmgrrtgTaskGroupName OBJECT-TYPE 
        SYNTAX        DisplayString (SIZE (0..48))
        MAX-ACCESS    read-only 
        STATUS        current 
        DESCRIPTION
           "Taskgroup name"  
        ::= { zxr10AdmmgrRoleTaskGroupEntry 2 }

    -- zxr10AdmmgrrtgRowStatus OBJECT-TYPE
    --     SYNTAX        RowStatus
    --     MAX-ACCESS    read-create 
    --     STATUS        current
    --     DESCRIPTION
    --        "Row Status"
    -- ::= { zxr10AdmmgrRoleTaskGroupEntry 100 }

    zxr10AdmmgrTaskGroupTable OBJECT-TYPE 
        SYNTAX       SEQUENCE OF Zxr10AdmmgrTaskGroupEntry 
        MAX-ACCESS   not-accessible 
        STATUS       current
        DESCRIPTION
            "Taskgroup table" 
        ::= { zxr10AdmmgrTaskGroupInfo 1 }
    
    zxr10AdmmgrTaskGroupEntry OBJECT-TYPE 
        SYNTAX       Zxr10AdmmgrTaskGroupEntry
        MAX-ACCESS   not-accessible 
        STATUS       current
        DESCRIPTION
            "Taskgroup entry" 
        INDEX { zxr10AdmmgrTaskGrpGroupName} 
            ::= { zxr10AdmmgrTaskGroupTable 1 }
            
        Zxr10AdmmgrTaskGroupEntry ::=  
        SEQUENCE {
            zxr10AdmmgrTaskGrpGroupName       DisplayString,
            zxr10AdmmgrTaskGrpDescription     DisplayString
            --zxr10AdmmgrTaskGrpRowStatus     RowStatus
            }
            
    zxr10AdmmgrTaskGrpGroupName OBJECT-TYPE 
        SYNTAX        DisplayString (SIZE (1..48))
        MAX-ACCESS    not-accessible 
        STATUS        current 
        DESCRIPTION
           "Taskgroup name"  
        ::= { zxr10AdmmgrTaskGroupEntry 1 }

    zxr10AdmmgrTaskGrpDescription OBJECT-TYPE 
        SYNTAX        DisplayString (SIZE (0..128))
        MAX-ACCESS    read-only 
        STATUS        current 
        DESCRIPTION
           "The description of taskgroup"  
        ::= { zxr10AdmmgrTaskGroupEntry 2 }

    -- zxr10AdmmgrTaskGrpRowStatus OBJECT-TYPE
    --     SYNTAX        RowStatus
    --     MAX-ACCESS    read-create 
    --     STATUS        current
    --     DESCRIPTION
    --        "Row Status"
    -- ::= { zxr10AdmmgrTaskGroupEntry 100 }

    zxr10AdmmgrtgInheritTable OBJECT-TYPE 
        SYNTAX       SEQUENCE OF Zxr10AdmmgrtgInheritEntry 
        MAX-ACCESS   not-accessible 
        STATUS       current
        DESCRIPTION
            "Taskgroup inherit table" 
        ::= { zxr10AdmmgrTaskGroupInfo 2 }
    
    zxr10AdmmgrtgInheritEntry OBJECT-TYPE 
        SYNTAX       Zxr10AdmmgrtgInheritEntry
        MAX-ACCESS   not-accessible 
        STATUS       current
        DESCRIPTION
            "Taskgroup inherit entry" 
        INDEX { zxr10AdmmgrtgiTaskGroupName,zxr10AdmmgrtgiInheritGroupName} 
            ::= { zxr10AdmmgrtgInheritTable 1 }
            
        Zxr10AdmmgrtgInheritEntry ::=  
        SEQUENCE {
            zxr10AdmmgrtgiTaskGroupName      DisplayString,
            zxr10AdmmgrtgiInheritGroupName   DisplayString
            --zxr10AdmmgrtgiRowStatus        RowStatus
            }
            
    zxr10AdmmgrtgiTaskGroupName OBJECT-TYPE 
        SYNTAX        DisplayString (SIZE (1..48))
        MAX-ACCESS    not-accessible
        STATUS        current 
        DESCRIPTION
           "Taskgroup name"  
        ::= { zxr10AdmmgrtgInheritEntry 1 }

    zxr10AdmmgrtgiInheritGroupName OBJECT-TYPE 
        SYNTAX        DisplayString (SIZE (0..48))
        MAX-ACCESS    read-only 
        STATUS        current 
        DESCRIPTION
           "Inherit taskgroup name"  
        ::= { zxr10AdmmgrtgInheritEntry 2 }

    -- zxr10AdmmgrtgiRowStatus OBJECT-TYPE
    --     SYNTAX        RowStatus
    --     MAX-ACCESS    read-create 
    --     STATUS        current
    --     DESCRIPTION
    --        "Row Status"
    -- ::= { zxr10AdmmgrtgInheritEntry 100 }
    
    zxr10AdmmgrTaskGrpTaskTable OBJECT-TYPE 
        SYNTAX       SEQUENCE OF Zxr10AdmmgrTaskGrpTaskEntry 
        MAX-ACCESS   not-accessible 
        STATUS       current
        DESCRIPTION
            "Taskgroup task table" 
        ::= { zxr10AdmmgrTaskGroupInfo 3 }
    
    zxr10AdmmgrTaskGrpTaskEntry OBJECT-TYPE 
        SYNTAX       Zxr10AdmmgrTaskGrpTaskEntry
        MAX-ACCESS   not-accessible 
        STATUS       current
        DESCRIPTION
            "taskgroup task entry." 
        INDEX { zxr10AdmmgrtgTaskGroupName, zxr10AdmmgrtgTaskClassName, 
                zxr10AdmmgrtgTaskName} 
            ::= { zxr10AdmmgrTaskGrpTaskTable 1 }
            
        Zxr10AdmmgrTaskGrpTaskEntry ::=  
        SEQUENCE {
            zxr10AdmmgrtgTaskGroupName        DisplayString,
            zxr10AdmmgrtgTaskClassName        INTEGER,
            zxr10AdmmgrtgTaskName             AdmmgrSysTaskName,
            zxr10AdmmgrtgTaskRead             INTEGER,
            zxr10AdmmgrtgTaskWrite            INTEGER,
            zxr10AdmmgrtgTaskExecute          INTEGER,
            zxr10AdmmgrtgTaskDebug            INTEGER
            --zxr10AdmmgrtgTaskRowStatus      RowStatus
            }
            
    zxr10AdmmgrtgTaskGroupName OBJECT-TYPE 
        SYNTAX        DisplayString (SIZE (1..48))
        MAX-ACCESS    not-accessible 
        STATUS        current 
        DESCRIPTION
           "Taskgroup name"  
        ::= { zxr10AdmmgrTaskGrpTaskEntry 1 }
            
    zxr10AdmmgrtgTaskClassName OBJECT-TYPE 
        SYNTAX  INTEGER (1..127)
        MAX-ACCESS    not-accessible 
        STATUS        current 
        DESCRIPTION
            "Task class name,
             advancedsysmanagement(1),
             sysmanagement(2),
             basicservice(3),
             flowmonitoring(4),
             idc(5),
             ipservice(6),
             lawfulinterception(7), 
             multicast(8),
             vpn(9),
             reliability(10),
             qos(11),
             routemanage(12),
             aaa(13),
             security(14),
             pppoeclient(15),
             accesslist(16),
             bras(17)"  
        ::= { zxr10AdmmgrTaskGrpTaskEntry 2 } 
    
    zxr10AdmmgrtgTaskName OBJECT-TYPE 
        SYNTAX        AdmmgrSysTaskName
        MAX-ACCESS    not-accessible
        STATUS        current 
        DESCRIPTION
            "Task name"
        ::= { zxr10AdmmgrTaskGrpTaskEntry 3 }

    zxr10AdmmgrtgTaskRead OBJECT-TYPE 
        SYNTAX    INTEGER
              {
                 true(1), 
                 false(2)
              }
        MAX-ACCESS    read-only 
        STATUS        current 
        DESCRIPTION
           "If task permission read configed, true(1) or false(2)"  
        ::= { zxr10AdmmgrTaskGrpTaskEntry 4 }

    zxr10AdmmgrtgTaskWrite OBJECT-TYPE 
        SYNTAX    INTEGER
              {
                 true(1), 
                 false(2)
              }
        MAX-ACCESS    read-only 
        STATUS        current 
        DESCRIPTION
           "If task permission write configed, true(1) or false(2)"  
        ::= { zxr10AdmmgrTaskGrpTaskEntry 5 }

    zxr10AdmmgrtgTaskExecute OBJECT-TYPE 
        SYNTAX    INTEGER
              {
                 true(1), 
                 false(2)
              }
        MAX-ACCESS    read-only 
        STATUS        current 
        DESCRIPTION
           "If task permission execute configed, true(1) or false(2)"  
        ::= { zxr10AdmmgrTaskGrpTaskEntry 6 }

    zxr10AdmmgrtgTaskDebug OBJECT-TYPE 
        SYNTAX    INTEGER
              {
                 true(1), 
                 false(2)
              }
        MAX-ACCESS    read-only 
        STATUS        current 
        DESCRIPTION
           "If task permission debug configed, true(1) or false(2)"  
        ::= { zxr10AdmmgrTaskGrpTaskEntry 7 }

     END
