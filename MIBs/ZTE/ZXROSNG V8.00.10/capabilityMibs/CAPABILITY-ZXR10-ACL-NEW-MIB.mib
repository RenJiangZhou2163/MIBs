--  ******************************************************
--  $Id: CAPABILITY-ZXR10-ACL-NEW-MIB.mib  
--  
--  CAPABILITY-ZXR10-ACL-NEW-MIB
--  
--  Nor. 2015, Qian Yi 
--  
--  Copyright(c) 2010 by ZTE Corporaton
--  All rights reservered
--  ******************************************************

CAPABILITY-ZXR10-ACL-NEW-MIB DEFINITIONS ::= BEGIN

IMPORTS
    MODULE-IDENTITY, OBJECT-TYPE, NOTIFICATION-TYPE,
    Integer32, Unsigned32, Counter32, enterprises, IpAddress, 
    Gauge32, Counter64, TimeTicks, mib-2
        FROM SNMPv2-SMI
    MODULE-COMPLIANCE, OBJECT-GROUP, NOTIFICATION-GROUP, AGENT-CAPABILITIES
        FROM SNMPv2-CONF
    DisplayString, MacAddress, TEXTUAL-CONVENTION, RowStatus
        FROM SNMPv2-TC
    zxr10,zxr10RosngMIB,zxr10RosngAgentCapability
        FROM ZXR10-SMI;

zxr10AclNewMIBCapability MODULE-IDENTITY
    LAST-UPDATED "201601221500Z"
    ORGANIZATION "ZTE Corporation"
    CONTACT-INFO
        "       Hu Jun
        Tel:    +86-25-52870000
        E-Mail: hu.jun11@zte.com.cn "
    DESCRIPTION
        "The MIB module to describe the ACL protocol."
    REVISION "201601221500Z"
    DESCRIPTION 
        "Add capability of zxr10ACLv4VxlanGroup"
    REVISION "201512211000Z"
    DESCRIPTION 
        "Add zxr10AclNewMIBCapabilityXGW.
         Add capability of zxr10ACLUsrDefinedGroup"
    REVISION "201512171000Z"
    DESCRIPTION 
        "Initial revision."   
    ::= { zxr10RosngAgentCapability 602 }

-- capabilities for 59 and 89
zxr10AclNewMIBCapabilitySwitch AGENT-CAPABILITIES  
    PRODUCT-RELEASE "SWITCH.59,SWITCH.89"          
    STATUS          current
    DESCRIPTION
        "ZXR10-ACL-NEW-MIB capabilities for 59, 89"
    SUPPORTS        ZXR10-ACL-NEW-MIB
    INCLUDES        {zxr10ACLv4Group, zxr10ACLv6Group, 
                     zxr10ACLLinkGroup, zxr10ACLv4MixGroup, 
                     zxr10ACLv6MixGroup, zxr10ACLUsrProtocolGroup,
                     zxr10ACLUsrDefinedGroup}

    VARIATION       zxr10ACLUsrProtocolRuleDMACMask
    ACCESS          not-implemented
    DESCRIPTION     "Not support MAC wildcard."

    VARIATION       zxr10ACLUsrProtocolRuleAnyEther
    ACCESS          not-implemented
    DESCRIPTION     "Not support any ethernet type."
    ::= { zxr10AclNewMIBCapability 1 }

-- capabilities for 99
zxr10AclNewMIBCapability99 AGENT-CAPABILITIES  
    PRODUCT-RELEASE "SWITCH.99"          
    STATUS          current
    DESCRIPTION
        "ZXR10-ACL-NEW-MIB capabilities for 99"
    SUPPORTS        ZXR10-ACL-NEW-MIB
    INCLUDES        {zxr10ACLv4Group, zxr10ACLv6Group, 
                     zxr10ACLLinkGroup, zxr10ACLv4MixGroup, 
                     zxr10ACLUsrProtocolGroup, zxr10ACLUsrDefinedGroup,
                     zxr10ACLv4VxlanGroup}

    VARIATION       zxr10ACLUsrProtocolRuleDMACMask
    ACCESS          not-implemented
    DESCRIPTION     "Not support MAC wildcard."

    VARIATION       zxr10ACLUsrProtocolRuleAnyEther
    ACCESS          not-implemented
    DESCRIPTION     "Not support any ethernet type."
    ::= { zxr10AclNewMIBCapability 2 }

-- capabilities for 15K
zxr10AclNewMIBCapability15K AGENT-CAPABILITIES  
    PRODUCT-RELEASE "HighEndPacket.15K"          
    STATUS          current
    DESCRIPTION
        "ZXR10-ACL-NEW-MIB capabilities for 15K"
    SUPPORTS        ZXR10-ACL-NEW-MIB
    INCLUDES        {zxr10ACLv4Group, zxr10ACLv6Group, 
                     zxr10ACLLinkGroup, zxr10ACLUsrProtocolGroup}
    ::= { zxr10AclNewMIBCapability 3 }

-- capabilities for T8K
zxr10AclNewMIBCapabilityT8K AGENT-CAPABILITIES  
    PRODUCT-RELEASE "HignEndRouter.T8000"          
    STATUS          current
    DESCRIPTION
        "ZXR10-ACL-NEW-MIB capabilities for T8000"
    SUPPORTS        ZXR10-ACL-NEW-MIB
    INCLUDES        {zxr10ACLv4Group, zxr10ACLv6Group}
    ::= { zxr10AclNewMIBCapability 4 }

-- capabilities for 5960
zxr10AclNewMIBCapability5960 AGENT-CAPABILITIES  
    PRODUCT-RELEASE "SWITCH.5960"          
    STATUS          current
    DESCRIPTION
        "ZXR10-ACL-NEW-MIB capabilities for 5960"
    SUPPORTS        ZXR10-ACL-NEW-MIB
    INCLUDES        {zxr10ACLv4Group, zxr10ACLv6Group, 
                     zxr10ACLLinkGroup, zxr10ACLv4MixGroup, 
                     zxr10ACLv6MixGroup, zxr10ACLUsrDefinedGroup,
                     zxr10ACLv4VxlanGroup}
    ::= { zxr10AclNewMIBCapability 5 }

-- capabilities for MSR
zxr10AclNewMIBCapabilityMSR AGENT-CAPABILITIES  
    PRODUCT-RELEASE "MSR.ASR,MSR.ZSRV2"          
    STATUS          current
    DESCRIPTION
        "ZXR10-ACL-NEW-MIB capabilities for MSR"
    SUPPORTS        ZXR10-ACL-NEW-MIB
    INCLUDES        {zxr10ACLv4Group, zxr10ACLv6Group, 
                     zxr10ACLLinkGroup, zxr10ACLv4MixGroup, 
                     zxr10ACLv6MixGroup}
    ::= { zxr10AclNewMIBCapability 6 }

-- capabilities for 6100
zxr10AclNewMIBCapability6100 AGENT-CAPABILITIES  
    PRODUCT-RELEASE "PTN.6100"          
    STATUS          current
    DESCRIPTION
        "ZXR10-ACL-NEW-MIB capabilities for 6100"
    SUPPORTS        ZXR10-ACL-NEW-MIB
    INCLUDES        {zxr10ACLv4Group, zxr10ACLv6Group, 
                     zxr10ACLLinkGroup, zxr10ACLv4MixGroup, 
                     zxr10ACLv6MixGroup}
    ::= { zxr10AclNewMIBCapability 7 }

-- capabilities for 6500
zxr10AclNewMIBCapability6500 AGENT-CAPABILITIES  
    PRODUCT-RELEASE "PTN.6500"          
    STATUS          current
    DESCRIPTION
        "ZXR10-ACL-NEW-MIB capabilities for 6500"
    SUPPORTS        ZXR10-ACL-NEW-MIB
    INCLUDES        {zxr10ACLv4Group, zxr10ACLLinkGroup, 
                     zxr10ACLv4MixGroup}
    ::= { zxr10AclNewMIBCapability 8 }

-- capabilities for M6000
zxr10AclNewMIBCapabilityM6K AGENT-CAPABILITIES  
    PRODUCT-RELEASE "MSE.M6000"          
    STATUS          current
    DESCRIPTION
        "ZXR10-ACL-NEW-MIB capabilities for M6000"
    SUPPORTS        ZXR10-ACL-NEW-MIB
    INCLUDES        {zxr10ACLv4Group, zxr10ACLv6Group}
    ::= { zxr10AclNewMIBCapability 9 }

-- capabilities for M6000-S
zxr10AclNewMIBCapabilityM6KS AGENT-CAPABILITIES  
    PRODUCT-RELEASE "MSE.M6000-S"          
    STATUS          current
    DESCRIPTION
        "ZXR10-ACL-NEW-MIB capabilities for M6000-S"
    SUPPORTS        ZXR10-ACL-NEW-MIB
    INCLUDES        {zxr10ACLv4Group, zxr10ACLv6Group, 
                     zxr10ACLLinkGroup}
    ::= { zxr10AclNewMIBCapability 10 }

-- capabilities for xGW
zxr10AclNewMIBCapabilityXGW AGENT-CAPABILITIES  
    PRODUCT-RELEASE "MSE.xGW"          
    STATUS          current
    DESCRIPTION
        "ZXR10-ACL-NEW-MIB capabilities for XGW"
    SUPPORTS        ZXR10-ACL-NEW-MIB
    INCLUDES        {zxr10ACLv4Group, zxr10ACLv6Group,
                    zxr10ACLUsrDefinedGroup}
    ::= { zxr10AclNewMIBCapability 11 }

END
