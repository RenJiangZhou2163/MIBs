-- *******************************************************************
-- RAISECOM-AC-MGMT-MIB.mib : Raisecom AC MGMT MIB file
-- January 2009, huangyuanbo
--
-- Copyright (c) 2009 by Raisecom Networks Co.,Ltd.
-- All rights reserved.
-- *******************************************************************
--
RAISECOM-AC-MGMT-MIB DEFINITIONS ::= BEGIN

IMPORTS
        IpAddress,
        OBJECT-TYPE,
        MODULE-IDENTITY,
        NOTIFICATION-TYPE,
        TimeTicks,
        Counter32
                FROM SNMPv2-SMI
        MacAddress,
        TruthValue,
        DisplayString,
        RowStatus
                FROM SNMPv2-TC
        MODULE-COMPLIANCE,
        NOTIFICATION-GROUP,
        OBJECT-GROUP
                FROM SNMPv2-CONF
        InetAddress,
        InetAddressType
                FROM INET-ADDRESS-MIB
        capwapBaseNtfChannelType
                FROM CAPWAP-BASE-MIB
        capwapBaseNtfAuthenMethod
                FROM CAPWAP-BASE-MIB
        capwapBaseNtfChannelDownReason
                FROM CAPWAP-BASE-MIB
        ruijieMgmt
                FROM RAISECOM-SMI; 
                
ruijieAcMgmtMIB MODULE-IDENTITY
    LAST-UPDATED "200909180000Z"
    ORGANIZATION "Raisecom Networks Co.,Ltd."
    CONTACT-INFO
        " 
    Tel: 4008-111-000

    E-mail: service@raisecom.com.cn"
    DESCRIPTION
        "This module defines ac management mibs."
    REVISION      "200909180000Z"
    DESCRIPTION
        "Initial version of this MIB module."
    ::= { ruijieMgmt 56}

--***************** define the AC root nodes *****************
ruijieAcMgmtAcMIBObjects OBJECT IDENTIFIER      ::= { ruijieAcMgmtMIB 1 }
ruijieAcMgmtAc     OBJECT IDENTIFIER ::= { ruijieAcMgmtAcMIBObjects 1 }
ruijieAcMgmtAcIf   OBJECT IDENTIFIER ::= { ruijieAcMgmtAcMIBObjects 2 }

--***************** define the AP root nodes *****************
ruijieAcMgmtApMIBObjects OBJECT IDENTIFIER      ::= { ruijieAcMgmtMIB 2 }
ruijieAcMgmtAp     OBJECT IDENTIFIER ::= { ruijieAcMgmtApMIBObjects 1 }
ruijieAcMgmtApIf   OBJECT IDENTIFIER ::= { ruijieAcMgmtApMIBObjects 2 }

--******** define the AP group root nodes ************
ruijieAcMgmtApgMIBObjects OBJECT IDENTIFIER      ::= { ruijieAcMgmtMIB 3 }
ruijieAcMgmtApg     OBJECT IDENTIFIER ::= { ruijieAcMgmtApgMIBObjects 1 }
ruijieAcMgmtApgIf   OBJECT IDENTIFIER ::= { ruijieAcMgmtApgMIBObjects 2 }

--******** define the Wlan root nodes ************
ruijieAcMgmtWlanMIBObjects OBJECT IDENTIFIER      ::= { ruijieAcMgmtMIB 4 }
ruijieAcMgmtWlan     OBJECT IDENTIFIER ::= { ruijieAcMgmtWlanMIBObjects 1 }
ruijieAcMgmtWlanIf   OBJECT IDENTIFIER ::= { ruijieAcMgmtWlanMIBObjects 2 }

--******** define the Sta root nodes ************
ruijieAcMgmtStaMIBObjects OBJECT IDENTIFIER      ::= { ruijieAcMgmtMIB 5 }
ruijieAcMgmtSta     OBJECT IDENTIFIER ::= { ruijieAcMgmtStaMIBObjects 1 }
ruijieAcMgmtStaIf   OBJECT IDENTIFIER ::= { ruijieAcMgmtStaMIBObjects 2 }

-- ******** define the notify nodes *************
ruijieAcMgmtNotificationsMIBObjects OBJECT IDENTIFIER      ::= { ruijieAcMgmtMIB 6 }
ruijieAcMgmtNtfObjects     OBJECT IDENTIFIER ::= { ruijieAcMgmtNotificationsMIBObjects 1 }
ruijieAcMgmtNotifications     OBJECT IDENTIFIER ::= { ruijieAcMgmtNotificationsMIBObjects 2 }   

--********************************************************************
--                                                                  **
--                  AC nodes                                        **
--                                                                  **
--********************************************************************

-- 1.sta_limit, the station num ac support
ruijieAcStaLimit OBJECT-TYPE
    SYNTAX  INTEGER (1..2147483647)
    MAX-ACCESS  read-write
    STATUS  current
    DESCRIPTION
            "The max station this AC supports."
    ::= { ruijieAcMgmtAc 1 }

-- 2.wtp_limit, the wtp num ac support
ruijieAcWtpLimit OBJECT-TYPE
    SYNTAX  INTEGER (1..2147483647)
    MAX-ACCESS  read-write
    STATUS  current
    DESCRIPTION
            "The max wtp this AC supports."
    ::= { ruijieAcMgmtAc 2 }

-- 3.[no] r_mac_field, 0-disable,1-enable
ruijieAcRMacField OBJECT-TYPE
    SYNTAX  INTEGER (0..1)
    MAX-ACCESS  read-write
    STATUS  current
    DESCRIPTION
            "Set AC's R-MAC Field."
    ::= { ruijieAcMgmtAc 3 }

-- 4.[no] data_dtls, 0-disable,1-enable
ruijieAcDataDtls OBJECT-TYPE
    SYNTAX  INTEGER (0..1)
    MAX-ACCESS  read-write
    STATUS  current
    DESCRIPTION
            "Set AC's DTLS Policy Field."
    ::= { ruijieAcMgmtAc 4 }
    
-- 5.[no] ecn_support, 0-disable,1-enable
ruijieAcEcnSupport OBJECT-TYPE
    SYNTAX  INTEGER (0..1)
    MAX-ACCESS  read-write
    STATUS  current
    DESCRIPTION
            "Set AC's ECN Support Field."
    ::= { ruijieAcMgmtAc 5 }

-- 6.[no] backup_ac_ip ip_address
ruijieAcAcIpTable OBJECT-TYPE
    SYNTAX  SEQUENCE OF RuijieAcAcIpTableEntry
    MAX-ACCESS  not-accessible
    STATUS  current
    DESCRIPTION
            "Add or Del the AC's backup ip address."
    ::= { ruijieAcMgmtAc 6 }

ruijieAcAcIpTableEntry OBJECT-TYPE
    SYNTAX  RuijieAcAcIpTableEntry
    MAX-ACCESS  not-accessible
    STATUS  current
    DESCRIPTION
        "The entry of Ac's backup ip address."
    INDEX   { ruijieAcAcIpIndex}
    ::= { ruijieAcAcIpTable 1 }

RuijieAcAcIpTableEntry ::=
    SEQUENCE {
        ruijieAcAcIpIndex      INTEGER,
        ruijieAcBackAcIp       IpAddress,
        ruijieAcAcIpRS         RowStatus
    }

-- The Ac name with priority index
ruijieAcAcIpIndex OBJECT-TYPE
    SYNTAX  INTEGER (1..512)
    MAX-ACCESS  read-only
    STATUS  current
    DESCRIPTION
            "AC's Ac name with priority index."
    ::= { ruijieAcAcIpTableEntry 1 }

ruijieAcBackAcIp OBJECT-TYPE
    SYNTAX  IpAddress
    MAX-ACCESS  read-write
    STATUS  current
    DESCRIPTION
            "Set AC's ip list."
    ::= { ruijieAcAcIpTableEntry 2 }
    
ruijieAcAcIpRS OBJECT-TYPE
    SYNTAX     RowStatus 
    MAX-ACCESS read-write
    STATUS     current
    DESCRIPTION
         "Used to add or del a backup ac ip address in the ac."
    ::= { ruijieAcAcIpTableEntry 3 }

-- 7.[no] ecn_support, set the mtu
ruijieAcMtu OBJECT-TYPE
    SYNTAX  INTEGER (0..1500)
    MAX-ACCESS  read-write
    STATUS  current
    DESCRIPTION
            "Set AC's MTU."
    ::= { ruijieAcMgmtAc 7 }

-- 8.ac_name, set the ac name
ruijieAcAcName OBJECT-TYPE
    SYNTAX  DisplayString (SIZE (0..255))
    MAX-ACCESS  read-write
    STATUS  current
    DESCRIPTION
            "Set AC's Name."
    ::= { ruijieAcMgmtAc 8 }

-- location location_string
ruijieAcLocation  OBJECT-TYPE
    SYNTAX  DisplayString (SIZE (1..255))
    MAX-ACCESS  read-write
    STATUS  current
    DESCRIPTION
            "Ac's location information."
    ::= { ruijieAcMgmtAc 9}

-- reset ap_name
ruijieAcResetAp  OBJECT-TYPE
    SYNTAX  DisplayString (SIZE (1..255))
    MAX-ACCESS  read-write
    STATUS  current
    DESCRIPTION
            "Delete the ap by assigning the ap name."
    ::= { ruijieAcMgmtAc 10}

-- The ap num attached to this ac.
ruijieAcApNum OBJECT-TYPE
    SYNTAX  INTEGER (1..800)
    MAX-ACCESS  read-only
    STATUS  current
    DESCRIPTION
            "Ap num attached to this ac."
    ::= { ruijieAcMgmtAc 11 }

-- The Ac's 802.11a rate set
ruijieAc80211aRateTable OBJECT-TYPE
    SYNTAX  SEQUENCE OF RuijieAc80211aRateEntry
    MAX-ACCESS  not-accessible
    STATUS  current
    DESCRIPTION
            "The Ap attributes."
    ::= { ruijieAcMgmtAc 12 }

ruijieAc80211aRateEntry OBJECT-TYPE
    SYNTAX  RuijieAc80211aRateEntry
    MAX-ACCESS  not-accessible
    STATUS  current
    DESCRIPTION
        "Get and set the Ap attribtues."
    INDEX   { ruijieAc80211aRate }
    ::= { ruijieAc80211aRateTable 1 }

RuijieAc80211aRateEntry ::=
    SEQUENCE {
        ruijieAc80211aRate     INTEGER,
        ruijieAc80211aRateType INTEGER
    }

ruijieAc80211aRate  OBJECT-TYPE
    SYNTAX  INTEGER (1..8)
    MAX-ACCESS  not-accessible
    STATUS  current
    DESCRIPTION
            "The global 802.11a rate set in this AC.
            802.11a-6, 9, 12, 18, 24, 36, 48, and 54 Mbps.
            set 1 for 6Mbps, set 2 for 9Mbps, set 3 for 12Mbps,etc..."
    ::= { ruijieAc80211aRateEntry 1}
    
ruijieAc80211aRateType  OBJECT-TYPE
    SYNTAX  INTEGER (1..3)
    MAX-ACCESS  read-write
    STATUS  current
    DESCRIPTION
            "The rate type:
            1--disable
            2--mandatory
            3--support"
    ::= { ruijieAc80211aRateEntry 2}

-- The Ac's 802.11b rate set
ruijieAc80211bRateTable OBJECT-TYPE
    SYNTAX  SEQUENCE OF RuijieAc80211bRateEntry
    MAX-ACCESS  not-accessible
    STATUS  current
    DESCRIPTION
            "The 802.11b rate attributes."
    ::= { ruijieAcMgmtAc 13 }

ruijieAc80211bRateEntry OBJECT-TYPE
    SYNTAX  RuijieAc80211bRateEntry
    MAX-ACCESS  not-accessible
    STATUS  current
    DESCRIPTION
        "Get and set the Ap attribtues."
    INDEX   { ruijieAc80211bRate }
    ::= { ruijieAc80211bRateTable 1 }

RuijieAc80211bRateEntry ::=
    SEQUENCE {
        ruijieAc80211bRate     INTEGER,
        ruijieAc80211bRateType INTEGER
    }

ruijieAc80211bRate  OBJECT-TYPE
    SYNTAX  INTEGER (1..3)
    MAX-ACCESS  not-accessible
    STATUS  current
    DESCRIPTION
            "The global 802.11b rate set in this AC.
            802.11b-1, 2, 5.5, 11Mbps.
            set 1 for 1Mbps, set 2 for 2Mbps, set 3 for 5.5Mbps,etc..."
    ::= { ruijieAc80211bRateEntry 1}
    
ruijieAc80211bRateType  OBJECT-TYPE
    SYNTAX  INTEGER (1..3)
    MAX-ACCESS  read-write
    STATUS  current
    DESCRIPTION
            "The rate type:
            1--disable
            2--mandatory
            3--support"
    ::= { ruijieAc80211bRateEntry 2}

ruijieAcFallback  OBJECT-TYPE
    SYNTAX  INTEGER (1..2)
    MAX-ACCESS  read-write
    STATUS  current
    DESCRIPTION
            "The fallback state:
            1--enable, 2--disable"
    ::= { ruijieAcMgmtAc 14}
    
ruijieAcStaNum  OBJECT-TYPE
    SYNTAX  INTEGER (1..24000)
    MAX-ACCESS  read-only
    STATUS  current
    DESCRIPTION
            "The client num in this AC."
    ::= { ruijieAcMgmtAc 15}
    
ruijieAcMacAddr  OBJECT-TYPE
    SYNTAX  MacAddress
    MAX-ACCESS  read-only
    STATUS  current
    DESCRIPTION
            "The AC's mac address."
    ::= { ruijieAcMgmtAc 16}

ruijieAcDescriptor  OBJECT-TYPE
    SYNTAX  DisplayString (SIZE (1..255))
    MAX-ACCESS  read-only
    STATUS  current
    DESCRIPTION
            "The AC's descriptor."
    ::= { ruijieAcMgmtAc 17}
    
ruijieAcPID  OBJECT-TYPE
    SYNTAX  DisplayString (SIZE (1..255))
    MAX-ACCESS  read-only
    STATUS  current
    DESCRIPTION
            "The AC's product id."
    ::= { ruijieAcMgmtAc 18}
    
ruijieAcHwId  OBJECT-TYPE
    SYNTAX  DisplayString (SIZE (1..255))
    MAX-ACCESS  read-only
    STATUS  current
    DESCRIPTION
            "The AC's Hardware Id."
    ::= { ruijieAcMgmtAc 19}
    
ruijieAcSN  OBJECT-TYPE
    SYNTAX  DisplayString (SIZE (1..255))
    MAX-ACCESS  read-only
    STATUS  current
    DESCRIPTION
            "The AC's serial number."
    ::= { ruijieAcMgmtAc 20}
 
ruijieAcTemp  OBJECT-TYPE
    SYNTAX  INTEGER
    MAX-ACCESS  read-only
    STATUS  current
    DESCRIPTION
            "The AC's temperature."
    ::= { ruijieAcMgmtAc 21}

ruijieAcAPUpDownCtrl  OBJECT-TYPE
    SYNTAX  INTEGER (0..1)
    MAX-ACCESS  read-write
    STATUS  current
    DESCRIPTION
            "The AP Up/Down trap control
                0 - off
                1 - on."
    ::= { ruijieAcMgmtAc 22}
    
ruijieAcAPJoinFailCtrl  OBJECT-TYPE
    SYNTAX  INTEGER (0..1)
    MAX-ACCESS  read-write
    STATUS  current
    DESCRIPTION
            "The AP join fail control
                0 - off
                1 - on."
    ::= { ruijieAcMgmtAc 23}
    
ruijieAcAPDecryEroReportCtrl  OBJECT-TYPE
    SYNTAX  INTEGER (0..1)
    MAX-ACCESS  read-write
    STATUS  current
    DESCRIPTION
            "The AP Decry Error Report control
                0 - off
                1 - on."
    ::= { ruijieAcMgmtAc 24}
    
ruijieAcApImageUpdtCtrl  OBJECT-TYPE
    SYNTAX  INTEGER (0..1)
    MAX-ACCESS  read-write
    STATUS  current
    DESCRIPTION
            "The AP Image Update Control
                0 - off
                1 - on."
    ::= { ruijieAcMgmtAc 25}
    
ruijieAcApConfigMsgEroCtrl  OBJECT-TYPE
    SYNTAX  INTEGER
    MAX-ACCESS  read-write
    STATUS  current
    DESCRIPTION
            "The AP Config Message Error
                0 - off
                1 - on."
    ::= { ruijieAcMgmtAc 26}
    
ruijieAcApRadioOperStatuCtrl  OBJECT-TYPE
    SYNTAX  INTEGER
    MAX-ACCESS  read-write
    STATUS  current
    DESCRIPTION
            "The AP Radio Oper Status
                0 - off
                1 - on."
    ::= { ruijieAcMgmtAc 27}
    
ruijieAcApAuthenFailCtrl  OBJECT-TYPE
    SYNTAX  INTEGER
    MAX-ACCESS  read-write
    STATUS  current
    DESCRIPTION
            "The AP Authen Fail trap control
                0 - off
                1 - on."
    ::= { ruijieAcMgmtAc 28}
    
ruijieAcApTimestampCtrl  OBJECT-TYPE
    SYNTAX  INTEGER
    MAX-ACCESS  read-write
    STATUS  current
    DESCRIPTION
            "The AP timestamp trap control
                0 - off
                1 - on."
    ::= { ruijieAcMgmtAc 29}
    
ruijieAcStaOperCtrl  OBJECT-TYPE
    SYNTAX  INTEGER
    MAX-ACCESS  read-write
    STATUS  current
    DESCRIPTION
            "The Sta operation trap control
                0 - off
                1 - on."
    ::= { ruijieAcMgmtAc 30}
    
ruijieAcType  OBJECT-TYPE
    SYNTAX  INTEGER {
        ws5302(1),
        ws5708(2),
        m8600ws(3),
        ws3302(4),
        m12000ws(5),
        ws5504(6),
        ws6108(7),
        ws6816(8),
        m18000-WS-ED(9),
        m8600E-WS-ED(10),
        eg2000(11),
        ws6008(12),
        ws6812(13),
        aw608(14),
        ws6024(15),
        eg350(16)
    }
    MAX-ACCESS  read-only
    STATUS  current
    DESCRIPTION
            "The Ac type."
    ::= { ruijieAcMgmtAc 31}
    
ruijieAcNeid  OBJECT-TYPE
    SYNTAX  DisplayString (SIZE (1..255))
    MAX-ACCESS  read-write
    STATUS  current
    DESCRIPTION
            "The Ac system net id."
    ::= { ruijieAcMgmtAc 32}
    
ruijieAcManufacturer  OBJECT-TYPE
    SYNTAX  DisplayString (SIZE (1..255))
    MAX-ACCESS  read-only
    STATUS  current
    DESCRIPTION
            "The Ac's Manufacturer."
    ::= { ruijieAcMgmtAc 33}

ruijieAcSwVer  OBJECT-TYPE
    SYNTAX  DisplayString (SIZE (1..255))
    MAX-ACCESS  read-only
    STATUS  current
    DESCRIPTION
            "The Ac's software version."
    ::= { ruijieAcMgmtAc 34}
    
ruijieAcSwManufacturer  OBJECT-TYPE
    SYNTAX  DisplayString (SIZE (1..255))
    MAX-ACCESS  read-only
    STATUS  current
    DESCRIPTION
            "The Ac's software Manufacturer."
    ::= { ruijieAcMgmtAc 35}
    
ruijieAcStaResourceNotEnough  OBJECT-TYPE
    SYNTAX  INTEGER
    MAX-ACCESS  read-only
    STATUS  current
    DESCRIPTION
            "The sta number which can not attach to 
             this system for not enough resource."
    ::= { ruijieAcMgmtAc 36}
    
ruijieAcPppoeClientAct  OBJECT-TYPE
    SYNTAX  INTEGER
    MAX-ACCESS  read-only
    STATUS  current
    DESCRIPTION
            "The active client number in this AC."
    ::= { ruijieAcMgmtAc 37}
    
ruijieAcPppoeClientMax  OBJECT-TYPE
    SYNTAX  INTEGER
    MAX-ACCESS  read-only
    STATUS  current
    DESCRIPTION
            "The client number which this AC support."
    ::= { ruijieAcMgmtAc 38}

ruijieAcStaActThredhold  OBJECT-TYPE
    SYNTAX  INTEGER
    MAX-ACCESS  read-write
    STATUS  current
    DESCRIPTION
            "The thredhold which the client attach to this AC in one hour."
    ::= { ruijieAcMgmtAc 39}
    
ruijieAcStaDisactThredhold  OBJECT-TYPE
    SYNTAX  INTEGER
    MAX-ACCESS  read-write
    STATUS  current
    DESCRIPTION
            "The thredhold which the client leave this AC in one hour."
    ::= { ruijieAcMgmtAc 40}
    
ruijieAcStaTotalRoamThredhold  OBJECT-TYPE
    SYNTAX  INTEGER
    MAX-ACCESS  read-only
    STATUS  current
    DESCRIPTION
            "The thredhold which the client's total roaming times."
    ::= { ruijieAcMgmtAc 41}
    
ruijieAcStaPerRoamThredhold  OBJECT-TYPE
    SYNTAX  INTEGER
    MAX-ACCESS  read-only
    STATUS  current
    DESCRIPTION
            "The thredhold which the client's roaming times per minite."
    ::= { ruijieAcMgmtAc 42}
    
-- [no] sta-off-line-remain-time number
ruijieAcStaOffLineRemainTime  OBJECT-TYPE
    SYNTAX  INTEGER(0..365)
    MAX-ACCESS  read-write
    STATUS  current
    DESCRIPTION
            "This object presents the time which the off line STA statistic remain in the AC."
    ::= { ruijieAcMgmtAc 43}

-- [no] sta-off-line-number number
ruijieAcStaOffLineNumber  OBJECT-TYPE
    SYNTAX  INTEGER(0..5000)
    MAX-ACCESS  read-write
    STATUS  current
    DESCRIPTION
            "This object presents the max number of the off line STA number statistic."
    ::= { ruijieAcMgmtAc 44}

-- sta-off-line-del mac-addr 
ruijieAcStaOffLineDelSingle  OBJECT-TYPE
    SYNTAX  MacAddress
    MAX-ACCESS  read-write
    STATUS  current
    DESCRIPTION
            "This object presents the mac address which the off line STA to remove its statistic."
    ::= { ruijieAcMgmtAc 45}

-- sta-off-line-del all
ruijieAcStaOffLineDelAll  OBJECT-TYPE
    SYNTAX  INTEGER(1..1)
    MAX-ACCESS  read-write
    STATUS  current
    DESCRIPTION
            "This object is set to clear all of the off line STA's statistic."
    ::= { ruijieAcMgmtAc 46}

-- no ap-config ap-name
ruijieAcRmOffLineApConfig  OBJECT-TYPE
    SYNTAX  DisplayString (SIZE (1..65))
    MAX-ACCESS  read-write
    STATUS  current
    DESCRIPTION
            "This object is set to delete the off line AP's configuration."
    ::= { ruijieAcMgmtAc 47}
    
ruijieAcFlowBlGroupTable OBJECT-TYPE
    SYNTAX  SEQUENCE OF RuijieAcFlowBlGroupEntry
    MAX-ACCESS  not-accessible
    STATUS  current
    DESCRIPTION
            "The flow balance group table"
    ::= { ruijieAcMgmtAc 48 }
	
ruijieAcFlowBlGroupEntry OBJECT-TYPE
    SYNTAX  RuijieAcFlowBlGroupEntry
    MAX-ACCESS  not-accessible
    STATUS  current
    DESCRIPTION
        "Get and set the flow balance group attribute."
    INDEX   { ruijieAcFlowBlGroupName }
    ::= { ruijieAcFlowBlGroupTable 1 }

RuijieAcFlowBlGroupEntry ::=
    SEQUENCE {
        ruijieAcFlowBlGroupName                DisplayString,
        ruijieAcFlowBlApName1                  DisplayString,
        ruijieAcFlowBlApName2                  DisplayString,
        ruijieAcFlowBlApName3                  DisplayString,
        ruijieAcFlowBlApName4                  DisplayString,
        ruijieAcFlowBlApName5                  DisplayString,
        ruijieAcFlowBlApName6                  DisplayString,
        ruijieAcFlowBlApName7                  DisplayString,
        ruijieAcFlowBlApName8                  DisplayString,
        ruijieAcFlowBlApName9                  DisplayString,
        ruijieAcFlowBlApName10                 DisplayString,
        ruijieAcFlowBlNum                      INTEGER,
        ruijieAcFlowBlRS                       RowStatus,
        ruijieAcFlowBlEnable                   INTEGER,
        ruijieAcFlowBlBase                     INTEGER,
        ruijieAcFlowBlIsEnable                 TruthValue
    }

ruijieAcFlowBlGroupName  OBJECT-TYPE
    SYNTAX  DisplayString
    MAX-ACCESS  read-only
    STATUS  current
    DESCRIPTION
            "The flow balance group's name."
    ::= { ruijieAcFlowBlGroupEntry 1}
    
ruijieAcFlowBlApName1  OBJECT-TYPE
    SYNTAX  DisplayString
    MAX-ACCESS  read-write
    STATUS  current
    DESCRIPTION
            "The AP name belong to this flow balance group."
    ::= { ruijieAcFlowBlGroupEntry 2}
    
ruijieAcFlowBlApName2  OBJECT-TYPE
    SYNTAX  DisplayString
    MAX-ACCESS  read-write
    STATUS  current
    DESCRIPTION
            "The AP name belong to this flow balance group."
    ::= { ruijieAcFlowBlGroupEntry 3}
    
ruijieAcFlowBlApName3  OBJECT-TYPE
    SYNTAX  DisplayString
    MAX-ACCESS  read-write
    STATUS  current
    DESCRIPTION
            "The AP name belong to this flow balance group."
    ::= { ruijieAcFlowBlGroupEntry 4}
    
ruijieAcFlowBlApName4  OBJECT-TYPE
    SYNTAX  DisplayString
    MAX-ACCESS  read-write
    STATUS  current
    DESCRIPTION
            "The AP name belong to this flow balance group."
    ::= { ruijieAcFlowBlGroupEntry 5}
    
ruijieAcFlowBlApName5  OBJECT-TYPE
    SYNTAX  DisplayString
    MAX-ACCESS  read-write
    STATUS  current
    DESCRIPTION
            "The AP name belong to this flow balance group."
    ::= { ruijieAcFlowBlGroupEntry 6}
    
ruijieAcFlowBlApName6  OBJECT-TYPE
    SYNTAX  DisplayString
    MAX-ACCESS  read-write
    STATUS  current
    DESCRIPTION
            "The AP name belong to this flow balance group."
    ::= { ruijieAcFlowBlGroupEntry 7}
    
ruijieAcFlowBlApName7  OBJECT-TYPE
    SYNTAX  DisplayString
    MAX-ACCESS  read-write
    STATUS  current
    DESCRIPTION
            "The AP name belong to this flow balance group."
    ::= { ruijieAcFlowBlGroupEntry 8}
    
ruijieAcFlowBlApName8  OBJECT-TYPE
    SYNTAX  DisplayString
    MAX-ACCESS  read-write
    STATUS  current
    DESCRIPTION
            "The AP name belong to this flow balance group."
    ::= { ruijieAcFlowBlGroupEntry 9}
    
ruijieAcFlowBlApName9  OBJECT-TYPE
    SYNTAX  DisplayString
    MAX-ACCESS  read-write
    STATUS  current
    DESCRIPTION
            "The AP name belong to this flow balance group."
    ::= { ruijieAcFlowBlGroupEntry 10}
    
ruijieAcFlowBlApName10  OBJECT-TYPE
    SYNTAX  DisplayString
    MAX-ACCESS  read-write
    STATUS  current
    DESCRIPTION
            "The AP name belong to this flow balance group."
    ::= { ruijieAcFlowBlGroupEntry 11}
    
ruijieAcFlowBlNum  OBJECT-TYPE
    SYNTAX  INTEGER(0..1000)
    MAX-ACCESS  read-write
    STATUS  current
    DESCRIPTION
            "The flow balance group's flow throshold."
    ::= { ruijieAcFlowBlGroupEntry 12}
        
ruijieAcFlowBlRS OBJECT-TYPE
    SYNTAX     RowStatus 
    MAX-ACCESS read-write
    STATUS     current
    DESCRIPTION
         "Used to add or del or modify the flow balance table."
    ::= { ruijieAcFlowBlGroupEntry 13 }

ruijieAcFlowBlEnable OBJECT-TYPE
    SYNTAX     INTEGER 
    MAX-ACCESS read-write
    STATUS     current
    DESCRIPTION
         "The flow balance group's flow enable throshold."
    ::= { ruijieAcFlowBlGroupEntry 14 }

ruijieAcFlowBlBase OBJECT-TYPE
    SYNTAX     INTEGER 
    MAX-ACCESS read-write
    STATUS     current
    DESCRIPTION
         "The flow balance group's flow base."
    ::= { ruijieAcFlowBlGroupEntry 15 }

ruijieAcFlowBlIsEnable  OBJECT-TYPE
    SYNTAX  TruthValue
    MAX-ACCESS  read-write
    STATUS  current
    DESCRIPTION
            "The flow balance group's enable/disable."
    ::= { ruijieAcFlowBlGroupEntry 16}

ruijieAcNumBlGroupTable OBJECT-TYPE
    SYNTAX  SEQUENCE OF RuijieAcNumBlGroupEntry
    MAX-ACCESS  not-accessible
    STATUS  current
    DESCRIPTION
            "The number balance group table"
    ::= { ruijieAcMgmtAc 49 }

ruijieAcNumBlGroupEntry OBJECT-TYPE
    SYNTAX  RuijieAcNumBlGroupEntry
    MAX-ACCESS  not-accessible
    STATUS  current
    DESCRIPTION
        "Get and set the number balance group attribute."
    INDEX   { ruijieAcNumBlGroupName }
    ::= { ruijieAcNumBlGroupTable 1 }

RuijieAcNumBlGroupEntry ::=
    SEQUENCE {
        ruijieAcNumBlGroupName                DisplayString,
        ruijieAcNumBlApName1                  DisplayString,
        ruijieAcNumBlApName2                  DisplayString,
        ruijieAcNumBlApName3                  DisplayString,
        ruijieAcNumBlApName4                  DisplayString,
        ruijieAcNumBlApName5                  DisplayString,
        ruijieAcNumBlApName6                  DisplayString,
        ruijieAcNumBlApName7                  DisplayString,
        ruijieAcNumBlApName8                  DisplayString,
        ruijieAcNumBlApName9                  DisplayString,
        ruijieAcNumBlApName10                 DisplayString,
        ruijieAcNumBlNum                      INTEGER,
        ruijieAcNumBlRS                       RowStatus,
        ruijieAcNumBlEnable                   INTEGER,
        ruijieAcNumBlIsEnable                 TruthValue
    }

ruijieAcNumBlGroupName  OBJECT-TYPE
    SYNTAX  DisplayString
    MAX-ACCESS  read-only
    STATUS  current
    DESCRIPTION
            "The number balance group's name."
    ::= { ruijieAcNumBlGroupEntry 1}
    
ruijieAcNumBlApName1  OBJECT-TYPE
    SYNTAX  DisplayString
    MAX-ACCESS  read-write
    STATUS  current
    DESCRIPTION
            "The AP name belong to this number balance group."
    ::= { ruijieAcNumBlGroupEntry 2}
    
ruijieAcNumBlApName2  OBJECT-TYPE
    SYNTAX  DisplayString
    MAX-ACCESS  read-write
    STATUS  current
    DESCRIPTION
            "The AP name belong to this number balance group."
    ::= { ruijieAcNumBlGroupEntry 3}
    
ruijieAcNumBlApName3  OBJECT-TYPE
    SYNTAX  DisplayString
    MAX-ACCESS  read-write
    STATUS  current
    DESCRIPTION
            "The AP name belong to this number balance group."
    ::= { ruijieAcNumBlGroupEntry 4}
    
ruijieAcNumBlApName4  OBJECT-TYPE
    SYNTAX  DisplayString
    MAX-ACCESS  read-write
    STATUS  current
    DESCRIPTION
            "The AP name belong to this number balance group."
    ::= { ruijieAcNumBlGroupEntry 5}
    
ruijieAcNumBlApName5  OBJECT-TYPE
    SYNTAX  DisplayString
    MAX-ACCESS  read-write
    STATUS  current
    DESCRIPTION
            "The AP name belong to this number balance group."
    ::= { ruijieAcNumBlGroupEntry 6}
    
ruijieAcNumBlApName6  OBJECT-TYPE
    SYNTAX  DisplayString
    MAX-ACCESS  read-write
    STATUS  current
    DESCRIPTION
            "The AP name belong to this number balance group."
    ::= { ruijieAcNumBlGroupEntry 7}
    
ruijieAcNumBlApName7  OBJECT-TYPE
    SYNTAX  DisplayString
    MAX-ACCESS  read-write
    STATUS  current
    DESCRIPTION
            "The AP name belong to this number balance group."
    ::= { ruijieAcNumBlGroupEntry 8}
    
ruijieAcNumBlApName8  OBJECT-TYPE
    SYNTAX  DisplayString
    MAX-ACCESS  read-write
    STATUS  current
    DESCRIPTION
            "The AP name belong to this number balance group."
    ::= { ruijieAcNumBlGroupEntry 9}
    
ruijieAcNumBlApName9  OBJECT-TYPE
    SYNTAX  DisplayString
    MAX-ACCESS  read-write
    STATUS  current
    DESCRIPTION
            "The AP name belong to this number balance group."
    ::= { ruijieAcNumBlGroupEntry 10}
    
ruijieAcNumBlApName10  OBJECT-TYPE
    SYNTAX  DisplayString
    MAX-ACCESS  read-write
    STATUS  current
    DESCRIPTION
            "The AP name belong to this number balance group."
    ::= { ruijieAcNumBlGroupEntry 11}
    
ruijieAcNumBlNum  OBJECT-TYPE
    SYNTAX  INTEGER(0..1000)
    MAX-ACCESS  read-write
    STATUS  current
    DESCRIPTION
            "The number balance group's number throshold."
    ::= { ruijieAcNumBlGroupEntry 12}
        
ruijieAcNumBlRS OBJECT-TYPE
    SYNTAX     RowStatus 
    MAX-ACCESS read-write
    STATUS     current
    DESCRIPTION
         "Used to add or del or modify the number balance table."
    ::= { ruijieAcNumBlGroupEntry 13 }

ruijieAcNumBlEnable  OBJECT-TYPE
    SYNTAX  INTEGER
    MAX-ACCESS  read-write
    STATUS  current
    DESCRIPTION
            "The number balance group's number enable throshold."
    ::= { ruijieAcNumBlGroupEntry 14}

ruijieAcNumBlIsEnable  OBJECT-TYPE
    SYNTAX  TruthValue
    MAX-ACCESS  read-write
    STATUS  current
    DESCRIPTION
            "The number balance group's enable/disable."
    ::= { ruijieAcNumBlGroupEntry 15}

ruijieAcInAcRoamNum  OBJECT-TYPE
    SYNTAX  INTEGER
    MAX-ACCESS  read-only
    STATUS  current
    DESCRIPTION
            "The Sta roaming in this AC."
    ::= { ruijieAcMgmtAc 50}
    
ruijieAcBetweenAcRoamInNum  OBJECT-TYPE
    SYNTAX  INTEGER
    MAX-ACCESS  read-only
    STATUS  current
    DESCRIPTION
            "The Sta roaming in timers while roaming between ACs."
    ::= { ruijieAcMgmtAc 51}
    
ruijieAcStaOnOverThrodOperCtrl  OBJECT-TYPE
    SYNTAX  INTEGER
    MAX-ACCESS  read-write
    STATUS  current
    DESCRIPTION
            "The Sta on times over thredhold trap control
                0 - off
                1 - on."
    ::= { ruijieAcMgmtAc 52}
    
ruijieAcStaOffOverThrodOperCtrl  OBJECT-TYPE
    SYNTAX  INTEGER
    MAX-ACCESS  read-write
    STATUS  current
    DESCRIPTION
            "The Sta off times over thredhold trap control
                0 - off
                1 - on."
    ::= { ruijieAcMgmtAc 53}
    
ruijieAcBetweenAcRoamOutNum OBJECT-TYPE
    SYNTAX  INTEGER
    MAX-ACCESS  read-only
    STATUS  current
    DESCRIPTION
            "The Sta roaming out timers while roaming between ACs."
    ::= { ruijieAcMgmtAc 54}
    
ruijieAcCpusageSwitch  OBJECT-TYPE
    SYNTAX  INTEGER
    MAX-ACCESS  read-write
    STATUS  current
    DESCRIPTION
            "This object presents the ruijieApCpuUsageTrapTimer node active or not.
             1 -- on
             2 -- off"
    ::= { ruijieAcMgmtAc 55 }
    
ruijieAcCpuUsageTrapTimer OBJECT-TYPE
    SYNTAX      INTEGER
    MAX-ACCESS  read-write
    STATUS      current
    DESCRIPTION
            "This object represents the AP's cpu usage info trap timer, 
             second. Set to all APs."
    ::= { ruijieAcMgmtAc 56 }
    
ruijieAcStatTrapTimer  OBJECT-TYPE
    SYNTAX  INTEGER
    MAX-ACCESS  read-write
    STATUS  current
    DESCRIPTION
            "This object present the AP's radio statistic
             trap timer, second. Set to all APs."
    ::= { ruijieAcMgmtAc 57}
    
ruijieAcHeartBeat  OBJECT-TYPE
    SYNTAX  INTEGER
    MAX-ACCESS  read-write
    STATUS  current
    DESCRIPTION
            "The heart beat between AC and AP，should not greater than 75s，second.
             Set 0 to turn off this function."
    ::= { ruijieAcMgmtAc 58}

ruijieAcTotalApSupNum  OBJECT-TYPE
    SYNTAX  INTEGER
    MAX-ACCESS  read-only
    STATUS  current
    DESCRIPTION
            "This object present the ACs' max num of supported APs."
    ::= { ruijieAcMgmtAc 59}

ruijieAcTotalStaSupNum  OBJECT-TYPE
    SYNTAX  INTEGER
    MAX-ACCESS  read-only
    STATUS  current
    DESCRIPTION
            "This object present the ACs' max num of supported STAs."
    ::= { ruijieAcMgmtAc 60}

ruijieAcTotalPppoeSupNum  OBJECT-TYPE
    SYNTAX  INTEGER
    MAX-ACCESS  read-only
    STATUS  current
    DESCRIPTION
            "This object present the ACs' maximum number of pppoe authentication."
    ::= { ruijieAcMgmtAc 61}
    
ruijieAcCurTotalApSupNum  OBJECT-TYPE
    SYNTAX  INTEGER
    MAX-ACCESS  read-only
    STATUS  current
    DESCRIPTION
            "This object present the current ACs' max num of supported STAs."
    ::= { ruijieAcMgmtAc 62}

ruijieAcCurTotalStaSupNum  OBJECT-TYPE
    SYNTAX  INTEGER
    MAX-ACCESS  read-only
    STATUS  current
    DESCRIPTION
            "This object present the current ACs' max num of supported STAs."
    ::= { ruijieAcMgmtAc 63}

ruijieAcCurTotalPppoeSupNum  OBJECT-TYPE
    SYNTAX  INTEGER
    MAX-ACCESS  read-only
    STATUS  current
    DESCRIPTION
            "This object present the current the ACs' maximum number of pppoe authentication."
    ::= { ruijieAcMgmtAc 64}

ruijieAcNasId  OBJECT-TYPE
    SYNTAX      DisplayString
    MAX-ACCESS  read-write
    STATUS      current
    DESCRIPTION
            "The NAS ID about this AC."
    ::= { ruijieAcMgmtAc 65}

ruijieAcStaLimitLicense OBJECT-TYPE
    SYNTAX  INTEGER
    MAX-ACCESS  read-only
    STATUS  current
    DESCRIPTION
            "The max station this AC supports by license."
    ::= { ruijieAcMgmtAc 66 }

ruijieAcWtpLimitLicense OBJECT-TYPE
    SYNTAX  INTEGER
    MAX-ACCESS  read-only
    STATUS  current
    DESCRIPTION
            "The max wtp this AC supports by license."
    ::= { ruijieAcMgmtAc 67 }

ruijieAcStaIpv6Num  OBJECT-TYPE
    SYNTAX  INTEGER (1..24000)
    MAX-ACCESS  read-only
    STATUS  current
    DESCRIPTION
            "The ipv6 client num in this AC."
    ::= { ruijieAcMgmtAc 68}

ruijieAcIpv6  OBJECT-TYPE
    SYNTAX      DisplayString
    MAX-ACCESS  read-only
    STATUS      current
    DESCRIPTION
            "AC's ipv6 address."
    ::= { ruijieAcMgmtAc 69}

ruijieAcIpv6Prefix  OBJECT-TYPE
    SYNTAX      DisplayString
    MAX-ACCESS  read-only
    STATUS      current
    DESCRIPTION
            "AC's ipv6 address prefix."
    ::= { ruijieAcMgmtAc 70}

ruijieAcIpv6Type  OBJECT-TYPE
    SYNTAX  INTEGER {
        unknown(0),
        unicase(1),
        anycase(2),
        multicase(3)
    }
    MAX-ACCESS  read-only
    STATUS      current
    DESCRIPTION
            "AC's ipv6 address type."
    ::= { ruijieAcMgmtAc 71}

ruijieAcIpv6AddrType  OBJECT-TYPE
    SYNTAX      DisplayString
    MAX-ACCESS  read-only
    STATUS      current
    DESCRIPTION
            "AC's anycast address type."
    ::= { ruijieAcMgmtAc 72}
    
ruijieAcKickClient  OBJECT-TYPE
    SYNTAX  MacAddress
    MAX-ACCESS  read-write
    STATUS  current
    DESCRIPTION
            "Set the mac and corresponding client will be kicked. Get this object will return last kicked client."
    ::= { ruijieAcMgmtAc 73}
    
ruijieAcOpenStaNum  OBJECT-TYPE
    SYNTAX  INTEGER
    MAX-ACCESS  read-only
    STATUS  current
    DESCRIPTION
            "Open client num in this AC."
    ::= { ruijieAcMgmtAc 74}

ruijieAcOpenStaAbnormalDownTimes  OBJECT-TYPE
    SYNTAX  INTEGER
    MAX-ACCESS  read-only
    STATUS  current
    DESCRIPTION
            "The times open client is abnormaly offline."
    ::= { ruijieAcMgmtAc 75} 

ruijieAcWepPskStaNum  OBJECT-TYPE
    SYNTAX  INTEGER
    MAX-ACCESS  read-only
    STATUS  current
    DESCRIPTION
            "WEP/PSK client num in this AC."
    ::= { ruijieAcMgmtAc 76}

ruijieAcWepPskStaAbnormalDownTimes  OBJECT-TYPE
    SYNTAX  INTEGER
    MAX-ACCESS  read-only
    STATUS  current
    DESCRIPTION
            "The times WEP/PSK client is abnormaly offline."
    ::= { ruijieAcMgmtAc 77} 
    
ruijieAcPriorStaTable OBJECT-TYPE
    SYNTAX  SEQUENCE OF RuijieAcPriorStaEntry
    MAX-ACCESS  not-accessible
    STATUS  current
    DESCRIPTION
            "The prior sta table"
    ::= { ruijieAcMgmtAc 78 }

ruijieAcMicroAPUpDownCtrl  OBJECT-TYPE
    SYNTAX  INTEGER (0..1)
    MAX-ACCESS  read-write
    STATUS  current
    DESCRIPTION
            "The Micro AP Up/Down trap control
                0 - off
                1 - on."
    ::= { ruijieAcMgmtAc 79}
ruijieAcPriorStaEntry OBJECT-TYPE
    SYNTAX  RuijieAcPriorStaEntry
    MAX-ACCESS  not-accessible
    STATUS  current
    DESCRIPTION
        "Get and set prior sta mac."
    INDEX   { ruijieAcPriorStaMac }
    ::= { ruijieAcPriorStaTable 1 }

RuijieAcPriorStaEntry ::=
    SEQUENCE {
        ruijieAcPriorStaMac                MacAddress,
        ruijieAcPriorStaRowStatus          RowStatus
    }
    
ruijieAcPriorStaMac  OBJECT-TYPE
    SYNTAX  MacAddress
    MAX-ACCESS  read-write
    STATUS  current
    DESCRIPTION
            "The prior sta mac."
    ::= { ruijieAcPriorStaEntry 1}
    
ruijieAcPriorStaRowStatus OBJECT-TYPE
    SYNTAX     RowStatus 
    MAX-ACCESS read-write
    STATUS     current
    DESCRIPTION
         "Used to add or del prior sta."
    ::= { ruijieAcPriorStaEntry 2}

ruijieAcOfflineApNum OBJECT-TYPE
    SYNTAX  INTEGER
    MAX-ACCESS  read-only
    STATUS  current
    DESCRIPTION
            "Offline ap num in this ac."
    ::= { ruijieAcMgmtAc 80 }

ruijieAcTotalApNum OBJECT-TYPE
    SYNTAX  INTEGER
    MAX-ACCESS  read-only
    STATUS  current
    DESCRIPTION
            "Total ap num in this ac."
    ::= { ruijieAcMgmtAc 81 }

--********************************************************************
--                                                                  **
--                  AP nodes                                        **
--                                                                  **
--********************************************************************
ruijieApCfgTable OBJECT-TYPE
    SYNTAX  SEQUENCE OF RuijieApCfgEntry
    MAX-ACCESS  not-accessible
    STATUS  current
    DESCRIPTION
            "The Ap attributes."
    ::= { ruijieAcMgmtAp 1 }

ruijieApCfgEntry OBJECT-TYPE
    SYNTAX  RuijieApCfgEntry
    MAX-ACCESS  not-accessible
    STATUS  current
    DESCRIPTION
        "Get and set the Ap attribtues."
    INDEX   { ruijieApMacAddr }
    ::= { ruijieApCfgTable 1 }

RuijieApCfgEntry ::=
    SEQUENCE {
        ruijieApMacAddr                 MacAddress,
        ruijieApApName                  DisplayString,
        ruijieApApgName                 DisplayString,
        ruijieApDiscTimer               INTEGER,
        ruijieApEchoReqTimer            INTEGER,
        ruijieApEroReportTimer          INTEGER,
        ruijieApStaTimeoutTimer         INTEGER,
        ruijieApStatisticsTimer         INTEGER,
        ruijieApFallback                INTEGER,
        ruijieApImageId                 DisplayString,
        ruijieApIpDhcp                  INTEGER,
        ruijieApLocation                DisplayString,
        ruijieApWpsMfp                  INTEGER,
        ruijieApLastRebootReason        INTEGER,
        ruijieApEthernetIfName          DisplayString,
        ruijieApEthernetIfMacAddress    MacAddress,
        ruijieApEthernetIfAdminStatus   INTEGER,
        ruijieApEthernetIfOperStatus    INTEGER,
        ruijieApEthernetIfRxUcastPkts   Counter32,
        ruijieApEthernetIfRxNUcastPkts  Counter32,
        ruijieApEthernetIfTxUcastPkts   Counter32,
        ruijieApEthernetIfTxNUcastPkts  Counter32,
        ruijieApEthernetIfDuplex        INTEGER,
        ruijieApEthernetIfLinkSpeed     INTEGER,
        ruijieApEthernetIfPOEPower      INTEGER,
        ruijieApEthernetIfRxBoardPkts   Counter32,
        ruijieApEthernetIfRxMultiPkts   Counter32,
        ruijieApEthernetIfTxBoardPkts   Counter32,
        ruijieApEthernetIfTxMultiPkts   Counter32,
        ruijieApEthernetIfDropPkts      Counter32,
        ruijieApAdminStatus             INTEGER,
        ruijieApSn                      DisplayString,
        ruijieApIp                      IpAddress,
        ruijieApStaNum                  INTEGER,
        ruijieApToFat                   INTEGER,
        ruijieApId                      INTEGER,
        ruijieApSwVer                   DisplayString,
        ruijieApBootVer                 DisplayString,
        ruijieApPID                     DisplayString,
        ruijieApHwVer                   DisplayString,
        ruijieApStaLimit                INTEGER,
        ruijieApFactoryDefault          INTEGER,
        ruijieApCpuUsageTrapTimer       INTEGER,
        ruijieApStatTrapTimer           INTEGER,
        ruijieApLinkOnTimeInterval      INTEGER,
        ruijieApNetId                   DisplayString,
        ruijieApUptime                  DisplayString,
        ruijieApState                   INTEGER,
        ruijieApNasId                   DisplayString,
        ruijieApCoverArea               INTEGER,
        ruijieApLinkOnTimeIntervalMs    TimeTicks,
        ruijieApUptimeMs                TimeTicks,
        ruijieApHbUptimeMs              TimeTicks,
        ruijieApIpv6                    InetAddress,
        ruijieApIpv6Prefix              DisplayString,
        ruijieApIpv6PrefixLen           INTEGER,
        ruijieApIpv6Type                INTEGER,
        ruijieApIpv6Gateway             DisplayString,
        ruijieApIpv6StaNum              INTEGER,
        ruijieApMacAddrColon            DisplayString,
        ruijieApMacAddrLine             DisplayString,
        ruijieApMacAddrDot              DisplayString
    }

ruijieApMacAddr  OBJECT-TYPE
    SYNTAX  MacAddress
    MAX-ACCESS  read-only
    STATUS  current
    DESCRIPTION
            "The AP's ethernet mac address."
    ::= { ruijieApCfgEntry 1}

-- The AP Name
ruijieApApName  OBJECT-TYPE
    SYNTAX  DisplayString (SIZE (1..64))
    MAX-ACCESS  read-write
    STATUS  current
    DESCRIPTION
            "Ap's Name."
    ::= { ruijieApCfgEntry 2}

-- The Ap group name
ruijieApApgName  OBJECT-TYPE
    SYNTAX  DisplayString (SIZE (1..255))
    MAX-ACCESS  read-write
    STATUS  current
    DESCRIPTION
            "Ap group Name."
    ::= { ruijieApCfgEntry 3 }

-- The Discovery timer
ruijieApDiscTimer  OBJECT-TYPE
    SYNTAX  INTEGER (2..180)
    MAX-ACCESS  read-write
    STATUS  current
    DESCRIPTION
            "Discovery timer."
    ::= { ruijieApCfgEntry 4 }

-- The Echo Request timer
ruijieApEchoReqTimer  OBJECT-TYPE
    SYNTAX  INTEGER (5..255)
    MAX-ACCESS  read-write
    STATUS  current
    DESCRIPTION
            "Echo Request timer."
    ::= { ruijieApCfgEntry 5 }

-- The Error Report timer
ruijieApEroReportTimer  OBJECT-TYPE
    SYNTAX  INTEGER (1..1080)
    MAX-ACCESS  read-write
    STATUS  current
    DESCRIPTION
            "Error Report timer."
    ::= { ruijieApCfgEntry 6 }

-- The Sta timeout timer
ruijieApStaTimeoutTimer  OBJECT-TYPE
    SYNTAX  INTEGER (1..2700)
    MAX-ACCESS  read-write
    STATUS  current
    DESCRIPTION
            "station idle timeout timer."
    ::= { ruijieApCfgEntry 7 }

-- The Statistics timeout timer
ruijieApStatisticsTimer  OBJECT-TYPE
    SYNTAX  INTEGER (1..65535)
    MAX-ACCESS  read-write
    STATUS  current
    DESCRIPTION
            "station idle timeout timer."
    ::= { ruijieApCfgEntry 8 }

-- The fallback value, 1-enable, 2-disable
ruijieApFallback  OBJECT-TYPE
    SYNTAX  INTEGER (1..2)
    MAX-ACCESS  read-write
    STATUS  current
    DESCRIPTION
            "The fallback value, 1--enable, 2--disable."
    ::= { ruijieApCfgEntry 9 }

-- The Image id
ruijieApImageId  OBJECT-TYPE
    SYNTAX  DisplayString (SIZE (1..128))
    MAX-ACCESS  read-write
    STATUS  current
    DESCRIPTION
            "The Image version."
    ::= { ruijieApCfgEntry 10 }

-- The ip dhcp option value, 0-standard, 1-private
ruijieApIpDhcp  OBJECT-TYPE
    SYNTAX  INTEGER (0..1)
    MAX-ACCESS  read-write
    STATUS  current
    DESCRIPTION
            "The ip dhcp option value, 0--standard, 1--private."
    ::= { ruijieApCfgEntry 11 }

-- The ap location
ruijieApLocation  OBJECT-TYPE
    SYNTAX  DisplayString (SIZE(1..255))
    MAX-ACCESS  read-write
    STATUS  current
    DESCRIPTION
            "Ap Location."
    ::= { ruijieApCfgEntry 12}

-- 0-disable, 1-enable
ruijieApWpsMfp  OBJECT-TYPE
    SYNTAX  INTEGER (0..1)
    MAX-ACCESS  read-write
    STATUS  current
    DESCRIPTION
            "0-disable, 1-enable."
    ::= { ruijieApCfgEntry 13}

ruijieApLastRebootReason  OBJECT-TYPE
    SYNTAX  INTEGER {
                notSupport(0),
                acInit(1),
                linkFail(2),
                sWFail(3),
                hWFail(4),
                otherFail(5),
                unknown(255)
            }
    MAX-ACCESS  read-only
    STATUS  current
    DESCRIPTION
            "The AP's last reboot reason."
    ::= { ruijieApCfgEntry 14}

ruijieApEthernetIfName OBJECT-TYPE
    SYNTAX DisplayString (SIZE(1..32))
    MAX-ACCESS read-only
    STATUS current
    DESCRIPTION
            "This object represents the name of the Ethernet interface."
    ::= { ruijieApCfgEntry 15 }

ruijieApEthernetIfMacAddress OBJECT-TYPE
    SYNTAX     MacAddress
    MAX-ACCESS read-only
    STATUS     current
    DESCRIPTION
            "This object represents MAC address of the Ethernet interface
             in the slot represented by ruijieApEthernetIfSlotId."
    ::= { ruijieApCfgEntry 16 }

ruijieApEthernetIfAdminStatus OBJECT-TYPE
    SYNTAX      INTEGER
    MAX-ACCESS read-only
    STATUS     current
    DESCRIPTION
            "This object represents the admin state of the physical
             Ethernet interface on the AP."
    ::= { ruijieApCfgEntry 17 }

ruijieApEthernetIfOperStatus OBJECT-TYPE
    SYNTAX      INTEGER
    MAX-ACCESS read-only
    STATUS     current
    DESCRIPTION
            "This object represents the operational state of the physical
             Ethernet interface on the AP."
    ::= { ruijieApCfgEntry 18 }

ruijieApEthernetIfRxUcastPkts OBJECT-TYPE
    SYNTAX     Counter32
    UNITS      "packets"
    MAX-ACCESS read-only
    STATUS     current
    DESCRIPTION
            "This object represents total number of unicast packets 
            received on the interface."
    ::= { ruijieApCfgEntry 19 }

ruijieApEthernetIfRxNUcastPkts OBJECT-TYPE
    SYNTAX      Counter32
    UNITS       "packets"
    MAX-ACCESS  read-only
    STATUS      current
    DESCRIPTION
            "This object represents total number of non-unicast or
            mulitcast packets received on the interface"
    ::= { ruijieApCfgEntry 20 }

ruijieApEthernetIfTxUcastPkts OBJECT-TYPE
    SYNTAX     Counter32
    UNITS      "packets"
    MAX-ACCESS read-only
    STATUS     current
    DESCRIPTION
            "This object represents total number of unicast packets 
            transmitted on the interface."
    ::= { ruijieApCfgEntry 21 }

ruijieApEthernetIfTxNUcastPkts OBJECT-TYPE
    SYNTAX     Counter32
    UNITS      "packets"
    MAX-ACCESS read-only
    STATUS     current
    DESCRIPTION
            "This object represents total number of non-unicast or
            mulitcast packets transmitted on the interface"
    ::= { ruijieApCfgEntry 22 }

ruijieApEthernetIfDuplex OBJECT-TYPE
    SYNTAX     INTEGER {
        unknown(1),
        halfduplex(2),
        fullduplex(3),
        auto(4)
    }
    MAX-ACCESS read-only
    STATUS     current
    DESCRIPTION
            "This object represents interface's duplex mode"
    ::= { ruijieApCfgEntry 23 }

ruijieApEthernetIfLinkSpeed OBJECT-TYPE
    SYNTAX     INTEGER
    MAX-ACCESS read-only
    STATUS     current
    DESCRIPTION
            "Speed of the interface in units of 1,000,000 bits per second"
    ::= { ruijieApCfgEntry 24 }

ruijieApEthernetIfPOEPower OBJECT-TYPE
    SYNTAX     INTEGER {
        none(1),
        drawn(2),
        notdrawn(3)
    }
    MAX-ACCESS read-only
    STATUS     current
    DESCRIPTION
      "This object represents whether this interface supports
      Power Over Ethernet (POE)
      none     - POE is not supported
      drawn    - This interface supports POE, and power is
                 being drawn
      notdrawn - POE power is not drawn"
    ::= { ruijieApCfgEntry 25 }


ruijieApAdminStatus OBJECT-TYPE
    SYNTAX     INTEGER {
        enable(1),
        disable(2)
    }
    MAX-ACCESS read-write
    STATUS     current
    DESCRIPTION
      "This object represents whether this interface supports
      Power Over Ethernet (POE)
      enable     - enable to admin
      disable    - disable to admin"
    ::= { ruijieApCfgEntry 26 }

ruijieApEthernetIfRxBoardPkts OBJECT-TYPE
    SYNTAX      Counter32
    UNITS       "packets"
    MAX-ACCESS  read-only
    STATUS      current
    DESCRIPTION
            "This object represents total number of boardcast packets received on the interface"
    ::= { ruijieApCfgEntry 27 }

ruijieApEthernetIfRxMultiPkts OBJECT-TYPE
    SYNTAX      Counter32
    UNITS       "packets"
    MAX-ACCESS  read-only
    STATUS      current
    DESCRIPTION
            "This object represents total number of mulitcast packets received on the interface"
    ::= { ruijieApCfgEntry 28 }

ruijieApEthernetIfTxBoardPkts OBJECT-TYPE
    SYNTAX      Counter32
    UNITS       "packets"
    MAX-ACCESS  read-only
    STATUS      current
    DESCRIPTION
            "This object represents total number of boardcast packets transmitted on the interface"
    ::= { ruijieApCfgEntry 29 }

ruijieApEthernetIfTxMultiPkts OBJECT-TYPE
    SYNTAX      Counter32
    UNITS       "packets"
    MAX-ACCESS  read-only
    STATUS      current
    DESCRIPTION
            "This object represents total number of multicast packets transmitted on the interface"
    ::= { ruijieApCfgEntry 30 }

ruijieApEthernetIfDropPkts OBJECT-TYPE
    SYNTAX      Counter32
    UNITS       "packets"
    MAX-ACCESS  read-only
    STATUS      current
    DESCRIPTION
            "This object represents total number of packets dropped on the interface"
    ::= { ruijieApCfgEntry 31 }

ruijieApSn OBJECT-TYPE
    SYNTAX      DisplayString
    MAX-ACCESS  read-only
    STATUS      current
    DESCRIPTION
            "This object represents SN string of the AP."
    ::= { ruijieApCfgEntry 32 }

ruijieApIp OBJECT-TYPE
    SYNTAX      IpAddress
    MAX-ACCESS  read-only
    STATUS      current
    DESCRIPTION
            "This object represents ip address of the AP."
    ::= { ruijieApCfgEntry 33 }

ruijieApStaNum OBJECT-TYPE
    SYNTAX      INTEGER
    MAX-ACCESS  read-only
    STATUS      current
    DESCRIPTION
            "This object represents Sta Num attach to the AP."
    ::= { ruijieApCfgEntry 34 }

ruijieApToFat OBJECT-TYPE
    SYNTAX      INTEGER(0..1)
    MAX-ACCESS  read-write
    STATUS      current
    DESCRIPTION
            "This object represents the ap mode, 0 - fit, 1 - fat."
    ::= { ruijieApCfgEntry 35 }
    
ruijieApId OBJECT-TYPE
    SYNTAX      INTEGER(1..800)
    MAX-ACCESS  read-only
    STATUS      current
    DESCRIPTION
            "The AP Id"
    ::= { ruijieApCfgEntry 36 }
    
ruijieApSwVer OBJECT-TYPE
    SYNTAX      DisplayString
    MAX-ACCESS  read-only
    STATUS      current
    DESCRIPTION
            "This object represents SN string of the AP."
    ::= { ruijieApCfgEntry 37 }

ruijieApBootVer OBJECT-TYPE
    SYNTAX      DisplayString
    MAX-ACCESS  read-only
    STATUS      current
    DESCRIPTION
            "This object represents boot version string of the AP."
    ::= { ruijieApCfgEntry 38 }
    
ruijieApPID OBJECT-TYPE
    SYNTAX      DisplayString
    MAX-ACCESS  read-only
    STATUS      current
    DESCRIPTION
            "This object represents product id string of the AP."
    ::= { ruijieApCfgEntry 39 }

ruijieApHwVer OBJECT-TYPE
    SYNTAX      DisplayString
    MAX-ACCESS  read-only
    STATUS      current
    DESCRIPTION
            "This object represents hardware string of the AP."
    ::= { ruijieApCfgEntry 40 }

ruijieApStaLimit OBJECT-TYPE
    SYNTAX      INTEGER(1..30)
    MAX-ACCESS  read-write
    STATUS      current
    DESCRIPTION
            "This object represents client num limit of the AP."
    ::= { ruijieApCfgEntry 41 }

ruijieApFactoryDefault OBJECT-TYPE
    SYNTAX      INTEGER {
        normal(0),
        reset(1)
    }
    MAX-ACCESS  read-write
    STATUS      current
    DESCRIPTION
            "1 -- Set the ap to reboot with the factory default configuration."
    ::= { ruijieApCfgEntry 42 }

ruijieApCpuUsageTrapTimer OBJECT-TYPE
    SYNTAX      INTEGER
    MAX-ACCESS  read-write
    STATUS      current
    DESCRIPTION
            "This object represents the AP's cpu usage info trap timer, 
             second."
    ::= { ruijieApCfgEntry 43 }
    
    
ruijieApStatTrapTimer  OBJECT-TYPE
    SYNTAX  INTEGER
    MAX-ACCESS  read-write
    STATUS  current
    DESCRIPTION
            "This object present the AP's radio statistic
             trap timer, second."
    ::= { ruijieApCfgEntry 44}
    
ruijieApLinkOnTimeInterval OBJECT-TYPE
    SYNTAX      INTEGER
    MAX-ACCESS  read-only
    STATUS      current
    DESCRIPTION
            "This object represents the AP's Link on time interval, seconds."
    ::= { ruijieApCfgEntry 45 }
    
ruijieApNetId OBJECT-TYPE
    SYNTAX      DisplayString
    MAX-ACCESS  read-write
    STATUS      current
    DESCRIPTION
            "This object represents the AP's net unit code."
    ::= { ruijieApCfgEntry 46 }
    
ruijieApUptime OBJECT-TYPE
    SYNTAX      DisplayString
    MAX-ACCESS  read-only
    STATUS      current
    DESCRIPTION
            "This object represents the AP's capwap uptime."
    ::= { ruijieApCfgEntry 47 }

ruijieApState OBJECT-TYPE
    SYNTAX      INTEGER
    MAX-ACCESS  read-only
    STATUS      current
    DESCRIPTION
            "This object represents the AP's state.
                1 -- on line;
                2 -- off line"
    ::= { ruijieApCfgEntry 48 }

ruijieApNasId  OBJECT-TYPE
    SYNTAX      DisplayString
    MAX-ACCESS  read-write
    STATUS      current
    DESCRIPTION
            "The NAS ID about this AP."
    ::= { ruijieApCfgEntry 49 }
    
ruijieApCoverArea OBJECT-TYPE
    SYNTAX      INTEGER
    MAX-ACCESS  read-write
    STATUS      current
    DESCRIPTION
            "This object represents the AP's cover type.
                1 -- Type A: School;
                2 -- Type B: Airfield, Station;
                3 -- Type C: Hospital, Hotel, Marketplace;
                4 -- Type D: Group customers with specific WLAN requirements"
    ::= { ruijieApCfgEntry 50 }

ruijieApLinkOnTimeIntervalMs OBJECT-TYPE
    SYNTAX      TimeTicks
    MAX-ACCESS  read-only
    STATUS      current
    DESCRIPTION
            "This object represents the AP's Link on time interval, 0.01seconds."
    ::= { ruijieApCfgEntry 51 }

ruijieApUptimeMs OBJECT-TYPE
    SYNTAX      TimeTicks
    MAX-ACCESS  read-only
    STATUS      current
    DESCRIPTION
            "This object represents the AP's capwap uptime, 0.01seconds."
    ::= { ruijieApCfgEntry 52 }

ruijieApHbUptimeMs OBJECT-TYPE
    SYNTAX      TimeTicks
    MAX-ACCESS  read-only
    STATUS      current
    DESCRIPTION
            "This object represents the AP's capwap hotback uptime, 0.01seconds."
    ::= { ruijieApCfgEntry 53 }

ruijieApIpv6 OBJECT-TYPE
    SYNTAX      InetAddress
    MAX-ACCESS  read-only
    STATUS      current
    DESCRIPTION
            "This object represents ipv6 address of the AP."
    ::= { ruijieApCfgEntry 54 }

ruijieApIpv6Prefix OBJECT-TYPE
    SYNTAX      DisplayString
    MAX-ACCESS  read-only
    STATUS      current
    DESCRIPTION
            "This object represents ipv6 address prefix of the AP."
    ::= { ruijieApCfgEntry 55 }

ruijieApIpv6PrefixLen OBJECT-TYPE
    SYNTAX      INTEGER
    MAX-ACCESS  read-only
    STATUS      current
    DESCRIPTION
            "This object represents ipv6 address prefix length of the AP."
    ::= { ruijieApCfgEntry 56 }

ruijieApIpv6Type OBJECT-TYPE
    SYNTAX  INTEGER {
        unknown(0),
        unicase(1),
        anycase(2),
        multicase(3)
    }
    MAX-ACCESS  read-only
    STATUS      current
    DESCRIPTION
            "This object represents ipv6 address type of the AP."
    ::= { ruijieApCfgEntry 57 }

ruijieApIpv6Gateway OBJECT-TYPE
    SYNTAX      DisplayString
    MAX-ACCESS  read-only
    STATUS      current
    DESCRIPTION
            "This object represents ipv6 gateway address of the AP."
    ::= { ruijieApCfgEntry 58 }

ruijieApIpv6StaNum OBJECT-TYPE
    SYNTAX      INTEGER
    MAX-ACCESS  read-only
    STATUS      current
    DESCRIPTION
            "This object represents ipv6 Sta Num attach to the AP."
    ::= { ruijieApCfgEntry 59 }

ruijieApMacAddrColon OBJECT-TYPE
    SYNTAX      DisplayString (SIZE (17..17))
    MAX-ACCESS  read-only
    STATUS      current
    DESCRIPTION
            "The AP's ethernet mac address separated by the colon character, format: XX:XX:XX:XX:XX:XX"
    ::= { ruijieApCfgEntry 60 }

ruijieApMacAddrLine OBJECT-TYPE
    SYNTAX      DisplayString (SIZE (17..17))
    MAX-ACCESS  read-only
    STATUS      current
    DESCRIPTION
            "The AP's ethernet mac address separated by the line character, format: XX-XX-XX-XX-XX-XX"
    ::= { ruijieApCfgEntry 61 }

ruijieApMacAddrDot OBJECT-TYPE
    SYNTAX      DisplayString (SIZE (14..14))
    MAX-ACCESS  read-only
    STATUS      current
    DESCRIPTION
            "The AP's ethernet mac address separated by the dot character, format: xxxx.xxxx.xxxx"
    ::= { ruijieApCfgEntry 62 }
	
-- ***********************************
-- ap configuration per radio
-- ***********************************
ruijieApCfgRadioTable OBJECT-TYPE
    SYNTAX  SEQUENCE OF RuijieApCfgRadioEntry
    MAX-ACCESS  not-accessible
    STATUS  current
    DESCRIPTION
            "Set the ap attribute per radio."
    ::= { ruijieAcMgmtAp 2 }

ruijieApCfgRadioEntry OBJECT-TYPE
    SYNTAX  RuijieApCfgRadioEntry
    MAX-ACCESS  not-accessible
    STATUS  current
    DESCRIPTION
        "The entry of image id table."
    INDEX   { ruijieApMacAddr, ruijieApCfgRadioId }
    ::= { ruijieApCfgRadioTable 1 }

RuijieApCfgRadioEntry ::=
    SEQUENCE {
        ruijieApCfgRadioId      INTEGER,
        ruijieApRadioEn         INTEGER,
        ruijieApTxPower         INTEGER,
        ruijieApDtimPeriod      INTEGER,
        ruijieApBeaconPeriod    INTEGER,
        ruijieApCountry         DisplayString,
        ruijieApPreaShort       INTEGER,
        ruijieApRadioBssid      MacAddress,
        ruijieApTxPowerLevel    INTEGER,
        ruijieApTxPowerGlobal   INTEGER,
        ruijieApCurChan         INTEGER,
        ruijieApRfGlobal        INTEGER,
        ruijieApRadioType       INTEGER,
        ruijieApRadio11bSup     INTEGER,
        ruijieApMaxTxPower      INTEGER,
        ruijieApMinTxPower      INTEGER,
        ruijieApCurTxPower      INTEGER,
        ruijieApMaxTxPowerPer   INTEGER,
        ruijieApMinTxPowerPer   INTEGER
    }

-- The radio id
ruijieApCfgRadioId  OBJECT-TYPE
    SYNTAX  INTEGER (1..31)
    MAX-ACCESS  read-only
    STATUS  current
    DESCRIPTION
            "The radio id, 1~31."
    ::= { ruijieApCfgRadioEntry 1 }

-- 0-disable, 1-enable
ruijieApRadioEn  OBJECT-TYPE
    SYNTAX  INTEGER (0..1)
    MAX-ACCESS  read-write
    STATUS  current
    DESCRIPTION
            "0--disable, 1--enable."
    ::= { ruijieApCfgRadioEntry 2 }

-- The AP Tx Power
ruijieApTxPower  OBJECT-TYPE
    SYNTAX  INTEGER (1..100)
    MAX-ACCESS  read-write
    STATUS  current
    DESCRIPTION
            "Tx power, 1%."
    ::= { ruijieApCfgRadioEntry 3}
    
-- The AP beacon dtim period
ruijieApDtimPeriod  OBJECT-TYPE
    SYNTAX  INTEGER (1..255)
    MAX-ACCESS  read-write
    STATUS  current
    DESCRIPTION
            "beacon dtim period, second."
    ::= { ruijieApCfgRadioEntry 4}

-- The beacon period
ruijieApBeaconPeriod  OBJECT-TYPE
    SYNTAX  INTEGER (20..1000)
    MAX-ACCESS  read-write
    STATUS  current
    DESCRIPTION
            "beacon period, millisecond."
    ::= { ruijieApCfgRadioEntry 5}

-- The ap country code
ruijieApCountry  OBJECT-TYPE
    SYNTAX  DisplayString (SIZE(0..255))
    MAX-ACCESS  read-write
    STATUS  current
    DESCRIPTION
            "Ap country code."
    ::= { ruijieApCfgRadioEntry 6}

-- 0-not support short preamble,1-support short preamble
ruijieApPreaShort  OBJECT-TYPE
    SYNTAX  INTEGER (0..1)
    MAX-ACCESS  read-write
    STATUS  current
    DESCRIPTION
            "Short preamble support."
    ::= { ruijieApCfgRadioEntry 7}

ruijieApRadioBssid  OBJECT-TYPE
    SYNTAX  MacAddress
    MAX-ACCESS  read-only
    STATUS  current
    DESCRIPTION
            "The AP's radio mac address(BSSID)."
    ::= { ruijieApCfgRadioEntry 8}

ruijieApTxPowerLevel  OBJECT-TYPE
    SYNTAX  INTEGER (1..600)
    MAX-ACCESS  read-only
    STATUS  current
    DESCRIPTION
            "The ap's tx power level in the radio."
    ::= { ruijieApCfgRadioEntry 9}

ruijieApTxPowerGlobal  OBJECT-TYPE
    SYNTAX  INTEGER (0..1)
    MAX-ACCESS  read-write
    STATUS  current
    DESCRIPTION
            "The ap's tx power config as the Global or not.
             0--customer, 1-global."
    ::= { ruijieApCfgRadioEntry 10}
    
ruijieApCurChan  OBJECT-TYPE
    SYNTAX  INTEGER (1..165)
    MAX-ACCESS  read-write
    STATUS  current
    DESCRIPTION
            "The ap's current channel in the radio."
    ::= { ruijieApCfgRadioEntry 11}
    
ruijieApRfGlobal  OBJECT-TYPE
    SYNTAX  INTEGER (0..1)
    MAX-ACCESS  read-write
    STATUS  current
    DESCRIPTION
            "The ap's channel config as the Global or not.
             0--customer, 1-global."
    ::= { ruijieApCfgRadioEntry 12}

ruijieApRadioType  OBJECT-TYPE
    SYNTAX  INTEGER (1..2)
    MAX-ACCESS  read-write
    STATUS  current
    DESCRIPTION
            "1--802.11b
             2--802.11a"
    ::= { ruijieApCfgRadioEntry 13}
    
ruijieApRadio11bSup  OBJECT-TYPE
    SYNTAX  INTEGER (1..2)
    MAX-ACCESS  read-only
    STATUS  current
    DESCRIPTION
            "1--support 802.11b
             2--not support 802.11b"
    ::= { ruijieApCfgRadioEntry 14}
    
-- The AP Max Tx Power
ruijieApMaxTxPower  OBJECT-TYPE
    SYNTAX  INTEGER
    MAX-ACCESS  read-only
    STATUS  current
    DESCRIPTION
            "Max tx power, mw."
    ::= { ruijieApCfgRadioEntry 15}
    
-- The AP Min Tx Power
ruijieApMinTxPower  OBJECT-TYPE
    SYNTAX  INTEGER
    MAX-ACCESS  read-only
    STATUS  current
    DESCRIPTION
            "Min tx power, mw."
    ::= { ruijieApCfgRadioEntry 16}
    
-- The AP Current Tx Power
ruijieApCurTxPower  OBJECT-TYPE
    SYNTAX  INTEGER
    MAX-ACCESS  read-write
    STATUS  current
    DESCRIPTION
            "Current tx power, mw."
    ::= { ruijieApCfgRadioEntry 17}
    
-- The AP Max Tx Power Percent
ruijieApMaxTxPowerPer  OBJECT-TYPE
    SYNTAX  INTEGER
    MAX-ACCESS  read-only
    STATUS  current
    DESCRIPTION
            "Max tx power percent, %."
    ::= { ruijieApCfgRadioEntry 18}
    
-- The AP Min Tx Power Percent
ruijieApMinTxPowerPer  OBJECT-TYPE
    SYNTAX  INTEGER
    MAX-ACCESS  read-only
    STATUS  current
    DESCRIPTION
            "Min tx power percent, %."
    ::= { ruijieApCfgRadioEntry 19}
    
ruijieApRadioRateCfgTable OBJECT-TYPE
    SYNTAX  SEQUENCE OF RuijieApRadioRateCfgEntry
    MAX-ACCESS  not-accessible
    STATUS  current
    DESCRIPTION
            "The rate set of the ap's radio."
    ::= { ruijieAcMgmtAp 3 }

ruijieApRadioRateCfgEntry OBJECT-TYPE
    SYNTAX  RuijieApRadioRateCfgEntry
    MAX-ACCESS  not-accessible
    STATUS  current
    DESCRIPTION
        "The attribute of the ap radio rate type."
    INDEX   { ruijieApMacAddr, ruijieApCfgRadioId, ruijieApRadioRate }
    ::= { ruijieApRadioRateCfgTable 1 }

RuijieApRadioRateCfgEntry ::=
        SEQUENCE {
            ruijieApRadioRate             INTEGER,
            ruijieApRadioRateType         INTEGER
        }
        
ruijieApRadioRate  OBJECT-TYPE
    SYNTAX  INTEGER (1..8)
    MAX-ACCESS  not-accessible
    STATUS  current
    DESCRIPTION
            "The ap's rate set in the radio.
            802.11a-6, 9, 12, 18, 24, 36, 48, and 54 Mbps.
            set 1 for 6Mbps, set 2 for 9Mbps, set 3 for 12Mbps,etc...
            802.11b-1, 2, 5.5, 11Mbps.
            set 1 for 1Mbps, set 2 for 2Mbps, set 3 for 5.5Mbps,etc..."
    ::= { ruijieApRadioRateCfgEntry 1}
    
ruijieApRadioRateType  OBJECT-TYPE
    SYNTAX  INTEGER (1..3)
    MAX-ACCESS  read-write
    STATUS  current
    DESCRIPTION
            "The rate type:
            1--disable
            2--mandatory
            3--support"
    ::= { ruijieApRadioRateCfgEntry 2}
    
    
-- static ip config
ruijieApStaticIpCfgTable OBJECT-TYPE
    SYNTAX  SEQUENCE OF RuijieApStaticIpCfgEntry
    MAX-ACCESS  not-accessible
    STATUS  current
    DESCRIPTION
            "The rate set of the ap's radio."
    ::= { ruijieAcMgmtAp 4 }

ruijieApStaticIpCfgEntry OBJECT-TYPE
    SYNTAX  RuijieApStaticIpCfgEntry
    MAX-ACCESS  not-accessible
    STATUS  current
    DESCRIPTION
        "Config the static ip address of the ap."
    INDEX   { ruijieApMacAddr }
    ::= { ruijieApStaticIpCfgTable 1 }

RuijieApStaticIpCfgEntry ::=
        SEQUENCE {
            ruijieApIpAddr             IpAddress,
            ruijieApIpMask             IpAddress,
            ruijieApIpGetway           IpAddress,
            ruijieApStaticIpRS         RowStatus
        }
        
ruijieApIpAddr  OBJECT-TYPE
    SYNTAX  IpAddress
    MAX-ACCESS  read-write
    STATUS  current
    DESCRIPTION
            "The AP's Static Ip Address"
    ::= { ruijieApStaticIpCfgEntry 1}
    
ruijieApIpMask  OBJECT-TYPE
    SYNTAX  IpAddress
    MAX-ACCESS  read-write
    STATUS  current
    DESCRIPTION
            "The AP's Static Ip Address Mask"
    ::= { ruijieApStaticIpCfgEntry 2}
    
ruijieApIpGetway  OBJECT-TYPE
    SYNTAX  IpAddress
    MAX-ACCESS  read-write
    STATUS  current
    DESCRIPTION
            "The AP's Static Ip Address Getway"
    ::= { ruijieApStaticIpCfgEntry 3}
    
ruijieApStaticIpRS  OBJECT-TYPE
    SYNTAX  RowStatus
    MAX-ACCESS  read-write
    STATUS  current
    DESCRIPTION
            "The AP's Static Ip Address Row status"
    ::= { ruijieApStaticIpCfgEntry 4}


ruijieApOfflineTable OBJECT-TYPE
    SYNTAX  SEQUENCE OF RuijieApOfflineEntry
    MAX-ACCESS  not-accessible
    STATUS  current
    DESCRIPTION
            "The Ap offline time attributes."
    ::= { ruijieAcMgmtAp 5 }

ruijieApOfflineEntry OBJECT-TYPE
    SYNTAX  RuijieApOfflineEntry
    MAX-ACCESS  not-accessible
    STATUS  current
    DESCRIPTION
        "Get and set the Ap attribtues."
    INDEX   { ruijieApOffMacAddr }
    ::= { ruijieApOfflineTable 1 }

RuijieApOfflineEntry ::=
    SEQUENCE {
        ruijieApOfftime                    INTEGER,
        ruijieApOffApName                  DisplayString,
        ruijieApOffMacAddr                 MacAddress,
        ruijieApOffIp                      IpAddress,
        ruijieApOffMacAddrColon            DisplayString,
        ruijieApOffMacAddrLine             DisplayString,
        ruijieApOffMacAddrDot              DisplayString
    }

ruijieApOfftime  OBJECT-TYPE
    SYNTAX  INTEGER
    MAX-ACCESS  read-only
    STATUS  current
    DESCRIPTION
            "The AP's ethernet mac address."
    ::= { ruijieApOfflineEntry 1}

-- The AP Name
ruijieApOffApName  OBJECT-TYPE
    SYNTAX  DisplayString (SIZE (1..32))
    MAX-ACCESS  read-only
    STATUS  current
    DESCRIPTION
            "Offline Ap's Name."
    ::= { ruijieApOfflineEntry 2}

ruijieApOffMacAddr  OBJECT-TYPE
    SYNTAX  MacAddress
    MAX-ACCESS  read-only
    STATUS  current
    DESCRIPTION
            "The offline AP's ethernet mac address."
    ::= { ruijieApOfflineEntry 3}

ruijieApOffIp OBJECT-TYPE
    SYNTAX      IpAddress
    MAX-ACCESS  read-only
    STATUS      current
    DESCRIPTION
            "The IP address for the last use of the offline AP."
    ::= { ruijieApOfflineEntry 4 }

ruijieApOffMacAddrColon OBJECT-TYPE
    SYNTAX      DisplayString (SIZE (17..17))
    MAX-ACCESS  read-only
    STATUS      current
    DESCRIPTION
            "The offline AP's ethernet mac address separated by the colon character, format: XX:XX:XX:XX:XX:XX"
    ::= { ruijieApOfflineEntry 5 }

ruijieApOffMacAddrLine OBJECT-TYPE
    SYNTAX      DisplayString (SIZE (17..17))
    MAX-ACCESS  read-only
    STATUS      current
    DESCRIPTION
            "The offline AP's ethernet mac address separated by the line character, format: XX-XX-XX-XX-XX-XX"
    ::= { ruijieApOfflineEntry 6 }

ruijieApOffMacAddrDot OBJECT-TYPE
    SYNTAX      DisplayString (SIZE (14..14))
    MAX-ACCESS  read-only
    STATUS      current
    DESCRIPTION
            "The offline AP's ethernet mac address separated by the dot character, format: xxxx.xxxx.xxxx"
    ::= { ruijieApOfflineEntry 7 }

--********************************************************************
--    ruijieApBackupState                                           **
--********************************************************************
ruijieApBackupStateTable OBJECT-TYPE
    SYNTAX  SEQUENCE OF RuijieApBackupStateEntry
    MAX-ACCESS  not-accessible
    STATUS  current
    DESCRIPTION
            "The Ap backup state."
    ::= { ruijieAcMgmtAp 6 }

ruijieApBackupStateEntry OBJECT-TYPE
    SYNTAX  RuijieApBackupStateEntry
    MAX-ACCESS  not-accessible
    STATUS  current
    DESCRIPTION
        "Get the Ap backup state."
    INDEX   { ruijieApMacAddr }
    ::= { ruijieApBackupStateTable 1 }

RuijieApBackupStateEntry ::=
    SEQUENCE {
        ruijieApBackupState             INTEGER
    }

ruijieApBackupState  OBJECT-TYPE
    SYNTAX  INTEGER {
                    unknown(0),
                    master(1),
                    slave(2)
                }
    MAX-ACCESS  read-only
    STATUS  current
    DESCRIPTION
            "The AP's backup state."
    ::= { ruijieApBackupStateEntry 1 }

--********************************************************************
--    ruijieApMicroAp                                               **
--********************************************************************
ruijieApMicroApTable OBJECT-TYPE
    SYNTAX  SEQUENCE OF RuijieApMicroApEntry
    MAX-ACCESS  not-accessible
    STATUS  current
    DESCRIPTION
            "The Micro AP configure."
    ::= { ruijieAcMgmtAp 7 }

ruijieApMicroApEntry OBJECT-TYPE
    SYNTAX  RuijieApMicroApEntry
    MAX-ACCESS  not-accessible
    STATUS  current
    DESCRIPTION
        "Config Micro AP."
    INDEX   { ruijieApMacAddr, ruijieApMicroApSlot }
    ::= { ruijieApMicroApTable 1 }

RuijieApMicroApEntry ::=
    SEQUENCE {
        ruijieApMicroApSlot             INTEGER,
		ruijieApMicroApName				DisplayString,
		ruijieApMicroApReset            INTEGER,
		ruijieApMicroApUninstall		INTEGER,
		ruijieApMicroApMac            	MacAddress,
		ruijieApMicroApBoard			DisplayString,
		ruijieApMicroApState			INTEGER		
    }

ruijieApMicroApSlot  OBJECT-TYPE
    SYNTAX  INTEGER (1..24)
    MAX-ACCESS  read-only
    STATUS  current
    DESCRIPTION
            "The Micro Ap's Slot Id."
    ::= { ruijieApMicroApEntry 1 }

ruijieApMicroApName  OBJECT-TYPE
    SYNTAX  DisplayString (SIZE (1..32))
    MAX-ACCESS  read-write
    STATUS  current
    DESCRIPTION
            "Micro Ap's Name."
    ::= { ruijieApMicroApEntry 2}

ruijieApMicroApReset  OBJECT-TYPE
    SYNTAX  INTEGER (0..1)
    MAX-ACCESS  read-write
    STATUS  current
    DESCRIPTION
            "Reset Micro AP:
            1--Reset"
    ::= { ruijieApMicroApEntry 3}

ruijieApMicroApUninstall  OBJECT-TYPE
    SYNTAX  INTEGER (0..1)
    MAX-ACCESS  read-write
    STATUS  current
    DESCRIPTION
            "Uninstall Micro AP:
            1--Uninstall"
    ::= { ruijieApMicroApEntry 4}

ruijieApMicroApMac  OBJECT-TYPE
    SYNTAX  MacAddress
    MAX-ACCESS  read-only
    STATUS  current
    DESCRIPTION
            "Micro AP Mac address"
    ::= { ruijieApMicroApEntry 5}

ruijieApMicroApBoard  OBJECT-TYPE
    SYNTAX  DisplayString (SIZE (1..32))
    MAX-ACCESS  read-only
    STATUS  current
    DESCRIPTION
            "Micro AP Board ID"
    ::= { ruijieApMicroApEntry 6}

ruijieApMicroApState  OBJECT-TYPE
    SYNTAX  INTEGER (0..2)
    MAX-ACCESS  read-only
    STATUS  current
    DESCRIPTION
            "Micro AP State:
            0--Not Exist
			1--Offline
			2--Online"
    ::= { ruijieApMicroApEntry 7}

--********************************************************************
--    ruijieApGeneralCfgTable                                       **
--********************************************************************

ruijieApGeneralCfgTable OBJECT-TYPE
    SYNTAX  SEQUENCE OF RuijieApGeneralCfgEntry
    MAX-ACCESS  not-accessible
    STATUS  current
    DESCRIPTION
            "The general Ap attribtues, include online and offline Aps."
    ::= { ruijieAcMgmtAp 8 }

ruijieApGeneralCfgEntry OBJECT-TYPE
    SYNTAX  RuijieApGeneralCfgEntry
    MAX-ACCESS  not-accessible
    STATUS  current
    DESCRIPTION
        "Get and set the general Ap attribtues."
    INDEX   { ruijieApGeneralMacAddr }
    ::= { ruijieApGeneralCfgTable 1 }

RuijieApGeneralCfgEntry ::=
    SEQUENCE {
        ruijieApGeneralMacAddr             MacAddress,
        ruijieApGeneralApName              DisplayString,
        ruijieApGeneralState               INTEGER,
        ruijieApGeneralTime                DisplayString,
        ruijieApGeneralTimeMs              TimeTicks,
        ruijieApGeneralIp                  IpAddress,
        ruijieApGeneralMacAddrColon        DisplayString,
        ruijieApGeneralMacAddrLine         DisplayString,
        ruijieApGeneralMacAddrDot          DisplayString
    }

ruijieApGeneralMacAddr  OBJECT-TYPE
    SYNTAX  MacAddress
    MAX-ACCESS  read-only
    STATUS  current
    DESCRIPTION
            "The AP's ethernet mac address."
    ::= { ruijieApGeneralCfgEntry 1}

-- The AP Name
ruijieApGeneralApName  OBJECT-TYPE
    SYNTAX  DisplayString (SIZE (1..64))
    MAX-ACCESS  read-only
    STATUS  current
    DESCRIPTION
            "The Ap's Name."
    ::= { ruijieApGeneralCfgEntry 2}

ruijieApGeneralState  OBJECT-TYPE
    SYNTAX  INTEGER {
        online(1),
        offline(2)
    }
    MAX-ACCESS  read-only
    STATUS  current
    DESCRIPTION
			"The AP's state.
			1 -- online;
			2 -- offline"
    ::= { ruijieApGeneralCfgEntry 3}

ruijieApGeneralTime OBJECT-TYPE
    SYNTAX      DisplayString
    MAX-ACCESS  read-only
    STATUS      current
    DESCRIPTION
            "The AP's capwap change time or add time, format: d:hh:mm:ss"
    ::= { ruijieApGeneralCfgEntry 4 }

ruijieApGeneralTimeMs OBJECT-TYPE
    SYNTAX      TimeTicks
    MAX-ACCESS  read-only
    STATUS      current
    DESCRIPTION
            "The AP's capwap change time or add time, 0.01seconds."
    ::= { ruijieApGeneralCfgEntry 5 }

ruijieApGeneralIp OBJECT-TYPE
    SYNTAX      IpAddress
    MAX-ACCESS  read-only
    STATUS      current
    DESCRIPTION
            "The AP's ip address."
    ::= { ruijieApGeneralCfgEntry 6 }

ruijieApGeneralMacAddrColon OBJECT-TYPE
    SYNTAX      DisplayString (SIZE (17..17))
    MAX-ACCESS  read-only
    STATUS      current
    DESCRIPTION
            "The AP's ethernet mac address separated by the colon character, format: XX:XX:XX:XX:XX:XX"
    ::= { ruijieApGeneralCfgEntry 7 }

ruijieApGeneralMacAddrLine OBJECT-TYPE
    SYNTAX      DisplayString (SIZE (17..17))
    MAX-ACCESS  read-only
    STATUS      current
    DESCRIPTION
            "The AP's ethernet mac address separated by the line character, format: XX-XX-XX-XX-XX-XX"
    ::= { ruijieApGeneralCfgEntry 8 }

ruijieApGeneralMacAddrDot OBJECT-TYPE
    SYNTAX      DisplayString (SIZE (14..14))
    MAX-ACCESS  read-only
    STATUS      current
    DESCRIPTION
            "The AP's ethernet mac address separated by the dot character, format: xxxx.xxxx.xxxx"
    ::= { ruijieApGeneralCfgEntry 9 }

--********************************************************************
--                                                                  **
--                  AP Group nodes                                  **
--                                                                  **
--********************************************************************
ruijieApgCfgTable OBJECT-TYPE
    SYNTAX  SEQUENCE OF RuijieApgCfgEntry
    MAX-ACCESS  not-accessible
    STATUS  current
    DESCRIPTION
            "The attribute of the ap group."
    ::= { ruijieAcMgmtApg 1 }

ruijieApgCfgEntry OBJECT-TYPE
    SYNTAX  RuijieApgCfgEntry
    MAX-ACCESS  not-accessible
    STATUS  current
    DESCRIPTION
        "The attribute of the ap group."
    INDEX   { ruijieApgApgName }
    ::= { ruijieApgCfgTable 1 }

RuijieApgCfgEntry ::=
        SEQUENCE {
            ruijieApgApgName             DisplayString,
            ruijieApgDiscTimer           INTEGER,
            ruijieApgEchoReqTimer        INTEGER,
            ruijieApgEroReportTimer      INTEGER,
            ruijieApgStaTimeoutTimer     INTEGER,
            ruijieApgStatisticsTimer     INTEGER,
            ruijieApgFallback            INTEGER,
            ruijieApgImageId             DisplayString,
            ruijieApgCreatEn             INTEGER
        }

-- The AP Group Name
ruijieApgApgName  OBJECT-TYPE
    SYNTAX  DisplayString (SIZE (1..64))
    MAX-ACCESS  read-only
    STATUS  current
    DESCRIPTION
            "Ap group's Name."
    ::= { ruijieApgCfgEntry 1}

-- The Discovery timer
ruijieApgDiscTimer  OBJECT-TYPE
    SYNTAX  INTEGER (2..180)
    MAX-ACCESS  read-write
    STATUS  current
    DESCRIPTION
            "Discovery timer."
    ::= { ruijieApgCfgEntry 2 }
    
-- The Echo Request timer
ruijieApgEchoReqTimer  OBJECT-TYPE
    SYNTAX  INTEGER (5..255)
    MAX-ACCESS  read-write
    STATUS  current
    DESCRIPTION
            "Echo Request timer."
    ::= { ruijieApgCfgEntry 3 }


-- The Error Report timer
ruijieApgEroReportTimer  OBJECT-TYPE
    SYNTAX  INTEGER (1..1080)
    MAX-ACCESS  read-write
    STATUS  current
    DESCRIPTION
            "Error Report timer."
    ::= { ruijieApgCfgEntry 4 }

-- The Sta timeout timer
ruijieApgStaTimeoutTimer  OBJECT-TYPE
    SYNTAX  INTEGER (60..86400)
    MAX-ACCESS  read-write
    STATUS  current
    DESCRIPTION
            "station idle timeout timer."
    ::= { ruijieApgCfgEntry 5 }

-- The Statistics timeout timer
ruijieApgStatisticsTimer  OBJECT-TYPE
    SYNTAX  INTEGER (1..65535)
    MAX-ACCESS  read-write
    STATUS  current
    DESCRIPTION
            "station idle timeout timer."
    ::= { ruijieApgCfgEntry 6 }

-- The fallback value, 1-enable, 2-disable
ruijieApgFallback  OBJECT-TYPE
    SYNTAX  INTEGER (1..2)
    MAX-ACCESS  read-write
    STATUS  current
    DESCRIPTION
            "The fallback value, 1--enable, 2--disable."
    ::= { ruijieApgCfgEntry 7 }

-- The Image id, should be 8 bytes
ruijieApgImageId  OBJECT-TYPE
    SYNTAX  DisplayString (SIZE (1..128))
    MAX-ACCESS  read-write
    STATUS  current
    DESCRIPTION
            "The Ap image version string."
    ::= { ruijieApgCfgEntry 8 }


-- 0-del, 1-creat
ruijieApgCreatEn  OBJECT-TYPE
    SYNTAX  INTEGER (0..1)
    MAX-ACCESS  read-write
    STATUS  current
    DESCRIPTION
            "0-del, 1-creat."
    ::= { ruijieApgCfgEntry 9 }
    
-- ***************************************
-- ap group attribute per radio
-- ***************************************
ruijieApgCfgRadioTable OBJECT-TYPE
    SYNTAX  SEQUENCE OF RuijieApgCfgRadioEntry
    MAX-ACCESS  not-accessible
    STATUS  current
    DESCRIPTION
            "The ap group attribute per radio."
    ::= { ruijieAcMgmtApg 2 }

ruijieApgCfgRadioEntry OBJECT-TYPE
    SYNTAX  RuijieApgCfgRadioEntry
    MAX-ACCESS  not-accessible
    STATUS  current
    DESCRIPTION
        "The ap group attribute per radio."
    INDEX   { ruijieApgApgName, ruijieApgEnableRadioId}
    ::= { ruijieApgCfgRadioTable 1 }

RuijieApgCfgRadioEntry ::=
    SEQUENCE {
        ruijieApgEnableRadioId    INTEGER,
        ruijieApgEnableRadioEn    INTEGER
    }

-- The radio id
ruijieApgEnableRadioId  OBJECT-TYPE
    SYNTAX  INTEGER (1..31)
    MAX-ACCESS  not-accessible
    STATUS  current
    DESCRIPTION
            "The radio id, 1~31."
    ::= { ruijieApgCfgRadioEntry 1 }

-- 0-disable, 1-enable
ruijieApgEnableRadioEn  OBJECT-TYPE
    SYNTAX  INTEGER (0..1)
    MAX-ACCESS  read-write
    STATUS  current
    DESCRIPTION
            "0--disable, 1--enable."
    ::= { ruijieApgCfgRadioEntry 2 }

-- ************************************
-- wlan-cvi mapping configure
-- ************************************
ruijieApgIntfMapTable OBJECT-TYPE
    SYNTAX  SEQUENCE OF RuijieApgIntfMapEntry
    MAX-ACCESS  not-accessible
    STATUS  current
    DESCRIPTION
            "Set the wlan-interface map table type."
    ::= { ruijieAcMgmtApg 3 }

ruijieApgIntfMapEntry OBJECT-TYPE
    SYNTAX  RuijieApgIntfMapEntry
    MAX-ACCESS  not-accessible
    STATUS  current
    DESCRIPTION
            "The entry of the wlan-interface map table."
    INDEX   { ruijieApgApgName, ruijieApgWlanIndex }
    ::= { ruijieApgIntfMapTable 1 }

RuijieApgIntfMapEntry ::=
    SEQUENCE {
        ruijieApgWlanIndex        INTEGER,
        ruijieApgWlanId           INTEGER,
        ruijieApgVlanId           INTEGER,
        ruijieApgRadioId          INTEGER,
        ruijieApgWlanIntfMapRS    RowStatus
    }

-- The wlan-intf map index
ruijieApgWlanIndex  OBJECT-TYPE
    SYNTAX  INTEGER (1..64)
    MAX-ACCESS  read-only
    STATUS  current
    DESCRIPTION
            "Wlan Id."
    ::= { ruijieApgIntfMapEntry 1 }
    
-- The Wlan Id
ruijieApgWlanId  OBJECT-TYPE
    SYNTAX  INTEGER (1..4094)
    MAX-ACCESS  read-write
    STATUS  current
    DESCRIPTION
            "Wlan Id."
    ::= { ruijieApgIntfMapEntry 2 }
    
-- The Intf Id
ruijieApgVlanId OBJECT-TYPE
    SYNTAX  INTEGER (1..4094)
    MAX-ACCESS  read-write
    STATUS  current
    DESCRIPTION
            "Vlan Id."
    ::= { ruijieApgIntfMapEntry 3 }

-- The Radio Id
ruijieApgRadioId  OBJECT-TYPE
    SYNTAX  INTEGER (1..16)
    MAX-ACCESS  read-write
    STATUS  current
    DESCRIPTION
            "Radio Id."
    ::= { ruijieApgIntfMapEntry 4 }

ruijieApgWlanIntfMapRS OBJECT-TYPE
    SYNTAX     RowStatus 
    MAX-ACCESS read-write
    STATUS     current
    DESCRIPTION
         "Used to add or del a wlan-intf map in the ap group."
    ::= { ruijieApgIntfMapEntry 5 }


--********************************************************************
--                                                                  **
--                  WLAN nodes                                      **
--                                                                  **
--********************************************************************
ruijieWlanCfgTable OBJECT-TYPE
    SYNTAX  SEQUENCE OF RuijieWlanCfgEntry
    MAX-ACCESS  not-accessible
    STATUS  current
    DESCRIPTION
            "The wlan attribute."
    ::= { ruijieAcMgmtWlan 1 }

ruijieWlanCfgEntry OBJECT-TYPE
    SYNTAX  RuijieWlanCfgEntry
    MAX-ACCESS  not-accessible
    STATUS  current
    DESCRIPTION
        "The wlan attribute."
    INDEX   { ruijieWlanId}
    ::= { ruijieWlanCfgTable 1 }

RuijieWlanCfgEntry ::=
    SEQUENCE {
        ruijieWlanId                INTEGER,
        ruijieWlanShort             INTEGER,
        ruijieWlanSpctMgmt          INTEGER,
        ruijieWlanEnQos             INTEGER,
        ruijieWlanShortSlotTime     INTEGER,
        ruijieWlanEnableApsd        INTEGER,
        ruijieWlanAckType           INTEGER,
        ruijieWlanTunnelType        INTEGER,
        ruijieWlanBroadSsid         INTEGER,
        ruijieWlanRts               INTEGER,
        ruijieWlanShortTry          INTEGER,
        ruijieWlanLongTry           INTEGER,
        ruijieWlanStaNum            INTEGER,
        ruijieWlanNasId             DisplayString
    }

-- The Wlan id
ruijieWlanId  OBJECT-TYPE
    SYNTAX  INTEGER (1..512)
    MAX-ACCESS  read-only
    STATUS  current
    DESCRIPTION
            "Wlan Id."
    ::= { ruijieWlanCfgEntry 1}

-- The short preamble value, 0-disable, 1-enable
ruijieWlanShort  OBJECT-TYPE
    SYNTAX  INTEGER (0..2)
    MAX-ACCESS  read-write
    STATUS  current
    DESCRIPTION
            "Short Preamble."
    ::= { ruijieWlanCfgEntry 2 }


-- The Spectrum_Management value, 0-disable, 1-enable
ruijieWlanSpctMgmt  OBJECT-TYPE
    SYNTAX  INTEGER (0..1)
    MAX-ACCESS  read-write
    STATUS  current
    DESCRIPTION
            "Spectrum_Management."
    ::= { ruijieWlanCfgEntry 3 }


-- The Spectrum_Management value, 0-disable, 1-enable
ruijieWlanEnQos  OBJECT-TYPE
    SYNTAX  INTEGER (0..1)
    MAX-ACCESS  read-write
    STATUS  current
    DESCRIPTION
            "enbale qos value."
    ::= { ruijieWlanCfgEntry 4 }

-- The Spectrum_Management value, 0-disable, 1-enable
ruijieWlanShortSlotTime  OBJECT-TYPE
    SYNTAX  INTEGER (0..1)
    MAX-ACCESS  read-write
    STATUS  current
    DESCRIPTION
            "short slot time value."
    ::= { ruijieWlanCfgEntry 5 }

-- The IEEE 802.11 Add WLAN.APSD value, 0-disable, 1-enable
ruijieWlanEnableApsd  OBJECT-TYPE
    SYNTAX  INTEGER (0..1)
    MAX-ACCESS  read-write
    STATUS  current
    DESCRIPTION
            "IEEE 802.11 Add WLAN.APSD value."
    ::= { ruijieWlanCfgEntry 6 }

-- 0-delayed, 1-immediate
ruijieWlanAckType  OBJECT-TYPE
    SYNTAX  INTEGER (0..1)
    MAX-ACCESS  read-write
    STATUS  current
    DESCRIPTION
            "Ack delayed or immediate value."
    ::= { ruijieWlanCfgEntry 7 }

-- 0-local, 1-80211, 2-8023
ruijieWlanTunnelType  OBJECT-TYPE
    SYNTAX  INTEGER (0..2)
    MAX-ACCESS  read-write
    STATUS  current
    DESCRIPTION
            "Tunnel type value."
    ::= { ruijieWlanCfgEntry 8 }

-- 0-disable, 1-enable
ruijieWlanBroadSsid  OBJECT-TYPE
    SYNTAX  INTEGER (0..1)
    MAX-ACCESS  read-write
    STATUS  current
    DESCRIPTION
            "Broad Ssid value, 0--disable, 1--enable."
    ::= { ruijieWlanCfgEntry 9 }
    
-- rts threshold
ruijieWlanRts  OBJECT-TYPE
    SYNTAX  INTEGER (0..255)
    MAX-ACCESS  read-write
    STATUS  current
    DESCRIPTION
            "rts threshold."
    ::= { ruijieWlanCfgEntry 10 }

-- Short retries
ruijieWlanShortTry  OBJECT-TYPE
    SYNTAX  INTEGER (0..255)
    MAX-ACCESS  read-write
    STATUS  current
    DESCRIPTION
            "Short retries."
    ::= { ruijieWlanCfgEntry 11 }

-- Long retries
ruijieWlanLongTry  OBJECT-TYPE
    SYNTAX  INTEGER (0..255)
    MAX-ACCESS  read-write
    STATUS  current
    DESCRIPTION
            "Long retries."
    ::= { ruijieWlanCfgEntry 12 }
    
-- WLAN sta number
ruijieWlanStaNum  OBJECT-TYPE
    SYNTAX  INTEGER
    MAX-ACCESS  read-only
    STATUS  current
    DESCRIPTION
            "The wireless stationes attach to this wlan."
    ::= { ruijieWlanCfgEntry 13 }
    
-- WLAN nas id
ruijieWlanNasId  OBJECT-TYPE
    SYNTAX  DisplayString
    MAX-ACCESS  read-write
    STATUS  current
    DESCRIPTION
            "The NAS ID about this wlan."
    ::= { ruijieWlanCfgEntry 14 }
    
-- *******************************
-- wlan creat table
-- *******************************
ruijieWlanWlanCreatTable OBJECT-TYPE
    SYNTAX  SEQUENCE OF RuijieWlanWlanCreatEntry
    MAX-ACCESS  not-accessible
    STATUS  current
    DESCRIPTION
            "Wlan creat table."
    ::= { ruijieAcMgmtWlan 2 }

ruijieWlanWlanCreatEntry OBJECT-TYPE
    SYNTAX  RuijieWlanWlanCreatEntry
    MAX-ACCESS  not-accessible
    STATUS  current
    DESCRIPTION
        "The entry of Braod Ssid value table."
    INDEX   { ruijieWlanId}
    ::= { ruijieWlanWlanCreatTable 1 }

RuijieWlanWlanCreatEntry ::=
    SEQUENCE {
        ruijieWlanWlanSsid          DisplayString,
        ruijieWlanWlanProfile       DisplayString,
        ruijieWlanCreateMapRS       RowStatus
    }
    
-- ssid string
ruijieWlanWlanSsid  OBJECT-TYPE
    SYNTAX  DisplayString (SIZE(1..255))
    MAX-ACCESS  read-write
    STATUS  current
    DESCRIPTION
            "Wlan Ssid."
    ::= { ruijieWlanWlanCreatEntry 1 }

-- profile string
ruijieWlanWlanProfile  OBJECT-TYPE
    SYNTAX  DisplayString (SIZE(1..255))
    MAX-ACCESS  read-write
    STATUS  current
    DESCRIPTION
            "Wlan profile."
    ::= { ruijieWlanWlanCreatEntry 2 }
    
ruijieWlanCreateMapRS OBJECT-TYPE
    SYNTAX     RowStatus 
    MAX-ACCESS read-write
    STATUS     current
    DESCRIPTION
             "Used to add a wlan."
    ::= { ruijieWlanWlanCreatEntry 3 }
    
-- *************************************
-- channel channel_num regulatory band {unii0-unii6} {enable|disable}
-- *************************************
ruijieWlanChanBandTable OBJECT-TYPE
    SYNTAX  SEQUENCE OF RuijieWlanChanBandEntry
    MAX-ACCESS  not-accessible
    STATUS  current
    DESCRIPTION
            "Channel band table type."
    ::= { ruijieAcMgmtWlan 3 }

ruijieWlanChanBandEntry OBJECT-TYPE
    SYNTAX  RuijieWlanChanBandEntry
    MAX-ACCESS  not-accessible
    STATUS  current
    DESCRIPTION
        "The entry of channel band table."
    INDEX   { ruijieWlanId, ruijieWlanBandV}
    ::= { ruijieWlanChanBandTable 1 }

RuijieWlanChanBandEntry ::=
    SEQUENCE {
        ruijieWlanChanV              INTEGER,
        ruijieWlanBandV              INTEGER,
        ruijieWlanChanBandEn         INTEGER,
        ruijieWlanChanBandRS         RowStatus
    }

-- band 
ruijieWlanBandV  OBJECT-TYPE
    SYNTAX  INTEGER (1..7)
    MAX-ACCESS  not-accessible
    STATUS  current
    DESCRIPTION
            "1 for unii0, 2 for unii1 .. 7 for unii6."
    ::= { ruijieWlanChanBandEntry 1 }

-- channel
ruijieWlanChanV  OBJECT-TYPE
    SYNTAX  INTEGER (0..255)
    MAX-ACCESS  read-write
    STATUS  current
    DESCRIPTION
            "fragment threshold."
    ::= { ruijieWlanChanBandEntry 2 }

-- 0-disable,1-enable 
ruijieWlanChanBandEn  OBJECT-TYPE
    SYNTAX  INTEGER (0..1)
    MAX-ACCESS  read-write
    STATUS  current
    DESCRIPTION
            "0-disable,1-enable ."
    ::= { ruijieWlanChanBandEntry 3 }
    
ruijieWlanChanBandRS OBJECT-TYPE
    SYNTAX     RowStatus 
    MAX-ACCESS read-write
    STATUS     current
    DESCRIPTION
             "Used to config a wlan channel band."
    ::= { ruijieWlanChanBandEntry 4 }

-- 15.speed speed_type radio radio_id 55555

-- ***************************************
-- regulatory limit First_Channel Number_of_Channels Mx_Tx_Power_Level
-- ***************************************
ruijieWlanLimitChanTable OBJECT-TYPE
    SYNTAX  SEQUENCE OF RuijieWlanLimitChanEntry
    MAX-ACCESS  not-accessible
    STATUS  current
    DESCRIPTION
            "Channel band table type."
    ::= { ruijieAcMgmtWlan 4 }

ruijieWlanLimitChanEntry OBJECT-TYPE
    SYNTAX  RuijieWlanLimitChanEntry
    MAX-ACCESS  not-accessible
    STATUS  current
    DESCRIPTION
            "The entry of channel band table."
    INDEX   { ruijieWlanId}
    ::= { ruijieWlanLimitChanTable 1 }

RuijieWlanLimitChanEntry ::=
    SEQUENCE {
        ruijieWlanLimitChanFirstV       INTEGER,
        ruijieWlanLimitChanNumV         INTEGER,
        ruijieWlanLimitChanMaxTxPowerLv INTEGER,
        ruijieWlanLimitChanRS           RowStatus
     }

-- first channel
ruijieWlanLimitChanFirstV  OBJECT-TYPE
    SYNTAX  INTEGER (0..255)
    MAX-ACCESS  read-write
    STATUS  current
    DESCRIPTION
            "first channel."
    ::= { ruijieWlanLimitChanEntry 1 }
    
-- Channel num
ruijieWlanLimitChanNumV  OBJECT-TYPE
    SYNTAX  INTEGER (0..6)
    MAX-ACCESS  read-write
    STATUS  current
    DESCRIPTION
            "Channel num."
    ::= { ruijieWlanLimitChanEntry 2 }

-- Max Tx Power Level
ruijieWlanLimitChanMaxTxPowerLv  OBJECT-TYPE
    SYNTAX  INTEGER (1..8)
    MAX-ACCESS  read-write
    STATUS  current
    DESCRIPTION
            "Max Tx Power Level ."
    ::= { ruijieWlanLimitChanEntry 3 }

ruijieWlanLimitChanRS OBJECT-TYPE
    SYNTAX     RowStatus 
    MAX-ACCESS read-write
    STATUS     current
    DESCRIPTION
             "Used to config a wlan limit chan."
    ::= { ruijieWlanLimitChanEntry 4 }


--********************************************************************
--                                                                  **
--                  STA nodes                                       **
--                                                                  **
--********************************************************************
ruijieStaTable OBJECT-TYPE
    SYNTAX  SEQUENCE OF RuijieStaEntry
    MAX-ACCESS  not-accessible
    STATUS  current
    DESCRIPTION
            "raisecom AC MGMT station table."
    ::= { ruijieAcMgmtSta 1 }

ruijieStaEntry OBJECT-TYPE
    SYNTAX  RuijieStaEntry
    MAX-ACCESS  not-accessible
    STATUS  current
    DESCRIPTION
        "raisecom AC MGMT station entry."
    INDEX   { ruijieStaMacAddr}
    ::= { ruijieStaTable 1 }

RuijieStaEntry ::=
    SEQUENCE {
        ruijieStaMacAddr                MacAddress,
        ruijieStaApMacAddr              MacAddress,
        ruijieStaVlan                   INTEGER,
        ruijieStaWlanId                 INTEGER,
        ruijieStaIp                     IpAddress,
        ruijieStaApIp                   IpAddress,
        ruijieStaApRadioId              INTEGER,
        ruijieStaApRadioType            INTEGER,
        ruijieStaAssoType               INTEGER,
        ruijieStaAuthType               INTEGER,
        ruijieStaRoamTimesPerMin        INTEGER,
        ruijieStaOnTimesPerHour         INTEGER,
        ruijieStaOffTimesPerHour        INTEGER,
        ruijieStaIpv6                   InetAddress,
        ruijieStaAssoAuthMode           INTEGER,
        ruijieStaNetAuthMode            INTEGER,
        ruijieStaSsid                   DisplayString,
        ruijieStaLinkRate               INTEGER,
        ruijieStaCurChan                INTEGER,
        ruijieStaClientType             DisplayString,
        ruijieStaRssi                   INTEGER,
        ruijieStaUserName               DisplayString,
        ruijieStaTerminalType           DisplayString,
        ruijieStaOnlineTime             DisplayString,
        ruijieStaUpTimeInterval         INTEGER,
        ruijieStaUserAuthTime           DisplayString
     }
         
ruijieStaMacAddr  OBJECT-TYPE
    SYNTAX  MacAddress
    MAX-ACCESS  read-only
    STATUS  current
    DESCRIPTION
            "The STA's mac address."
    ::= { ruijieStaEntry 1}

ruijieStaApMacAddr  OBJECT-TYPE
    SYNTAX  MacAddress
    MAX-ACCESS  read-only
    STATUS  current
    DESCRIPTION
            "The  mac address with the AP which the STA attached."
    ::= { ruijieStaEntry 2}

ruijieStaVlan  OBJECT-TYPE
    SYNTAX  INTEGER
    MAX-ACCESS  read-only
    STATUS  current
    DESCRIPTION
            "Vlan id the STA belong to."
    ::= { ruijieStaEntry 3 }

ruijieStaWlanId  OBJECT-TYPE
    SYNTAX  INTEGER
    MAX-ACCESS  read-only
    STATUS  current
    DESCRIPTION
            "Wlan id the STA belong to."
    ::= { ruijieStaEntry 4 }

ruijieStaIp OBJECT-TYPE
    SYNTAX      IpAddress
    MAX-ACCESS  read-only
    STATUS      current
    DESCRIPTION
            "This object represents ip address of the client."
    ::= { ruijieStaEntry 5 }
    
ruijieStaApIp OBJECT-TYPE
    SYNTAX      IpAddress
    MAX-ACCESS  read-only
    STATUS      current
    DESCRIPTION
            "This object represents ip address of AP which the client attaches to."
    ::= { ruijieStaEntry 6 }
    
ruijieStaApRadioId OBJECT-TYPE
    SYNTAX      INTEGER
    MAX-ACCESS  read-only
    STATUS      current
    DESCRIPTION
            "This object represents radio id of AP which the client attaches to."
    ::= { ruijieStaEntry 7 }
    
ruijieStaApRadioType OBJECT-TYPE
    SYNTAX      INTEGER
    MAX-ACCESS  read-only
    STATUS      current
    DESCRIPTION
            "This object represents ip address of AP which the client attaches to."
    ::= { ruijieStaEntry 8 }
    
ruijieStaAssoType OBJECT-TYPE
    SYNTAX      INTEGER
    MAX-ACCESS  read-only
    STATUS      current
    DESCRIPTION
            "This object represents sta's associate type."
    ::= { ruijieStaEntry 9 }
    
ruijieStaAuthType OBJECT-TYPE
    SYNTAX      INTEGER
    MAX-ACCESS  read-only
    STATUS      current
    DESCRIPTION
            "This object represents sta's authentication type."
    ::= { ruijieStaEntry 10 }
    
ruijieStaRoamTimesPerMin  OBJECT-TYPE
    SYNTAX  INTEGER
    MAX-ACCESS  read-only
    STATUS  current
    DESCRIPTION
            "The Sta roaming times in the last minite."
    ::= { ruijieStaEntry 11}
    
ruijieStaOnTimesPerHour  OBJECT-TYPE
    SYNTAX  INTEGER
    MAX-ACCESS  read-only
    STATUS  current
    DESCRIPTION
            "The Sta turn on times in the last hour."
    ::= { ruijieStaEntry 12}
    
ruijieStaOffTimesPerHour  OBJECT-TYPE
    SYNTAX  INTEGER
    MAX-ACCESS  read-only
    STATUS  current
    DESCRIPTION
            "The Sta turn off times in the last hour."
    ::= { ruijieStaEntry 13}

ruijieStaIpv6  OBJECT-TYPE
    SYNTAX  InetAddress
    MAX-ACCESS  read-only
    STATUS  current
    DESCRIPTION
            "The Sta ipv6 address."
    ::= { ruijieStaEntry 14}

ruijieStaAssoAuthMode  OBJECT-TYPE
    SYNTAX  INTEGER {
        open(0),
        wep(1),
        dot1x-wep(2),
        dot1x-wpa(3),
        dot1x-wpa2(4),
        mab(5),
        psk-wpa(6),
        psk-wpa2(7),
        wapi(8)
    }
    MAX-ACCESS  read-only
    STATUS  current
    DESCRIPTION
            "The Sta associate authentication mode."
    ::= { ruijieStaEntry 15}

ruijieStaNetAuthMode  OBJECT-TYPE
    SYNTAX  INTEGER {
        open(0),
        web(1)
    }
    MAX-ACCESS  read-only
    STATUS  current
    DESCRIPTION
            "The Sta's authentication mode after associated."
    ::= { ruijieStaEntry 16}

ruijieStaSsid  OBJECT-TYPE
    SYNTAX  DisplayString
    MAX-ACCESS  read-only
    STATUS  current
    DESCRIPTION
            "This object represents wlan ssid with the sta associated."
    ::= { ruijieStaEntry 17}

ruijieStaLinkRate  OBJECT-TYPE
    SYNTAX  INTEGER
    MAX-ACCESS  read-only
    STATUS  current
    DESCRIPTION
            "This object represents link rate with the sta associated, unit: kbps."
    ::= { ruijieStaEntry 18}

ruijieStaCurChan  OBJECT-TYPE
    SYNTAX  INTEGER
    MAX-ACCESS  read-only
    STATUS  current
    DESCRIPTION
            "The Sta's current channel."
    ::= { ruijieStaEntry 19}

ruijieStaClientType OBJECT-TYPE
    SYNTAX      DisplayString (SIZE (0..64))
    MAX-ACCESS  read-only
    STATUS      current
    DESCRIPTION
         "The sta's type."
    ::= { ruijieStaEntry 20 }

ruijieStaRssi OBJECT-TYPE
    SYNTAX  INTEGER
    MAX-ACCESS  read-only
    STATUS  current
    DESCRIPTION
            "The Sta's current RSSI."
    ::= { ruijieStaEntry 21}
	
ruijieStaUserName  OBJECT-TYPE
    SYNTAX  DisplayString
    MAX-ACCESS  read-only
    STATUS  current
    DESCRIPTION
            "This object represents user name with the sta associated."
    ::= { ruijieStaEntry 22}

ruijieStaTerminalType  OBJECT-TYPE
    SYNTAX  DisplayString
    MAX-ACCESS  read-only
    STATUS  current
    DESCRIPTION
            "This object represents terminal type with the sta associated."
    ::= { ruijieStaEntry 23}
    
ruijieStaOnlineTime  OBJECT-TYPE
    SYNTAX  DisplayString
    MAX-ACCESS  read-only
    STATUS  current
    DESCRIPTION
            "This object represents the time when sta is associated."
    ::= { ruijieStaEntry 24}
    
ruijieStaUpTimeInterval OBJECT-TYPE
    SYNTAX  INTEGER
    MAX-ACCESS  read-only
    STATUS  current
    DESCRIPTION
            "This object represents how long sta is online(in seconds)."
    ::= { ruijieStaEntry 25}
    
ruijieStaUserAuthTime OBJECT-TYPE
    SYNTAX  DisplayString
    MAX-ACCESS  read-only
    STATUS  current
    DESCRIPTION
            "This object represents the time when user is authed(dot1x or webauth)."
    ::= { ruijieStaEntry 26}

-- ****************************************
--
--               Notify nodes
--
-- ****************************************
ruijieNotifyApMac OBJECT-TYPE
    SYNTAX      MacAddress
    MAX-ACCESS  accessible-for-notify
    STATUS      current
    DESCRIPTION
        "Represents the unique identifier of a WTP."
    ::= { ruijieAcMgmtNtfObjects 1 }
    
ruijieNotifyStaMac OBJECT-TYPE
    SYNTAX      MacAddress
    MAX-ACCESS  accessible-for-notify
    STATUS      current
    DESCRIPTION
        "Represents the unique identifier of a STA."
    ::= { ruijieAcMgmtNtfObjects 2 }

ruijieNotifyApIp OBJECT-TYPE
    SYNTAX      IpAddress
    MAX-ACCESS  accessible-for-notify
    STATUS      current
    DESCRIPTION
        "Represents the Ip address of a WTP."
    ::= { ruijieAcMgmtNtfObjects 3 }

ruijieNotifyStaIp OBJECT-TYPE
    SYNTAX      IpAddress
    MAX-ACCESS  accessible-for-notify
    STATUS      current
    DESCRIPTION
        "Represents the Ip of a STA."
    ::= { ruijieAcMgmtNtfObjects 4 }
    
ruijieNotifyStaOperType OBJECT-TYPE
    SYNTAX      INTEGER
    MAX-ACCESS  accessible-for-notify
    STATUS      current
    DESCRIPTION
        "Represents the STA operation, 1-del,2-add,3-roaming,4-ipupdate,5-ipv6update"
    ::= { ruijieAcMgmtNtfObjects 5 }
    
ruijieNotifyStaApRadioId OBJECT-TYPE
    SYNTAX      INTEGER(1..2)
    MAX-ACCESS  accessible-for-notify
    STATUS      current
    DESCRIPTION
        "Represents the radio id which STA attach."
    ::= { ruijieAcMgmtNtfObjects 6 }
    
ruijieNotifyStaApRadioType OBJECT-TYPE
    SYNTAX      INTEGER (1..2)
    MAX-ACCESS  accessible-for-notify
    STATUS      current
    DESCRIPTION
              "1--802.11b
               2--802.11a"
    ::= { ruijieAcMgmtNtfObjects 7 }    
    
ruijieNotifyStaVlanId OBJECT-TYPE
    SYNTAX      INTEGER (1..4094)
    MAX-ACCESS  accessible-for-notify
    STATUS      current
    DESCRIPTION
              "Vlan Id the sta belongs to"
    ::= { ruijieAcMgmtNtfObjects 8 }
    
ruijieNotifyStaWlanId OBJECT-TYPE
    SYNTAX      INTEGER (1..4095)
    MAX-ACCESS  accessible-for-notify
    STATUS      current
    DESCRIPTION
              "Wlan Id the sta belongs to"
    ::= { ruijieAcMgmtNtfObjects 9 }
    
ruijieNotifyAcMBChangeV OBJECT-TYPE
    SYNTAX      INTEGER (1..2)
    MAX-ACCESS  accessible-for-notify
    STATUS      current
    DESCRIPTION
              "1 - Master to backup,
               2 - Backup to master"
    ::= { ruijieAcMgmtNtfObjects 10 }

ruijieNotifyStaOperTimes OBJECT-TYPE
    SYNTAX      INTEGER (1..65535)
    MAX-ACCESS  accessible-for-notify
    STATUS      current
    DESCRIPTION
              "This object present the times when the 
               STA is active, disactive, roaming."
    ::= { ruijieAcMgmtNtfObjects 11 }

ruijieNotifyAcPowerIndex OBJECT-TYPE
    SYNTAX      INTEGER
    MAX-ACCESS  accessible-for-notify
    STATUS      current
    DESCRIPTION
              "This object present the AC's power unit index."
    ::= { ruijieAcMgmtNtfObjects 12 }
    
ruijieNotifyAcPowerStatu OBJECT-TYPE
    SYNTAX      INTEGER
    MAX-ACCESS  accessible-for-notify
    STATUS      current
    DESCRIPTION
              "This object present the AC's power statu, 0-off, 1-on."
    ::= { ruijieAcMgmtNtfObjects 13 }
    
ruijieNotifyTime OBJECT-TYPE
    SYNTAX      DisplayString
    MAX-ACCESS  accessible-for-notify
    STATUS      current
    DESCRIPTION
              "This object present the sta operation current time."
    ::= { ruijieAcMgmtNtfObjects 14 }
    
ruijieNotifyOldVer OBJECT-TYPE
    SYNTAX      DisplayString
    MAX-ACCESS  accessible-for-notify
    STATUS      current
    DESCRIPTION
              "This object present the AP's old version."
    ::= { ruijieAcMgmtNtfObjects 15 }
    
ruijieNotifyNewVer OBJECT-TYPE
    SYNTAX      DisplayString
    MAX-ACCESS  accessible-for-notify
    STATUS      current
    DESCRIPTION
              "This object present the AP's new version."
    ::= { ruijieAcMgmtNtfObjects 16 }

ruijieNotifyVerUpdtReason OBJECT-TYPE
    SYNTAX      INTEGER (1..6)
    MAX-ACCESS  accessible-for-notify
    STATUS      current
    DESCRIPTION
              "This object present the AP's firmware updating fail reason.
                1 -- Image is not ready.
                2 -- AC send image fail.
                3 -- Link down when update ap image.
                4 -- Active image file error.
                5 -- AP response error.
                6 -- AP has image in flash."
    ::= { ruijieAcMgmtNtfObjects 17 }

ruijieNotifyStaIpv6 OBJECT-TYPE
    SYNTAX      InetAddress
    MAX-ACCESS  accessible-for-notify
    STATUS      current
    DESCRIPTION
              "Sta ipv6 address."
    ::= { ruijieAcMgmtNtfObjects 18 }

ruijieNotifyStaAssoAuthMode  OBJECT-TYPE
    SYNTAX  INTEGER {
        open(0),
        wep(1),
        dot1x-wep(2),
        dot1x-wpa(3),
        dot1x-wpa2(4),
        mab(5),
        psk-wpa(6),
        psk-wpa2(7),
        wapi(8)
    }
    MAX-ACCESS  accessible-for-notify
    STATUS  current
    DESCRIPTION
            "The Sta associate authentication mode."
    ::= { ruijieAcMgmtNtfObjects 19}

ruijieNotifyStaNetAuthMode  OBJECT-TYPE
    SYNTAX  INTEGER {
        open(0),
        web(1)
    }
    MAX-ACCESS  accessible-for-notify
    STATUS  current
    DESCRIPTION
            "The Sta's authentication mode after associated."
    ::= { ruijieAcMgmtNtfObjects 20}

ruijieNotifyStaSsid  OBJECT-TYPE
    SYNTAX  DisplayString
    MAX-ACCESS  accessible-for-notify
    STATUS  current
    DESCRIPTION
            "The wlan ssid with the sta associated."
    ::= { ruijieAcMgmtNtfObjects 21}

ruijieNotifyStaLinkRate  OBJECT-TYPE
    SYNTAX  INTEGER
    MAX-ACCESS  accessible-for-notify
    STATUS  current
    DESCRIPTION
            "The link rate with the sta associated, unit: 1kbps."
    ::= { ruijieAcMgmtNtfObjects 22}

ruijieNotifyStaCurChan  OBJECT-TYPE
    SYNTAX  INTEGER
    MAX-ACCESS  accessible-for-notify
    STATUS  current
    DESCRIPTION
            "The Sta current use channel after associated."
    ::= { ruijieAcMgmtNtfObjects 23}

ruijieNotifyStaClientType  OBJECT-TYPE
    SYNTAX  DisplayString
    MAX-ACCESS  accessible-for-notify
    STATUS  current
    DESCRIPTION
            "The Sta's type."
    ::= { ruijieAcMgmtNtfObjects 24}

ruijieNotifyStaRssi OBJECT-TYPE
    SYNTAX  INTEGER
    MAX-ACCESS  accessible-for-notify
    STATUS  current
    DESCRIPTION
            "The Sta's RSSI."
    ::= { ruijieAcMgmtNtfObjects 25}

ruijieNotifyStaReason OBJECT-TYPE
    SYNTAX  DisplayString
    MAX-ACCESS  accessible-for-notify
    STATUS  current
    DESCRIPTION
            "The Sta's down reason."
    ::= { ruijieAcMgmtNtfObjects 26}
    
ruijieNotifyStaTimestamp OBJECT-TYPE
    SYNTAX  INTEGER
    MAX-ACCESS  accessible-for-notify
    STATUS  current
    DESCRIPTION
            "Seconds since device bootup when this trap is sent."
    ::= { ruijieAcMgmtNtfObjects 27}
    
ruijieNotifyStaOnlineTimeval OBJECT-TYPE
    SYNTAX  INTEGER
    MAX-ACCESS  accessible-for-notify
    STATUS  current
    DESCRIPTION
            "Sta's total online time in seconds."
    ::= { ruijieAcMgmtNtfObjects 28}
    
ruijieNotifyStaIpv4Upflow OBJECT-TYPE
    SYNTAX  INTEGER
    MAX-ACCESS  accessible-for-notify
    STATUS  current
    DESCRIPTION
            "Sta's total IPv4 upflow in kbps."
    ::= { ruijieAcMgmtNtfObjects 29}
    
ruijieNotifyStaIpv4Downflow OBJECT-TYPE
    SYNTAX  INTEGER
    MAX-ACCESS  accessible-for-notify
    STATUS  current
    DESCRIPTION
            "Sta's total IPv4 downflow in kbps."
    ::= { ruijieAcMgmtNtfObjects 30}

ruijieNotifyMicroApSlot OBJECT-TYPE
    SYNTAX      INTEGER
    MAX-ACCESS  accessible-for-notify
    STATUS      current
    DESCRIPTION
        "Micro Ap Slot Id"
    ::= { ruijieAcMgmtNtfObjects 31 }

ruijieNotifyMicroApEvent OBJECT-TYPE
    SYNTAX      INTEGER
    MAX-ACCESS  accessible-for-notify
    STATUS      current
    DESCRIPTION
        "Micro Ap Event: 1---up 2---down"
    ::= { ruijieAcMgmtNtfObjects 32 }
	
ruijieNotifyApTimeStampFail NOTIFICATION-TYPE
    OBJECTS     {
                  ruijieNotifyApMac
                }
    STATUS      current
    DESCRIPTION
        "This notification is sent by the AC when an AP sync the time failed."
    ::= { ruijieAcMgmtNotifications 1 }

ruijieNotifyStaOper NOTIFICATION-TYPE
    OBJECTS     {
                  ruijieNotifyApMac,
                  ruijieNotifyStaMac,
                  ruijieNotifyApIp,
                  ruijieNotifyStaIp,
                  ruijieNotifyStaOperType,
                  ruijieNotifyStaApRadioId,
                  ruijieNotifyStaApRadioType,
                  ruijieNotifyStaVlanId,
                  ruijieNotifyStaWlanId,
                  ruijieNotifyTime,
                  ruijieNotifyStaIpv6,
                  ruijieNotifyStaAssoAuthMode,
                  ruijieNotifyStaNetAuthMode,
                  ruijieNotifyStaSsid,
                  ruijieNotifyStaLinkRate,
                  ruijieNotifyStaCurChan,
                  ruijieNotifyStaClientType,
                  ruijieNotifyStaRssi,
                  ruijieNotifyStaReason
                }
    STATUS      current
    DESCRIPTION
        "This notification is sent by the AC when a sta enter or quit or ip update."
    ::= { ruijieAcMgmtNotifications 2 }

ruijieNotifyAcMBChange NOTIFICATION-TYPE
    OBJECTS     {
                  ruijieNotifyAcMBChangeV
                }
    STATUS      current
    DESCRIPTION
        "This notification is sent by the AC change from 
         smaster to backup or backup to master."
    ::= { ruijieAcMgmtNotifications 3 }

ruijieNotifyApSwUpdtFail NOTIFICATION-TYPE
    OBJECTS     {
                  ruijieNotifyApMac,
                  ruijieNotifyOldVer,
                  ruijieNotifyNewVer,
                  ruijieNotifyVerUpdtReason
                }
    STATUS      current
    DESCRIPTION
        "This notification is sent by the AC when update the AP software failed."
    ::= { ruijieAcMgmtNotifications 4 }

ruijieNotifyStaActOverThredhold NOTIFICATION-TYPE
    OBJECTS     {
                  ruijieNotifyApMac,
                  ruijieNotifyStaMac,
                  ruijieNotifyStaApRadioId,
                  ruijieNotifyStaApRadioType,
                  ruijieNotifyStaOperTimes
                }
    STATUS      current
    DESCRIPTION
        "This notification is sent by the AC when a sta active times over thredhold."
    ::= { ruijieAcMgmtNotifications 5 }

ruijieNotifyStaDisactOverThredhold NOTIFICATION-TYPE
    OBJECTS     {
                  ruijieNotifyApMac,
                  ruijieNotifyStaMac,
                  ruijieNotifyStaApRadioId,
                  ruijieNotifyStaApRadioType,
                  ruijieNotifyStaOperTimes
                }
    STATUS      current
    DESCRIPTION
        "This notification is sent by the AC when a sta's disactive times over thredhold."
    ::= { ruijieAcMgmtNotifications 6 }

ruijieNotifyStaRoamTotal NOTIFICATION-TYPE
    OBJECTS     {
                  ruijieNotifyApMac,
                  ruijieNotifyStaMac,
                  ruijieNotifyStaApRadioId,
                  ruijieNotifyStaApRadioType,
                  ruijieNotifyStaOperTimes
                }
    STATUS      current
    DESCRIPTION
        "This notification is sent by the AC when a sta's total 
         roaming times over thredhold ."
    ::= { ruijieAcMgmtNotifications 7 }

ruijieNotifyStaRoamPerMin NOTIFICATION-TYPE
    OBJECTS     {
                  ruijieNotifyApMac,
                  ruijieNotifyStaMac,
                  ruijieNotifyStaApRadioId,
                  ruijieNotifyStaApRadioType,
                  ruijieNotifyStaOperTimes
                }
    STATUS      current
    DESCRIPTION
        "This notification is sent by the AC when a sta's 
         roaming times per minite over thredhold ."
    ::= { ruijieAcMgmtNotifications 8 }

ruijieNotifyAcPowerStatus NOTIFICATION-TYPE
    OBJECTS     {
                  ruijieNotifyAcPowerIndex,
                  ruijieNotifyAcPowerStatu
                }
    STATUS      current
    DESCRIPTION
        "This notification is sent by the AC when the 
         AC's power unit status changed."
    ::= { ruijieAcMgmtNotifications 9 }

ruijieNotify86PowerOffAlarm NOTIFICATION-TYPE
    OBJECTS     {
                  ruijieNotifyAcPowerIndex
                }
    STATUS      current
    DESCRIPTION
        "This notification is sent by the 86 power off."
    ::= { ruijieAcMgmtNotifications 10 }

ruijieNotify86PowerOffAlarmClear NOTIFICATION-TYPE
    OBJECTS     {
                  ruijieNotifyAcPowerIndex
                }
    STATUS      current
    DESCRIPTION
        "This notification is sent by the 86 power on."
    ::= { ruijieAcMgmtNotifications 11 }

ruijieNotifyApSwUpdtSuccess NOTIFICATION-TYPE
    OBJECTS     {
                  ruijieNotifyApMac,
                  ruijieNotifyOldVer,
                  ruijieNotifyNewVer
                }
    STATUS      current
    DESCRIPTION
        "This notification is sent by the AC when update the AP software success."
    ::= { ruijieAcMgmtNotifications 12 }

ruijieNotifyApUp NOTIFICATION-TYPE
    OBJECTS     {
                  ruijieApMacAddr,
                  capwapBaseNtfChannelType,
                  capwapBaseNtfAuthenMethod
                }
    STATUS      current
    DESCRIPTION
        "This notification is sent by the AC when a CAPWAP channel
         established."
    ::= { ruijieAcMgmtNotifications 13 }

ruijieNotifyApDown NOTIFICATION-TYPE
    OBJECTS     {
                  ruijieApMacAddr,
                  capwapBaseNtfChannelType,
                  capwapBaseNtfChannelDownReason
                }
    STATUS      current
    DESCRIPTION
        "This notification is sent by the AC when CAPWAP channel
         becomes down."
    ::= { ruijieAcMgmtNotifications 14 }

ruijieNotifyApSwUpdtFailApMac NOTIFICATION-TYPE
    OBJECTS     {
                  ruijieApMacAddr,
                  ruijieNotifyOldVer,
                  ruijieNotifyNewVer,
                  ruijieNotifyVerUpdtReason
                }
    STATUS      current
    DESCRIPTION
        "This notification is sent by the AC when update the AP software failed."
    ::= { ruijieAcMgmtNotifications 15 }

ruijieNotifyApTimeStampFailApMac NOTIFICATION-TYPE
    OBJECTS     {
                  ruijieApMacAddr
                }
    STATUS      current
    DESCRIPTION
        "This notification is sent by the AC when an AP sync the time failed."
    ::= { ruijieAcMgmtNotifications 16 }
    
ruijieNotifyStaOperAlternate NOTIFICATION-TYPE
    OBJECTS     {
                  ruijieNotifyStaOperType,
                  ruijieNotifyStaMac,
                  ruijieNotifyStaIp,
                  ruijieNotifyApMac,
                  ruijieNotifyApIp,
                  ruijieNotifyStaApRadioId,
                  ruijieNotifyStaApRadioType,
                  ruijieNotifyStaWlanId,
                  ruijieNotifyStaSsid,
                  ruijieNotifyStaVlanId,
                  ruijieNotifyStaLinkRate,
                  ruijieNotifyStaCurChan,
                  ruijieNotifyStaRssi,
                  ruijieNotifyStaTimestamp,
                  ruijieNotifyStaOnlineTimeval,
                  ruijieNotifyStaIpv4Upflow,
                  ruijieNotifyStaIpv4Downflow
                }
    STATUS      current
    DESCRIPTION
        "This notification is sent by the AC when a sta is up, down or roaming."
    ::= { ruijieAcMgmtNotifications 17 }

ruijieNotifyNonrootOper NOTIFICATION-TYPE
    OBJECTS     {
                  ruijieNotifyStaOperType,
                  ruijieNotifyStaMac,
                  ruijieNotifyApMac,
                  ruijieNotifyStaApRadioId,
                  ruijieNotifyStaTimestamp
                }
    STATUS      current
    DESCRIPTION
        "This notification is sent by the AC when a Nonroot is attach or leave."
    ::= { ruijieAcMgmtNotifications 18 }

ruijieNotifyMicroApAction NOTIFICATION-TYPE
    OBJECTS     {
                  ruijieNotifyApMac,
                  ruijieNotifyMicroApSlot,
                  ruijieNotifyMicroApEvent
                }
    STATUS      current
    DESCRIPTION
        "This notification when Micro Ap up or down."
    ::= { ruijieAcMgmtNotifications 19 }
	
--********************************************************************
--                                                                  **
--           conformance information                                **
--                                                                  **
--********************************************************************
ruijieAcMgmtAcMIBConformance OBJECT IDENTIFIER ::= { ruijieAcMgmtMIB 7 }
ruijieAcMgmtAcMIBCompliances OBJECT IDENTIFIER ::= { ruijieAcMgmtAcMIBConformance 1 }
ruijieAcMgmtAcMIBGroups      OBJECT IDENTIFIER ::= { ruijieAcMgmtAcMIBConformance 2 }


--********************************************************************
--                                                                  **
--           compliance statements                                  **
--                                                                  **
--********************************************************************
ruijieAcMgmtAcMIBCompliance MODULE-COMPLIANCE
        STATUS  current
        DESCRIPTION
                "The compliance statement for entities which implement
                the Raisecom Ac Manager Ac"
        MODULE  -- this module
                MANDATORY-GROUPS { ruijieAcMgmtAcMIBGroup, ruijieAcMgmtAcTrapGroup }
        ::= { ruijieAcMgmtAcMIBCompliances 1 }
        

--********************************************************************
--                                                                  **
--           units of conformance                                   **
--                                                                  **
--********************************************************************
ruijieAcMgmtAcMIBGroup OBJECT-GROUP
        OBJECTS {
            ruijieAcStaLimit,
            ruijieAcWtpLimit,
            ruijieAcRMacField,
            ruijieAcDataDtls,
            ruijieAcEcnSupport,
            ruijieAcBackAcIp,
            ruijieAcMtu,
            ruijieAcAcName,
            ruijieAcLocation,
            ruijieAcResetAp,
            ruijieAcApNum,
            ruijieAc80211aRateType,
            ruijieAc80211bRateType,
            ruijieAcFallback,
            ruijieAcStaNum,
            ruijieAcMacAddr,
            ruijieAcDescriptor,
            ruijieAcPID,
            ruijieAcHwId,
            ruijieAcSN,
            ruijieAcTemp,
            ruijieAcAPUpDownCtrl,
            ruijieAcAPJoinFailCtrl,
            ruijieAcAPDecryEroReportCtrl,
            ruijieAcApImageUpdtCtrl,
            ruijieAcApConfigMsgEroCtrl,
            ruijieAcApRadioOperStatuCtrl,
            ruijieAcApAuthenFailCtrl,
            ruijieAcApTimestampCtrl,
            ruijieAcStaOperCtrl,
            ruijieAcType,
            ruijieAcNeid,
            ruijieAcManufacturer,
            ruijieAcSwVer,
            ruijieAcSwManufacturer,
            ruijieAcStaResourceNotEnough,
            ruijieAcPppoeClientAct,
            ruijieAcPppoeClientMax,
            ruijieAcStaActThredhold,
            ruijieAcStaDisactThredhold,
            ruijieAcStaTotalRoamThredhold,
            ruijieAcStaPerRoamThredhold,
            ruijieAcStaOffLineRemainTime,
            ruijieAcStaOffLineNumber,
            ruijieAcStaOffLineDelSingle,
            ruijieAcStaOffLineDelAll,
            ruijieAcRmOffLineApConfig,
            ruijieAcFlowBlApName1,
            ruijieAcFlowBlApName2,
            ruijieAcFlowBlApName3,
            ruijieAcFlowBlApName4,
            ruijieAcFlowBlApName5,
            ruijieAcFlowBlApName6,
            ruijieAcFlowBlApName7,
            ruijieAcFlowBlApName8,
            ruijieAcFlowBlApName9,
            ruijieAcFlowBlApName10,
            ruijieAcFlowBlNum,
            ruijieAcFlowBlRS,
            ruijieAcNumBlApName1,
            ruijieAcNumBlApName2,
            ruijieAcNumBlApName3,
            ruijieAcNumBlApName4,
            ruijieAcNumBlApName5,
            ruijieAcNumBlApName6,
            ruijieAcNumBlApName7,
            ruijieAcNumBlApName8,
            ruijieAcNumBlApName9,
            ruijieAcNumBlApName10,
            ruijieAcNumBlNum,
            ruijieAcNumBlRS,
            ruijieAcInAcRoamNum,
            ruijieAcBetweenAcRoamInNum,
            ruijieAcStaOnOverThrodOperCtrl,
            ruijieAcStaOffOverThrodOperCtrl,
            ruijieAcBetweenAcRoamOutNum,
            ruijieAcCpusageSwitch,
            ruijieAcCpuUsageTrapTimer,
            ruijieAcStatTrapTimer,
            ruijieAcHeartBeat,
            ruijieAcTotalApSupNum,
            ruijieAcTotalStaSupNum,
            ruijieAcTotalPppoeSupNum,
            ruijieAcCurTotalApSupNum,
            ruijieAcCurTotalStaSupNum,
            ruijieAcCurTotalPppoeSupNum,
            ruijieAcNasId,
            ruijieAcStaLimitLicense,
            ruijieAcWtpLimitLicense,
            ruijieAcStaIpv6Num,
            ruijieAcIpv6,
            ruijieAcIpv6Prefix,
            ruijieAcIpv6Type,
            ruijieAcIpv6AddrType,
            ruijieApApName,
            ruijieApApgName,
            ruijieApDiscTimer,
            ruijieApEchoReqTimer,
            ruijieApEroReportTimer,
            ruijieApStaTimeoutTimer,
            ruijieApStatisticsTimer,
            ruijieApFallback,
            ruijieApImageId,
            ruijieApIpDhcp,
            ruijieApLocation,
            ruijieApWpsMfp,
            ruijieApLastRebootReason,
            ruijieApEthernetIfName,
            ruijieApEthernetIfMacAddress,
            ruijieApEthernetIfAdminStatus,
            ruijieApEthernetIfOperStatus,
            ruijieApEthernetIfRxUcastPkts,
            ruijieApEthernetIfRxNUcastPkts,
            ruijieApEthernetIfTxUcastPkts,
            ruijieApEthernetIfTxNUcastPkts,
            ruijieApEthernetIfDuplex,
            ruijieApEthernetIfLinkSpeed,
            ruijieApEthernetIfPOEPower,
            ruijieApAdminStatus,
            ruijieApEthernetIfRxBoardPkts,
            ruijieApEthernetIfRxMultiPkts,
            ruijieApEthernetIfTxBoardPkts,
            ruijieApEthernetIfTxMultiPkts,
            ruijieApEthernetIfDropPkts,
            ruijieApSn,
            ruijieApIp,
            ruijieApStaNum,
            ruijieApToFat,
            ruijieApId,
            ruijieApSwVer,
            ruijieApBootVer,
            ruijieApPID,
            ruijieApHwVer,
            ruijieApStaLimit,
            ruijieApFactoryDefault,
            ruijieApCpuUsageTrapTimer,
            ruijieApStatTrapTimer,
            ruijieApLinkOnTimeInterval,
            ruijieApNetId,
            ruijieApUptime,
            ruijieApOfftime,
            ruijieApState,
            ruijieApNasId,
            ruijieApCoverArea,
            ruijieApLinkOnTimeIntervalMs,
            ruijieApUptimeMs,
            ruijieApHbUptimeMs,
            ruijieApIpv6,
            ruijieApIpv6Prefix,
            ruijieApIpv6PrefixLen,
            ruijieApIpv6Type,
            ruijieApIpv6Gateway,
            ruijieApIpv6StaNum,
            ruijieApMacAddrColon,
            ruijieApMacAddrLine,
            ruijieApMacAddrDot,
            ruijieApRadioEn,
            ruijieApTxPower,
            ruijieApDtimPeriod,
            ruijieApBeaconPeriod,
            ruijieApCountry,
            ruijieApPreaShort,
            ruijieApRadioBssid,
            ruijieApTxPowerLevel,
            ruijieApTxPowerGlobal,
            ruijieApCurChan,
            ruijieApRfGlobal,
            ruijieApRadioRateType,
            ruijieApRadioType,
            ruijieApRadio11bSup,
            ruijieApMaxTxPower,
            ruijieApMinTxPower,
            ruijieApCurTxPower,
            ruijieApMaxTxPowerPer,
            ruijieApMinTxPowerPer,
            ruijieApIpAddr,
            ruijieApIpMask,
            ruijieApIpGetway,
            ruijieApStaticIpRS,
            ruijieApgDiscTimer,
            ruijieApgEchoReqTimer,
            ruijieApgEroReportTimer,
            ruijieApgStaTimeoutTimer,
            ruijieApgStatisticsTimer,
            ruijieApgFallback,
            ruijieApgImageId,
            ruijieApgCreatEn,
            ruijieApgEnableRadioEn,
            ruijieApgWlanId,
            ruijieApgVlanId,
            ruijieApgWlanIntfMapRS,
            ruijieWlanShort,
            ruijieWlanSpctMgmt,
            ruijieWlanEnQos,
            ruijieWlanShortSlotTime,
            ruijieWlanEnableApsd,
            ruijieWlanAckType,
            ruijieWlanTunnelType,
            ruijieWlanBroadSsid,
            ruijieWlanWlanSsid,
            ruijieWlanWlanProfile,
            ruijieWlanCreateMapRS,
            ruijieWlanRts,
            ruijieWlanShortTry,
            ruijieWlanLongTry,
            ruijieWlanStaNum,
            ruijieWlanNasId,
            ruijieWlanChanV,
            ruijieWlanChanBandEn,
            ruijieWlanLimitChanRS,
            ruijieWlanChanBandRS,
            ruijieStaApMacAddr,
            ruijieStaVlan,
            ruijieStaWlanId,
            ruijieStaIp,
            ruijieStaApIp,
            ruijieStaApRadioId,
            ruijieStaApRadioType,
            ruijieStaAssoType,
            ruijieStaAuthType,
            ruijieStaRoamTimesPerMin,
            ruijieStaOnTimesPerHour,
            ruijieStaOffTimesPerHour,
            ruijieNotifyApMac,
            ruijieNotifyStaMac,
            ruijieNotifyApIp,
            ruijieNotifyStaIp,
            ruijieNotifyStaOperType,
            ruijieNotifyStaApRadioId,
            ruijieNotifyStaApRadioType,
            ruijieNotifyStaVlanId,
            ruijieNotifyStaWlanId,
            ruijieNotifyTime,
            ruijieNotifyOldVer,
            ruijieNotifyNewVer,
            ruijieNotifyVerUpdtReason,
            ruijieNotifyAcMBChangeV,
            ruijieNotifyStaOperTimes,
            ruijieNotifyAcPowerIndex,
            ruijieNotifyAcPowerStatu,
            ruijieAcKickClient,
            ruijieAcOpenStaNum,
            ruijieAcOpenStaAbnormalDownTimes,
            ruijieAcWepPskStaNum,
            ruijieAcWepPskStaAbnormalDownTimes
        }
        STATUS  current
        DESCRIPTION
                "A collection of objects providing ac manager (echo) ability to a
                Raisecom agent."
        ::= { ruijieAcMgmtAcMIBGroups 1 }

ruijieAcMgmtAcTrapGroup NOTIFICATION-GROUP
    NOTIFICATIONS {
        ruijieNotifyApTimeStampFail,
        ruijieNotifyStaOper,
        ruijieNotifyAcMBChange,
        ruijieNotifyApSwUpdtFail,
        ruijieNotifyStaActOverThredhold,
        ruijieNotifyStaDisactOverThredhold,
        ruijieNotifyStaRoamTotal,
        ruijieNotifyStaRoamPerMin,
        ruijieNotifyAcPowerStatus,
        ruijieNotify86PowerOffAlarm,
        ruijieNotify86PowerOffAlarmClear,
        ruijieNotifyApSwUpdtSuccess,
        ruijieNotifyApUp,
        ruijieNotifyApDown,
        ruijieNotifyApSwUpdtFailApMac,
        ruijieNotifyApTimeStampFailApMac
        }
    STATUS  current
    DESCRIPTION
        "A collection of traps providing ac manager (echo) ability to a
         Raisecom agent."
    ::= { ruijieAcMgmtAcMIBGroups 2 }
    
END
