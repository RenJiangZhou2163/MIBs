-- *****************************************************************
-- RAISECOM-SYSTEM-MIB.mib:  Raisecom System MIB file
--
-- Feb 2012, HuangY
--
-- Copyright (c) 2012 by Raisecom Networks Co.,Ltd.
-- All rights reserved.
-- 
-- *****************************************************************
--

RAISECOM-TEMP-FAN-MIB DEFINITIONS ::= BEGIN

IMPORTS
        MODULE-IDENTITY,
        OBJECT-TYPE,
        NOTIFICATION-TYPE,
        Integer32
               FROM SNMPv2-SMI
        MODULE-COMPLIANCE
               FROM SNMPv2-CONF
        ruijieMgmt
                FROM RAISECOM-SMI
        ruijieSystemTemperatureCurrent
                FROM RAISECOM-SYSTEM-MIB;

ruijieTempFanMIB MODULE-IDENTITY
        LAST-UPDATED "200203200000Z"
        ORGANIZATION "Raisecom Networks Co.,Ltd."
        CONTACT-INFO
                " 
                Tel: 4008-111-000 

                E-mail: service@raisecom.com.cn"
        DESCRIPTION
                "This module defines raisecom system mibs."
        REVISION      "200203200000Z"
        DESCRIPTION
                "Initial version of this MIB module."
        ::= { ruijieMgmt 109}

ruijieTempFanTraps OBJECT IDENTIFIER ::= { ruijieTempFanMIB 1 }

--Temperature Too High Trap
temperatureTooHighTrap NOTIFICATION-TYPE
        OBJECTS   {ruijieSystemTemperatureCurrent}
        STATUS     current
        DESCRIPTION
                "Temperature Too High warning and report the current temperature."
        ::= { ruijieTempFanTraps 1 }   
           
--Temperature Too High Recover Trap 
temperTooHighRecovTrap NOTIFICATION-TYPE
        OBJECTS   {ruijieSystemTemperatureCurrent}
        STATUS     current
        DESCRIPTION
                "Clear the warning of temperature too high and report the current temperature."
        ::= { ruijieTempFanTraps 2 }

--Fan Failure Trap
fanFailure NOTIFICATION-TYPE
        STATUS     current
        DESCRIPTION
                "Fan stopped warning."
        ::= { ruijieTempFanTraps 3 }
  
END
