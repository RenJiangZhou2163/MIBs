-- *****************************************************************
-- RAISECOM-SOFTWARE-SMI.mib: Raisecom SOFTWARE SMI File
-- 
-- Aug. 2014, panshiyong
--
-- Copyright (c) 2014 by Raisecom Networks Co.,Ltd.
-- All rights reserved.
-- 
-- *****************************************************************
--

RAISECOM-SOFTWARE-SMI DEFINITIONS ::= BEGIN

IMPORTS
        MODULE-IDENTITY,
        OBJECT-IDENTITY
                FROM SNMPv2-SMI
        products
                FROM RAISECOM-SMI;
                
software OBJECT IDENTIFIER ::= { products 7 }

softwareMib MODULE-IDENTITY
        LAST-UPDATED "201408190000Z"
        ORGANIZATION "Raisecom Networks Co.,Ltd."
        CONTACT-INFO
                " 
                Tel: 4008-111-000 

                E-mail: service@raisecom.com.cn"
        DESCRIPTION
                "The Structure of Management Information for the
                 Raisecom enterprise."
        REVISION      "201005250000Z"
        DESCRIPTION
                "Initial version of this MIB module."
        ::= { software 1 }        

ruijieSoftwareProducts OBJECT-IDENTITY
        STATUS  current
        DESCRIPTION
                "ruijieSoftwareProducts is the root OBJECT IDENTIFIER from
                 which sysObjectID values are assigned for software.  Actual
                 values are defined in RAISECOM-PRODUCTS-MIB."
        ::= { softwareMib 1 }
        
END
