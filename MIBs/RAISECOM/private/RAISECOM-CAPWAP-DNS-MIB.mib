-- *******************************************************************
-- RAISECOM-CAPWAP-DNS-MIB.mib : Raisecom DNS MIB 
-- 
-- Jun 2010, chenfg1
--
-- Copyright (c) 2010 by Raisecom Networks Co.,Ltd.
-- All rights reserved.
-- *******************************************************************
--
RAISECOM-CAPWAP-DNS-MIB DEFINITIONS ::= BEGIN

IMPORTS 
        MODULE-IDENTITY, 
        OBJECT-TYPE,
		    Integer32,
	      NOTIFICATION-TYPE,	
        Unsigned32,
        IpAddress
                FROM SNMPv2-SMI
        OBJECT-GROUP,
        MODULE-COMPLIANCE
                FROM SNMPv2-CONF
        TruthValue,
        RowStatus,
        DisplayString
                FROM SNMPv2-TC 
        ruijieMgmt
                FROM RAISECOM-SMI
        ruijieIfIndex 
                FROM RAISECOM-INTERFACE-MIB;


ruijieCapwapDnsMIB   MODULE-IDENTITY
       LAST-UPDATED    "201007090000Z"
       ORGANIZATION    "Raisecom Networks Co.,Ltd."
       CONTACT-INFO  
                " 
                Tel: 4008-111-000 

                E-mail: service@raisecom.com.cn"

        DESCRIPTION             
                "This is DNS MIB"
        
        REVISION      "201007090000Z"
        DESCRIPTION
                "Initial version of this MIB module. "
        ::= { ruijieMgmt 88 }


ruijieCapwapDnsMIBObjects OBJECT IDENTIFIER 
    ::= { ruijieCapwapDnsMIB 0 }

ruijieCapwapDnsGlobalConfig OBJECT IDENTIFIER
	::= { ruijieCapwapDnsMIBObjects 1 }


--*************************************************
--DNS Global Config
--*************************************************

ruijieLDnsFirstServer     OBJECT-TYPE
	SYNTAX	                IpAddress
	MAX-ACCESS              read-write
	STATUS	                current
	DESCRIPTION
	     "The first dns server address."
	::= { ruijieCapwapDnsGlobalConfig  1 }
	
ruijieLDnsSecondServer    OBJECT-TYPE
	SYNTAX	                IpAddress
	MAX-ACCESS              read-write
	STATUS	                current
	DESCRIPTION
	     "The second dns server address."
	::= { ruijieCapwapDnsGlobalConfig  2 }



ruijieCapwapDnsMIBConformance OBJECT IDENTIFIER ::= { ruijieCapwapDnsMIB 2 }
ruijieCapwapDnsMIBCompliances OBJECT IDENTIFIER ::= { ruijieCapwapDnsMIBConformance 1 }
ruijieCapwapDnsMIBGroups      OBJECT IDENTIFIER ::= { ruijieCapwapDnsMIBConformance 2 }

-- compliance statements

ruijieCapwapDnsMIBCompliance MODULE-COMPLIANCE
        STATUS  current
        DESCRIPTION
                "The compliance statement for entities which implement
                the Raisecom Capwap Dns MIB"
        MODULE  -- this module
        MANDATORY-GROUPS { 
              ruijieCapwapDnsMIBGroup
        }
        ::= { ruijieCapwapDnsMIBCompliances 1 }

-- units of conformance

ruijieCapwapDnsMIBGroup OBJECT-GROUP
        OBJECTS {
              ruijieLDnsFirstServer,
	      ruijieLDnsSecondServer
        }
        STATUS  current
        DESCRIPTION
                "A collection of objects providing capwap dns information and
                opertion to a Raisecom agent."
        ::= { ruijieCapwapDnsMIBGroups 1 } 
		
END
