-- ===================================================================
-- Copyright (C) 2017 by HUAWEI TECHNOLOGIES. All rights reserved.
-- Description: The HUAWEI-SECURITY-CONFIG-MIB contains Changes of the configuration.
-- Reference:Huawei Enterprise MIB
-- Version: V1.00
-- ===================================================================

	HUAWEI-SECURITY-CONFIG-MIB DEFINITIONS ::= BEGIN
 
		IMPORTS
			enterprises			
				FROM RFC1155-SMI			
			OBJECT-GROUP, NOTIFICATION-GROUP			
				FROM SNMPv2-CONF			
			OBJECT-TYPE, MODULE-IDENTITY, NOTIFICATION-TYPE			
				FROM SNMPv2-SMI;
	
	
		-- 1.3.6.1.4.1.2011.6.122.83
		hwSecurityConfig MODULE-IDENTITY 
			LAST-UPDATED "201705161458Z"		-- May 16, 2017 at 14:58 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"The HUAWEI-SECURITY-CONFIG-MIB contains Changes of the configuration."
			REVISION "201705161458Z"		-- May 16, 2017 at 14:58 GMT
			DESCRIPTION 
				"The HUAWEI-SECURITY-CONFIG-MIB contains Changes of the configuration."
			::= { hwSecurity 83 }

		
	
--
-- Node definitions
--
	
--  1.3.6.1.4.1.2011.6.122.83
-- May 16, 2017 at 14:58 GMT
-- May 17, 2017 at 11:10 GMT
-- 
-- Node definitions
-- 
-- 1.3.6.1.4.1.2011
		-- 1.3.6.1.4.1.2011
		huawei OBJECT IDENTIFIER ::= { enterprises 2011 }

		
--  1.3.6.1.4.1.2011.6
		-- 1.3.6.1.4.1.2011.6
		huaweiUtility OBJECT IDENTIFIER ::= { huawei 6 }

		
--  1.3.6.1.4.1.2011.6.122
		-- 1.3.6.1.4.1.2011.6.122
		hwSecurity OBJECT IDENTIFIER ::= { huaweiUtility 122 }

		
--  1.3.6.1.4.1.2011.6.122.83.1
		-- 1.3.6.1.4.1.2011.6.122.83.1
		hwSecurityConfigTrap OBJECT IDENTIFIER ::= { hwSecurityConfig 1 }

		
--  1.3.6.1.4.1.2011.6.122.83.1.1
		-- 1.3.6.1.4.1.2011.6.122.83.1.1
		hwSecurityConfigObjects OBJECT IDENTIFIER ::= { hwSecurityConfigTrap 1 }

		
--  1.3.6.1.4.1.2011.6.122.83.1.1.1
		-- 1.3.6.1.4.1.2011.6.122.83.1.1.1
		hwSecConfigChangeUser OBJECT-TYPE
			SYNTAX OCTET STRING (SIZE (0..255))
			MAX-ACCESS accessible-for-notify
			STATUS current
			DESCRIPTION
				"The user of modify the configuration."
			::= { hwSecurityConfigObjects 1 }

		
--  1.3.6.1.4.1.2011.6.122.83.1.1.2
		-- 1.3.6.1.4.1.2011.6.122.83.1.1.2
		hwSecConfigChangeTerminalIP OBJECT-TYPE
			SYNTAX OCTET STRING (SIZE (0..255))
			MAX-ACCESS accessible-for-notify
			STATUS current
			DESCRIPTION
				"User ip."
			::= { hwSecurityConfigObjects 2 }

		
--  1.3.6.1.4.1.2011.6.122.83.1.1.3
		-- 1.3.6.1.4.1.2011.6.122.83.1.1.3
		hwSecConfigChangeVsys OBJECT-TYPE
			SYNTAX OCTET STRING (SIZE (0..255))
			MAX-ACCESS accessible-for-notify
			STATUS current
			DESCRIPTION
				"Vsys name."
			::= { hwSecurityConfigObjects 3 }

		
--  1.3.6.1.4.1.2011.6.122.83.1.1.4
		-- 1.3.6.1.4.1.2011.6.122.83.1.1.4
		hwSecConfigChangeModuleType OBJECT-TYPE
			SYNTAX OCTET STRING (SIZE (0..255))
			MAX-ACCESS accessible-for-notify
			STATUS current
			DESCRIPTION
				"The moudle of configuration changed."
			::= { hwSecurityConfigObjects 4 }

		
--  1.3.6.1.4.1.2011.6.122.83.1.1.5
		-- 1.3.6.1.4.1.2011.6.122.83.1.1.5
		hwSecConfigChangeModuleObject OBJECT-TYPE
			SYNTAX OCTET STRING (SIZE (0..255))
			MAX-ACCESS accessible-for-notify
			STATUS current
			DESCRIPTION
				"the object name of configuration changed ."
			::= { hwSecurityConfigObjects 5 }

		
--  1.3.6.1.4.1.2011.6.122.83.1.1.6
		-- 1.3.6.1.4.1.2011.6.122.83.1.1.6
		hwSecConfigChangeAction OBJECT-TYPE
			SYNTAX OCTET STRING (SIZE (0..255))
			MAX-ACCESS accessible-for-notify
			STATUS current
			DESCRIPTION
				"The action of the Configuration changed."
			::= { hwSecurityConfigObjects 6 }

		
--  1.3.6.1.4.1.2011.6.122.83.1.1.7
		-- 1.3.6.1.4.1.2011.6.122.83.1.1.7
		hwSecConfigChangeTargetObject OBJECT-TYPE
			SYNTAX OCTET STRING (SIZE (0..255))
			MAX-ACCESS accessible-for-notify
			STATUS current
			DESCRIPTION
				"The name of target object."
			::= { hwSecurityConfigObjects 7 }

		
--  1.3.6.1.4.1.2011.6.122.83.1.2
		-- 1.3.6.1.4.1.2011.6.122.83.1.2
		hwSecurityConfigChange OBJECT IDENTIFIER ::= { hwSecurityConfigTrap 2 }

		
--  1.3.6.1.4.1.2011.6.122.83.1.2.1
		-- 1.3.6.1.4.1.2011.6.122.83.1.2.1
		hwSecurityConfigChangeNotify NOTIFICATION-TYPE
			OBJECTS { hwSecConfigChangeUser, hwSecConfigChangeTerminalIP, hwSecConfigChangeVsys, hwSecConfigChangeModuleType , hwSecConfigChangeModuleObject, 
                                                                                      hwSecConfigChangeAction, hwSecConfigChangeTargetObject }
			STATUS current
			DESCRIPTION 
				"The trap of configuration changed."
			::= { hwSecurityConfigChange 1 }

		
--  1.3.6.1.4.1.2011.6.122.83.1.3
		-- 1.3.6.1.4.1.2011.6.122.83.1.3
		hwSecurityConfigGroup OBJECT IDENTIFIER ::= { hwSecurityConfigTrap 3 }

		
--  1.3.6.1.4.1.2011.6.122.83.1.3.1
		-- 1.3.6.1.4.1.2011.6.122.83.1.3.1
		hwSecurityConfigObjectGroup OBJECT-GROUP
			OBJECTS { hwSecConfigChangeUser, hwSecConfigChangeTerminalIP, hwSecConfigChangeVsys, hwSecConfigChangeAction, hwSecConfigChangeModuleType, 
				hwSecConfigChangeModuleObject, hwSecConfigChangeTargetObject }
			STATUS current
			DESCRIPTION 
				"The group of object."
			::= { hwSecurityConfigGroup 1 }

		
--  1.3.6.1.4.1.2011.6.122.83.1.3.2
		-- 1.3.6.1.4.1.2011.6.122.83.1.3.2
		hwSecurityConfigTrapGroup NOTIFICATION-GROUP
			NOTIFICATIONS { hwSecurityConfigChangeNotify }
			STATUS current
			DESCRIPTION 
				"The group of trap."
			::= { hwSecurityConfigGroup 2 }

		
	
	END

--
-- HUAWEI-SECURITY-CONFIG-MIB.mib
--
