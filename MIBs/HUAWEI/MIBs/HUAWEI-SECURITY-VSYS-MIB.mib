-- 
--  HUAWEI-SECURITY-VSYS-MIB.mib
-- MIB generated by MG-SOFT Visual MIB Builder Version 4.0 Build 341
-- Saturday, December 27, 2014 at 12:03:59
-- Wednesday, May 4, 2016 at 19:00:00
--   =============================================================================
-- Copyright (C) 2019 by HUAWEI TECHNOLOGIES. All rights reserved.
--    
-- Description:  
-- Reference: Huawei Enterprise MIB
-- Version: V1.06
-- History: 
--          V1.00 The initial version created by Zuoyi 90006056. 
--          V1.01 Checkout by zhuoqinghong 00358075
-- =============================================================================

	HUAWEI-SECURITY-VSYS-MIB DEFINITIONS ::= BEGIN
 
		IMPORTS
			enterprises			
				FROM RFC1155-SMI			
			OBJECT-GROUP, MODULE-COMPLIANCE			
				FROM SNMPv2-CONF			
			Integer32, Gauge32, Counter64, NOTIFICATION-TYPE, OBJECT-TYPE, MODULE-IDENTITY			
				FROM SNMPv2-SMI;
	
	
		-- 1.3.6.1.4.1.2011.6.122.70
		hwSecVSYS MODULE-IDENTITY 
			LAST-UPDATED "201903251913Z"		-- May 25, 2019 at 19:13 GMT
			ORGANIZATION 
				"Huawei Technologies Co.,Ltd."
			CONTACT-INFO 
				"Huawei Industrial Base Bantian, Longgang Shenzhen 518129 People's Republic of China Website: http://www.huawei.com Email: support@huawei.com
				"
			DESCRIPTION 
				"Add resource traps."
            
			REVISION "201903251913Z"		-- May 25, 2019 at 19:13 GMT
			DESCRIPTION 
				"V1.05
				The LOGIN mib is for Eudemon and USG product series."
                                                         
			REVISION "201712161000Z"		-- June 16, 2017 at 10:00 GMT
			DESCRIPTION 
				"modify describtion at 201712161000Z"
            
			REVISION "201606301000Z"		-- June 30, 2016 at 10:00 GMT
			DESCRIPTION 
				"modify describtion at 201604112100Z"

            REVISION "201606261900Z"		-- June 26, 2016 at 21:00 GMT
			DESCRIPTION 
				"Add for IO statistic of virtual system at 201604112100Z"
				                                                  
			REVISION "201605042100Z"		-- May 4, 2016 at 21:00 GMT
			DESCRIPTION 
				"modify for v5r1c30 at 201604112100Z"

			REVISION "201604112100Z"		-- Aprile 11, 2016 at 21:00 GMT
			DESCRIPTION 
				"modify for v5r1c30 at 201604112100Z"
				
			REVISION "201501051900Z"
            DESCRIPTION 
				"modify for v5r1 at 201501051900Z"      
			::= { hwSecurity 70 }

		
-- 
-- Node definitions
-- 
--  1.3.6.1.4.1.2011.6.122.70
-- June 09, 2014 at 20:24 GMT
-- ===============================================
-- Node definitions
-- ===============================================
		-- 1.3.6.1.4.1.2011
		huawei OBJECT IDENTIFIER ::= { enterprises 2011 }

	
		-- 1.3.6.1.4.1.2011.6
		huaweiUtility OBJECT IDENTIFIER ::= { huawei 6 }

		-- 1.3.6.1.4.1.2011.6.122
		hwSecurity OBJECT IDENTIFIER ::= { huaweiUtility 122 }

		-- 1.3.6.1.4.1.2011.6.122.70.1
		hwSecVSYSstatTable OBJECT-TYPE
			SYNTAX SEQUENCE OF HwSecVSYSstatEntry
			MAX-ACCESS not-accessible
			STATUS current
			DESCRIPTION
				"Description."
			::= { hwSecVSYS 1 }

		-- 1.3.6.1.4.1.2011.6.122.70.1.1
		hwSecVSYSstatEntry OBJECT-TYPE
			SYNTAX HwSecVSYSstatEntry
			MAX-ACCESS not-accessible
			STATUS current
			DESCRIPTION
				"Description."
			INDEX { hwSecVSYSstatIndex }
			::= { hwSecVSYSstatTable 1 }

		
		HwSecVSYSstatEntry ::=
			SEQUENCE { 
				hwSecVSYSstatIndex
					Integer32,
				hwSecVSYSstatUptime	 	 
					OCTET STRING,	 	 	 
				hwSecVSYSstatRuntime	 	 	 
					OCTET STRING,
				hwSecVSYSstatSessCount
					Gauge32,
				hwSecVSYSstatSessSpeed
					Gauge32,
				hwSecVSYSstatThroughput
					Gauge32,
				hwSecVSYSstatPolicy
					Gauge32,
				hwSecVSYSstatVsysname
					OCTET STRING,
				hwSecVSYSstatRcvHistoryPkt
					Counter64,
				hwSecVSYSstatSendHistoryPkt
					Counter64,
				hwSecVSYSstatRcvHistoryPktLen
					Counter64,
				hwSecVSYSstatSendHistoryPktLen
					Counter64,
				hwSecVSYSstatRcvPkt
					Counter64,
				hwSecVSYSstatSendPkt
					Counter64,
				hwSecVSYSstatRcvPktLen
					Counter64,
				hwSecVSYSstatSendPktLen
					Counter64
			 }

		-- 1.3.6.1.4.1.2011.6.122.70.1.1.1
		hwSecVSYSstatIndex OBJECT-TYPE
			SYNTAX Integer32 (0..4097)
			MAX-ACCESS not-accessible
			STATUS current
			DESCRIPTION
				"The index of hwSecVSYSstatTable."
			::= { hwSecVSYSstatEntry 1 }
			
		-- 1.3.6.1.4.1.2011.6.122.70.1.1.2	 	 	 
		hwSecVSYSstatUptime OBJECT-TYPE	 	 	 
			SYNTAX OCTET STRING	 	 	 
		MAX-ACCESS read-only	 	 	 
			STATUS current	 	 	 
		DESCRIPTION	 	 	 
			"The startup time of the vsys."	 	 	 
		::= { hwSecVSYSstatEntry 2 }	 	 	 

		-- 1.3.6.1.4.1.2011.6.122.70.1.1.3	 	 	 
		hwSecVSYSstatRuntime OBJECT-TYPE	 	 	 
			SYNTAX OCTET STRING	 	 	 
		MAX-ACCESS read-only	 	 	 
			STATUS current	 	 	 
		DESCRIPTION	 	 	 
			"The run time of the vsys."	 	 	 
		::= { hwSecVSYSstatEntry 3 }

		-- 1.3.6.1.4.1.2011.6.122.70.1.1.4
		hwSecVSYSstatSessCount OBJECT-TYPE
			SYNTAX Gauge32
			MAX-ACCESS read-only
			STATUS current
			DESCRIPTION
				"The session count of the vsys."
			::= { hwSecVSYSstatEntry 4 }

		-- 1.3.6.1.4.1.2011.6.122.70.1.1.5
		hwSecVSYSstatSessSpeed OBJECT-TYPE
			SYNTAX Gauge32
			MAX-ACCESS read-only
			STATUS current
			DESCRIPTION
				"The session creation ration of the vsys."
			::= { hwSecVSYSstatEntry 5 }

		-- 1.3.6.1.4.1.2011.6.122.70.1.1.6
		hwSecVSYSstatThroughput OBJECT-TYPE
			SYNTAX Gauge32
			MAX-ACCESS read-only
			STATUS current
			DESCRIPTION
				"The Throughput of the vsys."
			::= { hwSecVSYSstatEntry 6 }

		
		-- 1.3.6.1.4.1.2011.6.122.70.1.1.7
		hwSecVSYSstatPolicy OBJECT-TYPE
			SYNTAX Gauge32
			MAX-ACCESS read-only
			STATUS current
			DESCRIPTION
				"The Throughput of the vsys."
			::= { hwSecVSYSstatEntry 7 }

		-- 1.3.6.1.4.1.2011.6.122.70.1.1.8
		hwSecVSYSstatVsysname OBJECT-TYPE
			SYNTAX OCTET STRING
			MAX-ACCESS read-only
			STATUS current
			DESCRIPTION
				"The name of the vsys."
			::= { hwSecVSYSstatEntry 8 }     
			 
		-- 1.3.6.1.4.1.2011.6.122.70.1.1.9
		hwSecVSYSstatRcvHistoryPkt OBJECT-TYPE
			SYNTAX Counter64
			MAX-ACCESS read-only
			STATUS current
			DESCRIPTION
				"The total number of packets received by a virtual system."
			::= { hwSecVSYSstatEntry 9 }    
			
		-- 1.3.6.1.4.1.2011.6.122.70.1.1.10
		hwSecVSYSstatSendHistoryPkt OBJECT-TYPE
			SYNTAX Counter64
			MAX-ACCESS read-only
			STATUS current
			DESCRIPTION
				"The total number of packets sent by a virtual system."
			::= { hwSecVSYSstatEntry 10 }    
			
		-- 1.3.6.1.4.1.2011.6.122.70.1.1.11
		hwSecVSYSstatRcvHistoryPktLen OBJECT-TYPE
			SYNTAX Counter64
			MAX-ACCESS read-only
			STATUS current
			DESCRIPTION
				"The total length of packets received by a virtual system, in bytes."
			::= { hwSecVSYSstatEntry 11 }     
			
		-- 1.3.6.1.4.1.2011.6.122.70.1.1.12
		hwSecVSYSstatSendHistoryPktLen OBJECT-TYPE
			SYNTAX Counter64
			MAX-ACCESS read-only
			STATUS current
			DESCRIPTION
				"The total length of packets sent by a virtual system, in bytes."
			::= { hwSecVSYSstatEntry 12 }   
		
		-- 1.3.6.1.4.1.2011.6.122.70.1.1.13
		hwSecVSYSstatRcvPkt OBJECT-TYPE
			SYNTAX Counter64
			MAX-ACCESS read-only
			STATUS current
			DESCRIPTION
				"The number of packets that a virtual system receives per second."
			::= { hwSecVSYSstatEntry 13 }    
			
		-- 1.3.6.1.4.1.2011.6.122.70.1.1.14
		hwSecVSYSstatSendPkt OBJECT-TYPE
			SYNTAX Counter64
			MAX-ACCESS read-only
			STATUS current
			DESCRIPTION
				"The number of packets that a virtual system sends per second."
			::= { hwSecVSYSstatEntry 14 }    
			
		-- 1.3.6.1.4.1.2011.6.122.70.1.1.15
		hwSecVSYSstatRcvPktLen OBJECT-TYPE
			SYNTAX Counter64
			MAX-ACCESS read-only
			STATUS current
			DESCRIPTION
				"The rate at which a virtual system receives packets, in byte/s."
			::= { hwSecVSYSstatEntry 15 }     
			
		-- 1.3.6.1.4.1.2011.6.122.70.1.1.16
		hwSecVSYSstatSendPktLen OBJECT-TYPE
			SYNTAX Counter64
			MAX-ACCESS read-only
			STATUS current
			DESCRIPTION
				"The rate at which a virtual system sends packets, in byte/s."
			::= { hwSecVSYSstatEntry 16 }



		-- 1.3.6.1.4.1.2011.6.122.70.3
		hwSecVSYSstatConformance OBJECT IDENTIFIER ::= { hwSecVSYS 3 }

		-- 1.3.6.1.4.1.2011.6.122.70.3.1
		hwSecVSYSstatCompliances OBJECT IDENTIFIER ::= { hwSecVSYSstatConformance 1 }

		
-- this module
		-- 1.3.6.1.4.1.2011.6.122.70.3.1.1
		hwSecVSYSstatCompliance MODULE-COMPLIANCE
			STATUS current
			DESCRIPTION 
				"Description."
			MODULE -- this module
				MANDATORY-GROUPS { hwSecVSYSstatGroup }
			::= { hwSecVSYSstatCompliances 1 }

		-- 1.3.6.1.4.1.2011.6.122.70.3.2
		hwSecVSYSstatGroups OBJECT IDENTIFIER ::= { hwSecVSYSstatConformance 2 }

		-- 1.3.6.1.4.1.2011.6.122.70.3.2.1
		hwSecVSYSstatGroup OBJECT-GROUP
			OBJECTS {  hwSecVSYSstatUptime, hwSecVSYSstatRuntime,hwSecVSYSstatSessCount, hwSecVSYSstatSessSpeed, hwSecVSYSstatThroughput, 
			hwSecVSYSstatPolicy,hwSecVSYSstatVsysname, hwSecVSYSIntfInboundRate,hwSecVSYSIntfOutboundRate, hwSecVSYSIntfInboundHistory, 
			hwSecVSYSIntfOutboundHistory }
			STATUS current
			DESCRIPTION 
				"Description."
			::= { hwSecVSYSstatGroups 1 }

		-- 1.3.6.1.4.1.2011.6.122.70.4
		hwSecVSYSIntfInfoTable OBJECT-TYPE
			SYNTAX SEQUENCE OF HwSecVSYSIntfInfoEntry
			MAX-ACCESS not-accessible
			STATUS current
			DESCRIPTION
				"Description."
			::= { hwSecVSYS 4 }

		-- 1.3.6.1.4.1.2011.6.122.70.4.1
		hwSecVSYSIntfInfoEntry OBJECT-TYPE
			SYNTAX HwSecVSYSIntfInfoEntry
			MAX-ACCESS not-accessible
			STATUS current
			DESCRIPTION
				"Show the interface informaiton of indicated vsys."
			INDEX { hwSecVSYSIntfVsysName, hwSecVSYSIntfIntfName }
			::= { hwSecVSYSIntfInfoTable 1 }

		
		HwSecVSYSIntfInfoEntry ::=
			SEQUENCE { 
				hwSecVSYSIntfVsysName
					OCTET STRING,
				hwSecVSYSIntfIntfName
					OCTET STRING,
				hwSecVSYSIntfInboundRate
					Counter64,
				hwSecVSYSIntfOutboundRate
					Counter64,
				hwSecVSYSIntfInboundHistory
					Counter64,
				hwSecVSYSIntfOutboundHistory
					Counter64
			 }

		-- 1.3.6.1.4.1.2011.6.122.70.4.1.1
		hwSecVSYSIntfVsysName OBJECT-TYPE
			SYNTAX OCTET STRING
			MAX-ACCESS not-accessible
			STATUS current
			DESCRIPTION
				"The name of vsys."
			::= { hwSecVSYSIntfInfoEntry 1 }

		-- 1.3.6.1.4.1.2011.6.122.70.4.1.2
		hwSecVSYSIntfIntfName OBJECT-TYPE
			SYNTAX OCTET STRING
			MAX-ACCESS not-accessible
			STATUS current
			DESCRIPTION
				"The name of interface."
			::= { hwSecVSYSIntfInfoEntry 2 }

		-- 1.3.6.1.4.1.2011.6.122.70.4.1.3
		hwSecVSYSIntfInboundRate OBJECT-TYPE
			SYNTAX Counter64
			MAX-ACCESS read-only
			STATUS current
			DESCRIPTION
				"The inbound rate of the interface and  the unit is kbps."
			::= { hwSecVSYSIntfInfoEntry 3 }

		-- 1.3.6.1.4.1.2011.6.122.70.4.1.4
		hwSecVSYSIntfOutboundRate OBJECT-TYPE
			SYNTAX Counter64
			MAX-ACCESS read-only
			STATUS current
			DESCRIPTION
				"The outbound rate of the interface and the unit is kbps."
			::= { hwSecVSYSIntfInfoEntry 4 }

		-- 1.3.6.1.4.1.2011.6.122.70.4.1.5
		hwSecVSYSIntfInboundHistory OBJECT-TYPE
			SYNTAX Counter64
			MAX-ACCESS read-only
			STATUS current
			DESCRIPTION
				"The history inbound flow of the interface and the unit is mb."
			::= { hwSecVSYSIntfInfoEntry 5 }

		-- 1.3.6.1.4.1.2011.6.122.70.4.1.6
		hwSecVSYSIntfOutboundHistory OBJECT-TYPE
			SYNTAX Counter64
			MAX-ACCESS read-only
			STATUS current
			DESCRIPTION
				"The history outbound flow of the interface and the unit is mb."
			::= { hwSecVSYSIntfInfoEntry 6 }

		-- 1.3.6.1.4.1.2011.6.122.70.5
		hwSecVsysResourceTrapsInfo OBJECT IDENTIFIER ::= { hwSecVSYS 5 }
		
		hwSecVsysID OBJECT-TYPE
			SYNTAX Gauge32
			MAX-ACCESS accessible-for-notify
			STATUS current
			DESCRIPTION
				"The virtual system ID."
			::= { hwSecVsysResourceTrapsInfo 1 }
			
		hwSecVsysName OBJECT-TYPE
			SYNTAX OCTET STRING
			MAX-ACCESS accessible-for-notify
			STATUS current
			DESCRIPTION
				"The virtual system name."
			::= { hwSecVsysResourceTrapsInfo 2 }
			
		hwSecVsysResourceType OBJECT-TYPE
			SYNTAX OCTET STRING
			MAX-ACCESS accessible-for-notify
			STATUS current
			DESCRIPTION
				"The type of resource."
			::= { hwSecVsysResourceTrapsInfo 3 }
		
		hwSecVsysResourceUsageNum OBJECT-TYPE
			SYNTAX Gauge32
			MAX-ACCESS accessible-for-notify
			STATUS current
			DESCRIPTION
				"The usage of resource."
			::= { hwSecVsysResourceTrapsInfo 4 }
		
		hwSecVsysResourceThresholdNum OBJECT-TYPE
			SYNTAX Gauge32
			MAX-ACCESS accessible-for-notify
			STATUS current
			DESCRIPTION
				"The threshold of resource."
			::= { hwSecVsysResourceTrapsInfo 5 }
		
		-- 1.3.6.1.4.1.2011.6.122.70.6
		hwSecVsysResourceTraps OBJECT IDENTIFIER ::= { hwSecVSYS 6 }
		
		-- 1.3.6.1.4.1.2011.6.122.70.6.1
		hwSecStatVsysResourceOverThreshold NOTIFICATION-TYPE
			OBJECTS { hwSecVsysResourceType, hwSecVsysName, hwSecVsysID, hwSecVsysResourceUsageNum, hwSecVsysResourceThresholdNum
				 }
			STATUS current
			DESCRIPTION 
				"The CPU usage exceeded the upper threshold (alarm threshold)."
			::= { hwSecVsysResourceTraps 1 }
		
		-- 1.3.6.1.4.1.2011.6.122.70.6.2
		hwSecStatVsysResourceRecoverThreshold NOTIFICATION-TYPE
			OBJECTS { hwSecVsysResourceType, hwSecVsysName, hwSecVsysID, hwSecVsysResourceUsageNum, hwSecVsysResourceThresholdNum
				 }
			STATUS current
			DESCRIPTION 
				"The CPU usage fell below the lower threshold (alarm clearing threshold)."
			::= { hwSecVsysResourceTraps 2 }
	
	END

--
-- HUAWEI-SECURITY-VSYS-MIB.mib
--
