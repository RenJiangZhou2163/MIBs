-- =================================================================
-- Copyright (C) 2018 by  HUAWEI TECHNOLOGIES. All rights reserved.
--
-- Description:HUAWEI-DIAMETER-MIB DEFINITIONS
-- Reference:MIB generated by MG-SOFT Visual MIB Builder Version 4.0 Build 341
-- Version: V2.02
-- History:Saturday, November 27, 2010 at 11:45:27
--              modified by  x00403698 2018-01-27
--              modified by  g00347880 2018-08-13
-- =================================================================

	HUAWEI-DIAMETER-MIB DEFINITIONS ::= BEGIN
 
		IMPORTS
			hwDatacomm			
				FROM HUAWEI-MIB			
			OBJECT-GROUP, MODULE-COMPLIANCE, NOTIFICATION-GROUP			
				FROM SNMPv2-CONF			
			IpAddress, Unsigned32, OBJECT-TYPE, MODULE-IDENTITY, NOTIFICATION-TYPE			
				FROM SNMPv2-SMI			
			RowStatus, TEXTUAL-CONVENTION			
				FROM SNMPv2-TC;  
				
    EnabledStatus ::= TEXTUAL-CONVENTION
    STATUS      current
    DESCRIPTION
        "A simple status value for the object."
    SYNTAX      INTEGER { enabled(1), disabled(2) }	
	
--  June 25, 2010 at 14:53 GMT
		-- 1.3.6.1.4.1.2011.5.25.239
		hwDiameterMIB MODULE-IDENTITY 
			LAST-UPDATED "201808131030Z"		-- June 25, 2010 at 14:53 GMT
			ORGANIZATION 
				"Huawei Technologies Co.,Ltd."
			CONTACT-INFO 
"Huawei Industrial Base
  Bantian, Longgang
   Shenzhen 518129
   People's Republic of China
   Website: http://www.huawei.com
   Email: support@huawei.com
 "
			DESCRIPTION 
				"The MIB contains objects of module DIAMETER. Offer the set and query of diameter protcol."

            REVISION    "201808131030Z"
            DESCRIPTION 
                "Add hwDiameterPeerFaultyV6 and hwDiameterPeerFaultyResumeV6"

            REVISION    "201801271030Z"
            DESCRIPTION 
                "Modify translation information of hwDiameterPeerFaulty and hwDiameterPeerFaultyResume."

			::= { hwDatacomm 239 }

		
	
	
--
-- Node definitions
--
	
		-- 1.3.6.1.4.1.2011.5.25.239.1
		hwDiameterScalarsObjects OBJECT IDENTIFIER ::= { hwDiameterMIB 1 }
-- All scalars of Diameter.
		
		-- 1.3.6.1.4.1.2011.5.25.239.1.1
		hwDiameterEnable OBJECT-TYPE
			SYNTAX EnabledStatus
			MAX-ACCESS read-create
			STATUS current
			DESCRIPTION
				"Make diameter function enable."
			DEFVAL { disabled }
			::= { hwDiameterScalarsObjects 1 }

		
--  Node definitions
-- 
		-- 1.3.6.1.4.1.2011.5.25.239.2
		hwDiameterObjects OBJECT IDENTIFIER ::= { hwDiameterMIB 2 }
-- All Tables of Diameter.
		-- 1.3.6.1.4.1.2011.5.25.239.2.2
		hwDiameterGroupTable OBJECT-TYPE
			SYNTAX SEQUENCE OF HwDiameterGroupEntry
			MAX-ACCESS not-accessible
			STATUS current
			DESCRIPTION
				"Diameter group configuration table."
			::= { hwDiameterObjects 2 }

		-- 1.3.6.1.4.1.2011.5.25.239.2.2.1
		hwDiameterGroupEntry OBJECT-TYPE
			SYNTAX HwDiameterGroupEntry
			MAX-ACCESS not-accessible
			STATUS current
			DESCRIPTION
				"The entry of Diameter group server."
			INDEX { hwDiameterGroupName }
			::= { hwDiameterGroupTable 1 }

		
		HwDiameterGroupEntry ::=
			SEQUENCE { 
				hwDiameterGroupName
					OCTET STRING,
				hwDiameterGroupRowStatus
					RowStatus
			 }


		-- 1.3.6.1.4.1.2011.5.25.239.2.2.1.1
		hwDiameterGroupName OBJECT-TYPE
			SYNTAX OCTET STRING (SIZE (1..31))
			MAX-ACCESS read-only
			STATUS current
			DESCRIPTION
				"Diameter group name."
			::= { hwDiameterGroupEntry 1 }

		
		-- 1.3.6.1.4.1.2011.5.25.239.2.2.1.15
		hwDiameterGroupRowStatus OBJECT-TYPE
			SYNTAX RowStatus
			MAX-ACCESS read-create
			STATUS current
			DESCRIPTION
				"The operating state of the row, only can be Added or Deleted."
			::= { hwDiameterGroupEntry 15 }

		
		-- 1.3.6.1.4.1.2011.5.25.239.2.3
		hwDiameterLocalTable OBJECT-TYPE
			SYNTAX SEQUENCE OF HwDiameterLocalEntry
			MAX-ACCESS not-accessible
			STATUS current
			DESCRIPTION
				"Diameter local table configuration."
			::= { hwDiameterObjects 3 }

		
		-- 1.3.6.1.4.1.2011.5.25.239.2.3.1
		hwDiameterLocalEntry OBJECT-TYPE
			SYNTAX HwDiameterLocalEntry
			MAX-ACCESS not-accessible
			STATUS current
			DESCRIPTION
				"The entry of Diameter local table."
			INDEX { hwDiameterLocalName }
			::= { hwDiameterLocalTable 1 }

		
		HwDiameterLocalEntry ::=
			SEQUENCE { 
				hwDiameterLocalName
					OCTET STRING,
				hwDiameterLocalIf
					OCTET STRING,
				hwDiameterLocalHostName
					OCTET STRING,
				hwDiameterLocalRealmName
					OCTET STRING,
				hwDiameterLocalProductName
					OCTET STRING,
				hwDiameterLocalRowStatus
					RowStatus
			 }

	
		-- 1.3.6.1.4.1.2011.5.25.239.2.3.1.1
		hwDiameterLocalName OBJECT-TYPE
			SYNTAX OCTET STRING (SIZE (1..32))
			MAX-ACCESS read-only
			STATUS current
			DESCRIPTION
				"Diameter Local name."
			::= { hwDiameterLocalEntry 1 }

		
		-- 1.3.6.1.4.1.2011.5.25.239.2.3.1.2
		hwDiameterLocalIf OBJECT-TYPE
			SYNTAX OCTET STRING (SIZE (1..47))
			MAX-ACCESS read-create
			STATUS current
			DESCRIPTION
				"Diameter Local interface name"
			::= { hwDiameterLocalEntry 2 }

		
		-- 1.3.6.1.4.1.2011.5.25.239.2.3.1.3
		hwDiameterLocalHostName OBJECT-TYPE
			SYNTAX OCTET STRING (SIZE (1..127))
			MAX-ACCESS read-create
			STATUS current
			DESCRIPTION
				"Diameter Local Host-Name."
			::= { hwDiameterLocalEntry 3 }

		
		-- 1.3.6.1.4.1.2011.5.25.239.2.3.1.4
		hwDiameterLocalRealmName OBJECT-TYPE
			SYNTAX OCTET STRING (SIZE (1..127))
			MAX-ACCESS read-create
			STATUS current
			DESCRIPTION
				"Diameter Local Realm-Name."
			::= { hwDiameterLocalEntry 4 }

		
		-- 1.3.6.1.4.1.2011.5.25.239.2.3.1.5
		hwDiameterLocalProductName OBJECT-TYPE
			SYNTAX OCTET STRING (SIZE (1..127))
			MAX-ACCESS read-create
			STATUS current
			DESCRIPTION
				"Diameter Local Product-Name."
			::= { hwDiameterLocalEntry 5 }

		
		-- 1.3.6.1.4.1.2011.5.25.239.2.3.1.15
		hwDiameterLocalRowStatus OBJECT-TYPE
			SYNTAX RowStatus
			MAX-ACCESS read-create
			STATUS current
			DESCRIPTION
				"The operating state of the row."
			::= { hwDiameterLocalEntry 15 }

		
		-- 1.3.6.1.4.1.2011.5.25.239.2.4
		hwDiameterPeerTable OBJECT-TYPE
			SYNTAX SEQUENCE OF HwDiameterPeerEntry
			MAX-ACCESS not-accessible
			STATUS current
			DESCRIPTION
				"Diameter Peer table configuration."
			::= { hwDiameterObjects 4 }

		
		-- 1.3.6.1.4.1.2011.5.25.239.2.4.1
		hwDiameterPeerEntry OBJECT-TYPE
			SYNTAX HwDiameterPeerEntry
			MAX-ACCESS not-accessible
			STATUS current
			DESCRIPTION
				"Diameter Peer entry."
			INDEX { hwDiameterPeerName }
			::= { hwDiameterPeerTable 1 }

		
		HwDiameterPeerEntry ::=
			SEQUENCE { 
				hwDiameterPeerName
					OCTET STRING,
				hwDiameterPeerIP
					IpAddress,
				hwDiameterPeerPort
					Unsigned32,
				hwDiameterPeerHostName
					OCTET STRING,
				hwDiameterPeerRealmName
					OCTET STRING,
				hwDiameterPeerRowStatus
					RowStatus
			 }

		
	
		-- 1.3.6.1.4.1.2011.5.25.239.2.4.1.1
		hwDiameterPeerName OBJECT-TYPE
			SYNTAX OCTET STRING (SIZE (1..32))
			MAX-ACCESS read-only
			STATUS current
			DESCRIPTION
				"Diameter Peer name."
			::= { hwDiameterPeerEntry 1 }

		
		-- 1.3.6.1.4.1.2011.5.25.239.2.4.1.2
		hwDiameterPeerIP OBJECT-TYPE
			SYNTAX IpAddress
			MAX-ACCESS read-create
			STATUS current
			DESCRIPTION
				"Diameter Peer ip address."
			::= { hwDiameterPeerEntry 2 }

		
		-- 1.3.6.1.4.1.2011.5.25.239.2.4.1.3
		hwDiameterPeerPort OBJECT-TYPE
			SYNTAX Unsigned32 (1..49151)
			MAX-ACCESS read-create
			STATUS current
			DESCRIPTION
				"Diameter Peer port."
			::= { hwDiameterPeerEntry 3 }

		
		-- 1.3.6.1.4.1.2011.5.25.239.2.4.1.4
		hwDiameterPeerHostName OBJECT-TYPE
			SYNTAX OCTET STRING (SIZE (1..127))
			MAX-ACCESS read-create
			STATUS current
			DESCRIPTION
				"Diameter Peer host name."
			::= { hwDiameterPeerEntry 4 }

		
		-- 1.3.6.1.4.1.2011.5.25.239.2.4.1.5
		hwDiameterPeerRealmName OBJECT-TYPE
			SYNTAX OCTET STRING (SIZE (1..127))
			MAX-ACCESS read-create
			STATUS current
			DESCRIPTION
				"Diameter Peer realm name."
			::= { hwDiameterPeerEntry 5 }

		-- 1.3.6.1.4.1.2011.5.25.239.2.4.1.15
		hwDiameterPeerRowStatus OBJECT-TYPE
			SYNTAX RowStatus
			MAX-ACCESS read-create
			STATUS current
			DESCRIPTION
				"The operating state of the row"
			::= { hwDiameterPeerEntry 15 }

		
		-- 1.3.6.1.4.1.2011.5.25.239.2.5
		hwDiameterGrpLinkTable OBJECT-TYPE
			SYNTAX SEQUENCE OF HwDiameterGrpLinkEntry
			MAX-ACCESS not-accessible
			STATUS current
			DESCRIPTION
				"Diameter link table."
			::= { hwDiameterObjects 5 }

		
		-- 1.3.6.1.4.1.2011.5.25.239.2.5.1
		hwDiameterGrpLinkEntry OBJECT-TYPE
			SYNTAX HwDiameterGrpLinkEntry
			MAX-ACCESS not-accessible
			STATUS current
			DESCRIPTION
				"Diameter group link entry."
			INDEX { hwDiameterGrpLinkGroupName, hwDiameterGrpLinkLocalName,hwDiameterGrpLinkPeerName,hwDiameterGrpLinkLocalPort}
			::= { hwDiameterGrpLinkTable 1 }

		
		HwDiameterGrpLinkEntry ::=
			SEQUENCE { 
				hwDiameterGrpLinkGroupName
					OCTET STRING,
                hwDiameterGrpLinkLocalName
                    OCTET STRING,
                hwDiameterGrpLinkPeerName
                    OCTET STRING,
                hwDiameterGrpLinkLocalPort
                    Unsigned32,
                hwDiameterGrpLinkWeight
                    Unsigned32,
                hwDiameterGrpLinkState
                    OCTET STRING,    
				hwDiameterGrpLinkRowStatus
					RowStatus
			 }

		
		-- 1.3.6.1.4.1.2011.5.25.239.2.5.1.1
		hwDiameterGrpLinkGroupName OBJECT-TYPE
			SYNTAX OCTET STRING (SIZE (1..31))
			MAX-ACCESS read-only
			STATUS current
			DESCRIPTION
				"Diameter group name."
			::= { hwDiameterGrpLinkEntry 1 }

		-- 1.3.6.1.4.1.2011.5.25.239.2.5.1.2
		hwDiameterGrpLinkLocalName OBJECT-TYPE
			SYNTAX OCTET STRING (SIZE (1..32))
			MAX-ACCESS read-only
			STATUS current
			DESCRIPTION
				"Diameter group link local name."
			::= { hwDiameterGrpLinkEntry 2 }

		-- 1.3.6.1.4.1.2011.5.25.239.2.5.1.3
		hwDiameterGrpLinkPeerName OBJECT-TYPE
			SYNTAX OCTET STRING (SIZE (1..32))
			MAX-ACCESS read-only
			STATUS current
			DESCRIPTION
				"Diameter group link peer name."
			::= { hwDiameterGrpLinkEntry 3 }

		-- 1.3.6.1.4.1.2011.5.25.239.2.5.1.4
		hwDiameterGrpLinkLocalPort OBJECT-TYPE
			SYNTAX Unsigned32 (0..49151)
			MAX-ACCESS read-only
			STATUS current
			DESCRIPTION
				"Diameter group link local port."
			::= { hwDiameterGrpLinkEntry 4 }

		-- 1.3.6.1.4.1.2011.5.25.239.2.5.1.5
		hwDiameterGrpLinkWeight OBJECT-TYPE
			SYNTAX Unsigned32 (0..100)
			MAX-ACCESS read-create
			STATUS current
			DESCRIPTION
				"Diameter group link weight."
			::= { hwDiameterGrpLinkEntry 5 }

		-- 1.3.6.1.4.1.2011.5.25.239.2.5.1.6
		hwDiameterGrpLinkState OBJECT-TYPE
			SYNTAX OCTET STRING
			MAX-ACCESS read-create
			STATUS current
			DESCRIPTION
				"Link state of diameter (Up/Down)."
			::= { hwDiameterGrpLinkEntry 6 }

		
		
		-- 1.3.6.1.4.1.2011.5.25.239.2.5.1.15
		hwDiameterGrpLinkRowStatus OBJECT-TYPE
			SYNTAX RowStatus
			MAX-ACCESS read-create
			STATUS current
			DESCRIPTION
				"The operating state of the row. "
			::= { hwDiameterGrpLinkEntry 15 }

		
		-- 1.3.6.1.4.1.2011.5.25.239.4
		hwDiameterNotifications OBJECT IDENTIFIER ::= { hwDiameterMIB 4 }

		
		-- 1.3.6.1.4.1.2011.5.25.239.4.1
		hwDiameterPeerFaulty NOTIFICATION-TYPE
			OBJECTS { hwDiameterPeerHostName,hwDiameterPeerIP,hwDiameterPeerPort,hwDiameterLocalIf,hwDiameterGrpLinkLocalPort }
			STATUS current
			DESCRIPTION 
				"This object indicates that the link between the host and the policy server fails."
			::= { hwDiameterNotifications 1 }

		
		-- 1.3.6.1.4.1.2011.5.25.239.4.2
		hwDiameterPeerFaultyResume NOTIFICATION-TYPE
			OBJECTS { hwDiameterPeerHostName,hwDiameterPeerIP,hwDiameterPeerPort,hwDiameterLocalIf,hwDiameterGrpLinkLocalPort }
			STATUS current
			DESCRIPTION 
				"This object indicates that the failure of the link between the host and the policy server is removed."
			::= { hwDiameterNotifications 2 }
		
		-- 1.3.6.1.4.1.2011.5.25.239.4.3
		hwDiameterPeerFaultyV6 NOTIFICATION-TYPE
			OBJECTS { hwDiameterPeerHostName, hwDiameterPeerIpStr, hwDiameterPeerPort, hwDiameterLocalIf, hwDiameterGrpLinkLocalPort
				 }
			STATUS current
			DESCRIPTION 
				"The link between pcef and pcrf is abnormal."
			::= { hwDiameterNotifications 3 }
		
		-- 1.3.6.1.4.1.2011.5.25.239.4.4
		hwDiameterPeerFaultyV6Resume NOTIFICATION-TYPE
			OBJECTS { hwDiameterPeerHostName, hwDiameterPeerIpStr, hwDiameterPeerPort, hwDiameterLocalIf, hwDiameterGrpLinkLocalPort
				 }
			STATUS current
			DESCRIPTION 
				"The link between pcef and pcrf is normal."
			::= { hwDiameterNotifications 4 }
		
		-- 1.3.6.1.4.1.2011.5.25.239.5
		hwDiameterConformance OBJECT IDENTIFIER ::= { hwDiameterMIB 5 }

		
		-- 1.3.6.1.4.1.2011.5.25.239.5.1
		hwDiameterCompliances OBJECT IDENTIFIER ::= { hwDiameterConformance 1 }

		
		-- 1.3.6.1.4.1.2011.5.25.239.5.1.1
		hwDiameterCompliance MODULE-COMPLIANCE
			STATUS current
			DESCRIPTION 
				"The compliance statement for systems supporting the this module."
			MODULE -- this module
				MANDATORY-GROUPS { hwDiameterEnableGroup, hwDiameterGroupGroup, hwDiameterLocalGroup, hwDiameterPeerGroup,hwDiameterGrpLinkGroup }
			::= { hwDiameterCompliances 1 }

		
		-- 1.3.6.1.4.1.2011.5.25.239.5.2
		hwDiameterGroups OBJECT IDENTIFIER ::= { hwDiameterConformance 2 }

		
		-- 1.3.6.1.4.1.2011.5.25.239.5.2.1
		hwDiameterEnableGroup OBJECT-GROUP
			OBJECTS { hwDiameterEnable }
			STATUS current
			DESCRIPTION 
				"Diameter function enable."
			::= { hwDiameterGroups 1 }

		
		-- 1.3.6.1.4.1.2011.5.25.239.5.2.2
		hwDiameterGroupGroup OBJECT-GROUP
			OBJECTS { hwDiameterGroupName, hwDiameterGroupRowStatus }
			STATUS current
			DESCRIPTION 
				"Diameter group."
			::= { hwDiameterGroups 2 }

		
		-- 1.3.6.1.4.1.2011.5.25.239.5.2.3
		hwDiameterLocalGroup OBJECT-GROUP
			OBJECTS { hwDiameterLocalName, hwDiameterLocalIf, hwDiameterLocalHostName, hwDiameterLocalRealmName, 
				hwDiameterLocalProductName, hwDiameterLocalRowStatus }
			STATUS current
			DESCRIPTION 
				"Diameter Local."
			::= { hwDiameterGroups 3 }

		
		-- 1.3.6.1.4.1.2011.5.25.239.5.2.4
		hwDiameterPeerGroup OBJECT-GROUP
			OBJECTS { hwDiameterPeerName, hwDiameterPeerIP, hwDiameterPeerPort,hwDiameterPeerHostName,
			    hwDiameterPeerRealmName, hwDiameterPeerRowStatus }
			STATUS current
			DESCRIPTION 
				"Diameter Peer."
			::= { hwDiameterGroups 4 }

		
		-- 1.3.6.1.4.1.2011.5.25.239.5.2.5
		hwDiameterGrpLinkGroup OBJECT-GROUP
			OBJECTS { hwDiameterGrpLinkGroupName,hwDiameterGrpLinkLocalName,hwDiameterGrpLinkPeerName,
                hwDiameterGrpLinkLocalPort,hwDiameterGrpLinkWeight,hwDiameterGrpLinkState, hwDiameterGrpLinkRowStatus }
			STATUS current
			DESCRIPTION 
				"Diameter Link."
			::= { hwDiameterGroups 5 }

		
		-- 1.3.6.1.4.1.2011.5.25.239.5.2.6
		hwDiameternotificationsGroup NOTIFICATION-GROUP
			NOTIFICATIONS { hwDiameterPeerFaulty, hwDiameterPeerFaultyResume, hwDiameterPeerFaultyV6, hwDiameterPeerFaultyV6Resume }
			STATUS current
			DESCRIPTION 
				"Diameter nofifications."
			::= { hwDiameterGroups 6 }
		
		-- 1.3.6.1.4.1.2011.5.25.239.7
		hwDiameterNoticationOid OBJECT IDENTIFIER ::= { hwDiameterMIB 7 }
		
		-- 1.3.6.1.4.1.2011.5.25.239.7.1
		hwDiameterPeerIpStr OBJECT-TYPE
			SYNTAX OCTET STRING
			MAX-ACCESS accessible-for-notify
			STATUS current
			DESCRIPTION
				"Description."
			::= { hwDiameterNoticationOid 1 }
		
	
	END

--
-- HUAWEI-DIAMETER-MIB.mib
--
