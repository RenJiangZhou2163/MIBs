-- ===================================================================
-- Copyright (C) 2019 by HUAWEI TECHNOLOGIES. All rights reserved.
-- Description: MIB of intelligent services.
-- Reference:
-- Version: V1.00
-- History:
-- <author>, <date>, <contents>
--  liujing, 2019-12-19, Create MIB file and add intelligent anomaly detection objects and traps.
--  xubaohua, 2019-12-23, Add intelligent resource prediction objects and traps.
-- ===================================================================


    HUAWEI-INTELLIGENT-SERV-MIB DEFINITIONS ::= BEGIN
 
        IMPORTS                                            
            OBJECT-GROUP, MODULE-COMPLIANCE, NOTIFICATION-GROUP            
                FROM SNMPv2-CONF            
            DisplayString, RowStatus                        
                FROM SNMPv2-TC
            TimeTicks, Integer32, Unsigned32, IpAddress, Counter32, OBJECT-TYPE, 
            MODULE-IDENTITY, NOTIFICATION-TYPE            
                FROM SNMPv2-SMI
            hwDatacomm            
                FROM HUAWEI-MIB;
    
    
        hwIntelligentServ MODULE-IDENTITY 
            LAST-UPDATED "201912231100Z"        
            ORGANIZATION 
                  "Huawei Technologies Co.,Ltd."
            CONTACT-INFO 
                  "Huawei Industrial Base
  Bantian, Longgang
   Shenzhen 518129
   People's Republic of China
   Website: http://www.huawei.com
   Email: support@huawei.com
 "
            DESCRIPTION 
                "MIB of intelligent services."
            REVISION    "201912231100Z"   
            DESCRIPTION "Add intelligent resource prediction objects and traps."
            REVISION    "201912190000Z"   
            DESCRIPTION "Create MIB file and add intelligent anomaly detection objects and traps."
    
            ::= { hwDatacomm 179 }

-- 1.3.6.1.4.1.2011.5.25.179

-- ===================================================================
-- Node Definition
-- ===================================================================

    -- 1.3.6.1.4.1.2011.5.25.179.1
    
    hwIntelligentServObjects OBJECT IDENTIFIER ::= { hwIntelligentServ 1 }

    -- 1.3.6.1.4.1.2011.5.25.179.2
    
    hwIntelligentServTrap OBJECT IDENTIFIER ::= { hwIntelligentServ 2 }

    -- 1.3.6.1.4.1.2011.5.25.179.3
    
    hwIntelligentServConformance OBJECT IDENTIFIER ::= { hwIntelligentServ 3 }

-- ===================================================================
-- Configuration Object Definition
-- ===================================================================

    -- 1.3.6.1.4.1.2011.5.25.179.1.1
    
    hwIntelligentServConfigObjects OBJECT IDENTIFIER ::= { hwIntelligentServObjects 1 }

    -- 1.3.6.1.4.1.2011.5.25.179.1.2
                    
    hwIntelligentServStatsObjects OBJECT IDENTIFIER ::= { hwIntelligentServObjects 2 }

-- ===================================================================
-- Trap Definition
-- ===================================================================

    -- 1.3.6.1.4.1.2011.5.25.179.3.1
    
    hwIntelligentServTrapObjects OBJECT IDENTIFIER ::= { hwIntelligentServTrap 1 }

    -- 1.3.6.1.4.1.2011.5.25.179.3.1.1
    
    hwInterfaceNames OBJECT-TYPE
       SYNTAX OCTET STRING
       MAX-ACCESS accessible-for-notify
       STATUS current
       DESCRIPTION
           "The information for the interface names with sudden flow change."
       ::= { hwIntelligentServTrapObjects 1 }

    -- 1.3.6.1.4.1.2011.5.25.179.3.1.2
    
    hwForwardingChipInfo OBJECT-TYPE
       SYNTAX OCTET STRING
       MAX-ACCESS accessible-for-notify
       STATUS current
       DESCRIPTION
           "The information for the forwarding chips with packet loss."
       ::= { hwIntelligentServTrapObjects 2 }
       
    -- 1.3.6.1.4.1.2011.5.25.179.3.1.3
    
    hwResChassisId OBJECT-TYPE
       SYNTAX Unsigned32
       MAX-ACCESS accessible-for-notify
       STATUS current
       DESCRIPTION
           "The information for the chassis."
       ::= { hwIntelligentServTrapObjects 3 }

    -- 1.3.6.1.4.1.2011.5.25.179.3.1.4
    
    hwResSlotId OBJECT-TYPE
       SYNTAX Unsigned32
       MAX-ACCESS accessible-for-notify
       STATUS current
       DESCRIPTION
           "The value for the kpi belonged to the slot."
       ::= { hwIntelligentServTrapObjects 4 }
       
    -- 1.3.6.1.4.1.2011.5.25.179.3.1.5
    
    hwResObject OBJECT-TYPE
       SYNTAX OCTET STRING
       MAX-ACCESS accessible-for-notify
       STATUS current
       DESCRIPTION
           "The information for the object."
       ::= { hwIntelligentServTrapObjects 5 }
       
    -- 1.3.6.1.4.1.2011.5.25.179.3.1.6
    
    hwResPreReasonId OBJECT-TYPE
       SYNTAX INTEGER
           {
           memoryUsage(1),
           arpEntryCount(2),
           ndbasPrefixTable(3),
           ndbasTable(4)
           }
       MAX-ACCESS accessible-for-notify
       STATUS current
       DESCRIPTION
           "To describe the type of resource."
       ::= { hwIntelligentServTrapObjects 6 }

    -- 1.3.6.1.4.1.2011.5.25.179.3.1.7
    
    hwResPreReasonDesc OBJECT-TYPE
       SYNTAX OCTET STRING(SIZE(0..256))
       MAX-ACCESS accessible-for-notify
       STATUS current
       DESCRIPTION
           "The information for trend predict reason."
       ::= { hwIntelligentServTrapObjects 7 }

    -- 1.3.6.1.4.1.2011.5.25.179.3.1.8

    -- 1.3.6.1.4.1.2011.5.25.179.3.2
    
    hwIntelligentServTraps OBJECT IDENTIFIER ::= { hwIntelligentServTrap 2 }

    -- 1.3.6.1.4.1.2011.5.25.179.3.2.1
    
    hwAnomalyPacketLoss NOTIFICATION-TYPE
        OBJECTS { hwInterfaceNames, hwForwardingChipInfo }
        STATUS current
        DESCRIPTION 
            "Interface flow sudden change and forwarding chip packets loss is detected."
        ::= { hwIntelligentServTraps 1 }
        
    -- 1.3.6.1.4.1.2011.5.25.179.3.2.2
    
    hwAnomalyPacketLossResume NOTIFICATION-TYPE
        OBJECTS { hwInterfaceNames, hwForwardingChipInfo }
        STATUS current
        DESCRIPTION 
            "Interface flow sudden change and forwarding chip packets loss is resumed."
        ::= { hwIntelligentServTraps 2 }

    -- 1.3.6.1.4.1.2011.5.25.179.3.2.3
    
    hwResourcePredictOverThres NOTIFICATION-TYPE
        OBJECTS { hwResChassisId, hwResSlotId, hwResObject, hwResPreReasonId, hwResPreReasonDesc }
        STATUS current
        DESCRIPTION 
            "Resource trend predict will exceed threshold under current circumstance."
        ::= { hwIntelligentServTraps 3 }
        
    -- 1.3.6.1.4.1.2011.5.25.179.3.2.4
    
    hwResourcePredictOverThresResume NOTIFICATION-TYPE
        OBJECTS { hwResChassisId, hwResSlotId, hwResObject, hwResPreReasonId, hwResPreReasonDesc }
        STATUS current
        DESCRIPTION 
            "Resource trend predict over threshold resume."
        ::= { hwIntelligentServTraps 4 }
    
-- ===================================================================
-- Conformance Definition
-- ===================================================================

    -- 1.3.6.1.4.1.2011.5.25.179.3.1

    hwIntelligentServCompliances OBJECT IDENTIFIER ::= { hwIntelligentServConformance 1 }
        
    -- 1.3.6.1.4.1.2011.5.25.179.3.1.1
    
    hwIntelligentServCompliance MODULE-COMPLIANCE
        STATUS current
        DESCRIPTION 
            "Compliance statement for agents that provide full support for hwIntelligentServ."
        MODULE 
             MANDATORY-GROUPS { hwIntelligentServObjectGroup }
        ::= { hwIntelligentServCompliances 1 }
        
    -- 1.3.6.1.4.1.2011.5.25.179.3.2
    
    hwIntelligentServGroups OBJECT IDENTIFIER ::= { hwIntelligentServConformance 2 }

    -- 1.3.6.1.4.1.2011.5.25.179.3.2.1
    
    hwIntelligentServObjectGroup OBJECT-GROUP
        OBJECTS { hwInterfaceNames, hwForwardingChipInfo, hwResChassisId, hwResSlotId, hwResObject, hwResPreReasonId, hwResPreReasonDesc }
        STATUS current
        DESCRIPTION 
            "Group for trap objects."
        ::= { hwIntelligentServGroups 1 }

    -- 1.3.6.1.4.1.2011.5.25.179.3.2.2
    
    hwIntelligentServTrapGroup NOTIFICATION-GROUP
        NOTIFICATIONS { hwAnomalyPacketLoss, hwAnomalyPacketLossResume, hwResourcePredictOverThres, hwResourcePredictOverThresResume }
        STATUS current
        DESCRIPTION 
            "Group for all traps."
        ::= { hwIntelligentServGroups 2 }


    END

--
-- HUAWEI-INTELLIGENT-SERV-MIB.mib
--
