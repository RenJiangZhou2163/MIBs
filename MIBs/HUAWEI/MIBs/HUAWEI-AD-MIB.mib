--
-- HUAWEI-AD-MIB.my
-- MIB generated by MG-SOFT Visual MIB Builder Version 3.0 Build 253
-- Wednesday, February 28, 2018 at 14:44:45
--

--  ===================================================================
-- Copyright (C) 2018 by HUAWEI TECHNOLOGIES. All rights reserved.
-- Description: 
-- Reference:
-- Version: V1.01
-- modified by  l00347324 2018-04-23
-- ===================================================================

	HUAWEI-AD-MIB DEFINITIONS ::= BEGIN
 
		IMPORTS
			huaweiMgmt			
				FROM HUAWEI-MIB			
			IpAddress, Integer32, Unsigned32, OBJECT-TYPE, MODULE-IDENTITY			
				FROM SNMPv2-SMI			
			RowStatus			
				FROM SNMPv2-TC;
	
	
		hwAD MODULE-IDENTITY 
			LAST-UPDATED "201804231600Z"		-- January 29, 2018 at 16:00 GMT
			ORGANIZATION 
				"Huawei Technologies Co.,Ltd."
			CONTACT-INFO 
				"Huawei Industrial Base
				Bantian, Longgang
				 Shenzhen 518129
				 People's Republic of China
				 Website: http://www.huawei.com
				 Email: support@huawei.com
				"
			DESCRIPTION 
				"Please provide the descritpion."
			REVISION "201804231600Z"		-- August 11, 2018 at 16:00 GMT	
			DESCRIPTION 
				"modify hwADServerGroupManagerDN."
			REVISION "201802111600Z"		-- August 11, 2010 at 16:00 GMT
			DESCRIPTION
				"V1.00, initial version."
			REVISION "201801291600Z"		-- January 29, 2018 at 16:00 GMT
			DESCRIPTION
				"create a new ad mib file."
			::= { huaweiMgmt 121 }
		
	
	
--
-- Node definitions
--
	
--  Node definitions
-- 
-- 1.3.6.1.4.1.2011.5.121.1
		-- 1.3.6.1.4.1.2011.5.121.1
		hwAdServerGroupTable OBJECT-TYPE
			SYNTAX SEQUENCE OF HwAdServerGroupEntry
			MAX-ACCESS not-accessible
			STATUS current
			DESCRIPTION
				"Description."
			::= { hwAD 1 }
		
--  1.3.6.1.4.1.2011.5.121.1.1
		-- 1.3.6.1.4.1.2011.5.121.1.1
		hwAdServerGroupEntry OBJECT-TYPE
			SYNTAX HwAdServerGroupEntry
			MAX-ACCESS not-accessible
			STATUS current
			DESCRIPTION
				"Description."
			INDEX { hwADServerGroupIndex }
			::= { hwAdServerGroupTable 1 }
		
		HwAdServerGroupEntry ::=
			SEQUENCE { 
				hwADServerGroupIndex
					Integer32,
				hwADServerGroupName
					OCTET STRING,
				hwADServerGroupPriAuthenAddr
					IpAddress,
				hwADServerGroupPriAuthenPort
					Unsigned32,
				hwADServerGroupPriAuthenSslEnable
					INTEGER,
				hwADServerGroupPriAuthenHostName
					OCTET STRING,
				hwADServerGroupSecAuthenAddr
					IpAddress,
				hwADServerGroupSecAuthenPort
					Unsigned32,
				hwADServerGroupSecAuthenSslEnable
					INTEGER,
				hwADServerGroupSecAuthenHostName
					OCTET STRING,
				hwADServerGroupThiAuthenAddr
					IpAddress,
				hwADServerGroupThiAuthenPort
					Unsigned32,
				hwADServerGroupThiAuthenSslEnable
					INTEGER,
				hwADServerGroupThiAuthenHostName
					OCTET STRING,
				hwADServerGroupAuthenSrvUrl
					OCTET STRING,
				hwADServerGroupAuthenSrvUrlPort
					Unsigned32,
				hwADServerGroupAuthenSrvUrlSslEnable
					INTEGER,
				hwADServerGroupBaseDN
					OCTET STRING,
				hwADServerGroupLDAPPort
					Integer32,
				hwADServerGroupManagerDN
					OCTET STRING,
				hwADServerGroupManagerPSW
					OCTET STRING,
				hwADServerGroupManagerAnonymous
					INTEGER,
				hwADServerGroupManagerWithBaseDN
					INTEGER,
				hwADServerGroupAuthorBindUser
					INTEGER,
				hwADServerGroupGroupFlt
					OCTET STRING,
				hwADServerGroupIpAddrFlt
					OCTET STRING,
				hwADServerGroupMaskFlt
					OCTET STRING,
				hwADServerGroupMobileNumFlt
					OCTET STRING,
				hwADServerGroupTimeStampFlt
					OCTET STRING,
				hwADServerGroupUserFlt
					OCTET STRING,
				hwADServerGroupStatus
					RowStatus
			 }

--  1.3.6.1.4.1.2011.5.121.1.1.2
		-- 1.3.6.1.4.1.2011.5.121.1.1.2
		hwADServerGroupIndex OBJECT-TYPE
			SYNTAX Integer32 (0..2147483647)
			MAX-ACCESS read-only
			STATUS current
			DESCRIPTION
				"Description."
			::= { hwAdServerGroupEntry 2 }
		
--  1.3.6.1.4.1.2011.5.121.1.1.3
		-- 1.3.6.1.4.1.2011.5.121.1.1.3
		hwADServerGroupName OBJECT-TYPE
			SYNTAX OCTET STRING (SIZE (1..32))
			MAX-ACCESS read-create
			STATUS current
			DESCRIPTION
				"Description."
			::= { hwAdServerGroupEntry 3 }
		
--  1.3.6.1.4.1.2011.5.121.1.1.4
		-- 1.3.6.1.4.1.2011.5.121.1.1.4
		hwADServerGroupPriAuthenAddr OBJECT-TYPE
			SYNTAX IpAddress
			MAX-ACCESS read-create
			STATUS current
			DESCRIPTION
				"Description."
			::= { hwAdServerGroupEntry 4 }
		
--  1.3.6.1.4.1.2011.5.121.1.1.5
		-- 1.3.6.1.4.1.2011.5.121.1.1.5
		hwADServerGroupPriAuthenPort OBJECT-TYPE
			SYNTAX Unsigned32 (1..65535 | 4294967295)
			MAX-ACCESS read-write
			STATUS current
			DESCRIPTION
				"Description."
			::= { hwAdServerGroupEntry 5 }
		
--  1.3.6.1.4.1.2011.5.121.1.1.6
		-- 1.3.6.1.4.1.2011.5.121.1.1.6
		hwADServerGroupPriAuthenSslEnable OBJECT-TYPE
			SYNTAX INTEGER
				{
				true(1),
				false(0)
				}
			MAX-ACCESS read-create
			STATUS current
			DESCRIPTION
				"Description."
			::= { hwAdServerGroupEntry 6 }
		
--  1.3.6.1.4.1.2011.5.121.1.1.7
		-- 1.3.6.1.4.1.2011.5.121.1.1.7
		hwADServerGroupPriAuthenHostName OBJECT-TYPE
			SYNTAX OCTET STRING (SIZE (0..127))
			MAX-ACCESS read-write
			STATUS current
			DESCRIPTION
				"Description."
			::= { hwAdServerGroupEntry 7 }
		
--  1.3.6.1.4.1.2011.5.121.1.1.8
		-- 1.3.6.1.4.1.2011.5.121.1.1.8
		hwADServerGroupSecAuthenAddr OBJECT-TYPE
			SYNTAX IpAddress
			MAX-ACCESS read-create
			STATUS current
			DESCRIPTION
				"Description."
			::= { hwAdServerGroupEntry 8 }
		
--  1.3.6.1.4.1.2011.5.121.1.1.9
		-- 1.3.6.1.4.1.2011.5.121.1.1.9
		hwADServerGroupSecAuthenPort OBJECT-TYPE
			SYNTAX Unsigned32 (1..65535 | 4294967295)
			MAX-ACCESS read-create
			STATUS current
			DESCRIPTION
				"Description."
			::= { hwAdServerGroupEntry 9 }
		
--  1.3.6.1.4.1.2011.5.121.1.1.10
		-- 1.3.6.1.4.1.2011.5.121.1.1.10
		hwADServerGroupSecAuthenSslEnable OBJECT-TYPE
			SYNTAX INTEGER
				{
				true(1),
				false(0)
				}
			MAX-ACCESS read-create
			STATUS current
			DESCRIPTION
				"Description."
			::= { hwAdServerGroupEntry 10 }
		
--  1.3.6.1.4.1.2011.5.121.1.1.11
		-- 1.3.6.1.4.1.2011.5.121.1.1.11
		hwADServerGroupSecAuthenHostName OBJECT-TYPE
			SYNTAX OCTET STRING (SIZE (0..127))
			MAX-ACCESS read-create
			STATUS current
			DESCRIPTION
				"Description."
			::= { hwAdServerGroupEntry 11 }
		
--  1.3.6.1.4.1.2011.5.121.1.1.12
		-- 1.3.6.1.4.1.2011.5.121.1.1.12
		hwADServerGroupThiAuthenAddr OBJECT-TYPE
			SYNTAX IpAddress
			MAX-ACCESS read-create
			STATUS current
			DESCRIPTION
				"Description."
			::= { hwAdServerGroupEntry 12 }
		
--  1.3.6.1.4.1.2011.5.121.1.1.13
		-- 1.3.6.1.4.1.2011.5.121.1.1.13
		hwADServerGroupThiAuthenPort OBJECT-TYPE
			SYNTAX Unsigned32 (1..65535 | 4294967295)
			MAX-ACCESS read-write
			STATUS current
			DESCRIPTION
				"Description."
			::= { hwAdServerGroupEntry 13 }
		
--  1.3.6.1.4.1.2011.5.121.1.1.14
		-- 1.3.6.1.4.1.2011.5.121.1.1.14
		hwADServerGroupThiAuthenSslEnable OBJECT-TYPE
			SYNTAX INTEGER
				{
				true(1),
				false(0)
				}
			MAX-ACCESS read-create
			STATUS current
			DESCRIPTION
				"Description."
			::= { hwAdServerGroupEntry 14 }
		
--  1.3.6.1.4.1.2011.5.121.1.1.15
		-- 1.3.6.1.4.1.2011.5.121.1.1.15
		hwADServerGroupThiAuthenHostName OBJECT-TYPE
			SYNTAX OCTET STRING (SIZE (0..127))
			MAX-ACCESS read-create
			STATUS current
			DESCRIPTION
				"Description."
			::= { hwAdServerGroupEntry 15 }
		
--  1.3.6.1.4.1.2011.5.121.1.1.16
		-- 1.3.6.1.4.1.2011.5.121.1.1.16
		hwADServerGroupAuthenSrvUrl OBJECT-TYPE
			SYNTAX OCTET STRING (SIZE (0..127))
			MAX-ACCESS read-create
			STATUS current
			DESCRIPTION
				"Description."
			::= { hwAdServerGroupEntry 16 }
		
--  1.3.6.1.4.1.2011.5.121.1.1.17
		-- 1.3.6.1.4.1.2011.5.121.1.1.17
		hwADServerGroupAuthenSrvUrlPort OBJECT-TYPE
			SYNTAX Unsigned32 (1..65535 | 4294967295)
			MAX-ACCESS read-write
			STATUS current
			DESCRIPTION
				"Description."
			DEFVAL { 88 }
			::= { hwAdServerGroupEntry 17 }
		
--  1.3.6.1.4.1.2011.5.121.1.1.18
		-- 1.3.6.1.4.1.2011.5.121.1.1.18
		hwADServerGroupAuthenSrvUrlSslEnable OBJECT-TYPE
			SYNTAX INTEGER
				{
				true(1),
				false(0)
				}
			MAX-ACCESS read-create
			STATUS current
			DESCRIPTION
				"Description."
			::= { hwAdServerGroupEntry 18 }
		
--  1.3.6.1.4.1.2011.5.121.1.1.19
		-- 1.3.6.1.4.1.2011.5.121.1.1.19
		hwADServerGroupBaseDN OBJECT-TYPE
			SYNTAX OCTET STRING (SIZE (0..256))
			MAX-ACCESS read-create
			STATUS current
			DESCRIPTION
				"Description."
			::= { hwAdServerGroupEntry 19 }
		
--  1.3.6.1.4.1.2011.5.121.1.1.20
		-- 1.3.6.1.4.1.2011.5.121.1.1.20
		hwADServerGroupLDAPPort OBJECT-TYPE
			SYNTAX Integer32 (1..65535)
			MAX-ACCESS read-create
			STATUS current
			DESCRIPTION
				"Description."
			::= { hwAdServerGroupEntry 20 }
		
--  1.3.6.1.4.1.2011.5.121.1.1.21
		-- 1.3.6.1.4.1.2011.5.121.1.1.21
		hwADServerGroupManagerDN OBJECT-TYPE
			SYNTAX OCTET STRING (SIZE (0..180))
			MAX-ACCESS read-create
			STATUS current
			DESCRIPTION
				"Description."
			::= { hwAdServerGroupEntry 21 }
		
--  1.3.6.1.4.1.2011.5.121.1.1.22
		-- 1.3.6.1.4.1.2011.5.121.1.1.22
		hwADServerGroupManagerPSW OBJECT-TYPE
			SYNTAX OCTET STRING (SIZE (0..68))
			MAX-ACCESS read-create
			STATUS current
			DESCRIPTION
				"Description."
			::= { hwAdServerGroupEntry 22 }
		
--  1.3.6.1.4.1.2011.5.121.1.1.23
		-- 1.3.6.1.4.1.2011.5.121.1.1.23
		hwADServerGroupManagerAnonymous OBJECT-TYPE
			SYNTAX INTEGER
				{
				true(1),
				false(0)
				}
			MAX-ACCESS read-create
			STATUS current
			DESCRIPTION
				"Description."
			::= { hwAdServerGroupEntry 23 }
		
--  1.3.6.1.4.1.2011.5.121.1.1.24
		-- 1.3.6.1.4.1.2011.5.121.1.1.24
		hwADServerGroupManagerWithBaseDN OBJECT-TYPE
			SYNTAX INTEGER
				{
				true(1),
				false(0)
				}
			MAX-ACCESS read-create
			STATUS current
			DESCRIPTION
				"Description."
			::= { hwAdServerGroupEntry 24 }
		
--  1.3.6.1.4.1.2011.5.121.1.1.25
		-- 1.3.6.1.4.1.2011.5.121.1.1.25
		hwADServerGroupAuthorBindUser OBJECT-TYPE
			SYNTAX INTEGER
				{
				true(1),
				false(0)
				}
			MAX-ACCESS read-create
			STATUS current
			DESCRIPTION
				"Description."
			::= { hwAdServerGroupEntry 25 }
		
--  1.3.6.1.4.1.2011.5.121.1.1.26
		-- 1.3.6.1.4.1.2011.5.121.1.1.26
		hwADServerGroupGroupFlt OBJECT-TYPE
			SYNTAX OCTET STRING (SIZE (0..63))
			MAX-ACCESS read-create
			STATUS current
			DESCRIPTION
				"Description."
			::= { hwAdServerGroupEntry 26 }
		
--  1.3.6.1.4.1.2011.5.121.1.1.27
		-- 1.3.6.1.4.1.2011.5.121.1.1.27
		hwADServerGroupIpAddrFlt OBJECT-TYPE
			SYNTAX OCTET STRING (SIZE (0..63))
			MAX-ACCESS read-create
			STATUS current
			DESCRIPTION
				"Description."
			::= { hwAdServerGroupEntry 27 }
		
--  1.3.6.1.4.1.2011.5.121.1.1.28
		-- 1.3.6.1.4.1.2011.5.121.1.1.28
		hwADServerGroupMaskFlt OBJECT-TYPE
			SYNTAX OCTET STRING (SIZE (0..63))
			MAX-ACCESS read-create
			STATUS current
			DESCRIPTION
				"Description."
			::= { hwAdServerGroupEntry 28 }
		
--  1.3.6.1.4.1.2011.5.121.1.1.29
		-- 1.3.6.1.4.1.2011.5.121.1.1.29
		hwADServerGroupMobileNumFlt OBJECT-TYPE
			SYNTAX OCTET STRING (SIZE (0..63))
			MAX-ACCESS read-create
			STATUS current
			DESCRIPTION
				"Description."
			::= { hwAdServerGroupEntry 29 }
		
--  1.3.6.1.4.1.2011.5.121.1.1.30
		-- 1.3.6.1.4.1.2011.5.121.1.1.30
		hwADServerGroupTimeStampFlt OBJECT-TYPE
			SYNTAX OCTET STRING (SIZE (0..63))
			MAX-ACCESS read-create
			STATUS current
			DESCRIPTION
				"Description."
			::= { hwAdServerGroupEntry 30 }
		
--  1.3.6.1.4.1.2011.5.121.1.1.31
		-- 1.3.6.1.4.1.2011.5.121.1.1.31
		hwADServerGroupUserFlt OBJECT-TYPE
			SYNTAX OCTET STRING (SIZE (0..63))
			MAX-ACCESS read-create
			STATUS current
			DESCRIPTION
				"Description."
			::= { hwAdServerGroupEntry 31 }
		
		-- 1.3.6.1.4.1.2011.5.121.1.1.32
		hwADServerGroupStatus OBJECT-TYPE
			SYNTAX RowStatus
				{
				active(1),
				notInService(2),
				notReady(3),
				createAndGo(4),
				destroy(6)
				}
			MAX-ACCESS read-write
			STATUS current
			DESCRIPTION
				"Description."
			::= { hwAdServerGroupEntry 32 }
		
	
	END

--
-- HUAWEI-AD-MIB.my
--
