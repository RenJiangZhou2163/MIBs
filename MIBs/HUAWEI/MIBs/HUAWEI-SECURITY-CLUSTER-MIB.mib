-- ===================================================================
-- Copyright (C) 2017 by HUAWEI TECHNOLOGIES. All rights reserved.
-- Description: 
-- Reference:
-- Version: V1.00
-- ===================================================================


        HUAWEI-SECURITY-CLUSTER-MIB DEFINITIONS ::= BEGIN
 
        IMPORTS
	    enterprises			
		FROM RFC1155-SMI
            OBJECT-GROUP            
                FROM SNMPv2-CONF            
            Gauge32, NOTIFICATION-TYPE, Integer32, Counter64, OBJECT-TYPE, MODULE-IDENTITY            
                FROM SNMPv2-SMI            
            TruthValue            
                FROM SNMPv2-TC;
    
    -- 1.3.6.1.4.1.2011.6.122.85 
    hwSecClusterMibObjects MODULE-IDENTITY
       LAST-UPDATED "201710140000Z" 
       ORGANIZATION "Huawei Technologies Co.,Ltd."
       CONTACT-INFO 
                   "Huawei Industrial Base
                    Bantian, Longgang
                    Shenzhen 518129
                    People's Republic of China
                    Website: http://www.huawei.com
                    Email: support@huawei.com
                   "
       DESCRIPTION
           "The MIB module is for entities implementing the access node
            side of the Access Node Control Protocol (ANCP).

            Copyright (C) The IETF Trust (2008).  The initial version of
            this MIB module was published in RFC yyyy; for full legal
            notices see the RFC itself."
-- RFC Ed.: replace yyyy with actual RFC number & remove this note
       
       --  Revision history

       REVISION    "201710140000Z"
       DESCRIPTION "V1.00, initial version."

       
-- RFC Ed.: replace yyyy with actual RFC number & remove this note
       ::= { hwSecurity 85 }
-- The value xxx to be assigned by IANA.
    

--
-- Node definitions
--                       
		-- 1.3.6.1.4.1.2011
		huawei OBJECT IDENTIFIER ::= { enterprises 2011 }
        
        -- 1.3.6.1.4.1.2011.6
        huaweiUtility OBJECT IDENTIFIER ::= { huawei 6 }
        
        -- 1.3.6.1.4.1.2011.6.122
        hwSecurity OBJECT IDENTIFIER ::= { huaweiUtility 122 }          
        
        -- 1.3.6.1.4.1.2011.6.122.85
        -- hwSecClusterMibObjects OBJECT IDENTIFIER ::= { hwSecurity 85 }
   
       	-- 1.3.6.1.4.1.2011.6.122.85.1                          
    	hwSecClusterNegTrapsObjests OBJECT IDENTIFIER ::= { hwSecClusterMibObjects 1 } 
    	        	
        -- 1.3.6.1.4.1.2011.6.122.85.1.1	//cluster id     
    	hwSecClusterID OBJECT-TYPE
        	SYNTAX Integer32 (0..10000)        	
        	MAX-ACCESS accessible-for-notify
        	STATUS current
        	DESCRIPTION
            		"Cluster ID."
        	::= { hwSecClusterNegTrapsObjests 1 }


       -- 1.3.6.1.4.1.2011.6.122.85.1.2 	//device id    
    	hwSecClusterDeviceID OBJECT-TYPE
        	SYNTAX Integer32 (0..64)        	
        	MAX-ACCESS accessible-for-notify
        	STATUS current
        	DESCRIPTION
            		"Device id."
        	::= { hwSecClusterNegTrapsObjests 2 }    
        		        	     
	
        -- 1.3.6.1.4.1.2011.6.122.85.1.3	//status 		
       	hwSecClusterStatus OBJECT-TYPE
        	SYNTAX OCTET STRING (SIZE (1..64))
        	MAX-ACCESS accessible-for-notify
        	STATUS current
        	DESCRIPTION
            		"Cluster node negotiation(business group/channel) status."
        	::= { hwSecClusterNegTrapsObjests 3 } 
			
		-- 1.3.6.1.4.1.2011.6.122.85.1.4	//status 
		hwSecClusterNewStatus OBJECT-TYPE
        	SYNTAX OCTET STRING (SIZE (1..64))
        	MAX-ACCESS accessible-for-notify
        	STATUS current
        	DESCRIPTION
            		"Cluster node negotiation(business group/channel) new status."
        	::= { hwSecClusterNegTrapsObjests 4 } 			
        
        -- 1.3.6.1.4.1.2011.6.122.85.1.5	//peer id        
    	hwSecClusterPeerID OBJECT-TYPE
        	SYNTAX Integer32 (1..64) 
        	MAX-ACCESS accessible-for-notify
       	 	STATUS current
        	DESCRIPTION
            		"Peer id."
        	::= { hwSecClusterNegTrapsObjests 5 }  

		-- 1.3.6.1.4.1.2011.6.122.85.1.6	//old priority        
    	hwSecClusterNegPriority OBJECT-TYPE
        	SYNTAX Integer32 (0..65535) 
        	MAX-ACCESS accessible-for-notify
       	 	STATUS current
        	DESCRIPTION
            		"Negotiation old priority."
        	::= { hwSecClusterNegTrapsObjests 6 }
        
		-- 1.3.6.1.4.1.2011.6.122.85.1.7	//new priority        
    	hwSecClusterNegNewPriority OBJECT-TYPE
        	SYNTAX Integer32 (0..65535) 
        	MAX-ACCESS accessible-for-notify
       	 	STATUS current
        	DESCRIPTION
            		"Negotiation new priority after health priority change, "
        	::= { hwSecClusterNegTrapsObjests 7 }
		
		-- 1.3.6.1.4.1.2011.6.122.85.1.8	//packet type        
    	hwSecClusterNegHelloType OBJECT-TYPE
        	SYNTAX OCTET STRING (SIZE (1..64)) 
        	MAX-ACCESS accessible-for-notify
       	 	STATUS current
        	DESCRIPTION
            		"Hello packet type,including master hello, slave hello, and probe hello."
        	::= { hwSecClusterNegTrapsObjests 8 }

		-- 1.3.6.1.4.1.2011.6.122.85.1.9	//up or down status        
    	hwSecClusterNegUporDown OBJECT-TYPE
        	SYNTAX OCTET STRING (SIZE (1..64)) 
        	MAX-ACCESS accessible-for-notify
       	 	STATUS current
        	DESCRIPTION
            		"Neighbor old up or down."
        	::= { hwSecClusterNegTrapsObjests 9 }
		
		-- 1.3.6.1.4.1.2011.6.122.85.1.10	//new up or down status 		
	    hwSecClusterNegNewUporDown OBJECT-TYPE
        	SYNTAX OCTET STRING (SIZE (1..64)) 
        	MAX-ACCESS accessible-for-notify
       	 	STATUS current
        	DESCRIPTION
            		"Neighbor up or down new status ."
        	::= { hwSecClusterNegTrapsObjests 10 }
	
		-- 1.3.6.1.4.1.2011.6.122.85.1.11	//Peer priority        
    	hwSecClusterNegPeerPriority OBJECT-TYPE
        	SYNTAX Integer32 (0..65535) 
        	MAX-ACCESS accessible-for-notify
       	 	STATUS current
        	DESCRIPTION
            		"Peer priority."
        	::= { hwSecClusterNegTrapsObjests 11 }
			
		-- 1.3.6.1.4.1.2011.6.122.85.1.12	//Local slave number        
    	hwSecClusterNegLocalSlaveNum OBJECT-TYPE
        	SYNTAX Integer32 (0..64) 
        	MAX-ACCESS accessible-for-notify
       	 	STATUS current
        	DESCRIPTION
            		"Local slave numbers."
        	::= { hwSecClusterNegTrapsObjests 12 }
	
		-- 1.3.6.1.4.1.2011.6.122.85.1.13	//Peer slave number        
    	hwSecClusterNegPeerSlaveNum OBJECT-TYPE
        	SYNTAX Integer32 (0..64) 
        	MAX-ACCESS accessible-for-notify
       	 	STATUS current
        	DESCRIPTION
            		"Peer slave numbers."
        	::= { hwSecClusterNegTrapsObjests 13 }

 		-- 1.3.6.1.4.1.2011.6.122.85.1.14	 		
	    hwSecClusterChannelType OBJECT-TYPE
        	SYNTAX OCTET STRING (SIZE (1..64)) 
        	MAX-ACCESS accessible-for-notify
       	 	STATUS current
        	DESCRIPTION
            		"Channel type(negotiation,backup,forward)."
        	::= { hwSecClusterNegTrapsObjests 14 }

		-- 1.3.6.1.4.1.2011.6.122.85.1.15	 		
	    hwSecClusterChannelProtocol OBJECT-TYPE
        	SYNTAX OCTET STRING (SIZE (1..64)) 
        	MAX-ACCESS accessible-for-notify
       	 	STATUS current
        	DESCRIPTION
            		"Channel protocol."
        	::= { hwSecClusterNegTrapsObjests 15 }
        	
  		-- 1.3.6.1.4.1.2011.6.122.85.1.16	       
    	hwSecClusterbgid OBJECT-TYPE
        	SYNTAX Integer32 (0..65535) 
        	MAX-ACCESS accessible-for-notify
       	 	STATUS current
        	DESCRIPTION
            		"Business group id."
        	::= { hwSecClusterNegTrapsObjests 16 }

       
			                                
        -- 1.3.6.1.4.1.2011.6.122.85.2                          
    	hwSecClusterTraps OBJECT IDENTIFIER ::= { hwSecClusterMibObjects 2 }   	 
         
        -- 1.3.6.1.4.1.2011.6.122.85.2.1        		                                
        hwSecClusterNegPriorityChange NOTIFICATION-TYPE
		OBJECTS { 			  
			  hwSecClusterID,
              hwSecClusterDeviceID, 
			  hwSecClusterStatus,
			  hwSecClusterPeerID,
			  hwSecClusterNegPriority,
			  hwSecClusterNegNewPriority, 
              hwSecClusterNegHelloType		
		        }
		STATUS     current
		DESCRIPTION
		    "The Priority Change Trap."
		::= { hwSecClusterTraps 1 }   
		  
		-- 1.3.6.1.4.1.2011.6.122.85.2.2 
		hwSecClusterNBRChange NOTIFICATION-TYPE
		OBJECTS { 
			  hwSecClusterID,
              hwSecClusterDeviceID, 
			  hwSecClusterStatus,
			  hwSecClusterPeerID,
			  hwSecClusterNegUporDown,
			  hwSecClusterNegNewUporDown, 
              hwSecClusterNegHelloType			  
		        }
		STATUS     current
		DESCRIPTION
		    "The neighbor up or down changed."
		::= { hwSecClusterTraps 2 }
		
		-- 1.3.6.1.4.1.2011.6.122.85.2.3 
		hwSecClusterFSMChange NOTIFICATION-TYPE
		OBJECTS { 
			  hwSecClusterID,
              hwSecClusterDeviceID, 
			  hwSecClusterStatus,
			  hwSecClusterNewStatus			  
		        }
		STATUS     current
		DESCRIPTION
		    "The negotiation status change."
		::= { hwSecClusterTraps 3 }
		
		-- 1.3.6.1.4.1.2011.6.122.85.2.4 
		hwSecClusterDoubleMaster NOTIFICATION-TYPE
		OBJECTS { 
			  hwSecClusterID,
              hwSecClusterDeviceID, 
			  hwSecClusterNegPriority,
			  hwSecClusterNegLocalSlaveNum,
			  hwSecClusterPeerID,
			  hwSecClusterNegPeerPriority,
			  hwSecClusterNegPeerSlaveNum, 
              hwSecClusterNegHelloType		  
		        }
		STATUS     current
		DESCRIPTION
		    "Double master in one cluster."
		::= { hwSecClusterTraps 4 }


		-- 1.3.6.1.4.1.2011.6.122.85.2.5 
		hwSecClusterChannelChange NOTIFICATION-TYPE
		OBJECTS { 
			  hwSecClusterPeerID,
              hwSecClusterDeviceID, 
              hwSecClusterChannelType,  
              hwSecClusterChannelProtocol,
              hwSecClusterNewStatus		  
		        }
		STATUS     current
		DESCRIPTION
		    "Channel protocol type(negotiation,backup,forward) change."
		::= { hwSecClusterTraps 5 }



		-- 1.3.6.1.4.1.2011.6.122.85.2.6 
		hwSecClusterBgChange NOTIFICATION-TYPE
		OBJECTS {  
			  hwSecClusterID,  
			  hwSecClusterDeviceID,
			  hwSecClusterbgid,  
			  hwSecClusterStatus,  
              hwSecClusterNewStatus		  
		        }
		STATUS     current
		DESCRIPTION
		    "Business group status change."
		::= { hwSecClusterTraps 6 }
		
    END

--
-- HUAWEI-SECURITY-CLUSTER-MIB.mib
--
