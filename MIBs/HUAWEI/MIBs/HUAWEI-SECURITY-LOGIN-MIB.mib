--    ================================================================================================
-- Copyright (C) 2017 by HUAWEI TECHNOLOGIES. All rights reserved.
--    
-- Description:  
-- Reference: Huawei Enterprise MIB
-- Version: V1.03
-- History: 
--          V1.0 The initial version created by Zuoyi 90006056.
--          V1.03 Modify the description for 1.3.6.1.4.1.2011.6.122.62.2.1 and 1.3.6.1.4.1.2011.6.122.62.2.2 by Liuyisha 00355330
-- =================================================================================================

	HUAWEI-SECURITY-LOGIN-MIB DEFINITIONS ::= BEGIN
 
		IMPORTS
			enterprises			
				FROM RFC1155-SMI			
			OBJECT-GROUP, MODULE-COMPLIANCE, NOTIFICATION-GROUP			
				FROM SNMPv2-CONF			
			IpAddress, OBJECT-TYPE, MODULE-IDENTITY, NOTIFICATION-TYPE			
				FROM SNMPv2-SMI;
	
	
		-- 1.3.6.1.4.1.2011.6.122.62
		hwLOGIN MODULE-IDENTITY 
			LAST-UPDATED "201701031102Z"		-- January 03, 2017 at 11:02 GMT
			ORGANIZATION 
				"Huawei Technologies Co.,Ltd."
			CONTACT-INFO 
				"Huawei Industrial Base
                                 Bantian, Longgang
                                 Shenzhen 518129
                                 People's Republic of China
                                 Website: http://www.huawei.com
                                 Email: support@huawei.com"   
                                 


			DESCRIPTION 
				"V1.00
				The LOGIN mib is for Eudemon and USG product series."
             --  Revision history
                                                                REVISION    "201701031102Z"
											DESCRIPTION "V1.03, modify 1.3.6.1.4.1.2011.6.122.62.2.1 and 1.3.6.1.4.1.2011.6.122.62.2.2."
                                                                REVISION    "201604141736Z"
											DESCRIPTION "V1.01, completed the first draft."
			REVISION    "201303081900Z"
											DESCRIPTION "V1.00, completed the first draft."
			::= { hwSecurity 62 }

		
	
-- ===============================================
-- Node definitions
-- ===============================================
		-- 1.3.6.1.4.1.2011
		huawei OBJECT IDENTIFIER ::= { enterprises 2011 }

		
		-- 1.3.6.1.4.1.2011.6
		huaweiUtility OBJECT IDENTIFIER ::= { huawei 6 }

		
		-- 1.3.6.1.4.1.2011.6.122
		hwSecurity OBJECT IDENTIFIER ::= { huaweiUtility 122 }

		
		-- 1.3.6.1.4.1.2011.6.122.62.1
		hwSecLOGINTrapObjects OBJECT IDENTIFIER ::= { hwLOGIN 1 }

		
--       ===============================================
-- TrapObject.
-- ===============================================
	                     -- 1.3.6.1.4.1.2011.6.122.62.1.1
		hwSecLOGINUser OBJECT-TYPE
			SYNTAX OCTET STRING (SIZE (1..64))
			MAX-ACCESS accessible-for-notify
			STATUS current
			DESCRIPTION
				"The user name."
			::= { hwSecLOGINTrapObjects 1 }

		-- 1.3.6.1.4.1.2011.6.122.62.1.2
		hwSecLOGINIP OBJECT-TYPE
			SYNTAX IpAddress
			MAX-ACCESS accessible-for-notify
			STATUS current
			DESCRIPTION
				"The User IP address."
			::= { hwSecLOGINTrapObjects 2 }

                                         -- 1.3.6.1.4.1.2011.6.122.62.1.3
                                         hwSecLOGINTime OBJECT-TYPE
			SYNTAX OCTET STRING (SIZE (1..32))
			MAX-ACCESS accessible-for-notify
			STATUS current
			DESCRIPTION
				"The User login time."
			::= { hwSecLOGINTrapObjects 3 }

                                         -- 1.3.6.1.4.1.2011.6.122.62.1.4
                                         hwSecLOGINType OBJECT-TYPE
			SYNTAX OCTET STRING (SIZE (1..32))
			MAX-ACCESS accessible-for-notify
			STATUS current
			DESCRIPTION
				"The User access type."
			::= { hwSecLOGINTrapObjects 4 }

                                         -- 1.3.6.1.4.1.2011.6.122.62.1.5
                                         hwSecLOGINLevel OBJECT-TYPE			
                                                                SYNTAX OCTET STRING (SIZE (1..32))	
                                                                MAX-ACCESS accessible-for-notify
			STATUS current
			DESCRIPTION
				"The User login level."
			::= { hwSecLOGINTrapObjects 5 }

                                           
		-- 1.3.6.1.4.1.2011.6.122.62.2
		hwSecLOGINTraps OBJECT IDENTIFIER ::= { hwLOGIN 2 }

		
		-- 1.3.6.1.4.1.2011.6.122.62.2.1
		hwSecLOGINFailed NOTIFICATION-TYPE
			OBJECTS { hwSecLOGINUser, hwSecLOGINIP, hwSecLOGINTime,hwSecLOGINType,hwSecLOGINLevel}
			STATUS current
			DESCRIPTION 
				"The user login failed."
			::= { hwSecLOGINTraps 1 }

		 
		-- 1.3.6.1.4.1.2011.6.122.62.2.2
		hwSecLOGINSucced NOTIFICATION-TYPE
			OBJECTS { hwSecLOGINUser, hwSecLOGINIP, hwSecLOGINTime,hwSecLOGINType,hwSecLOGINLevel}
			STATUS current
			DESCRIPTION 
				"The user login succeeded."
			::= { hwSecLOGINTraps 2 }


                                        -- 1.3.6.1.4.1.2011.6.122.62.2.3
		hwSecLOGOUTSucced NOTIFICATION-TYPE
			OBJECTS { hwSecLOGINUser, hwSecLOGINIP, hwSecLOGINTime,hwSecLOGINType}
			STATUS current
			DESCRIPTION 
				"The user logout succeeded."
			::= { hwSecLOGINTraps 3 }

		 
		-- 1.3.6.1.4.1.2011.6.122.62.2.4
		hwSecLOGOUTFailed NOTIFICATION-TYPE
			OBJECTS { hwSecLOGINUser, hwSecLOGINIP, hwSecLOGINTime,hwSecLOGINType}
			STATUS current
			DESCRIPTION 
				"The user logout failed."
			::= { hwSecLOGINTraps 4 }

		 
		-- 1.3.6.1.4.1.2011.6.122.62.3
		hwSecLOGINConformance OBJECT IDENTIFIER ::= { hwLOGIN 3 }

		
		-- 1.3.6.1.4.1.2011.6.122.62.3.1
		hwSecLOGINCompliances OBJECT IDENTIFIER ::= { hwSecLOGINConformance 1 }

		
-- this module
		-- 1.3.6.1.4.1.2011.6.122.62.3.1.1
		hwSecLOGINCompliance MODULE-COMPLIANCE
			STATUS current
			DESCRIPTION 
				"Description."
			MODULE -- this module
				MANDATORY-GROUPS { hwSecLOGINTrapObjectsGroup, hwSecLOGINTrapGroup }
			::= { hwSecLOGINCompliances 1 }

		
		-- 1.3.6.1.4.1.2011.6.122.62.3.2
		hwSecLOGINGroups OBJECT IDENTIFIER ::= { hwSecLOGINConformance 2 }

		
		-- 1.3.6.1.4.1.2011.6.122.62.3.2.1
		hwSecLOGINTrapObjectsGroup OBJECT-GROUP
			OBJECTS { hwSecLOGINUser, hwSecLOGINIP, hwSecLOGINTime,hwSecLOGINType,hwSecLOGINLevel}			
                                                                STATUS current
			DESCRIPTION 
				"Description."
			::= { hwSecLOGINGroups 1 }

		-- 1.3.6.1.4.1.2011.6.122.62.3.2.2
		hwSecLOGINTrapGroup NOTIFICATION-GROUP
			NOTIFICATIONS { hwSecLOGINSucced }
			STATUS current
			DESCRIPTION 
				"Description."
			::= { hwSecLOGINGroups 2 }
                           		

	END

--
-- HUAWEI-SECURITY-LOGIN-MIB.mib
--
