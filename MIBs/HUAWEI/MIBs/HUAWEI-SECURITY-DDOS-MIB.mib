--
-- HUAWEI-SECURITY-DDOS-MIB.mib
-- MIB generated by MG-SOFT Visual MIB Builder Version 6.0  Build 88
-- Wednesday, January 31, 2018 at 15:17:24
--

--  HUAWEISECURITYDDOSMIB.mib
-- MIB generated by MGSOFT Visual MIB Builder Version 6.0  Build 88
-- Monday, January 22, 2018 at 14:44:13
-- 
--   =============================================================================
-- Copyright (C) 2018 by HUAWEI TECHNOLOGIES. All rights reserved.
--    
-- Description:  
-- Reference: Huawei Enterprise MIB
-- Version: V1.00
-- History: 
--          V1.00 The initial version created by Wujiaying 428238. 
-- =============================================================================

	HUAWEI-SECURITY-DDOS-MIB DEFINITIONS ::= BEGIN
 
		IMPORTS
			enterprises			
				FROM RFC1155-SMI			
			OBJECT-GROUP, MODULE-COMPLIANCE, NOTIFICATION-GROUP			
				FROM SNMPv2-CONF			
			Integer32, OBJECT-TYPE, MODULE-IDENTITY, NOTIFICATION-TYPE			
				FROM SNMPv2-SMI;
	
	
		-- 1.3.6.1.4.1.2011.6.122.1
		hwSecDDOS MODULE-IDENTITY 
			LAST-UPDATED "201801221444Z"		-- January 22, 2018 at 14:44 GMT
			ORGANIZATION 
				"Huawei Technologies Co.,Ltd."
			CONTACT-INFO 
				"Huawei Industrial Base Bantian, Longgang Shenzhen 518129 People's Republic of China Website: http://www.huawei.com Email: support@huawei.com
				"
			DESCRIPTION 
				"V1.00
				DDOS trap function."
			REVISION "201801221444Z"		-- January 22, 2018 at 14:44 GMT
			DESCRIPTION 
				"V1.00, completed the first draft."
			::= { hwSecurity 1 }

		
	
--
-- Node definitions
--
	
--  1.3.6.1.4.1.2011.6.122.1
-- January 22, 2018 at 14:44 GMT
-- 
-- Node definitions
-- 
--  1.3.6.1.4.1.2011.6.122.1
-- January 22, 2018 at 14:44 GMT
-- 
-- Node definitions
-- 
--  1.3.6.1.4.1.2011.6.122.1
-- June 09, 2014 at 20:24 GMT
-- 
-- Node definitions
-- 
--  1.3.6.1.4.1.2011.6.122.1
-- June 09, 2014 at 20:24 GMT
-- 
-- Node definitions
-- 
-- 1.3.6.1.4.1.2011
-- 1.3.6.1.4.1.2011
-- 1.3.6.1.4.1.2011
-- 1.3.6.1.4.1.2011
		-- 1.3.6.1.4.1.2011
		huawei OBJECT IDENTIFIER ::= { enterprises 2011 }

		
--     1.3.6.1.4.1.2011.6
-- 1.3.6.1.4.1.2011.6
-- 1.3.6.1.4.1.2011.6
-- 1.3.6.1.4.1.2011.6
		-- 1.3.6.1.4.1.2011.6
		huaweiUtility OBJECT IDENTIFIER ::= { huawei 6 }

		
--     1.3.6.1.4.1.2011.6.122
-- 1.3.6.1.4.1.2011.6.122
-- 1.3.6.1.4.1.2011.6.122
-- 1.3.6.1.4.1.2011.6.122
		-- 1.3.6.1.4.1.2011.6.122
		hwSecurity OBJECT IDENTIFIER ::= { huaweiUtility 122 }

		
--     1.3.6.1.4.1.2011.6.122.1.1
-- 1.3.6.1.4.1.2011.6.122.1.1
-- 1.3.6.1.4.1.2011.6.122.1.1
-- 1.3.6.1.4.1.2011.6.122.1.1
		-- 1.3.6.1.4.1.2011.6.122.1.1
		hwSecDDOSTrapObjects OBJECT IDENTIFIER ::= { hwSecDDOS 1 }

		
--     1.3.6.1.4.1.2011.6.122.1.1.1
-- 1.3.6.1.4.1.2011.6.122.1.1.1
-- 1.3.6.1.4.1.2011.6.122.1.1.1
-- 1.3.6.1.4.1.2011.6.122.1.1.1
		-- 1.3.6.1.4.1.2011.6.122.1.1.1
		hwSecDDOSAttackType OBJECT-TYPE
			SYNTAX OCTET STRING
			MAX-ACCESS accessible-for-notify
			STATUS current
			DESCRIPTION
				"The type of DDoS attack(SYNFLOOD,ACKFLOOD,UDPFLOOD,etc.)"
			::= { hwSecDDOSTrapObjects 1 }

		
--     1.3.6.1.4.1.2011.6.122.1.1.2
-- 1.3.6.1.4.1.2011.6.122.1.1.2
-- 1.3.6.1.4.1.2011.6.122.1.1.2
-- 1.3.6.1.4.1.2011.6.122.1.1.2
		-- 1.3.6.1.4.1.2011.6.122.1.1.2
		hwSecDDOSZoneId OBJECT-TYPE
			SYNTAX Integer32
			MAX-ACCESS accessible-for-notify
			STATUS current
			DESCRIPTION
				"The ID of protected network zone."
			::= { hwSecDDOSTrapObjects 2 }

		
--     1.3.6.1.4.1.2011.6.122.1.1.3
-- 1.3.6.1.4.1.2011.6.122.1.1.3
-- 1.3.6.1.4.1.2011.6.122.1.1.3
-- 1.3.6.1.4.1.2011.6.122.1.1.3
		-- 1.3.6.1.4.1.2011.6.122.1.1.3
		hwSecDDOSZoneName OBJECT-TYPE
			SYNTAX OCTET STRING
			MAX-ACCESS accessible-for-notify
			STATUS current
			DESCRIPTION
				"The name of protected network zone."
			::= { hwSecDDOSTrapObjects 3 }

		
--     1.3.6.1.4.1.2011.6.122.1.1.5
-- 1.3.6.1.4.1.2011.6.122.1.1.5
-- 1.3.6.1.4.1.2011.6.122.1.1.4
-- 1.3.6.1.4.1.2011.6.122.1.1.4
		-- 1.3.6.1.4.1.2011.6.122.1.1.4
		hwSecDDOSDstIP OBJECT-TYPE
			SYNTAX OCTET STRING
			MAX-ACCESS accessible-for-notify
			STATUS current
			DESCRIPTION
				"Attacked destination IP address."
			::= { hwSecDDOSTrapObjects 4 }

		
--     1.3.6.1.4.1.2011.6.122.1.1.6
-- 1.3.6.1.4.1.2011.6.122.1.1.6
-- 1.3.6.1.4.1.2011.6.122.1.1.5
-- 1.3.6.1.4.1.2011.6.122.1.1.5
		-- 1.3.6.1.4.1.2011.6.122.1.1.5
		hwSecDDOSStartTime OBJECT-TYPE
			SYNTAX OCTET STRING
			MAX-ACCESS accessible-for-notify
			STATUS current
			DESCRIPTION
				"The start time of DDoS attack."
			::= { hwSecDDOSTrapObjects 5 }

		
--     1.3.6.1.4.1.2011.6.122.1.1.7
-- 1.3.6.1.4.1.2011.6.122.1.1.7
-- 1.3.6.1.4.1.2011.6.122.1.1.6
-- 1.3.6.1.4.1.2011.6.122.1.1.6
		-- 1.3.6.1.4.1.2011.6.122.1.1.6
		hwSecDDOSEndTime OBJECT-TYPE
			SYNTAX OCTET STRING
			MAX-ACCESS accessible-for-notify
			STATUS current
			DESCRIPTION
				"The end time of DDoS attack."
			::= { hwSecDDOSTrapObjects 6 }

		
		-- 1.3.6.1.4.1.2011.6.122.1.1.7
		hwSecDDOSDeviceType OBJECT-TYPE
			SYNTAX OCTET STRING
			MAX-ACCESS accessible-for-notify
			STATUS current
			DESCRIPTION
				"The type of device,including DETECT and CLEAN."
			::= { hwSecDDOSTrapObjects 7 }

		
--     1.3.6.1.4.1.2011.6.122.1.2
-- 1.3.6.1.4.1.2011.6.122.1.2
-- 1.3.6.1.4.1.2011.6.122.1.2
-- 1.3.6.1.4.1.2011.6.122.1.2
		-- 1.3.6.1.4.1.2011.6.122.1.2
		hwSecDDOSTraps OBJECT IDENTIFIER ::= { hwSecDDOS 2 }

		
--     1.3.6.1.4.1.2011.6.122.1.2.1
-- 1.3.6.1.4.1.2011.6.122.1.2.1
-- 1.3.6.1.4.1.2011.6.122.1.2.1
-- 1.3.6.1.4.1.2011.6.122.1.2.1
		-- 1.3.6.1.4.1.2011.6.122.1.2.1
		hwSecDDOSAttackBegin NOTIFICATION-TYPE
			OBJECTS { hwSecDDOSAttackType, hwSecDDOSZoneId, hwSecDDOSZoneName, hwSecDDOSDstIP, hwSecDDOSStartTime, 
				hwSecDDOSDeviceType }
			STATUS current
			DESCRIPTION 
				"The ddos attack start."
			::= { hwSecDDOSTraps 1 }

		
--     1.3.6.1.4.1.2011.6.122.1.2.2
-- 1.3.6.1.4.1.2011.6.122.1.2.2
-- 1.3.6.1.4.1.2011.6.122.1.2.2
-- 1.3.6.1.4.1.2011.6.122.1.2.2
		-- 1.3.6.1.4.1.2011.6.122.1.2.2
		hwSecDDOSAttackEnd NOTIFICATION-TYPE
			OBJECTS { hwSecDDOSAttackType, hwSecDDOSZoneId, hwSecDDOSZoneName, hwSecDDOSDstIP, hwSecDDOSEndTime, 
				hwSecDDOSDeviceType }
			STATUS current
			DESCRIPTION 
				"The ddos attack end."
			::= { hwSecDDOSTraps 2 }

		
--     1.3.6.1.4.1.2011.6.122.1.3
-- 1.3.6.1.4.1.2011.6.122.1.3
-- 1.3.6.1.4.1.2011.6.122.1.3
-- 1.3.6.1.4.1.2011.6.122.1.3
		-- 1.3.6.1.4.1.2011.6.122.1.3
		hwSecDDOSConformance OBJECT IDENTIFIER ::= { hwSecDDOS 3 }

		
--     1.3.6.1.4.1.2011.6.122.1.3.1
-- 1.3.6.1.4.1.2011.6.122.1.3.1
-- 1.3.6.1.4.1.2011.6.122.1.3.1
-- 1.3.6.1.4.1.2011.6.122.1.3.1
		-- 1.3.6.1.4.1.2011.6.122.1.3.1
		hwSecDDOSCompliances OBJECT IDENTIFIER ::= { hwSecDDOSConformance 1 }

		
--     1.3.6.1.4.1.2011.6.122.1.3.1.1
-- 1.3.6.1.4.1.2011.6.122.1.3.1.1
-- 1.3.6.1.4.1.2011.6.122.1.3.1.1
-- 1.3.6.1.4.1.2011.6.122.1.3.1.1
		-- 1.3.6.1.4.1.2011.6.122.1.3.1.1
		hwSecDDOSCompliance MODULE-COMPLIANCE
			STATUS current
			DESCRIPTION 
				"Description."
			MODULE HUAWEI-SECURITY-DDOS-MIB
				MANDATORY-GROUPS { hwSecDDOSTrapObjectsGroup, hwSecDDOSTrapGroup }
			::= { hwSecDDOSCompliances 1 }

		
--     1.3.6.1.4.1.2011.6.122.1.3.2
-- 1.3.6.1.4.1.2011.6.122.1.3.2
-- 1.3.6.1.4.1.2011.6.122.1.3.2
-- 1.3.6.1.4.1.2011.6.122.1.3.2
		-- 1.3.6.1.4.1.2011.6.122.1.3.2
		hwSecDDOSGroups OBJECT IDENTIFIER ::= { hwSecDDOSConformance 2 }

		
--     1.3.6.1.4.1.2011.6.122.1.3.2.1
-- 1.3.6.1.4.1.2011.6.122.1.3.2.1
-- 1.3.6.1.4.1.2011.6.122.1.3.2.1
-- 1.3.6.1.4.1.2011.6.122.1.3.2.1
		-- 1.3.6.1.4.1.2011.6.122.1.3.2.1
		hwSecDDOSTrapObjectsGroup OBJECT-GROUP
			OBJECTS { hwSecDDOSAttackType, hwSecDDOSZoneId, hwSecDDOSZoneName, hwSecDDOSDstIP, hwSecDDOSStartTime, 
				hwSecDDOSEndTime, hwSecDDOSDeviceType }
			STATUS current
			DESCRIPTION 
				"Description."
			::= { hwSecDDOSGroups 1 }

		
--     1.3.6.1.4.1.2011.6.122.1.3.2.2
-- 1.3.6.1.4.1.2011.6.122.1.3.2.2
-- 1.3.6.1.4.1.2011.6.122.1.3.2.2
-- 1.3.6.1.4.1.2011.6.122.1.3.2.2
		-- 1.3.6.1.4.1.2011.6.122.1.3.2.2
		hwSecDDOSTrapGroup NOTIFICATION-GROUP
			NOTIFICATIONS { hwSecDDOSAttackBegin, hwSecDDOSAttackEnd }
			STATUS current
			DESCRIPTION 
				"Description."
			::= { hwSecDDOSGroups 2 }

		
	
	END

--
-- HUAWEI-SECURITY-DDOS-MIB.mib
--
