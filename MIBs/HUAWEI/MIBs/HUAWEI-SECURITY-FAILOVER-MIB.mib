--
-- HUAWEI-SECURITY-FAILOVER-MIB.mib
-- MIB generated by MG-SOFT Visual MIB Builder Version 4.0 Build 341
-- Monday, August 7, 2017 at 15:31:13
-- 
-- =================================================================
-- Copyright (C) 2017 by  HUAWEI TECHNOLOGIES. All rights reserved
-- 
-- Description:
-- Reference:
-- Version: V1.00
-- History:
-- =================================================================

	HUAWEI-SECURITY-FAILOVER-MIB DEFINITIONS ::= BEGIN
 
		IMPORTS
			enterprises			
				FROM RFC1155-SMI			
			OBJECT-GROUP			
				FROM SNMPv2-CONF			
			Integer32, Gauge32, Counter64, OBJECT-TYPE, MODULE-IDENTITY, 
			NOTIFICATION-TYPE			
				FROM SNMPv2-SMI			
			TruthValue			
				FROM SNMPv2-TC;	
	
		-- 1.3.6.1.4.1.2011.6.122.84.1
		hwSecFailoverTrap MODULE-IDENTITY 
			LAST-UPDATED "201708071531Z"		-- Aug 07, 2017 at 15:31 GMT
			ORGANIZATION 
				"Huawei Technologies Co.,Ltd."
			CONTACT-INFO
				"Huawei Industrial Base
                                 Bantian, Longgang
                                 Shenzhen 518129
                                 People's Republic of China
                                 Website: http://www.huawei.com
                                 Email: support@huawei.com"
								 
			
			DESCRIPTION 
                "
                V1.00
                The HUAWEI-SECURITY-FAILOVER-MIB contains objects to manage the firewall failover module.
                "        
			REVISION  "201708071531Z"		
			DESCRIPTION "The HUAWEI-SECURITY-FAILOVER-MIB contains objects to manage the firewall failover module. "  
                 			     ::= { hwSecFailoverMib 1 }  		
	
--
-- Node definitions
--
	
		-- 1.3.6.1.4.1.2011
		huawei OBJECT IDENTIFIER ::= { enterprises 2011 }

		
		-- 1.3.6.1.4.1.2011.6
		huaweiUtility OBJECT IDENTIFIER ::= { huawei 6 }
		
		-- 1.3.6.1.4.1.2011.6.122
		hwSecurity OBJECT IDENTIFIER ::= { huaweiUtility 122 }

		-- 1.3.6.1.4.1.2011.6.122.84
		hwSecFailoverMib OBJECT IDENTIFIER ::= { hwSecurity 84 }

		-- 1.3.6.1.4.1.2011.6.122.84.1.1
		hwSecFailoverObjects OBJECT IDENTIFIER ::= { hwSecFailoverTrap 1 }
		
		-- 1.3.6.1.4.1.2011.6.122.84.1.1.1
		hwSecFailoverTrapSlot OBJECT-TYPE
			SYNTAX Integer32 (1..16)
			MAX-ACCESS accessible-for-notify
			STATUS current
			DESCRIPTION
				"The slot number."
			::= { hwSecFailoverObjects 1 }
		
		-- 1.3.6.1.4.1.2011.6.122.84.1.1.2
		hwSecFailoverTrapCPU OBJECT-TYPE
			SYNTAX Integer32 (0..3)
			MAX-ACCESS accessible-for-notify
			STATUS current
			DESCRIPTION
				"The CPU number."
			::= { hwSecFailoverObjects 2 }
			
		-- 1.3.6.1.4.1.2011.6.122.84.1.1.3
		hwSecFailoverOldState OBJECT-TYPE
			SYNTAX OCTET STRING (SIZE(0..16))
			MAX-ACCESS read-only
			STATUS current
			DESCRIPTION
				"The CPU old state."
			::= { hwSecFailoverObjects 3 }
		
		-- 1.3.6.1.4.1.2011.6.122.84.1.1.4
		hwSecFailoverNewState OBJECT-TYPE
			SYNTAX OCTET STRING (SIZE(0..16))
			MAX-ACCESS read-only
			STATUS current
			DESCRIPTION
				"The CPU new state."
			::= { hwSecFailoverObjects 4 }	
	
		-- 1.3.6.1.4.1.2011.6.122.84.1.2
		hwSecFailoverCpuTraps OBJECT IDENTIFIER ::= { hwSecFailoverTrap 2 }
		
		-- 1.3.6.1.4.1.2011.6.122.84.1.2.1
		hwSecFailoverCpuState NOTIFICATION-TYPE
			OBJECTS { hwSecFailoverTrapSlot, hwSecFailoverTrapCPU, hwSecFailoverOldState, hwSecFailoverNewState }
			STATUS current
			DESCRIPTION 
				"The failover CPU state change from old state to new state."
			::= { hwSecFailoverCpuTraps 1 }
			 								
	END

--
-- HUAWEI-SECURITY-FAILOVER-MIB.mib
--
