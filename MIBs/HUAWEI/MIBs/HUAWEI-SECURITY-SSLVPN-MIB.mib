--
-- HUAWEI-SECURITY-SSLVPN-MIB.mib
-- MIB generated by MG-SOFT Visual MIB Builder Version 4.0 Build 341
-- Friday, February 3, 2017 at 15:31:13
-- 
-- =================================================================
-- Copyright (C) 2018 by  HUAWEI TECHNOLOGIES. All rights reserved
-- 
-- Description:
-- Reference:
-- Version: V1.01
-- History:
-- =================================================================

	HUAWEI-SECURITY-SSLVPN-MIB DEFINITIONS ::= BEGIN
 
		IMPORTS
			enterprises			
				FROM RFC1155-SMI			
			OBJECT-GROUP			
				FROM SNMPv2-CONF			
			Integer32, Gauge32, Counter64, OBJECT-TYPE, MODULE-IDENTITY, 
			NOTIFICATION-TYPE			
				FROM SNMPv2-SMI			
			TruthValue			
				FROM SNMPv2-TC;	
	
		-- 1.3.6.1.4.1.2011.6.122.44.1
		hwSecSslvpnTrap MODULE-IDENTITY 
			LAST-UPDATED "201810111531Z"		-- Oct 11, 2018 at 15:31 GMT
			ORGANIZATION 
				"Huawei Technologies Co.,Ltd."
			CONTACT-INFO
				"Huawei Industrial Base
                                 Bantian, Longgang
                                 Shenzhen 518129
                                 People's Republic of China
                                 Website: http://www.huawei.com
                                 Email: support@huawei.com"
								 
		DESCRIPTION 
			"V1.01 The HUAWEI-SECURITY-SSLVPN-MIB contains objects to manage the firewall sslvpn module."
			REVISION "201810111531Z"		
			DESCRIPTION 
            "V1.00 The HUAWEI-SECURITY-SSLVPN-MIB contains objects to manage the firewall sslvpn module."        
			REVISION "201702031531Z"		
			DESCRIPTION "The HUAWEI-SECURITY-SSLVPN-MIB contains objects to manage the firewall sslvpn module. "  
                 			     ::= { hwSecSslvpnMib 1 }  		
	
--
-- Node definitions
--
	
		-- 1.3.6.1.4.1.2011
		huawei OBJECT IDENTIFIER ::= { enterprises 2011 }

		
		-- 1.3.6.1.4.1.2011.6
		huaweiUtility OBJECT IDENTIFIER ::= { huawei 6 }
		
		-- 1.3.6.1.4.1.2011.6.122
		hwSecurity OBJECT IDENTIFIER ::= { huaweiUtility 122 }

		-- 1.3.6.1.4.1.2011.6.122.44
		hwSecSslvpnMib OBJECT IDENTIFIER ::= { hwSecurity 44 }

		-- 1.3.6.1.4.1.2011.6.122.44.1.1
		hwSecSslvpnObjects OBJECT IDENTIFIER ::= { hwSecSslvpnTrap 1 }
		
		-- 1.3.6.1.4.1.2011.6.122.44.1.1.1
		hwSecSslvpnTrapSlot OBJECT-TYPE
			SYNTAX Integer32 (1..16)
			MAX-ACCESS accessible-for-notify
			STATUS current
			DESCRIPTION
				"The slot number."
			::= { hwSecSslvpnObjects 1 }
		
		-- 1.3.6.1.4.1.2011.6.122.44.1.1.2
		hwSecSslvpnTrapCPU OBJECT-TYPE
			SYNTAX Integer32 (0..3)
			MAX-ACCESS accessible-for-notify
			STATUS current
			DESCRIPTION
				"The CPU number."
			::= { hwSecSslvpnObjects 2 }
			
		-- 1.3.6.1.4.1.2011.6.122.44.1.1.3
		hwSecSslvpnVsysName OBJECT-TYPE
			SYNTAX OCTET STRING (SIZE(0..33))
			MAX-ACCESS read-only
			STATUS current
			DESCRIPTION
				"The virtual system name."
			::= { hwSecSslvpnObjects 3 }
		
		-- 1.3.6.1.4.1.2011.6.122.44.1.1.4
		hwSecSslvpnVgName OBJECT-TYPE
			SYNTAX OCTET STRING (SIZE(0..16))
			MAX-ACCESS read-only
			STATUS current
			DESCRIPTION
				"The virtual gateway name."
			::= { hwSecSslvpnObjects 4 }

		-- 1.3.6.1.4.1.2011.6.122.44.1.1.5
		hwSecSslvpnUserTrapCount OBJECT-TYPE
			SYNTAX Gauge32
			MAX-ACCESS read-write
			STATUS current
			DESCRIPTION
				"Number of online user."
			::= { hwSecSslvpnObjects 5 }
			
	    -- 1.3.6.1.4.1.2011.6.122.44.1.1.6
		hwSecSslvpnUserTrapThreshold OBJECT-TYPE
			SYNTAX Integer32 (10..100)
			MAX-ACCESS read-write
			STATUS current
			DESCRIPTION
				"Alarm threshold of online user."
			::= { hwSecSslvpnObjects 6 }
	
		-- 1.3.6.1.4.1.2011.6.122.44.1.1.7
		hwSecSslvpnNetPoolCount OBJECT-TYPE
			SYNTAX Gauge32
			MAX-ACCESS read-write
			STATUS current
			DESCRIPTION
				"Number of used address."
			::= { hwSecSslvpnObjects 7 }
			
	    -- 1.3.6.1.4.1.2011.6.122.44.1.1.8
		hwSecSslvpnNetPoolThreshold OBJECT-TYPE
			SYNTAX Integer32 (10..100)
			MAX-ACCESS read-write
			STATUS current
			DESCRIPTION
				"Alarm threshold of used address."
			::= { hwSecSslvpnObjects 8 }	
	
	
		-- 1.3.6.1.4.1.2011.6.122.44.1.2
		hwSecSslvpnUserTraps OBJECT IDENTIFIER ::= { hwSecSslvpnTrap 2 }
		
		-- 1.3.6.1.4.1.2011.6.122.44.1.2.1
		hwSecSslvpnOnlineUserOverSpec NOTIFICATION-TYPE
			STATUS current
			DESCRIPTION 
				"The online user number of the device exceeds the specification."
			::= { hwSecSslvpnUserTraps 1 }
			
		-- 1.3.6.1.4.1.2011.6.122.44.1.2.2
		hwSecSslvpnOnlineUserBelowSpec NOTIFICATION-TYPE
			STATUS current
			DESCRIPTION 
				"The online user number of the device restores to be lower than the specification."
			::= { hwSecSslvpnUserTraps 2 }
			
		-- 1.3.6.1.4.1.2011.6.122.44.1.2.3
		hwSecSslvpnOnlineUserOverCpuSpec NOTIFICATION-TYPE
			OBJECTS { hwSecSslvpnTrapSlot, hwSecSslvpnTrapCPU }
			STATUS current
			DESCRIPTION 
				"The online user number of the CPU exceeds the specification."
			::= { hwSecSslvpnUserTraps 3 }
			
		-- 1.3.6.1.4.1.2011.6.122.44.1.2.4
		hwSecSslvpnOnlineUserBelowCpuSpec NOTIFICATION-TYPE
			OBJECTS { hwSecSslvpnTrapSlot, hwSecSslvpnTrapCPU }
			STATUS current
			DESCRIPTION 
				"The online user number of the CPU exceeds the specification."
			::= { hwSecSslvpnUserTraps 4 }
		
		-- 1.3.6.1.4.1.2011.6.122.44.1.2.5
		hwSecSslvpnUserOverThreshold NOTIFICATION-TYPE
			OBJECTS { hwSecSslvpnVsysName, hwSecSslvpnVgName, hwSecSslvpnUserTrapCount, hwSecSslvpnUserTrapThreshold }
			STATUS current
			DESCRIPTION 
				"The online user number of the virtual gateway exceeds the upper limit of the threshold."
			::= { hwSecSslvpnUserTraps 5 }

		-- 1.3.6.1.4.1.2011.6.122.44.1.2.6
		hwSecSslvpnUserBelowThreshold NOTIFICATION-TYPE
			OBJECTS { hwSecSslvpnVsysName, hwSecSslvpnVgName, hwSecSslvpnUserTrapCount, hwSecSslvpnUserTrapThreshold  }
			STATUS current
			DESCRIPTION 
				"The online user number of the virtual gateway restores to be lower than the threshold corresponding to the upper limit of the threshold."
			::= { hwSecSslvpnUserTraps 6 }
						
		-- 1.3.6.1.4.1.2011.6.122.44.1.3
		hwSecSslvpnNetPoolTraps OBJECT IDENTIFIER ::= { hwSecSslvpnTrap 3 }

		
		-- 1.3.6.1.4.1.2011.6.122.44.1.3.1
		hwSecSslvpnNetPoolOverThreshold NOTIFICATION-TYPE
			OBJECTS { hwSecSslvpnVsysName, hwSecSslvpnVgName, hwSecSslvpnNetPoolCount, hwSecSslvpnNetPoolThreshold  }
			STATUS current
			DESCRIPTION 
				"The used address number of the network extension exceeds the upper limit of the threshold."
			::= { hwSecSslvpnNetPoolTraps 1 }

		
		-- 1.3.6.1.4.1.2011.6.122.15.1.3.2
		hwSecSslvpnNetPoolBelowThreshold NOTIFICATION-TYPE
			OBJECTS { hwSecSslvpnVsysName, hwSecSslvpnVgName, hwSecSslvpnNetPoolCount, hwSecSslvpnNetPoolThreshold }
			STATUS current
			DESCRIPTION 
				"The used address number of the network extension restores to be lower than the threshold corresponding to the upper limit of the threshold."
			::= { hwSecSslvpnNetPoolTraps 2 }			 								
			 								
		-- 1.3.6.1.4.1.2011.6.122.44.2
		hwSecSslvpnDeviceUser OBJECT IDENTIFIER ::= { hwSecSslvpnMib 2 }
		
		-- 1.3.6.1.4.1.2011.6.122.44.2.1
		hwSecSslvpnDeviceUserNum OBJECT-TYPE 
			SYNTAX Gauge32
			MAX-ACCESS read-only
			STATUS current
			DESCRIPTION
				"The number of online users."
			::= { hwSecSslvpnDeviceUser 1 }			
					 						
			 								
	END

--
-- HUAWEI-SECURITY-SSLVPN-MIB.mib
--
