--
-- HUAWEI-SECURITY-SMARTLINK-MIB.mib
-- MIB generated by MG-SOFT Visual MIB Builder Version 4.0 Build 341
-- Friday, March 24, 2017 at 15:31:13
-- 
-- =================================================================
-- Copyright (C) 2017 by  HUAWEI TECHNOLOGIES. All rights reserved
-- 
-- Description:
-- Reference:
-- Version: V1.00
-- History:
-- =================================================================

	HUAWEI-SECURITY-SMARTLINK-MIB DEFINITIONS ::= BEGIN
 
		IMPORTS
			enterprises			
				FROM RFC1155-SMI			
			OBJECT-GROUP			
				FROM SNMPv2-CONF			
			Integer32, Gauge32, Counter64, OBJECT-TYPE, MODULE-IDENTITY, 
			NOTIFICATION-TYPE			
				FROM SNMPv2-SMI			
			TruthValue			
				FROM SNMPv2-TC;	
	
		-- 1.3.6.1.4.1.2011.6.122.82.1
		hwSecSmartLinkMib MODULE-IDENTITY 
			LAST-UPDATED "201703241531Z"		-- Mar 24, 2017 at 15:31 GMT
			ORGANIZATION 
				"Huawei Technologies Co.,Ltd."
			CONTACT-INFO
				"Huawei Industrial Base
                                 Bantian, Longgang
                                 Shenzhen 518129
                                 People's Republic of China
                                 Website: http://www.huawei.com
                                 Email: support@huawei.com"
								 
			
			DESCRIPTION 
                "
                V1.00
                The HUAWEI-SECURITY-SMARTLINK-MIB contains objects to manage the firewall smart-link module.
                "        
			REVISION  "201703241531Z"		
			DESCRIPTION "The HUAWEI-SECURITY-SMARTLINK-MIB contains objects to manage the firewall smart-link module. "  
                 			     ::= { hwSecurity 82 }  		
	
--
-- Node definitions
--
	
		-- 1.3.6.1.4.1.2011
		huawei OBJECT IDENTIFIER ::= { enterprises 2011 }

		
		-- 1.3.6.1.4.1.2011.6
		huaweiUtility OBJECT IDENTIFIER ::= { huawei 6 }
		
		-- 1.3.6.1.4.1.2011.6.122
		hwSecurity OBJECT IDENTIFIER ::= { huaweiUtility 122 }

		
		-- 1.3.6.1.4.1.2011.6.122.82.1.1
		hwSecSmartLinkObjects OBJECT IDENTIFIER ::= { hwSecSmartLinkMib 1 }
		
		-- 1.3.6.1.4.1.2011.6.122.82.1.1.1
		hwSmartLinkTrapTunnelPolicyName OBJECT-TYPE
			SYNTAX OCTET STRING (SIZE (1..255))
			MAX-ACCESS accessible-for-notify
			STATUS current
			DESCRIPTION
					"Security policy for the IPSec tunnel."
			::= { hwSecSmartLinkObjects 1 }  
		-- 1.3.6.1.4.1.2011.6.122.82.1.1.2
		hwSmartLinkTrapOldLinkDstIP OBJECT-TYPE
        	SYNTAX OCTET STRING (SIZE (1..128))
        	MAX-ACCESS accessible-for-notify
        	STATUS current
        	DESCRIPTION
            		"Destination IP address of the old link (peer end)."
        	::= { hwSecSmartLinkObjects 2 }
        			-- 1.3.6.1.4.1.2011.6.122.82.1.1.3
        hwSmartLinkTrapOldLinkSrcIP OBJECT-TYPE
        	SYNTAX OCTET STRING (SIZE (1..128))
        	MAX-ACCESS accessible-for-notify
        	STATUS current
        	DESCRIPTION
            		"Source IP address of the old link."
        	::= { hwSecSmartLinkObjects 3 }
		-- 1.3.6.1.4.1.2011.6.122.82.1.1.4
		hwSmartLinkTrapLossRate OBJECT-TYPE
        	SYNTAX Gauge32
        	MAX-ACCESS accessible-for-notify
        	STATUS current
        	DESCRIPTION
            		"Loss rate of IPSec."
        	::= { hwSecSmartLinkObjects 4 }	  
		-- 1.3.6.1.4.1.2011.6.122.82.1.1.5
       hwSmartLinkTrapDelay OBJECT-TYPE
        	SYNTAX Gauge32
        	MAX-ACCESS accessible-for-notify
        	STATUS current
        	DESCRIPTION
            		"Delay time of IPSec."
        	::= { hwSecSmartLinkObjects 5 }	
		-- 1.3.6.1.4.1.2011.6.122.82.1.1.6
       hwSmartLinkTrapSwitchType OBJECT-TYPE
        	SYNTAX OCTET STRING (SIZE (1..16))
        	MAX-ACCESS accessible-for-notify
        	STATUS current
        	DESCRIPTION
            		"Switch type of IPSec."
        	::= { hwSecSmartLinkObjects 6 }	
		
       hwSmartLinkTrapOldID OBJECT-TYPE
        	SYNTAX Gauge32
        	MAX-ACCESS accessible-for-notify
        	STATUS current
        	DESCRIPTION
            		"Old link ID of smart link."
        	::= { hwSecSmartLinkObjects 7 }	
		-- 1.3.6.1.4.1.2011.6.122.82.1.1.6
       hwSmartLinkTrapNewID OBJECT-TYPE
        	SYNTAX Gauge32
        	MAX-ACCESS accessible-for-notify
        	STATUS current
        	DESCRIPTION
            		"New link ID of smart link."
        	::= { hwSecSmartLinkObjects 8 }	
			
	hwSmartLinkTrapNewLinkDstIP OBJECT-TYPE
        	SYNTAX OCTET STRING (SIZE (1..128))
        	MAX-ACCESS accessible-for-notify
        	STATUS current
        	DESCRIPTION
            		"Destination IP address of the new link (peer end)."
        	::= { hwSecSmartLinkObjects 9 }
        			-- 1.3.6.1.4.1.2011.6.122.82.1.1.3
        hwSmartLinkTrapNewLinkSrcIP OBJECT-TYPE
        	SYNTAX OCTET STRING (SIZE (1..128))
        	MAX-ACCESS accessible-for-notify
        	STATUS current
        	DESCRIPTION
            		"Source IP address of the new link."
        	::= { hwSecSmartLinkObjects 10 }
		
		-- 1.3.6.1.4.1.2011.6.122.82.1.2
      hwSecSmartLinkTraps OBJECT IDENTIFIER ::= { hwSecSmartLinkMib 2 }
		
		-- 1.3.6.1.4.1.2011.6.122.82.1.2.1
		hwSecSmartLinkSwitchTrap NOTIFICATION-TYPE
		 OBJECTS {    
				hwSmartLinkTrapOldID,
				hwSmartLinkTrapOldLinkSrcIP,
				hwSmartLinkTrapOldLinkDstIP,
				hwSmartLinkTrapNewID,
				hwSmartLinkTrapNewLinkSrcIP,
				hwSmartLinkTrapNewLinkDstIP,
                hwSmartLinkTrapTunnelPolicyName,              
				hwSmartLinkTrapLossRate,       
				hwSmartLinkTrapDelay,       
				hwSmartLinkTrapSwitchType       
				} 
			STATUS current
			DESCRIPTION 
				 "Send the message when IPSec smart link switch."
			::= { hwSecSmartLinkTraps 1 }
				 								
	END

--
-- HUAWEI-SECURITY-SMARTLINK-MIB.mib
--
