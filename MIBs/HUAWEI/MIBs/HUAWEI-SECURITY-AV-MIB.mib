--
-- HUAWEI-SECURITY-AV-MIB.mib
-- MIB generated by MG-SOFT Visual MIB Builder Version 6.0  Build 88
-- Wednesday, June 06, 2018 at 17:14:35
--
-- 
--   =================================================================
-- Copyright (C) 2018 by  HUAWEI TECHNOLOGIES. All rights reserved
-- 
-- Description:
-- Reference:
-- Version: V1.00
-- History:
--          V1.00 The initial version created by WeiYingbin w00427251. 
-- =================================================================

	HUAWEI-SECURITY-AV-MIB DEFINITIONS ::= BEGIN
 
		IMPORTS
			enterprises			
				FROM RFC1155-SMI			
			OBJECT-GROUP, MODULE-COMPLIANCE, NOTIFICATION-GROUP			
				FROM SNMPv2-CONF			
			Integer32, OBJECT-TYPE, MODULE-IDENTITY, NOTIFICATION-TYPE			
				FROM SNMPv2-SMI;
	
	
		-- 1.3.6.1.4.1.2011.6.122.86
		hwSecAV MODULE-IDENTITY 
			LAST-UPDATED "201806061601Z"		-- June 06, 2018 at 16:01 GMT
			ORGANIZATION 
				"Huawei Technologies Co.,Ltd."
			CONTACT-INFO 
				"
				Huawei Industrial Base Bantian, Longgang Shenzhen 518129 People's Republic of China Website: http://www.huawei.com Email: support@huawei.com
				"
			DESCRIPTION 
				"
				V1.00  Pulled Out AV event Alert.
				"
			REVISION "201806061601Z"		-- June 06, 2018 at 16:01 GMT
			DESCRIPTION 
				"Version 1.0"
			::= { hwSecurity 86 }

		
	
-- ===============================================
-- Node definitions
-- ===============================================

-- 1.3.6.1.4.1.2011
		-- 1.3.6.1.4.1.2011
		huawei OBJECT IDENTIFIER ::= { enterprises 2011 }

		
--    1.3.6.1.4.1.2011.6
		-- 1.3.6.1.4.1.2011.6
		huaweiUtility OBJECT IDENTIFIER ::= { huawei 6 }

		
--    1.3.6.1.4.1.2011.6.122
		-- 1.3.6.1.4.1.2011.6.122
		hwSecurity OBJECT IDENTIFIER ::= { huaweiUtility 122 }

		
--    1.3.6.1.4.1.2011.6.122.86
-- hwSecAV OBJECT IDENTIFIER ::= { hwSecurity 86 }


		-- 1.3.6.1.4.1.2011.6.122.86.1
		hwSecAvTraps OBJECT IDENTIFIER ::= { hwSecAV 1 }

		
		-- 1.3.6.1.4.1.2011.6.122.86.1.1
		hwSecAvObjests OBJECT IDENTIFIER ::= { hwSecAvTraps 1 }

		
		-- 1.3.6.1.4.1.2011.6.122.86.1.1.2
		hwSecAvDetectObjects OBJECT IDENTIFIER ::= { hwSecAvObjests 2 }

		
		-- 1.3.6.1.4.1.2011.6.122.86.1.1.2.1
		hwSecAvDetectSrcIp OBJECT-TYPE
			SYNTAX OCTET STRING (SIZE (0..255))
			MAX-ACCESS accessible-for-notify
			STATUS current
			DESCRIPTION
				"
				Indicate the source IP address.
				"
			::= { hwSecAvDetectObjects 1 }

		
		-- 1.3.6.1.4.1.2011.6.122.86.1.1.2.2
		hwSecAvDetectDstIp OBJECT-TYPE
			SYNTAX OCTET STRING (SIZE (0..255))
			MAX-ACCESS accessible-for-notify
			STATUS current
			DESCRIPTION
				"
				Indicate the destination IP address.
				"
			::= { hwSecAvDetectObjects 2 }

		
		-- 1.3.6.1.4.1.2011.6.122.86.1.1.2.3
		hwSecAvDetectSrcPort OBJECT-TYPE
			SYNTAX Integer32 (0..65535)
			MAX-ACCESS accessible-for-notify
			STATUS current
			DESCRIPTION
				"
				Indicate the source port.
				"
			::= { hwSecAvDetectObjects 3 }

		
		-- 1.3.6.1.4.1.2011.6.122.86.1.1.2.4
		hwSecAvDetectDstPort OBJECT-TYPE
			SYNTAX Integer32 (0..65535)
			MAX-ACCESS accessible-for-notify
			STATUS current
			DESCRIPTION
				"
				Indicate the destination port.
				"
			::= { hwSecAvDetectObjects 4 }

		
		-- 1.3.6.1.4.1.2011.6.122.86.1.1.2.5
		hwSecAvDetectProtoType OBJECT-TYPE
			SYNTAX OCTET STRING (SIZE (0..255))
			MAX-ACCESS accessible-for-notify
			STATUS current
			DESCRIPTION
				"
				Indicate the protocol name or type.
				"
			::= { hwSecAvDetectObjects 5 }

		
		-- 1.3.6.1.4.1.2011.6.122.86.1.1.2.6
		hwSecAvDetectVirusName OBJECT-TYPE
			SYNTAX OCTET STRING (SIZE (0..255))
			MAX-ACCESS accessible-for-notify
			STATUS current
			DESCRIPTION
				"
				Indicate the virus name.
				"
			::= { hwSecAvDetectObjects 6 }

		
		-- 1.3.6.1.4.1.2011.6.122.86.1.1.2.7
		hwSecAvDetectFileName OBJECT-TYPE
			SYNTAX OCTET STRING (SIZE (0..255))
			MAX-ACCESS accessible-for-notify
			STATUS current
			DESCRIPTION
				"
				Indicate the file name.
				"
			::= { hwSecAvDetectObjects 7 }

		
		-- 1.3.6.1.4.1.2011.6.122.86.1.1.2.8
		hwSecAvDetectFileType OBJECT-TYPE
			SYNTAX OCTET STRING (SIZE (0..255))
			MAX-ACCESS accessible-for-notify
			STATUS current
			DESCRIPTION
				"
				Indicate the file type.
				"
			::= { hwSecAvDetectObjects 8 }

		
		-- 1.3.6.1.4.1.2011.6.122.86.1.1.2.9
		hwSecAvDetectAction OBJECT-TYPE
			SYNTAX INTEGER 
				{
                                                                             unknow(0),
				allow(1),
				alert(2),
                                                                             discard(3),
				block(4),
				pcap(5),
                                                                             blockIP(6),
				blockService(7),
				default(8),
                                                                             declare(9),
				deleteAttachment(10)
				}
			MAX-ACCESS read-only
			STATUS current
			DESCRIPTION
				"
				Indicate the action performed by the AV detector.
				"
			::= { hwSecAvDetectObjects 9 }

		
	    -- 1.3.6.1.4.1.2011.6.122.86.1.1.2.10
		hwSecAvDetectTime OBJECT-TYPE
			SYNTAX OCTET STRING (SIZE (1..64))
			MAX-ACCESS accessible-for-notify
			STATUS current
			DESCRIPTION
				"
				Indicate the AV detect time.
				"
			::= { hwSecAvDetectObjects 10 }

		
-- ===============================================
-- definition of traps.      
-- ===============================================
-- 1.3.6.1.4.1.2011.6.122.86.1.2
		hwSecAvAlert OBJECT IDENTIFIER ::= { hwSecAvTraps 2 }

		
-- 1.3.6.1.4.1.2011.6.122.86.1.2.1
		hwSecAvThreatAlert NOTIFICATION-TYPE
			OBJECTS { hwSecAvDetectSrcIp, hwSecAvDetectDstIp, hwSecAvDetectSrcPort, hwSecAvDetectDstPort, hwSecAvDetectProtoType, 
				hwSecAvDetectVirusName, hwSecAvDetectFileName, hwSecAvDetectFileType, hwSecAvDetectAction, hwSecAvDetectTime
				 }
			STATUS current
			DESCRIPTION 
				"
				When a virus was detected, send the trap information. 
				"
			::= { hwSecAvAlert 1 }

		
	
	END

--
-- HUAWEI-SECURITY-AV-MIB.mib
--
