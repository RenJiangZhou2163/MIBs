--
-- HUAWEI-LDAP-MIB1.my
-- MIB generated by MG-SOFT Visual MIB Builder Version 3.0 Build 253
-- Wednesday, February 28, 2018 at 16:15:11
--

--  ===================================================================
-- Copyright (C) 2017 by HUAWEI TECHNOLOGIES. All rights reserved.
-- Description: 
-- Reference:
-- Version: V1.00
-- ===================================================================

	HUAWEI-LDAP-MIB DEFINITIONS ::= BEGIN
 
		IMPORTS
			huaweiMgmt			
				FROM HUAWEI-MIB			
			IpAddress, Integer32, Unsigned32,Gauge32, OBJECT-TYPE, MODULE-IDENTITY			
				FROM SNMPv2-SMI			
			RowStatus			
				FROM SNMPv2-TC;
	
	
		hwLDAP MODULE-IDENTITY 
			LAST-UPDATED "201708111600Z"		-- August 11, 2017 at 16:00 GMT
			ORGANIZATION 
				"Huawei Technologies Co.,Ltd."
			CONTACT-INFO 
				"Huawei Industrial Base
				Bantian, Longgang
				Shenzhen 518129
				People's Republic of China
				Website: http://www.huawei.com
				Email: support@huawei.com
				"
			DESCRIPTION 
				"Please provide the descritpion."
			REVISION "201708111600Z"		-- August 11, 2017 at 16:00 GMT
			DESCRIPTION
				"V1.00, initial version."
			::= { huaweiMgmt 120 }
		
	
	
--
-- Node definitions
--
	
		-- 1.3.6.1.4.1.2011.5.120.1
		hwLdapSettingTable OBJECT IDENTIFIER ::= { hwLDAP 1 }
		
		-- 1.3.6.1.4.1.2011.5.120.1.1
		hwLdapSettingEntry OBJECT IDENTIFIER ::= { hwLdapSettingTable 1 }
		
		-- 1.3.6.1.4.1.2011.5.120.1.1.1
		hwSslVersion OBJECT-TYPE
			SYNTAX INTEGER
				{
				tlsv10(2),
				tlsv11(4),
				tlsv10tlsv11(6),
				tlsv12(8),
				tlsv10tlsv12(10),
				tlsv11tlsv12(12),
				tlsv10tlsv11tlsv12(14)
				}
			MAX-ACCESS read-create
			STATUS current
			DESCRIPTION
				"Description."
			::= { hwLdapSettingEntry 1 }
		
--  1.3.6.1.4.1.2011.5.120.2
		-- 1.3.6.1.4.1.2011.5.120.2
		hwLdapServerGroupTable OBJECT-TYPE
			SYNTAX SEQUENCE OF HwLdapServerGroupEntry
			MAX-ACCESS not-accessible
			STATUS current
			DESCRIPTION
				"Description."
			::= { hwLDAP 2 }
		
--  1.3.6.1.4.1.2011.5.120.2.1
		-- 1.3.6.1.4.1.2011.5.120.2.1
		hwLdapServerGroupEntry OBJECT-TYPE
			SYNTAX HwLdapServerGroupEntry
			MAX-ACCESS not-accessible
			STATUS current
			DESCRIPTION
				"Description."
			INDEX { hwLDAPServerGroupIndex }
			::= { hwLdapServerGroupTable 1 }
		
		HwLdapServerGroupEntry ::=
			SEQUENCE { 
				hwLDAPServerGroupIndex
					Integer32,
				hwLDAPServerGroupName
					OCTET STRING,
				hwLDAPServerGroupPriAuthenAddr
					IpAddress,
				hwLDAPServerGroupPriAuthenPort
					Unsigned32,
				hwLDAPServerGroupPriAuthenSslEnable
					INTEGER,
				hwLDAPServerGroupSecAuthenAddr
					IpAddress,
				hwLDAPServerGroupSecAuthenPort
					Unsigned32,
				hwLDAPServerGroupSecAuthenSslEnable
					INTEGER,
				hwLDAPServerGroupThiAuthenAddr
					IpAddress,
				hwLDAPServerGroupThiAuthenPort
					Unsigned32,
				hwLDAPServerGroupThiAuthenSslEnable
					INTEGER,
				hwLDAPServerGroupBaseDN
					OCTET STRING,
				hwLDAPServerGroupManagerDN
					OCTET STRING,
				hwLDAPServerGroupManagerPSW
					OCTET STRING,
				hwLDAPServerGroupManagerAnonymous
					INTEGER,
				hwLDAPServerGroupManagerWithBaseDN
					INTEGER,
				hwLDAPServerGroupAuthorBindUser
					INTEGER,
				hwLDAPServerGroupGroupFlt
					OCTET STRING,
				hwLDAPServerGroupIpAddrFlt
					OCTET STRING,
				hwLDAPServerGroupMaskFlt
					OCTET STRING,
				hwLDAPServerGroupMobileNumFlt
					OCTET STRING,
				hwLDAPServerGroupTimeStampFlt
					OCTET STRING,
				hwLDAPServerGroupUserFlt
					OCTET STRING,
				hwLDAPServerGroupStatus
					RowStatus,
				hwLDAPServerGroupServerType
					INTEGER
			 }

--  1.3.6.1.4.1.2011.5.120.3.1.1
		-- 1.3.6.1.4.1.2011.5.120.2.1.1
		hwLDAPServerGroupIndex OBJECT-TYPE
			SYNTAX Integer32 (0..2147483647)
			MAX-ACCESS read-only
			STATUS current
			DESCRIPTION
				"Description."
			::= { hwLdapServerGroupEntry 1 }
		
--  1.3.6.1.4.1.2011.5.120.3.1.2
		-- 1.3.6.1.4.1.2011.5.120.2.1.2
		hwLDAPServerGroupName OBJECT-TYPE
			SYNTAX OCTET STRING (SIZE (1..32))
			MAX-ACCESS read-write
			STATUS current
			DESCRIPTION
				"Description."
			::= { hwLdapServerGroupEntry 2 }
		
--  1.3.6.1.4.1.2011.5.120.3.1.3
		-- 1.3.6.1.4.1.2011.5.120.2.1.3
		hwLDAPServerGroupPriAuthenAddr OBJECT-TYPE
			SYNTAX IpAddress
			MAX-ACCESS read-create
			STATUS current
			DESCRIPTION
				"Description."
			::= { hwLdapServerGroupEntry 3 }
		
--  1.3.6.1.4.1.2011.5.120.3.1.4
		-- 1.3.6.1.4.1.2011.5.120.2.1.4
		hwLDAPServerGroupPriAuthenPort OBJECT-TYPE
			SYNTAX Unsigned32 (1..65535 | 4294967295)
			MAX-ACCESS read-create
			STATUS current
			DESCRIPTION
				"Description."
			::= { hwLdapServerGroupEntry 4 }
		
--  1.3.6.1.4.1.2011.5.120.3.1.5
		-- 1.3.6.1.4.1.2011.5.120.2.1.5
		hwLDAPServerGroupPriAuthenSslEnable OBJECT-TYPE
			SYNTAX INTEGER
				{
				true(1),
				false(0)
				}
			MAX-ACCESS read-create
			STATUS current
			DESCRIPTION
				"Description."
			::= { hwLdapServerGroupEntry 5 }
		
--  1.3.6.1.4.1.2011.5.120.3.1.6
		-- 1.3.6.1.4.1.2011.5.120.2.1.6
		hwLDAPServerGroupSecAuthenAddr OBJECT-TYPE
			SYNTAX IpAddress
			MAX-ACCESS read-create
			STATUS current
			DESCRIPTION
				"Description."
			::= { hwLdapServerGroupEntry 6 }
		
--  1.3.6.1.4.1.2011.5.120.3.1.7
		-- 1.3.6.1.4.1.2011.5.120.2.1.7
		hwLDAPServerGroupSecAuthenPort OBJECT-TYPE
			SYNTAX Unsigned32 (1..65535 | 4294967295)
			MAX-ACCESS read-create
			STATUS current
			DESCRIPTION
				"Description."
			::= { hwLdapServerGroupEntry 7 }
		
--  1.3.6.1.4.1.2011.5.120.3.1.8
		-- 1.3.6.1.4.1.2011.5.120.2.1.8
		hwLDAPServerGroupSecAuthenSslEnable OBJECT-TYPE
			SYNTAX INTEGER
				{
				true(1),
				false(0)
				}
			MAX-ACCESS read-create
			STATUS current
			DESCRIPTION
				"Description."
			::= { hwLdapServerGroupEntry 8 }
		
--  1.3.6.1.4.1.2011.5.120.3.1.9
		-- 1.3.6.1.4.1.2011.5.120.2.1.9
		hwLDAPServerGroupThiAuthenAddr OBJECT-TYPE
			SYNTAX IpAddress
			MAX-ACCESS read-create
			STATUS current
			DESCRIPTION
				"Description."
			::= { hwLdapServerGroupEntry 9 }
		
--  1.3.6.1.4.1.2011.5.120.3.1.10
		-- 1.3.6.1.4.1.2011.5.120.2.1.10
		hwLDAPServerGroupThiAuthenPort OBJECT-TYPE
			SYNTAX Unsigned32 (1..65535 | 4294967295)
			MAX-ACCESS read-create
			STATUS current
			DESCRIPTION
				"Description."
			::= { hwLdapServerGroupEntry 10 }
		
--  1.3.6.1.4.1.2011.5.120.3.1.11
		-- 1.3.6.1.4.1.2011.5.120.2.1.11
		hwLDAPServerGroupThiAuthenSslEnable OBJECT-TYPE
			SYNTAX INTEGER
				{
				true(1),
				false(0)
				}
			MAX-ACCESS read-create
			STATUS current
			DESCRIPTION
				"Description."
			::= { hwLdapServerGroupEntry 11 }
		
--  1.3.6.1.4.1.2011.5.120.3.1.12
		-- 1.3.6.1.4.1.2011.5.120.2.1.12
		hwLDAPServerGroupBaseDN OBJECT-TYPE
			SYNTAX OCTET STRING (SIZE (0..1030))
			MAX-ACCESS read-create
			STATUS current
			DESCRIPTION
				"Description."
			::= { hwLdapServerGroupEntry 12 }
		
--  1.3.6.1.4.1.2011.5.120.3.1.13
		-- 1.3.6.1.4.1.2011.5.120.2.1.13
		hwLDAPServerGroupManagerDN OBJECT-TYPE
			SYNTAX OCTET STRING (SIZE (0..63))
			MAX-ACCESS read-create
			STATUS current
			DESCRIPTION
				"Description."
			::= { hwLdapServerGroupEntry 13 }
		
--  1.3.6.1.4.1.2011.5.120.3.1.14
		-- 1.3.6.1.4.1.2011.5.120.2.1.14
		hwLDAPServerGroupManagerPSW OBJECT-TYPE
			SYNTAX OCTET STRING (SIZE (0..68))
			MAX-ACCESS read-create
			STATUS current
			DESCRIPTION
				"Description."
			::= { hwLdapServerGroupEntry 14 }
		
--  1.3.6.1.4.1.2011.5.120.3.1.15
		-- 1.3.6.1.4.1.2011.5.120.2.1.15
		hwLDAPServerGroupManagerAnonymous OBJECT-TYPE
			SYNTAX INTEGER
				{
				true(1),
				false(0)
				}
			MAX-ACCESS read-create
			STATUS current
			DESCRIPTION
				"Description."
			::= { hwLdapServerGroupEntry 15 }
		
--  1.3.6.1.4.1.2011.5.120.3.1.16
		-- 1.3.6.1.4.1.2011.5.120.2.1.16
		hwLDAPServerGroupManagerWithBaseDN OBJECT-TYPE
			SYNTAX INTEGER
				{
				true(1),
				false(0)
				}
			MAX-ACCESS read-create
			STATUS current
			DESCRIPTION
				"Description."
			::= { hwLdapServerGroupEntry 16 }
		
--  1.3.6.1.4.1.2011.5.120.3.1.17
		-- 1.3.6.1.4.1.2011.5.120.2.1.17
		hwLDAPServerGroupAuthorBindUser OBJECT-TYPE
			SYNTAX INTEGER
				{
				true(1),
				false(0)
				}
			MAX-ACCESS read-write
			STATUS current
			DESCRIPTION
				"Description."
			::= { hwLdapServerGroupEntry 17 }
		
--  1.3.6.1.4.1.2011.5.120.3.1.18
		-- 1.3.6.1.4.1.2011.5.120.2.1.18
		hwLDAPServerGroupGroupFlt OBJECT-TYPE
			SYNTAX OCTET STRING (SIZE (0..63))
			MAX-ACCESS read-create
			STATUS current
			DESCRIPTION
				"Description."
			::= { hwLdapServerGroupEntry 18 }
		
--  1.3.6.1.4.1.2011.5.120.3.1.19
		-- 1.3.6.1.4.1.2011.5.120.2.1.19
		hwLDAPServerGroupIpAddrFlt OBJECT-TYPE
			SYNTAX OCTET STRING (SIZE (0..63))
			MAX-ACCESS read-create
			STATUS current
			DESCRIPTION
				"Description."
			::= { hwLdapServerGroupEntry 19 }
		
--  1.3.6.1.4.1.2011.5.120.3.1.20
		-- 1.3.6.1.4.1.2011.5.120.2.1.20
		hwLDAPServerGroupMaskFlt OBJECT-TYPE
			SYNTAX OCTET STRING (SIZE (0..63))
			MAX-ACCESS read-create
			STATUS current
			DESCRIPTION
				"Description."
			::= { hwLdapServerGroupEntry 20 }
		
--  1.3.6.1.4.1.2011.5.120.3.1.21
		-- 1.3.6.1.4.1.2011.5.120.2.1.21
		hwLDAPServerGroupMobileNumFlt OBJECT-TYPE
			SYNTAX OCTET STRING (SIZE (0..63))
			MAX-ACCESS read-create
			STATUS current
			DESCRIPTION
				"Description."
			::= { hwLdapServerGroupEntry 21 }
		
--  1.3.6.1.4.1.2011.5.120.3.1.22
		-- 1.3.6.1.4.1.2011.5.120.2.1.22
		hwLDAPServerGroupTimeStampFlt OBJECT-TYPE
			SYNTAX OCTET STRING (SIZE (1..63))
			MAX-ACCESS read-create
			STATUS current
			DESCRIPTION
				"Description."
			::= { hwLdapServerGroupEntry 22 }
		
--  1.3.6.1.4.1.2011.5.120.3.1.23
		-- 1.3.6.1.4.1.2011.5.120.2.1.23
		hwLDAPServerGroupUserFlt OBJECT-TYPE
			SYNTAX OCTET STRING (SIZE (0..63))
			MAX-ACCESS read-create
			STATUS current
			DESCRIPTION
				"Description."
			::= { hwLdapServerGroupEntry 23 }
		
		-- 1.3.6.1.4.1.2011.5.120.2.1.24
		hwLDAPServerGroupStatus OBJECT-TYPE
			SYNTAX RowStatus
			MAX-ACCESS read-create
			STATUS current
			DESCRIPTION
				"Description."
			::= { hwLdapServerGroupEntry 24 }
			
		-- 1.3.6.1.4.1.2011.5.120.2.1.25
		hwLDAPServerGroupServerType OBJECT-TYPE
			SYNTAX INTEGER
				{
				ldapAD(0),
				ldapIBMTIVOLI(1),
				ldapSUNONE(2),
				ldapOPENLDAP(3)
				}
			MAX-ACCESS read-create
			STATUS current
			DESCRIPTION
				"Description."
			::= { hwLdapServerGroupEntry 25 }
		
	
	END

--
-- HUAWEI-LDAP-MIB1.my
--
