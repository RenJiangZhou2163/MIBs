--
-- HUAWEI-SECURITY-STATBOARDPHY-MIB.mib
-- MIB generated by MG-SOFT Visual MIB Builder Version 4.0 Build 341
-- Thursday, October 31, 2013 at 15:04:27
--



-- =================================================================
-- Copyright (C) 2013 by  HUAWEI TECHNOLOGIES. All rights reserved
-- 
-- Description:
-- Reference:
-- Version: V1.00
-- History:
-- shaoyu,2009-03-12,<contents>
-- =================================================================

	HUAWEI-SECURITY-STATBOARDPHY-MIB DEFINITIONS ::= BEGIN
 
		IMPORTS
			enterprises			
				FROM RFC1155-SMI			
			OBJECT-GROUP, MODULE-COMPLIANCE			
				FROM SNMPv2-CONF			
			Integer32, OBJECT-TYPE, MODULE-IDENTITY			
				FROM SNMPv2-SMI;
	
	
		-- 1.3.6.1.4.1.2011.6.122.65
		hwSecStatBoardPhy MODULE-IDENTITY 
			LAST-UPDATED "201310170900Z"		-- October 17, 2013 at 09:00 GMT
			ORGANIZATION 
		            "Huawei Technologies Co.,Ltd."
			CONTACT-INFO 
		            "Huawei Industrial Base
                                 Bantian, Longgang
                                 Shenzhen 518129
                                 People's Republic of China
                                 Website: http://www.huawei.com
                                 Email: support@huawei.com"
			DESCRIPTION 
				"
				V1.00
				The HUAWEI-SECSTAT-MIB contains objects to manage the security statistics for firewall product.
				"
		--  Revision history
				 REVISION    "201310170900Z"
                                 DESCRIPTION "V1.00, completed the first draft."  				
			::= { hwSecurity 65 }

		
	
	
--
-- Node definitions
--
	
--  1.3.6.1.4.1.2011.6.122.15.1
-- October 09, 2010 at 09:00 GMT
-- 
-- Node definitions
-- 
-- 1.3.6.1.4.1.2011
		-- 1.3.6.1.4.1.2011
		huawei OBJECT IDENTIFIER ::= { enterprises 2011 }

		
--  1.3.6.1.4.1.2011.6
		-- 1.3.6.1.4.1.2011.6
		huaweiUtility OBJECT IDENTIFIER ::= { huawei 6 }

		
--  1.3.6.1.4.1.2011.6.122
		-- 1.3.6.1.4.1.2011.6.122
		hwSecurity OBJECT IDENTIFIER ::= { huaweiUtility 122 }

		
--  1.3.6.1.4.1.2011.6.122.15
		-- 1.3.6.1.4.1.2011.6.122.65.1
		hwSecStatBoardPhyMibObjects OBJECT IDENTIFIER ::= { hwSecStatBoardPhy 1 }

		
		-- 1.3.6.1.4.1.2011.6.122.65.1.1
		hwSecBoardPhyStatTable OBJECT-TYPE
			SYNTAX SEQUENCE OF HwSecBoardPhyStatEntry
			MAX-ACCESS not-accessible
			STATUS current
			DESCRIPTION
				"Description."
			::= { hwSecStatBoardPhyMibObjects 1 }

		
		-- 1.3.6.1.4.1.2011.6.122.65.1.1.1
		hwSecBoardPhyStatEntry OBJECT-TYPE
			SYNTAX HwSecBoardPhyStatEntry
			MAX-ACCESS not-accessible
			STATUS current
			DESCRIPTION
				"Description."
			INDEX { hwSecBoardPhyStatType }
			::= { hwSecBoardPhyStatTable 1 }

		
		HwSecBoardPhyStatEntry ::=
			SEQUENCE { 
				hwSecBoardPhyStatType
					INTEGER,
				hwSecBoardPhyMemAverageUsage
					Integer32,
				hwSecBoardPhyMemMaxUsage
					Integer32,
				hwSecBoardPhyCPUMaxUsage
					Integer32,
				hwSecBoardPhyCPUAverageUsage
					Integer32
			 }

		-- 1.3.6.1.4.1.2011.6.122.65.1.1.1.1
		hwSecBoardPhyStatType OBJECT-TYPE
			SYNTAX INTEGER
				{
				mpu(1),
				lpun(2),
				lpuk(3),
				lpug(4),
				lpuf100c(5),
				spump(6),
				spudp(7),
				ipsmp(8),
				ipsdp(9)
				}
			MAX-ACCESS not-accessible
			STATUS current
			DESCRIPTION
				"Description."
			::= { hwSecBoardPhyStatEntry 1 }

		
		-- 1.3.6.1.4.1.2011.6.122.65.1.1.1.2
		hwSecBoardPhyMemAverageUsage OBJECT-TYPE
			SYNTAX Integer32
			MAX-ACCESS read-only
			STATUS current
			DESCRIPTION
				"Description."
			::= { hwSecBoardPhyStatEntry 2 }

		
		-- 1.3.6.1.4.1.2011.6.122.65.1.1.1.3
		hwSecBoardPhyMemMaxUsage OBJECT-TYPE
			SYNTAX Integer32
			MAX-ACCESS read-only
			STATUS current
			DESCRIPTION
				"Description."
			::= { hwSecBoardPhyStatEntry 3 }

		
		-- 1.3.6.1.4.1.2011.6.122.65.1.1.1.4
		hwSecBoardPhyCPUMaxUsage OBJECT-TYPE
			SYNTAX Integer32
			MAX-ACCESS read-only
			STATUS current
			DESCRIPTION
				"Description."
			::= { hwSecBoardPhyStatEntry 4 }

		
		-- 1.3.6.1.4.1.2011.6.122.65.1.1.1.5
		hwSecBoardPhyCPUAverageUsage OBJECT-TYPE
			SYNTAX Integer32
			MAX-ACCESS read-only
			STATUS current
			DESCRIPTION
				"Description."
			::= { hwSecBoardPhyStatEntry 5 }

		
--  1.3.6.1.4.1.2011.6.122.15.1.3
		-- 1.3.6.1.4.1.2011.6.122.65.3
		hwSecStatBoardPhyConformance OBJECT IDENTIFIER ::= { hwSecStatBoardPhy 3 }

		
		-- 1.3.6.1.4.1.2011.6.122.65.3.2
		hwSecStatBoardPhyCompliances OBJECT IDENTIFIER ::= { hwSecStatBoardPhyConformance 2 }

		
		-- 1.3.6.1.4.1.2011.6.122.65.3.2.1
		hwSecStatBoardPhyCompliance MODULE-COMPLIANCE
			STATUS current
			DESCRIPTION 
				"Description."
			MODULE -- this module
				MANDATORY-GROUPS { hwSecStatBoardPhyGroup }
			::= { hwSecStatBoardPhyCompliances 1 }

		
--  1.3.6.1.4.1.2011.6.122.15.1.3.2
		-- 1.3.6.1.4.1.2011.6.122.65.3.4
		hwSecStatBoardPhyMibGroups OBJECT IDENTIFIER ::= { hwSecStatBoardPhyConformance 4 }

		
--  1.3.6.1.4.1.2011.6.122.15.1.3.2.2
		-- 1.3.6.1.4.1.2011.6.122.65.3.4.1
		hwSecStatBoardPhyGroup OBJECT-GROUP
			OBJECTS { hwSecBoardPhyStatType, hwSecBoardPhyCPUMaxUsage, hwSecBoardPhyCPUAverageUsage, hwSecBoardPhyMemAverageUsage, hwSecBoardPhyMemMaxUsage
				 }
			STATUS current
			DESCRIPTION 
				"Description."
			::= { hwSecStatBoardPhyMibGroups 1 }

		
	
	END

--
-- HUAWEI-SECURITY-STATBOARDPHY-MIB.mib
--
