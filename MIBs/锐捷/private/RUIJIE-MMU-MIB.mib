-- *****************************************************************
-- RUIJIE-MMU-MIB.mib: Ruijie MMU MIB File for 3PJ1
-- 
-- June 2015, chenlong
--
-- Copyright (c) 2015 by Ruijie Networks Co.,Ltd.
-- All rights reserved.
-- 
-- *****************************************************************
--

RUIJIE-MMU-MIB DEFINITIONS ::= BEGIN

IMPORTS
        MODULE-IDENTITY,
        OBJECT-TYPE,
        Integer32,
        Counter64,
        NOTIFICATION-TYPE
                FROM SNMPv2-SMI
        MODULE-COMPLIANCE,
        OBJECT-GROUP,
        NOTIFICATION-GROUP
                FROM SNMPv2-CONF
        IfIndex
                FROM RUIJIE-TC
        ruijieMgmt
                FROM RUIJIE-SMI;

ruijieMMUMIB MODULE-IDENTITY
        LAST-UPDATED "201506240000Z"
        ORGANIZATION "Ruijie Networks Co.,Ltd."
        CONTACT-INFO
                " 
                Tel: 4008-111-000

                E-mail: service@ruijie.com.cn"
        DESCRIPTION
                "This module defines ruijie NFPP mibs."
        REVISION      "201506240000Z"
        DESCRIPTION
                "Initial version of this MIB module."
        ::= { ruijieMgmt 141 }

-- 第一个消息，统计端口入口方向的报文

ruijieMmuIfVoqInTable OBJECT-TYPE
        SYNTAX SEQUENCE OF RuijieMmuIfVoqInEntry
        MAX-ACCESS not-accessible
        STATUS current
        DESCRIPTION
            "Packet statistics of IN direction."
        ::= { ruijieMMUMIB 1 }

ruijieMmuIfVoqInEntry OBJECT-TYPE
        SYNTAX RuijieMmuIfVoqInEntry
        MAX-ACCESS not-accessible
        STATUS current
        DESCRIPTION
            "Parameters of ruijieMmuIfVoqInTable."
            INDEX { ruijieInIfxId, ruijieInQueueId, ruijieInDevId, ruijieInSlotId, ruijieInPgId }
        ::= { ruijieMmuIfVoqInTable 1 }

RuijieMmuIfVoqInEntry ::=
        SEQUENCE {
            ruijieInIfxId IfIndex,
            ruijieInQueueId Integer32,
            ruijieInDevId Integer32,
            ruijieInSlotId Integer32,
            ruijieInPgId Integer32,
            ruijieInTransmitPackets Counter64,
            ruijieInTransmitBytes Counter64,
            ruijieInDropPackets Counter64,
            ruijieInDropBytes Counter64
        }

ruijieInIfxId OBJECT-TYPE
        SYNTAX IfIndex
        MAX-ACCESS read-only
        STATUS current
        DESCRIPTION
            "Interface index."
        ::= { ruijieMmuIfVoqInEntry 1 }

ruijieInQueueId OBJECT-TYPE
        SYNTAX Integer32
        MAX-ACCESS read-only
        STATUS current
        DESCRIPTION
            "Queue index."
        ::= { ruijieMmuIfVoqInEntry 2 }

ruijieInDevId OBJECT-TYPE
        SYNTAX Integer32
        MAX-ACCESS read-only
        STATUS current
        DESCRIPTION
            "Device index."
        ::= { ruijieMmuIfVoqInEntry 3 }

ruijieInSlotId OBJECT-TYPE
        SYNTAX Integer32
        MAX-ACCESS read-only
        STATUS current
        DESCRIPTION
            "Slot index."
        ::= { ruijieMmuIfVoqInEntry 4 }

ruijieInPgId OBJECT-TYPE
        SYNTAX Integer32
        MAX-ACCESS read-only
        STATUS current
        DESCRIPTION
            "Port group index."
        ::= { ruijieMmuIfVoqInEntry 5 }

ruijieInTransmitPackets OBJECT-TYPE
        SYNTAX Counter64
        MAX-ACCESS read-only
        STATUS current
        DESCRIPTION
            "Transmitted packets."
        ::= { ruijieMmuIfVoqInEntry 6 }

ruijieInTransmitBytes OBJECT-TYPE
        SYNTAX Counter64
        MAX-ACCESS read-only
        STATUS current
        DESCRIPTION
            "Transmitted bytes."
        ::= { ruijieMmuIfVoqInEntry 7 }

ruijieInDropPackets OBJECT-TYPE
        SYNTAX Counter64
        MAX-ACCESS read-only
        STATUS current
        DESCRIPTION
            "Dropped packets."
        ::= { ruijieMmuIfVoqInEntry 8 }

ruijieInDropBytes OBJECT-TYPE
        SYNTAX Counter64
        MAX-ACCESS read-only
        STATUS current
        DESCRIPTION
            "Dropped bytes."
        ::= { ruijieMmuIfVoqInEntry 9 }

-- 第二个消息，统计端口出口方向的报文

ruijieMmuIfVoqOutTable OBJECT-TYPE
        SYNTAX SEQUENCE OF RuijieMmuIfVoqOutEntry
        MAX-ACCESS not-accessible
        STATUS current
        DESCRIPTION
            "Packet statistics of OUT direction."
        ::= { ruijieMMUMIB 2 }

ruijieMmuIfVoqOutEntry OBJECT-TYPE
        SYNTAX RuijieMmuIfVoqOutEntry
        MAX-ACCESS not-accessible
        STATUS current
        DESCRIPTION
            "Parameters of ruijieMmuIfVoqOutTable."
            INDEX { ruijieOutIfxId, ruijieOutQueueId, ruijieOutDevId, ruijieOutSlotId, ruijieOutPgId }
        ::= { ruijieMmuIfVoqOutTable 1 }

RuijieMmuIfVoqOutEntry ::=
        SEQUENCE {
            ruijieOutIfxId IfIndex,
            ruijieOutQueueId Integer32,
            ruijieOutDevId Integer32,
            ruijieOutSlotId Integer32,
            ruijieOutPgId Integer32,
            ruijieOutTransmitPackets Counter64,
            ruijieOutTransmitBytes Counter64,
            ruijieOutDropPackets Counter64,
            ruijieOutDropBytes Counter64
        }

ruijieOutIfxId OBJECT-TYPE
        SYNTAX IfIndex
        MAX-ACCESS read-only
        STATUS current
        DESCRIPTION
            "Interface index."
        ::= { ruijieMmuIfVoqOutEntry 1 }

ruijieOutQueueId OBJECT-TYPE
        SYNTAX Integer32
        MAX-ACCESS read-only
        STATUS current
        DESCRIPTION
            "Queue index."
        ::= { ruijieMmuIfVoqOutEntry 2 }

ruijieOutDevId OBJECT-TYPE
        SYNTAX Integer32
        MAX-ACCESS read-only
        STATUS current
        DESCRIPTION
            "Device index."
        ::= { ruijieMmuIfVoqOutEntry 3 }

ruijieOutSlotId OBJECT-TYPE
        SYNTAX Integer32
        MAX-ACCESS read-only
        STATUS current
        DESCRIPTION
            "Slot index."
        ::= { ruijieMmuIfVoqOutEntry 4 }

ruijieOutPgId OBJECT-TYPE
        SYNTAX Integer32
        MAX-ACCESS read-only
        STATUS current
        DESCRIPTION
            "Port group index."
        ::= { ruijieMmuIfVoqOutEntry 5 }

ruijieOutTransmitPackets OBJECT-TYPE
        SYNTAX Counter64
        MAX-ACCESS read-only
        STATUS current
        DESCRIPTION
            "Transmitted packets."
        ::= { ruijieMmuIfVoqOutEntry 6 }

ruijieOutTransmitBytes OBJECT-TYPE
        SYNTAX Counter64
        MAX-ACCESS read-only
        STATUS current
        DESCRIPTION
            "Transmitted bytes."
        ::= { ruijieMmuIfVoqOutEntry 7 }

ruijieOutDropPackets OBJECT-TYPE
        SYNTAX Counter64
        MAX-ACCESS read-only
        STATUS current
        DESCRIPTION
            "Dropped packets."
        ::= { ruijieMmuIfVoqOutEntry 8 }

ruijieOutDropBytes OBJECT-TYPE
        SYNTAX Counter64
        MAX-ACCESS read-only
        STATUS current
        DESCRIPTION
            "Dropped bytes."
        ::= { ruijieMmuIfVoqOutEntry 9 }

-- 第三个消息，统计buffer超过门限的次数

ruijieMmuIfWarnTable OBJECT-TYPE
        SYNTAX SEQUENCE OF RuijieMmuIfWarnEntry
        MAX-ACCESS not-accessible
        STATUS current
        DESCRIPTION
            "Times buffer over usage-warn-limit."
        ::= { ruijieMMUMIB 3 }

ruijieMmuIfWarnEntry OBJECT-TYPE
        SYNTAX RuijieMmuIfWarnEntry
        MAX-ACCESS not-accessible
        STATUS current
        DESCRIPTION
            "Parameters of ruijieMmuIfWarnTable."
            INDEX { ruijieWarnIfxId, ruijieWarnDevId, ruijieWarnSlotId, ruijieWarnPgId }
        ::= { ruijieMmuIfWarnTable 1 }

RuijieMmuIfWarnEntry ::=
        SEQUENCE {
            ruijieWarnIfxId IfIndex,
            ruijieWarnDevId Integer32,
            ruijieWarnSlotId Integer32,
            ruijieWarnPgId Integer32,
            ruijieWarnUsedCell Integer32,
            ruijieWarnTotalCell Integer32,
            ruijieWarnLimit Integer32,
            ruijieWarnCount Integer32
        }

ruijieWarnIfxId OBJECT-TYPE
        SYNTAX IfIndex
        MAX-ACCESS read-only
        STATUS current
        DESCRIPTION
            "Interface index."
        ::= { ruijieMmuIfWarnEntry 1 }


ruijieWarnDevId OBJECT-TYPE
        SYNTAX Integer32
        MAX-ACCESS read-only
        STATUS current
        DESCRIPTION
            "Device index."
        ::= { ruijieMmuIfWarnEntry 2 }

ruijieWarnSlotId OBJECT-TYPE
        SYNTAX Integer32
        MAX-ACCESS read-only
        STATUS current
        DESCRIPTION
            "Slot index."
        ::= { ruijieMmuIfWarnEntry 3 }

ruijieWarnPgId OBJECT-TYPE
        SYNTAX Integer32
        MAX-ACCESS read-only
        STATUS current
        DESCRIPTION
            "Port group index."
        ::= { ruijieMmuIfWarnEntry 4 }

ruijieWarnUsedCell OBJECT-TYPE
        SYNTAX Integer32
        MAX-ACCESS read-only
        STATUS current
        DESCRIPTION
            "Used cell num."
        ::= { ruijieMmuIfWarnEntry 5 }

ruijieWarnTotalCell OBJECT-TYPE
        SYNTAX Integer32
        MAX-ACCESS read-only
        STATUS current
        DESCRIPTION
            "Total cell num."
        ::= { ruijieMmuIfWarnEntry 6 }

ruijieWarnLimit OBJECT-TYPE
        SYNTAX Integer32
        MAX-ACCESS read-only
        STATUS current
        DESCRIPTION
            "The usage-warn-limit value."
        ::= { ruijieMmuIfWarnEntry 7 }

ruijieWarnCount OBJECT-TYPE
        SYNTAX Integer32
        MAX-ACCESS read-only
        STATUS current
        DESCRIPTION
            "The count buffer over usage-warn-limit."
        ::= { ruijieMmuIfWarnEntry 8 }
		
		
		
-- 第四个消息，统计端口的buffer

ruijieMmuIfVoqWarnTable OBJECT-TYPE
        SYNTAX SEQUENCE OF RuijieMmuIfVoqWarnEntry
        MAX-ACCESS not-accessible
        STATUS current
        DESCRIPTION
            "buffer statistics ."
        ::= { ruijieMMUMIB 4 }

ruijieMmuIfVoqWarnEntry OBJECT-TYPE
        SYNTAX RuijieMmuIfVoqWarnEntry
        MAX-ACCESS not-accessible
        STATUS current
        DESCRIPTION
            "Parameters of ruijieMmuIfVoqWarnTable."
            INDEX { ruijieVoqWarnIfxId, ruijieVoqWarnQueueId, ruijieVoqWarnDevId, ruijieVoqWarnSlotId, ruijieVoqWarnPgId }
        ::= { ruijieMmuIfVoqWarnTable 1 }

RuijieMmuIfVoqWarnEntry ::=
        SEQUENCE {
            ruijieVoqWarnIfxId IfIndex,
            ruijieVoqWarnQueueId Integer32,
			ruijieVoqWarnDevId Integer32,
            ruijieVoqWarnSlotId Integer32,
            ruijieVoqWarnPgId Integer32,
            ruijieVoqWarnUsedcells Counter64,
            ruijieVoqWarnAvailablecells Counter64,
            ruijieVoqWarnTotalcells Counter64,
            ruijieVoqWarnUsage Counter64,
            ruijieVoqWarnUsagewarnlimit Counter64,
            ruijieVoqWarnUsagewarncount Counter64,
			ruijieVoqWarnPeakedcells Counter64
        }

ruijieVoqWarnIfxId OBJECT-TYPE
        SYNTAX IfIndex
        MAX-ACCESS read-only
        STATUS current
        DESCRIPTION
            "Interface index."
        ::= { ruijieMmuIfVoqWarnEntry 1 }

ruijieVoqWarnQueueId OBJECT-TYPE
        SYNTAX Integer32
        MAX-ACCESS read-only
        STATUS current
        DESCRIPTION
            "Queue index."
        ::= { ruijieMmuIfVoqWarnEntry 2 }

ruijieVoqWarnDevId OBJECT-TYPE
        SYNTAX Integer32
        MAX-ACCESS read-only
        STATUS current
        DESCRIPTION
            "Device index."
        ::= { ruijieMmuIfVoqWarnEntry 3 }		
		
ruijieVoqWarnSlotId OBJECT-TYPE
        SYNTAX Integer32
        MAX-ACCESS read-only
        STATUS current
        DESCRIPTION
            "Slot index."
        ::= { ruijieMmuIfVoqWarnEntry 4 }

ruijieVoqWarnPgId OBJECT-TYPE
        SYNTAX Integer32
        MAX-ACCESS read-only
        STATUS current
        DESCRIPTION
            "Port group index."
        ::= { ruijieMmuIfVoqWarnEntry 5 }

ruijieVoqWarnUsedcells OBJECT-TYPE
        SYNTAX Counter64
        MAX-ACCESS read-only
        STATUS current
        DESCRIPTION
            "Used cells."
        ::= { ruijieMmuIfVoqWarnEntry 6 }

ruijieVoqWarnAvailablecells OBJECT-TYPE
        SYNTAX Counter64
        MAX-ACCESS read-only
        STATUS current
        DESCRIPTION
            "Available cells."
        ::= { ruijieMmuIfVoqWarnEntry 7 }

ruijieVoqWarnTotalcells OBJECT-TYPE
        SYNTAX Counter64
        MAX-ACCESS read-only
        STATUS current
        DESCRIPTION
            "Total cells."
        ::= { ruijieMmuIfVoqWarnEntry 8 }

ruijieVoqWarnUsage OBJECT-TYPE
        SYNTAX Counter64
        MAX-ACCESS read-only
        STATUS current
        DESCRIPTION
            "Usage."
        ::= { ruijieMmuIfVoqWarnEntry 9 }

ruijieVoqWarnUsagewarnlimit OBJECT-TYPE
        SYNTAX Counter64
        MAX-ACCESS read-only
        STATUS current
        DESCRIPTION
            "Usage warn limit."
        ::= { ruijieMmuIfVoqWarnEntry 10 }
		
ruijieVoqWarnUsagewarncount OBJECT-TYPE
        SYNTAX Counter64
        MAX-ACCESS read-only
        STATUS current
        DESCRIPTION
            "Usage warn count."
        ::= { ruijieMmuIfVoqWarnEntry 11 }
		
ruijieVoqWarnPeakedcells OBJECT-TYPE
        SYNTAX Counter64
        MAX-ACCESS read-only
        STATUS current
        DESCRIPTION
            "Peaked cells."
        ::= { ruijieMmuIfVoqWarnEntry 12 }

--mmu queue  support
ruijieMmuIfQueueSupportTable OBJECT-TYPE
        SYNTAX SEQUENCE OF RuijieMmuIfQueueSupportEntry
        MAX-ACCESS not-accessible
        STATUS current
        DESCRIPTION
            "List  queues  of interfaces."
        ::= { ruijieMMUMIB 5 }
    
ruijieMmuIfQueueSupportEntry OBJECT-TYPE
        SYNTAX RuijieMmuIfQueueSupportEntry
        MAX-ACCESS not-accessible
        STATUS current
        DESCRIPTION
            "Queue Entry."
        INDEX { ruijieMmuIfIndex, ruijieMmuIfQueueIndex,ruijieMmuIfSliceIndex}
        ::= { ruijieMmuIfQueueSupportTable 1 }

RuijieMmuIfQueueSupportEntry ::=
        SEQUENCE {
            ruijieMmuIfIndex IfIndex,
            ruijieMmuIfQueueIndex Integer32,
            ruijieMmuIfSliceIndex Integer32,
            ruijieMmuIfQueueSupportUsedCells Counter64,
            ruijieMmuIfQueueSupportAvailableCells Counter64,
            ruijieMmuIfQueueSupportTotalCells Counter64,
            ruijieMmuIfQueueSupportUsage Counter64,
            ruijieMmuIfQueueSupportUsageWarnLimit Counter64,
            ruijieMmuIfQueueSupportUsageWarnCount Counter64,
            ruijieMmuIfQueueSupportPeakedCells Counter64,
            ruijieMmuIfQueueSupportServicePoolID Counter64
        }

ruijieMmuIfIndex OBJECT-TYPE
        SYNTAX IfIndex
        MAX-ACCESS read-only
        STATUS current
        DESCRIPTION
            "Interface index."
        ::= { ruijieMmuIfQueueSupportEntry 1 }
		
ruijieMmuIfQueueIndex OBJECT-TYPE
        SYNTAX Integer32
        MAX-ACCESS read-only
        STATUS current
        DESCRIPTION
            "Queue index."
        ::= { ruijieMmuIfQueueSupportEntry 2 }

ruijieMmuIfSliceIndex OBJECT-TYPE
        SYNTAX Integer32
        MAX-ACCESS read-only
        STATUS current
        DESCRIPTION
            "Slice index."
        ::= { ruijieMmuIfQueueSupportEntry 3 }

ruijieMmuIfQueueSupportUsedCells OBJECT-TYPE
        SYNTAX Counter64 
        MAX-ACCESS read-only
        STATUS current
        DESCRIPTION
            "Used Cells of queues."
        ::= { ruijieMmuIfQueueSupportEntry 4 }
        
ruijieMmuIfQueueSupportAvailableCells OBJECT-TYPE
        SYNTAX Counter64 
        MAX-ACCESS read-only
        STATUS current
        DESCRIPTION
            "Available Cells of queues."
        ::= { ruijieMmuIfQueueSupportEntry 5 }

ruijieMmuIfQueueSupportTotalCells OBJECT-TYPE
        SYNTAX Counter64 
        MAX-ACCESS read-only
        STATUS current
        DESCRIPTION
            "size of queues."
        ::= { ruijieMmuIfQueueSupportEntry 6 }
        
ruijieMmuIfQueueSupportUsage OBJECT-TYPE
        SYNTAX Counter64 
        MAX-ACCESS read-only
        STATUS current
        DESCRIPTION
            "usage of queues."
        ::= { ruijieMmuIfQueueSupportEntry 7 }
	
ruijieMmuIfQueueSupportUsageWarnLimit OBJECT-TYPE
        SYNTAX Counter64 
        MAX-ACCESS read-only
        STATUS current
        DESCRIPTION
            "Usage Warn Limit of queues."
        ::= { ruijieMmuIfQueueSupportEntry 8 }

ruijieMmuIfQueueSupportUsageWarnCount OBJECT-TYPE
        SYNTAX Counter64 
        MAX-ACCESS read-only
        STATUS current
        DESCRIPTION
            "Usage Warn Count of queues."
        ::= { ruijieMmuIfQueueSupportEntry 9 }

ruijieMmuIfQueueSupportPeakedCells OBJECT-TYPE
        SYNTAX Counter64 
        MAX-ACCESS read-only
        STATUS current
        DESCRIPTION
            "Peaked Cells of queues."
        ::= { ruijieMmuIfQueueSupportEntry 10 }

ruijieMmuIfQueueSupportServicePoolID OBJECT-TYPE
        SYNTAX Counter64 
        MAX-ACCESS read-only
        STATUS current
        DESCRIPTION
            "Service Pool ID of Unicast Queue."
        ::= { ruijieMmuIfQueueSupportEntry 11 }

-- mmu multicast queue support
ruijieMmuIfMulticastQueueSupportTable OBJECT-TYPE
        SYNTAX SEQUENCE OF RuijieMmuIfMulticastQueueSupportEntry
        MAX-ACCESS not-accessible
        STATUS current
        DESCRIPTION
            "List multicast queues of interfaces."
        ::= { ruijieMMUMIB 6 }
    
ruijieMmuIfMulticastQueueSupportEntry OBJECT-TYPE
        SYNTAX RuijieMmuIfMulticastQueueSupportEntry
        MAX-ACCESS not-accessible
        STATUS current
        DESCRIPTION
            "Multicast Queue Entry."
        INDEX { ruijieMmuIfIndexMulticast, ruijieMmuIfMulticastQueueIndex, ruijieMmuIfSliceIndexMulticast}
        ::= { ruijieMmuIfMulticastQueueSupportTable 1 }

RuijieMmuIfMulticastQueueSupportEntry ::=
        SEQUENCE {
            ruijieMmuIfIndexMulticast IfIndex,
            ruijieMmuIfMulticastQueueIndex Integer32,
            ruijieMmuIfSliceIndexMulticast Integer32,
      	    ruijieMmuIfMulticastQueueSupportUsedCells Counter64,
            ruijieMmuIfMulticastQueueSupportAvailableCells Counter64,
            ruijieMmuIfMulticastQueueSupportTotalCells Counter64,
            ruijieMmuIfMulticastQueueSupportUsage Counter64,
            ruijieMmuIfMulticastQueueSupportUsageWarnLimit Counter64,
            ruijieMmuIfMulticastQueueSupportUsageWarnCount Counter64,
            ruijieMmuIfMulticastQueueSupportPeakedCells Counter64,
            ruijieMmuIfMulticastQueueSupportServicePoolID Counter64
        }

ruijieMmuIfIndexMulticast OBJECT-TYPE
        SYNTAX IfIndex
        MAX-ACCESS read-only
        STATUS current
        DESCRIPTION
            "Interface index."
        ::= { ruijieMmuIfMulticastQueueSupportEntry 1 }
		
ruijieMmuIfMulticastQueueIndex OBJECT-TYPE
        SYNTAX Integer32
        MAX-ACCESS read-only
        STATUS current
        DESCRIPTION
            "Multicast Queue index."
        ::= { ruijieMmuIfMulticastQueueSupportEntry 2 }

ruijieMmuIfSliceIndexMulticast OBJECT-TYPE
        SYNTAX Integer32
        MAX-ACCESS read-only
        STATUS current
        DESCRIPTION
            "Slice of index."
        ::= { ruijieMmuIfMulticastQueueSupportEntry 3 }


ruijieMmuIfMulticastQueueSupportUsedCells OBJECT-TYPE
        SYNTAX Counter64 
        MAX-ACCESS read-only
        STATUS current
        DESCRIPTION
            "Used Cells of multicast queues."
        ::= { ruijieMmuIfMulticastQueueSupportEntry 4 }
        
ruijieMmuIfMulticastQueueSupportAvailableCells OBJECT-TYPE
        SYNTAX Counter64 
        MAX-ACCESS read-only
        STATUS current
        DESCRIPTION
            "Available Cells of multicast queues."
        ::= { ruijieMmuIfMulticastQueueSupportEntry 5 }

ruijieMmuIfMulticastQueueSupportTotalCells OBJECT-TYPE
        SYNTAX Counter64 
        MAX-ACCESS read-only
        STATUS current
        DESCRIPTION
            "size of multicast queues."
        ::= { ruijieMmuIfMulticastQueueSupportEntry 6 }
        
ruijieMmuIfMulticastQueueSupportUsage OBJECT-TYPE
        SYNTAX Counter64 
        MAX-ACCESS read-only
        STATUS current
        DESCRIPTION
            "Usage of multicast queues."
        ::= { ruijieMmuIfMulticastQueueSupportEntry 7 }
		

ruijieMmuIfMulticastQueueSupportUsageWarnLimit OBJECT-TYPE
        SYNTAX Counter64 
        MAX-ACCESS read-only
        STATUS current
        DESCRIPTION
            "Usage Warn Limit of multicast queues."
        ::= { ruijieMmuIfMulticastQueueSupportEntry 8 }

ruijieMmuIfMulticastQueueSupportUsageWarnCount OBJECT-TYPE
        SYNTAX Counter64 
        MAX-ACCESS read-only
        STATUS current
        DESCRIPTION
            "Usage Warn Count of multicast queues."
        ::= { ruijieMmuIfMulticastQueueSupportEntry 9 }


ruijieMmuIfMulticastQueueSupportPeakedCells OBJECT-TYPE
        SYNTAX Counter64 
        MAX-ACCESS read-only
        STATUS current
        DESCRIPTION
            "Usage Warn Limit of multicast queues."
        ::= { ruijieMmuIfMulticastQueueSupportEntry 10 }

ruijieMmuIfMulticastQueueSupportServicePoolID OBJECT-TYPE
        SYNTAX Counter64 
        MAX-ACCESS read-only
        STATUS current
        DESCRIPTION
            "Service Pool ID of Multicast Queue."
        ::= { ruijieMmuIfMulticastQueueSupportEntry 11 }

-- Mmu if  Priority Group Support
ruijieMmuIfPriorityGroupSupportTable OBJECT-TYPE
        SYNTAX SEQUENCE OF RuijieMmuIfPriorityGroupSupportEntry
        MAX-ACCESS not-accessible
        STATUS current
        DESCRIPTION
            "Priority Group of interfaces."
        ::= { ruijieMMUMIB 7 }
    
ruijieMmuIfPriorityGroupSupportEntry OBJECT-TYPE
        SYNTAX RuijieMmuIfPriorityGroupSupportEntry
        MAX-ACCESS not-accessible
        STATUS current
        DESCRIPTION
            "Priority Group Entry."
        INDEX { ruijieMmuIfIndexPriorityGroup, ruijieMmuIfPriorityGroupIdIndex, ruijieMmuIfSliceIndexPriorityGroup}
        ::= { ruijieMmuIfPriorityGroupSupportTable 1 }

RuijieMmuIfPriorityGroupSupportEntry ::=
        SEQUENCE {
            ruijieMmuIfIndexPriorityGroup IfIndex,
            ruijieMmuIfPriorityGroupIdIndex Integer32,
            ruijieMmuIfSliceIndexPriorityGroup Integer32,
      	    ruijieMmuIfPriorityGroupSupportUsedCells Counter64,
            ruijieMmuIfPriorityGroupSupportAvailableCells Counter64,
            ruijieMmuIfPriorityGroupSupportTotalCells Counter64,
            ruijieMmuIfPriorityGroupSupportUsage Counter64,
            ruijieMmuIfPriorityGroupSupportPeakedCells Counter64,
            ruijieMmuIfPriorityGroupSupportUsedHeadroom Counter64,
            ruijieMmuIfPriorityGroupSupportAvailableHeadroom Counter64,
            ruijieMmuIfPriorityGroupSupportPeakedHeadroom Counter64,
            ruijieMmuIfPriorityGroupSupportUsageWarnLimit Counter64,
            ruijieMmuIfPriorityGroupSupportUsageWarnCount Counter64,
            ruijieMmuIfPriorityGroupSupportServicePoolID Counter64,
            ruijieMmuIfPriorityGroupSupportTotalHeadroom Counter64,
            ruijieMmuIfPriorityGroupSupportHeadroomUsage Counter64,
            ruijieMmuIfPriorityGroupSupportHeadroomUsageWarnLimit Counter64,
            ruijieMmuIfPriorityGroupSupportHeadroomUsageWarnCount Counter64
        }

ruijieMmuIfIndexPriorityGroup OBJECT-TYPE
        SYNTAX IfIndex
        MAX-ACCESS read-only
        STATUS current
        DESCRIPTION
            "Interface of index."
        ::= { ruijieMmuIfPriorityGroupSupportEntry 1 }
		
ruijieMmuIfPriorityGroupIdIndex OBJECT-TYPE
        SYNTAX Integer32
        MAX-ACCESS read-only
        STATUS current
        DESCRIPTION
            "Priority Group Id of Index."
        ::= { ruijieMmuIfPriorityGroupSupportEntry 2 }

ruijieMmuIfSliceIndexPriorityGroup OBJECT-TYPE
        SYNTAX Integer32
        MAX-ACCESS read-only
        STATUS current
        DESCRIPTION
            "Slice of index."
        ::= { ruijieMmuIfPriorityGroupSupportEntry 3 }


ruijieMmuIfPriorityGroupSupportUsedCells OBJECT-TYPE
        SYNTAX Counter64 
        MAX-ACCESS read-only
        STATUS current
        DESCRIPTION
            "Used Cells of Priority Group."
        ::= { ruijieMmuIfPriorityGroupSupportEntry 4 }
        
ruijieMmuIfPriorityGroupSupportAvailableCells OBJECT-TYPE
        SYNTAX Counter64 
        MAX-ACCESS read-only
        STATUS current
        DESCRIPTION
            "Available Cells of Priority Group."
        ::= { ruijieMmuIfPriorityGroupSupportEntry 5 }

ruijieMmuIfPriorityGroupSupportTotalCells OBJECT-TYPE
        SYNTAX Counter64 
        MAX-ACCESS read-only
        STATUS current
        DESCRIPTION
            "size of Priority Group."
        ::= { ruijieMmuIfPriorityGroupSupportEntry 6 }
        
ruijieMmuIfPriorityGroupSupportUsage OBJECT-TYPE
        SYNTAX Counter64 
        MAX-ACCESS read-only
        STATUS current
        DESCRIPTION
            "Usage of Priority Group."
        ::= { ruijieMmuIfPriorityGroupSupportEntry 7 }
		
ruijieMmuIfPriorityGroupSupportPeakedCells OBJECT-TYPE
        SYNTAX Counter64 
        MAX-ACCESS read-only
        STATUS current
        DESCRIPTION
            "Peaked Cells of Priority Group."
        ::= { ruijieMmuIfPriorityGroupSupportEntry 8 }

ruijieMmuIfPriorityGroupSupportUsedHeadroom OBJECT-TYPE
        SYNTAX Counter64 
        MAX-ACCESS read-only
        STATUS current
        DESCRIPTION
            "Used Headroom of Priority Group."
        ::= { ruijieMmuIfPriorityGroupSupportEntry 9 }

ruijieMmuIfPriorityGroupSupportAvailableHeadroom OBJECT-TYPE
        SYNTAX Counter64 
        MAX-ACCESS read-only
        STATUS current
        DESCRIPTION
            "Available Headroom of Priority Group."
        ::= { ruijieMmuIfPriorityGroupSupportEntry 10 }

ruijieMmuIfPriorityGroupSupportPeakedHeadroom OBJECT-TYPE
        SYNTAX Counter64 
        MAX-ACCESS read-only
        STATUS current
        DESCRIPTION
            "Peaked Headroom of Priority Group."
        ::= { ruijieMmuIfPriorityGroupSupportEntry 11 }

ruijieMmuIfPriorityGroupSupportUsageWarnLimit OBJECT-TYPE
        SYNTAX Counter64 
        MAX-ACCESS read-only
        STATUS current
        DESCRIPTION
            "Usage Warn Limit of priority group."
        ::= { ruijieMmuIfPriorityGroupSupportEntry 12 }

ruijieMmuIfPriorityGroupSupportUsageWarnCount OBJECT-TYPE
        SYNTAX Counter64 
        MAX-ACCESS read-only
        STATUS current
        DESCRIPTION
            "Usage Warn Count of priority group."
        ::= { ruijieMmuIfPriorityGroupSupportEntry 13 }

ruijieMmuIfPriorityGroupSupportServicePoolID OBJECT-TYPE
        SYNTAX Counter64 
        MAX-ACCESS read-only
        STATUS current
        DESCRIPTION
            "Service Pool ID of Priority Group."
        ::= { ruijieMmuIfPriorityGroupSupportEntry 14 }

ruijieMmuIfPriorityGroupSupportTotalHeadroom OBJECT-TYPE
        SYNTAX Counter64 
        MAX-ACCESS read-only
        STATUS current
        DESCRIPTION
            "Size of pg headroom."
        ::= { ruijieMmuIfPriorityGroupSupportEntry 15 }

ruijieMmuIfPriorityGroupSupportHeadroomUsage OBJECT-TYPE
        SYNTAX Counter64 
        MAX-ACCESS read-only
        STATUS current
        DESCRIPTION
            "Usage of pg headroom."
        ::= { ruijieMmuIfPriorityGroupSupportEntry 16 }

ruijieMmuIfPriorityGroupSupportHeadroomUsageWarnLimit OBJECT-TYPE
        SYNTAX Counter64 
        MAX-ACCESS read-only
        STATUS current
        DESCRIPTION
            "Usage Warn Limit of pg headrrom."
        ::= { ruijieMmuIfPriorityGroupSupportEntry 17 }

ruijieMmuIfPriorityGroupSupportHeadroomUsageWarnCount OBJECT-TYPE
        SYNTAX Counter64 
        MAX-ACCESS read-only
        STATUS current
        DESCRIPTION
            "Usage Warn Count of pg headrrom."
        ::= { ruijieMmuIfPriorityGroupSupportEntry 18 }

END
