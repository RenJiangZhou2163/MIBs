-- *****************************************************************
-- RUIJIE-TIMERANGE-MIB.mib:  Ruijie timerange MIB file
--
-- Sep 2015, sukunlin
--
-- Copyright (c) 2002 by Ruijie Networks Co.,Ltd.
-- All rights reserved.
-- 
-- *****************************************************************
--

RUIJIE-TIMERANGE-MIB DEFINITIONS ::= BEGIN

IMPORTS
        MODULE-IDENTITY,
        OBJECT-TYPE,
        Integer32,
        Unsigned32,
        IpAddress
                FROM SNMPv2-SMI
        TruthValue,
        DisplayString,
        RowStatus,
        MacAddress
                FROM SNMPv2-TC
        MODULE-COMPLIANCE,
        OBJECT-GROUP
                FROM SNMPv2-CONF
        IfIndex,
        ConfigStatus
                FROM RUIJIE-TC        
        ruijieMgmt
                FROM RUIJIE-SMI;
				
ruijieTrsMIB MODULE-IDENTITY
        LAST-UPDATED "201509200000Z"
        ORGANIZATION "Ruijie Networks Co.,Ltd."
        CONTACT-INFO
                " 
                Tel: 4008-111-000 

                E-mail: service@ruijie.com.cn"
        DESCRIPTION
                "This module defines ruijie timerange server mibs."
        REVISION      "201509200000Z"
        DESCRIPTION
                "Initial version of this MIB module."
        ::= { ruijieMgmt 144}

ruijieTrsMIBObjects OBJECT IDENTIFIER ::= { ruijieTrsMIB 1 }


ruijieTRTable OBJECT-TYPE
        SYNTAX SEQUENCE OF RuijieTREntry
        MAX-ACCESS not-accessible
        STATUS current
        DESCRIPTION
               "A table of timerange entries."
        ::= { ruijieTrsMIBObjects 1 }

ruijieTREntry OBJECT-TYPE
        SYNTAX RuijieTREntry
        MAX-ACCESS not-accessible
        STATUS current
        DESCRIPTION
                "Entry contains timerange name."  
        INDEX { ruijieTRName }
        ::= { ruijieTRTable 1 }

RuijieTREntry ::= 
        SEQUENCE {
                ruijieTRName DisplayString,
				ruijieAbsTRStr  DisplayString,
				ruijieTRIndex INTEGER,
                ruijieTRMode INTEGER
        }

ruijieTRName OBJECT-TYPE
        SYNTAX DisplayString(SIZE (1..32))
        MAX-ACCESS read-only
        STATUS current
        DESCRIPTION
            "Timerange name what we config, This value is unique for every entry.
            When this string be used as an index, Value of a sub-identifier equal 
            ASCII value of corresponding character(first sub-identifier corresponds
            first character of string). The number of sub-identifiers of this string
            should not larger then 32 characters, or it'll failed."
        ::= { ruijieTREntry 1 }

ruijieAbsTRStr OBJECT-TYPE
        SYNTAX DisplayString(SIZE (1..64))
        MAX-ACCESS read-create
        STATUS current
        DESCRIPTION
            "Absolute time range what we config for a TR, each timerange should only has a abs range.
			the string include start time and end time.
			example:
			absolute start 15:23 21 February 2015 end 16:58 31 December 2016
			2015-02-21-15:23:00to2016-12-31-16:58:00
			"
        ::= { ruijieTREntry 2 }

ruijieTRIndex OBJECT-TYPE
        SYNTAX INTEGER
        MAX-ACCESS read-only
        STATUS current
        DESCRIPTION
               "each timerange will get an index dynamic"
        ::= { ruijieTREntry 3 }
		
ruijieTRMode OBJECT-TYPE
        SYNTAX INTEGER{
               tr-add(1),   
               tr-del(2)
            }
        MAX-ACCESS read-create
        STATUS current
        DESCRIPTION
               " add or del this timerange"
        ::= { ruijieTREntry 4 }

-- periodic range table
ruijieTRPeriTable OBJECT-TYPE
        SYNTAX SEQUENCE OF RuijieTRPeriEntry
        MAX-ACCESS not-accessible
        STATUS current
        DESCRIPTION
               "A table of absolute timerange."
        ::= { ruijieTrsMIBObjects 3 }

ruijieTRPeriEntry OBJECT-TYPE
        SYNTAX RuijieTRPeriEntry
        MAX-ACCESS not-accessible
        STATUS current
        DESCRIPTION
                "Index with time range name and periodic time string."  
        INDEX { ruijiePeriTRName, ruijiePeriTRStr }
        ::= { ruijieTRPeriTable 1 }

RuijieTRPeriEntry ::= 
        SEQUENCE {
                ruijiePeriTRName DisplayString,
				ruijiePeriTRStr  DisplayString,
				ruijiePeriTRIndex INTEGER,
				ruijiePeriTRMode INTEGER
        }

ruijiePeriTRName OBJECT-TYPE
        SYNTAX DisplayString(SIZE (1..32))
        MAX-ACCESS read-only
        STATUS current
        DESCRIPTION
            "Timerange name of this periodic belongs to.
            When this string be used as an index, Value of a sub-identifier equal 
            ASCII value of corresponding character(first sub-identifier corresponds
            first character of string). The number of sub-identifiers of this string
            should less then 33."
        ::= { ruijieTRPeriEntry 1 }	

ruijiePeriTRStr OBJECT-TYPE
        SYNTAX DisplayString(SIZE (1..10))
        MAX-ACCESS read-create
        STATUS current
        DESCRIPTION
            "Entry contains absolute time parameters and results.
            string like this [1122112459] means mondy 12:21 to 24:59
			str[0] instead of timemode by it's 8 bits
			00000001 means Monday
			00000010 means Tuesday
			00000100 means Wednesday
			00001000 means Thursday
			00010000 means Friday
			00100000 means Saturday
			01000000 means Sunday
			01111111 means Daily
			01100000 means Weekend
			00011111 means Weekdays
			"
        ::= { ruijieTRPeriEntry 2 }	

ruijiePeriTRIndex OBJECT-TYPE
        SYNTAX INTEGER
        MAX-ACCESS read-only
        STATUS current
        DESCRIPTION
               "an index of each periodic range, it will less then 100"
        ::= { ruijieTRPeriEntry 3 }
		
ruijiePeriTRMode OBJECT-TYPE
        SYNTAX INTEGER{
               periodic-add(1), 
               periodic-del(2)		   
            }
        MAX-ACCESS read-create
        STATUS current
        DESCRIPTION
               " add daily or del periodic timerange"
        ::= { ruijieTRPeriEntry 4 }
END
