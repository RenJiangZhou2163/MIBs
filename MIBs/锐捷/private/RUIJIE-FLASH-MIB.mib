-- *****************************************************************
-- RUIJIE-FLASH-MIB.mib:  Ruijie Flash MIB file
--
-- October 2009, linshuangfeng
--
-- Copyright (c) 2009 by Ruijie Networks Co.,Ltd.
-- All rights reserved.
-- 
-- *****************************************************************
--

RUIJIE-FLASH-MIB DEFINITIONS ::= BEGIN

IMPORTS
        MODULE-IDENTITY,
        OBJECT-TYPE,
        Unsigned32
                FROM SNMPv2-SMI
        DisplayString
                FROM SNMPv2-TC
        MODULE-COMPLIANCE,
        OBJECT-GROUP
                FROM SNMPv2-CONF
        ruijieMgmt
                FROM RUIJIE-SMI;

ruijieFlashMIB MODULE-IDENTITY
        LAST-UPDATED "200910090000Z"
        ORGANIZATION "Ruijie Networks Co.,Ltd."
        CONTACT-INFO
                " 
                Tel: 4008-111-000 

                E-mail: service@ruijie.com.cn"
        DESCRIPTION
                "This module defines ruijie system mibs."
        REVISION      "200910090000Z"
        DESCRIPTION
                "Initial version of this MIB module."
        ::= { ruijieMgmt 47}


ruijieFlashMIBObjects OBJECT IDENTIFIER ::= { ruijieFlashMIB 1 }

    
ruijieFlashDeviceTable OBJECT-TYPE
  SYNTAX      SEQUENCE OF RuijieFlashDeviceEntry
  MAX-ACCESS  not-accessible
  STATUS      current
  DESCRIPTION
    "A table of flash device entries. Each of the
     objects provides the flash device information."
  ::= { ruijieFlashMIBObjects 1 }

ruijieFlashDeviceEntry OBJECT-TYPE
  SYNTAX      RuijieFlashDeviceEntry
  MAX-ACCESS  not-accessible
  STATUS      current
  DESCRIPTION
    "An entry in the flash device table."
  INDEX { ruijieFlashDeviceIndex }
  ::= { ruijieFlashDeviceTable 1 }

RuijieFlashDeviceEntry ::=
  SEQUENCE {
    ruijieFlashDeviceIndex  Unsigned32,
    ruijieFlashDeviceName   DisplayString,
    ruijieFlashDeviceSize   Unsigned32,
    ruijieFlashDeviceUsed   Unsigned32,
    ruijieFlashDeviceFree   Unsigned32
  }
    
ruijieFlashDeviceIndex OBJECT-TYPE
    SYNTAX        Unsigned32
    MAX-ACCESS    read-only
    STATUS        current
    DESCRIPTION
        "An index that uniquely represents a flash device."
    ::= { ruijieFlashDeviceEntry 1 }

ruijieFlashDeviceName OBJECT-TYPE
    SYNTAX        DisplayString
    MAX-ACCESS    read-only
    STATUS        current
    DESCRIPTION
        "A textual name assigned to the flash device."
    ::= { ruijieFlashDeviceEntry 2 }
    
ruijieFlashDeviceSize OBJECT-TYPE
    SYNTAX        Unsigned32
    MAX-ACCESS    read-only
    STATUS        current
    DESCRIPTION
        "This is the total size of the flash device."
    ::= { ruijieFlashDeviceEntry 3 }

ruijieFlashDeviceUsed OBJECT-TYPE
    SYNTAX        Unsigned32
    MAX-ACCESS    read-only
    STATUS        current
    DESCRIPTION
        "This is the used size of the flash device."
    ::= { ruijieFlashDeviceEntry 4 }

ruijieFlashDeviceFree OBJECT-TYPE
    SYNTAX        Unsigned32
    MAX-ACCESS    read-only
    STATUS        current
    DESCRIPTION
        "This is the free size of the flash device."
    ::= { ruijieFlashDeviceEntry 5 }
        
ruijieBootromDeviceTable OBJECT-TYPE
  SYNTAX      SEQUENCE OF RuijieBootromDeviceEntry
  MAX-ACCESS  not-accessible
  STATUS      current
  DESCRIPTION
    "A table of bootrom device entries. Each of the
     objects provides the bootrom device information."
  ::= { ruijieFlashMIBObjects 2 }

ruijieBootromDeviceEntry OBJECT-TYPE
  SYNTAX      RuijieBootromDeviceEntry
  MAX-ACCESS  not-accessible
  STATUS      current
  DESCRIPTION
    "An entry in the bootrom device table."
  INDEX { ruijieBootromDeviceIndex }
  ::= { ruijieBootromDeviceTable 1 }

RuijieBootromDeviceEntry ::=
  SEQUENCE {
    ruijieBootromDeviceIndex  Unsigned32,
    ruijieBootromDeviceName   DisplayString,
    ruijieBootromDeviceSize   Unsigned32
  }
    
ruijieBootromDeviceIndex OBJECT-TYPE
    SYNTAX        Unsigned32
    MAX-ACCESS    read-only
    STATUS        current
    DESCRIPTION
        "An index that uniquely represents a bootrom device."
    ::= { ruijieBootromDeviceEntry 1 }

ruijieBootromDeviceName OBJECT-TYPE
    SYNTAX        DisplayString
    MAX-ACCESS    read-only
    STATUS        current
    DESCRIPTION
        "A textual name assigned to the bootrom device."
    ::= { ruijieBootromDeviceEntry 2 }  
    
ruijieBootromDeviceSize OBJECT-TYPE
    SYNTAX        Unsigned32
    MAX-ACCESS    read-only
    STATUS        current
    DESCRIPTION
        "This is the total size of the bootrom device."
    ::= { ruijieBootromDeviceEntry 3 }
    
ruijieFlashMIBConformance OBJECT IDENTIFIER ::= { ruijieFlashMIB 2 }
ruijieFlashMIBCompliances OBJECT IDENTIFIER ::= { ruijieFlashMIBConformance 1 }
ruijieFlashMIBGroups      OBJECT IDENTIFIER ::= { ruijieFlashMIBConformance 2 }


-- compliance statements

ruijieFlashMIBCompliance MODULE-COMPLIANCE
        STATUS  current
        DESCRIPTION
                "The compliance statement for entities which implement
                the Ruijie Flash MIB"
        MODULE  -- this module
                MANDATORY-GROUPS { ruijieFlashMIBGroup
                 }
        ::= { ruijieFlashMIBCompliances 1 }
                
-- units of conformance

ruijieFlashMIBGroup OBJECT-GROUP
        OBJECTS {
          ruijieFlashDeviceIndex,
          ruijieFlashDeviceName,
          ruijieFlashDeviceSize,
          ruijieFlashDeviceUsed,
          ruijieFlashDeviceFree
        }
        STATUS  current
        DESCRIPTION
                "A collection of objects providing flash information to a Ruijie agent."
        ::= { ruijieFlashMIBGroups 1 } 
  
ruijieBootromDeviceMIBGroup OBJECT-GROUP
        OBJECTS {
          ruijieBootromDeviceIndex,
          ruijieBootromDeviceName,
          ruijieBootromDeviceSize
        }
        STATUS  current
        DESCRIPTION
                "A collection of objects providing bootrom device information to a Ruijie agent."
        ::= { ruijieFlashMIBGroups 2 } 
  
END
