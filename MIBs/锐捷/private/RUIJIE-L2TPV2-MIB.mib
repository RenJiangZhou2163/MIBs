--
-- RUIJIE-L2TPV2-MIB.mib
-- MIB generated by MG-SOFT Visual MIB Builder Version 6.0  Build 88
-- Friday, March 01, 2013 at 14:57:31
--

RUIJIE-L2TPV2-MIB DEFINITIONS ::= BEGIN

		IMPORTS
			ruijieMgmt			
				FROM RUIJIE-SMI			
			IpAddress, 
			Integer32, 
			Unsigned32, 
			Counter64, 
			OBJECT-TYPE, 
			MODULE-IDENTITY, 
			NOTIFICATION-TYPE			
				FROM SNMPv2-SMI;
	
		-- 1.3.6.1.4.1.4881.1.1.10.2.117
		ruijieL2TPv2MIB MODULE-IDENTITY 
			LAST-UPDATED "201210110959Z"		-- October 11, 2012 at 09:59 GMT
			ORGANIZATION 
				"Ruijie Networks Co.,Ltd."
			CONTACT-INFO 
				"Contact-info."
			DESCRIPTION 
				"Description."
			::= { ruijieMgmt 117 }

--
-- Node definitions
--

		-- 1.3.6.1.4.1.4881.1.1.10.2.117.1
		ruijieL2TPv2Objects OBJECT IDENTIFIER ::= { ruijieL2TPv2MIB 1 }

		-- 1.3.6.1.4.1.4881.1.1.10.2.117.1.1
		ruijieL2TPv2TunnelTable OBJECT-TYPE
			SYNTAX SEQUENCE OF RuijieL2TPv2TunnelEntry
			MAX-ACCESS not-accessible
			STATUS current
			DESCRIPTION
				"Description."
			::= { ruijieL2TPv2Objects 1 }

		-- 1.3.6.1.4.1.4881.1.1.10.2.117.1.1.1
		ruijieL2TPv2TunnelEntry OBJECT-TYPE
			SYNTAX RuijieL2TPv2TunnelEntry
			MAX-ACCESS not-accessible
			STATUS current
			DESCRIPTION
				"Description."
			INDEX { ruijieL2TPv2TunnelLocalID }
			::= { ruijieL2TPv2TunnelTable 1 }

		RuijieL2TPv2TunnelEntry ::=
			SEQUENCE { 
				ruijieL2TPv2TunnelLocalID
					Unsigned32,
				ruijieL2TPv2TunnelRemoteID
					Unsigned32,
				ruijieL2TPv2TunnelStatus
					Unsigned32,
				ruijieL2TPv2TunnelSrcIP
					IpAddress,
				ruijieL2TPv2TunnelDstIP
					IpAddress,
				ruijieL2TPv2TunnelLacHostname
					OCTET STRING,
				ruijieL2TPv2TunnelLacVendor
					OCTET STRING
			 }

		-- 1.3.6.1.4.1.4881.1.1.10.2.117.1.1.1.1
		ruijieL2TPv2TunnelLocalID OBJECT-TYPE
			SYNTAX Unsigned32 (1..4294967295)
			MAX-ACCESS read-only
			STATUS current
			DESCRIPTION
				"Description."
			::= { ruijieL2TPv2TunnelEntry 1 }

		-- 1.3.6.1.4.1.4881.1.1.10.2.117.1.1.1.2
		ruijieL2TPv2TunnelRemoteID OBJECT-TYPE
			SYNTAX Unsigned32
			MAX-ACCESS read-only
			STATUS current
			DESCRIPTION
				"Description."
			::= { ruijieL2TPv2TunnelEntry 2 }

		-- 1.3.6.1.4.1.4881.1.1.10.2.117.1.1.1.3
		ruijieL2TPv2TunnelStatus OBJECT-TYPE
			SYNTAX Unsigned32
			MAX-ACCESS read-write
			STATUS current
			DESCRIPTION
				"Description."
			::= { ruijieL2TPv2TunnelEntry 3 }

		-- 1.3.6.1.4.1.4881.1.1.10.2.117.1.1.1.4
		ruijieL2TPv2TunnelSrcIP OBJECT-TYPE
			SYNTAX IpAddress
			MAX-ACCESS read-only
			STATUS current
			DESCRIPTION
				"Description."
			::= { ruijieL2TPv2TunnelEntry 4 }

		-- 1.3.6.1.4.1.4881.1.1.10.2.117.1.1.1.5
		ruijieL2TPv2TunnelDstIP OBJECT-TYPE
			SYNTAX IpAddress
			MAX-ACCESS read-only
			STATUS current
			DESCRIPTION
				"Description."
			::= { ruijieL2TPv2TunnelEntry 5 }

		-- 1.3.6.1.4.1.4881.1.1.10.2.117.1.1.1.6
		ruijieL2TPv2TunnelLacHostname OBJECT-TYPE
			SYNTAX OCTET STRING
			MAX-ACCESS read-only
			STATUS current
			DESCRIPTION
				"Description."
			::= { ruijieL2TPv2TunnelEntry 6 }

		-- 1.3.6.1.4.1.4881.1.1.10.2.117.1.1.1.7
		ruijieL2TPv2TunnelLacVendor OBJECT-TYPE
			SYNTAX OCTET STRING
			MAX-ACCESS read-only
			STATUS current
			DESCRIPTION
				"Description."
			::= { ruijieL2TPv2TunnelEntry 7 }

		-- 1.3.6.1.4.1.4881.1.1.10.2.117.1.2
		ruijieL2TPv2SessionTable OBJECT-TYPE
			SYNTAX SEQUENCE OF RuijieL2TPv2SessionEntry
			MAX-ACCESS not-accessible
			STATUS current
			DESCRIPTION
				"Description."
			::= { ruijieL2TPv2Objects 2 }

		-- 1.3.6.1.4.1.4881.1.1.10.2.117.1.2.1
		ruijieL2TPv2SessionEntry OBJECT-TYPE
			SYNTAX RuijieL2TPv2SessionEntry
			MAX-ACCESS not-accessible
			STATUS current
			DESCRIPTION
				"Description."
			INDEX { ruijieL2TPv2TunnelLocalID, ruijieL2TPv2SessionLocalID }
			::= { ruijieL2TPv2SessionTable 1 }

		RuijieL2TPv2SessionEntry ::=
			SEQUENCE { 
				ruijieL2TPv2SessionLocalID
					Unsigned32,
				ruijieL2TPv2SessionRemoteID
					Unsigned32,
				ruijieL2TPv2SessionUserName
					OCTET STRING,
				ruijieL2TPv2SessionStatus
					Unsigned32,
				ruijieL2TPv2SessionSrcIP
					IpAddress,
				ruijieL2TPv2SessionDstIP
					IpAddress,
				ruijieL2TPv2SessionLocalVrf
					Integer32,
				ruijieL2TPv2SessionExistTime
					Integer32,
				ruijieL2TPv2SessionIMSI
					OCTET STRING,
				ruijieL2TPv2SessionAccessDeviceID
					OCTET STRING
			 }

		-- 1.3.6.1.4.1.4881.1.1.10.2.117.1.2.1.1
		ruijieL2TPv2SessionLocalID OBJECT-TYPE
			SYNTAX Unsigned32 (1..4294967295)
			MAX-ACCESS read-only
			STATUS current
			DESCRIPTION
				"Description."
			::= { ruijieL2TPv2SessionEntry 1 }

		-- 1.3.6.1.4.1.4881.1.1.10.2.117.1.2.1.2
		ruijieL2TPv2SessionRemoteID OBJECT-TYPE
			SYNTAX Unsigned32
			MAX-ACCESS read-only
			STATUS current
			DESCRIPTION
				"Description."
			::= { ruijieL2TPv2SessionEntry 2 }

		-- 1.3.6.1.4.1.4881.1.1.10.2.117.1.2.1.3
		ruijieL2TPv2SessionUserName OBJECT-TYPE
			SYNTAX OCTET STRING
			MAX-ACCESS read-only
			STATUS current
			DESCRIPTION
				"Description."
			::= { ruijieL2TPv2SessionEntry 3 }

		-- 1.3.6.1.4.1.4881.1.1.10.2.117.1.2.1.4
		ruijieL2TPv2SessionStatus OBJECT-TYPE
			SYNTAX Unsigned32
			MAX-ACCESS read-write
			STATUS current
			DESCRIPTION
				"Description."
			::= { ruijieL2TPv2SessionEntry 4 }

		-- 1.3.6.1.4.1.4881.1.1.10.2.117.1.2.1.5
		ruijieL2TPv2SessionSrcIP OBJECT-TYPE
			SYNTAX IpAddress
			MAX-ACCESS read-only
			STATUS current
			DESCRIPTION
				"Description."
			::= { ruijieL2TPv2SessionEntry 5 }

		-- 1.3.6.1.4.1.4881.1.1.10.2.117.1.2.1.6
		ruijieL2TPv2SessionDstIP OBJECT-TYPE
			SYNTAX IpAddress
			MAX-ACCESS read-only
			STATUS current
			DESCRIPTION
				"Description."
			::= { ruijieL2TPv2SessionEntry 6 }

		-- 1.3.6.1.4.1.4881.1.1.10.2.117.1.2.1.7
		ruijieL2TPv2SessionLocalVrf OBJECT-TYPE
			SYNTAX Integer32
			MAX-ACCESS read-only
			STATUS current
			DESCRIPTION
				"Description."
			::= { ruijieL2TPv2SessionEntry 7 }

		-- 1.3.6.1.4.1.4881.1.1.10.2.117.1.2.1.8
		ruijieL2TPv2SessionExistTime OBJECT-TYPE
			SYNTAX Integer32
			MAX-ACCESS read-only
			STATUS current
			DESCRIPTION
				"Description."
			::= { ruijieL2TPv2SessionEntry 8 }

		-- 1.3.6.1.4.1.4881.1.1.10.2.117.1.2.1.9
		ruijieL2TPv2SessionIMSI OBJECT-TYPE
			SYNTAX OCTET STRING
			MAX-ACCESS read-only
			STATUS current
			DESCRIPTION
				"Description."
			::= { ruijieL2TPv2SessionEntry 9 }

		-- 1.3.6.1.4.1.4881.1.1.10.2.117.1.2.1.10
		ruijieL2TPv2SessionAccessDeviceID OBJECT-TYPE
			SYNTAX OCTET STRING
			MAX-ACCESS read-only
			STATUS current
			DESCRIPTION
				"Description."
			::= { ruijieL2TPv2SessionEntry 10 }

		-- 1.3.6.1.4.1.4881.1.1.10.2.117.1.3
		ruijieL2TPv2SessionTrafficStatTable OBJECT-TYPE
			SYNTAX SEQUENCE OF RuijieL2TPv2SessionTrafficStatEntry
			MAX-ACCESS not-accessible
			STATUS current
			DESCRIPTION
				"Description."
			::= { ruijieL2TPv2Objects 3 }

		-- 1.3.6.1.4.1.4881.1.1.10.2.117.1.3.1
		ruijieL2TPv2SessionTrafficStatEntry OBJECT-TYPE
			SYNTAX RuijieL2TPv2SessionTrafficStatEntry
			MAX-ACCESS not-accessible
			STATUS current
			DESCRIPTION
				"Description."
			INDEX { ruijieL2TPv2TunnelLocalID, ruijieL2TPv2SessionLocalID }
			::= { ruijieL2TPv2SessionTrafficStatTable 1 }

		RuijieL2TPv2SessionTrafficStatEntry ::=
			SEQUENCE { 
				ruijieL2TPv2SessionTrafficStatRxBytes
					Counter64,
				ruijieL2TPv2SessionTrafficStatRxPkts
					Counter64,
				ruijieL2TPv2SessionTrafficStatRxErrPkts
					Counter64,
				ruijieL2TPv2SessionTrafficStatRxSpeed
					Counter64,
				ruijieL2TPv2SessionTrafficStatTxBytes
					Counter64,
				ruijieL2TPv2SessionTrafficStatTxPkts
					Counter64,
				ruijieL2TPv2SessionTrafficStatTxSpeed
					Counter64
			 }

		-- 1.3.6.1.4.1.4881.1.1.10.2.117.1.3.1.1
		ruijieL2TPv2SessionTrafficStatRxBytes OBJECT-TYPE
			SYNTAX Counter64
			MAX-ACCESS read-only
			STATUS current
			DESCRIPTION
				"Description."
			::= { ruijieL2TPv2SessionTrafficStatEntry 1 }

		-- 1.3.6.1.4.1.4881.1.1.10.2.117.1.3.1.2
		ruijieL2TPv2SessionTrafficStatRxPkts OBJECT-TYPE
			SYNTAX Counter64
			MAX-ACCESS read-only
			STATUS current
			DESCRIPTION
				"Description."
			::= { ruijieL2TPv2SessionTrafficStatEntry 2 }

		-- 1.3.6.1.4.1.4881.1.1.10.2.117.1.3.1.3
		ruijieL2TPv2SessionTrafficStatRxErrPkts OBJECT-TYPE
			SYNTAX Counter64
			MAX-ACCESS read-only
			STATUS current
			DESCRIPTION
				"Description."
			::= { ruijieL2TPv2SessionTrafficStatEntry 3 }

		-- 1.3.6.1.4.1.4881.1.1.10.2.117.1.3.1.4
		ruijieL2TPv2SessionTrafficStatRxSpeed OBJECT-TYPE
			SYNTAX Counter64
			MAX-ACCESS read-only
			STATUS current
			DESCRIPTION
				"Description."
			::= { ruijieL2TPv2SessionTrafficStatEntry 4 }

		-- 1.3.6.1.4.1.4881.1.1.10.2.117.1.3.1.5
		ruijieL2TPv2SessionTrafficStatTxBytes OBJECT-TYPE
			SYNTAX Counter64
			MAX-ACCESS read-only
			STATUS current
			DESCRIPTION
				"Description."
			::= { ruijieL2TPv2SessionTrafficStatEntry 5 }

		-- 1.3.6.1.4.1.4881.1.1.10.2.117.1.3.1.6
		ruijieL2TPv2SessionTrafficStatTxPkts OBJECT-TYPE
			SYNTAX Counter64
			MAX-ACCESS read-only
			STATUS current
			DESCRIPTION
				"Description."
			::= { ruijieL2TPv2SessionTrafficStatEntry 6 }

		-- 1.3.6.1.4.1.4881.1.1.10.2.117.1.3.1.7
		ruijieL2TPv2SessionTrafficStatTxSpeed OBJECT-TYPE
			SYNTAX Counter64
			MAX-ACCESS read-only
			STATUS current
			DESCRIPTION
				"Description."
			::= { ruijieL2TPv2SessionTrafficStatEntry 7 }

		-- 1.3.6.1.4.1.4881.1.1.10.2.117.2
		ruijieL2TPv2Notifications OBJECT IDENTIFIER ::= { ruijieL2TPv2MIB 2 }

		-- 1.3.6.1.4.1.4881.1.1.10.2.117.2.1
		ruijieL2TPv2SessionNotifications OBJECT IDENTIFIER ::= { ruijieL2TPv2Notifications 1 }

		-- 1.3.6.1.4.1.4881.1.1.10.2.117.2.1.1
		ruijieL2TPv2SessionStart NOTIFICATION-TYPE
			OBJECTS { 
         ruijieL2TPv2TunnelDstIP, 
			   ruijieL2TPv2TunnelLocalID, 
			   ruijieL2TPv2SessionLocalID, 
			   ruijieL2TPv2SessionIMSI, 
			   ruijieL2TPv2SessionAccessDeviceID, 
				 ruijieL2TPv2SessionSrcIP, 
				 ruijieL2TPv2SessionExistTime, 
				 ruijieL2TPv2SessionLocalVrf, 
				 ruijieL2TPv2SessionDstIP, 
				 ruijieL2TPv2TunnelSrcIP
			}
			STATUS current
			DESCRIPTION 
				"Description."
			::= { ruijieL2TPv2SessionNotifications 1 }

		-- 1.3.6.1.4.1.4881.1.1.10.2.117.2.1.2
		ruijieL2TPv2SessionStop NOTIFICATION-TYPE
			OBJECTS { 
			   ruijieL2TPv2TunnelLocalID, 
			   ruijieL2TPv2SessionLocalID, 
			   ruijieL2TPv2TunnelSrcIP, 
			   ruijieL2TPv2TunnelDstIP, 
			   ruijieL2TPv2SessionSrcIP, 
				 ruijieL2TPv2SessionDstIP, 
				 ruijieL2TPv2SessionLocalVrf, 
				 ruijieL2TPv2SessionExistTime, 
				 ruijieL2TPv2SessionIMSI, 
				 ruijieL2TPv2SessionAccessDeviceID
			}
			STATUS current
			DESCRIPTION 
				"Description."
			::= { ruijieL2TPv2SessionNotifications 2 }

		-- 1.3.6.1.4.1.4881.1.1.10.2.117.3
		ruijieL2TPVersion OBJECT-TYPE
			SYNTAX OCTET STRING
			MAX-ACCESS read-only
			STATUS current
			DESCRIPTION
				"Description."
			::= { ruijieL2TPv2MIB 3 }

	END

--
-- RUIJIE-L2TPV2-MIB.mib
--
