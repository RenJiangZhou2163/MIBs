-- *******************************************************************
-- Ruijie-FRAME-RELAY-MIB.mib
--        Ruijie Frame Relay MIB file, providing Frame Relay specific
--        information that are either excluded by RFC 1315 (FR DTE MIB)
--        or specific to Ruijie products.
--
-- May 2009, juncheng hong
--
-- Copyright (c) 2009 by Ruijie Networks Co.,Ltd.
-- All rights reserved.
--
-- *******************************************************************

-- Note:
-- Until future change, it is no intention for this MIB to cover 
-- every Frame Relay related feature, configuration statement, or
-- exec command display. The focus is to provide key information
-- that are unavailable in any of the existing MIB's, but are
-- currently available through the Frame Relay show commands and/or
-- configuration displays.


RUIJIE-FRAME-RELAY-MIB DEFINITIONS ::= BEGIN

IMPORTS
        MODULE-IDENTITY,
        OBJECT-TYPE,
        Counter32,
        Integer32,
        IpAddress
                FROM SNMPv2-SMI
        MODULE-COMPLIANCE,
        OBJECT-GROUP
                FROM SNMPv2-CONF
        TEXTUAL-CONVENTION,
        DisplayString,
        TruthValue
                FROM SNMPv2-TC
        ruijieMgmt
                FROM RUIJIE-SMI
        InterfaceIndex,
        ifIndex
                FROM IF-MIB
        frDlcmiEntry,
        frCircuitEntry,
        frCircuitIfIndex,
        frCircuitDlci
                FROM FRAME-RELAY-DTE-MIB;

-- All table indicies in this MIB that involve interface index and
-- DLCI are derived from frCircuitIfIndex and frCircuitDlci 
-- respectively from RFC 1315.

ruijieFrameRelayMIB     MODULE-IDENTITY
        LAST-UPDATED   "200010130000Z"
        ORGANIZATION   "Ruijie Networks Co.,Ltd."
        CONTACT-INFO
                " 
                Tel: 4008-111-000 

                E-mail: service@ruijie.com.cn"
        DESCRIPTION
                "Ruijie Frame Relay MIB"

        REVISION        "200010130000Z"
        DESCRIPTION
                "(1) Added objects of FR Switching, FR Fragmentation 
                and FR/ATM Interworking.
                (2) Objects for per PVC I/O rate is added to 
                cfrExtCircuitTable"

        REVISION        "200005220000Z"
        DESCRIPTION
                "(1) Added  ELMI subgroup for ELMI objects."

        REVISION        "200005160000Z"
        DESCRIPTION
                "(1) Added Traffic Shaping parameter objects to
                ruijiefrExtCircuitTable.
                (2) Deprecated ruijiefrSvcMinThruputOut and 
                ruijiefrSvcMinThruputIn. Added ruijiefrExtCircuitMinThruputOut 
                and ruijiefrExtCircuitMinThruputIn in ruijiefrExtCircuitTable 
                inorder to make them applicable to both PVC/SVC. 
                (3) Added ruijiefrExtCircuitBandwidth object to 
                ruijiefrExtCircuitTable."

        REVISION        "200905180000Z"
        DESCRIPTION
                "(1) add an integer value for ruijiefrMapPayloadCompressType;
                (2) reword the Description statements for 
                      { ruijiefrMapPayloadCompressType,
                      ruijiefrExtCircuitUncompressIns,
                      ruijiefrExtCircuitUncompressOuts }
                so that they are not limited to software compression."

        REVISION        "9908210000Z"
        DESCRIPTION
                "(1) Added ruijiefrExtCircuitUncompressOuts and
                ruijiefrExtCircuitUncompressIns to the circuit subgroup;
                (2) Added ruijiefrMapRtpHdrCompress and ruijiefrMapPayloadCompressType
                to the mapping subgroup;
                (3) ruijiefrMapPayloadCompress becomes deprecated, obsoleted
                by ruijiefrMapPayloadCompressType;
                (4) frCircuitSentOctets and frCircuitReceivedOctets
                per RFC1315 will reflect the number of bytes in Frame Relay
                frames sent to and received from the physical layer. Same
                effect is applied to ifOutOctets and ifInOctets as well
                when ifIndex refers to a Frame Relay subinterface."

        REVISION        "9608150000Z"
        DESCRIPTION
                "Initial version of this MIB module."

        ::= { ruijieMgmt 50 }


ruijieFrMIBObjects OBJECT IDENTIFIER ::= { ruijieFrameRelayMIB 1 }

-- Subgroups:
-- The objects include four subgroups on the topics of
--        o LMI (Local Management Interface, see ANSI T1.617 Annex D and
--          the Frame Relay Specification with Extensions by DEC,
--          NT, StrataCom, and Ruijie.),
--        o Virtual circuits,
--        o Circuit mapping information, 
--        o SVC (switched virtual circuits, see CCITT/ITU Q.933 and 
--           Q.922.),
--        o ELMI (Enhanced Link Management Interface) objects,
--        o Fragmentation objects,
--        o Frame Relay/ATM Network Interworking objects,
--        o Frame Relay/ATM PVC Service Interworking objects, and
--        o Frame Relay Switching objects.

ruijiefrLmiObjs        OBJECT IDENTIFIER ::= { ruijieFrMIBObjects 1 }

ruijiefrCircuitObjs    OBJECT IDENTIFIER ::= { ruijieFrMIBObjects 2 }

ruijiefrMapObjs        OBJECT IDENTIFIER ::= { ruijieFrMIBObjects 3 }

ruijiefrSvcObjs        OBJECT IDENTIFIER ::= { ruijieFrMIBObjects 4 }

ruijiefrElmiObjs       OBJECT IDENTIFIER ::= { ruijieFrMIBObjects 5 }

ruijiefrFragObjs       OBJECT IDENTIFIER ::= { ruijieFrMIBObjects 6 }

ruijiefrConnectionObjs  OBJECT IDENTIFIER ::= { ruijieFrMIBObjects 7 }

DlciNumber ::= TEXTUAL-CONVENTION
        STATUS  current
        DESCRIPTION
                "Numerical format of Data Link Connection Identifier
                (DLCI) in decimal, identical to the 'DLCI' as INTEGER
                of 0..DLCINumber in RFC1315. The maximum value depends
                on Frame Relay implementation, which is currently set
                to be 1023 for 2-octet address format per UNI
                Implementation Agreement FRF.1."
        SYNTAX        INTEGER (0..1023)

RuijiefrMapProtocols ::= TEXTUAL-CONVENTION
        STATUS  current
        DESCRIPTION
                "Ruijie link types (network protocols) that run
                over Frame Relay. Associated values, except for
                wildcard, match assigned values of internal software
                respectively."
        SYNTAX  INTEGER
        {
                arp(1),
                serialArp(6),
                ip(7),
                xns(10),
                novell(11),
                apollo(12),
                vines(13),
                appletalk(16),
                ieeeSpanning(18),
                decnet(22),
                clns(25),
                rsrb(37),
                bridge(38),
                stun(39),
                frArp(40),
                uncompressedTcp(47),
                compressedTcp(48),
                llc2(49),
                frSwitch(53),
                dlsw(63),
                nhrp(74),
                compressedRtp(83),
                wildcard(999)        -- either means no applicable type for
                                -- the circuit or means point-to-point
        }


-- LMI sub-group {

ruijiefrLmiTable OBJECT-TYPE
        SYNTAX      SEQUENCE OF RuijiefrLmiEntry
        MAX-ACCESS  not-accessible
        STATUS      current
        DESCRIPTION
                "Table of Frame Relay LMI information that are
                either supplemental to the frDlcmiTable of RFC 1315
                or specific to Ruijie's implementation."
        REFERENCE
                "American National Standard T1.617-1991, Annex D"
        ::= { ruijiefrLmiObjs 1 }

ruijiefrLmiEntry OBJECT-TYPE
        SYNTAX      RuijiefrLmiEntry
        MAX-ACCESS  not-accessible
        STATUS      current
        DESCRIPTION
                "Each entry of the table contains information
                of Frame Relay LMI over one physical interface.
                They are mostly FR generic and some Ruijie specific."
        AUGMENTS { frDlcmiEntry }
        ::= { ruijiefrLmiTable 1 }

RuijiefrLmiEntry ::=
        SEQUENCE {
            ruijiefrLmiLinkstatus             INTEGER, 
            ruijiefrLmiLinkType               INTEGER, 
            ruijiefrLmiEnquiryIns             Counter32,
            ruijiefrLmiEnquiryOuts            Counter32,
            ruijiefrLmiStatusIns              Counter32, 
            ruijiefrLmiStatusOuts             Counter32,
            ruijiefrLmiUpdateStatusIns        Counter32, 
            ruijiefrLmiUpdateStatusOuts       Counter32, 
            ruijiefrLmiStatusTimeouts         Counter32,
            ruijiefrLmiStatusEnqTimeouts      Counter32,
            ruijiefrLmiN392Dce                INTEGER,
            ruijiefrLmiN393Dce                INTEGER,
            ruijiefrLmiT392Dce                INTEGER
        }

-- Note: for LMI type, i.e. ANSI or cisco, see frDlcmiState
-- of RFC 1315. Also, for LMI parameters for DTE not listed here,
-- e.g. T391, N391, N392, and N393, see RFC 1315.
--
-- Although based on the current logic the value for
-- cfrLmiDLstatus is equivalent to ifOperStatus, the object
-- remains herein for future possible development change.

ruijiefrLmiLinkstatus OBJECT-TYPE
        SYNTAX  INTEGER {
                    up(1),
                    down(2)
                }
        MAX-ACCESS  read-only
        STATUS      current
        DESCRIPTION
                "Data link status via LMI."
        ::= { ruijiefrLmiEntry 1 }

ruijiefrLmiLinkType OBJECT-TYPE
        SYNTAX  INTEGER {
                    dte(1),
                    dce(2),
                    nni(3)
                }
        MAX-ACCESS  read-only
        STATUS      current
        DESCRIPTION
                "Frame Relay link type."
        ::= { ruijiefrLmiEntry 2 }


ruijiefrLmiEnquiryIns OBJECT-TYPE
        SYNTAX      Counter32
        UNITS       "messages"
        MAX-ACCESS  read-only
        STATUS      current
        DESCRIPTION
                "Number of Status Enquiry messages received."
        ::= { ruijiefrLmiEntry 3 }

ruijiefrLmiEnquiryOuts OBJECT-TYPE
        SYNTAX      Counter32
        UNITS       "messages"
        MAX-ACCESS  read-only
        STATUS      current
        DESCRIPTION
                "Number of Status Enquiry messages sent."
        ::= { ruijiefrLmiEntry 4 }

ruijiefrLmiStatusIns OBJECT-TYPE
        SYNTAX      Counter32
        UNITS       "messages"
        MAX-ACCESS  read-only
        STATUS      current
        DESCRIPTION
                "Number of Status messages received."
        ::= { ruijiefrLmiEntry 5 }

ruijiefrLmiStatusOuts OBJECT-TYPE
        SYNTAX      Counter32
        UNITS       "messages"
        MAX-ACCESS  read-only
        STATUS      current
        DESCRIPTION
                "Number of Status messages sent."
        ::= { ruijiefrLmiEntry 6 }

ruijiefrLmiUpdateStatusIns OBJECT-TYPE
        SYNTAX      Counter32
        UNITS       "messages"
        MAX-ACCESS  read-only
        STATUS      current
        DESCRIPTION
                "Number of Update Status messages received."
        ::= { ruijiefrLmiEntry 7 }

ruijiefrLmiUpdateStatusOuts OBJECT-TYPE
        SYNTAX      Counter32
        UNITS       "messages"
        MAX-ACCESS  read-only
        STATUS      current
        DESCRIPTION
                "Number of Update Status messages sent"
        ::= { ruijiefrLmiEntry 8 }

ruijiefrLmiStatusTimeouts OBJECT-TYPE
        SYNTAX      Counter32
        UNITS       "times"
        MAX-ACCESS  read-only
        STATUS      current
        DESCRIPTION
                "Number of times when timeout occurred on waiting
                for Status message"
        ::= { ruijiefrLmiEntry 9 }

ruijiefrLmiStatusEnqTimeouts OBJECT-TYPE
        SYNTAX      Counter32
        UNITS       "times"
        MAX-ACCESS  read-only
        STATUS      current
        DESCRIPTION
                "Number of times when timeout occurred on waiting
                for Status Enquiry message"
        ::= { ruijiefrLmiEntry 10 }

ruijiefrLmiN392Dce OBJECT-TYPE
        SYNTAX      INTEGER (0..10)
        MAX-ACCESS  read-only
        STATUS      current
        DESCRIPTION
                "LMI error threshold for DCE interface.
                For DTE, value becomes 0."
        ::= { ruijiefrLmiEntry 11 }

ruijiefrLmiN393Dce OBJECT-TYPE
        SYNTAX      INTEGER (0..10)
        MAX-ACCESS  read-only
        STATUS      current
        DESCRIPTION
                "LMI monitored event count for DCE interface.
                For DTE, value becomes zero (0)."
        ::= { ruijiefrLmiEntry 12 }

ruijiefrLmiT392Dce OBJECT-TYPE
        SYNTAX      INTEGER (0..30)
        UNITS       "seconds"
        MAX-ACCESS  read-only
        STATUS      current
        DESCRIPTION
                "DCE polling verification timer for DCE interface
                For DTE, the value becomes zero (0)."
        ::= { ruijiefrLmiEntry 13 }

-- end LMI subgroup }

-- Circut sub-group {

ruijiefrCircuitTable OBJECT-TYPE
        SYNTAX      SEQUENCE OF RuijiefrCircuitEntry
        MAX-ACCESS  not-accessible
        STATUS      current
        DESCRIPTION
                "Table of descriptive and statistics information
                that are generic to Frame Relay virtual circuits."
        ::= { ruijiefrCircuitObjs 1 }

ruijiefrCircuitEntry OBJECT-TYPE
        SYNTAX      RuijiefrCircuitEntry
        MAX-ACCESS  not-accessible
        STATUS      current
        DESCRIPTION
                "Each entry of the table contains information of a
                circuit that are not included in frCircuitTable of
                RFC1315 but are generic to Frame Relay."
        AUGMENTS { frCircuitEntry }
                -- indexed by { frCircuitIfIndex, frCircuitDlci }
        ::= { ruijiefrCircuitTable 1 }

RuijiefrCircuitEntry ::=
        SEQUENCE {
            ruijiefrCircuitDEins              Counter32,
            ruijiefrCircuitDEouts             Counter32,
            ruijiefrCircuitDropPktsOuts       Counter32,
            ruijiefrCircuitType               INTEGER
        }

ruijiefrCircuitDEins OBJECT-TYPE
        SYNTAX      Counter32
        UNITS       "packets"
        MAX-ACCESS  read-only
        STATUS      current
        DESCRIPTION
                "Number of packets received with the Discarded
                Eligibility indictor (the DE bit) set."
        ::= { ruijiefrCircuitEntry 1 }

ruijiefrCircuitDEouts OBJECT-TYPE
        SYNTAX      Counter32
        UNITS       "packets"
        MAX-ACCESS  read-only
        STATUS      current
        DESCRIPTION
                "Number of packets transmitted with DE bit set."
        ::= { ruijiefrCircuitEntry 2 }

ruijiefrCircuitDropPktsOuts OBJECT-TYPE
        SYNTAX      Counter32
        UNITS       "packets"
        MAX-ACCESS  read-only
        STATUS      current
        DESCRIPTION
                "Number of discarded packets that were to be sent."
        ::= { ruijiefrCircuitEntry 3 }

ruijiefrCircuitType OBJECT-TYPE
        SYNTAX  INTEGER
                {
                    pvc(1),        -- permanent virtual circuit
                    svc(2)        -- switched virtual circuit
                }
        MAX-ACCESS  read-only
        STATUS      current
        DESCRIPTION
                "Basic circuit type"
        ::= { ruijiefrCircuitEntry 4 }

-- Ruijie specific circuit information:

ruijiefrExtCircuitTable  OBJECT-TYPE
        SYNTAX      SEQUENCE OF RuijiefrExtCircuitEntry
        MAX-ACCESS  not-accessible
        STATUS      current
        DESCRIPTION
                "Table of Ruijie implementation specific FR
                circuit information. This is a Ruijie extension
                for the frCircuitTable of RFC 1315."
        ::= { ruijiefrCircuitObjs 2 }

ruijiefrExtCircuitEntry  OBJECT-TYPE
        SYNTAX      RuijiefrExtCircuitEntry
        MAX-ACCESS  not-accessible
        STATUS      current
        DESCRIPTION
                "Each entry of the table contains information
                of a Frame Relay virtual circuit that are specific
                to Ruijie implementation."
        AUGMENTS { frCircuitEntry }
                -- indexed by { frCircuitIfIndex, frCircuitDlci }
        ::= { ruijiefrExtCircuitTable 1 }

RuijiefrExtCircuitEntry ::=
        SEQUENCE {
            ruijiefrExtCircuitIfName             DisplayString,
            ruijiefrExtCircuitIfType             INTEGER,
            ruijiefrExtCircuitSubifIndex         InterfaceIndex,
            ruijiefrExtCircuitMapStatus          INTEGER,
            ruijiefrExtCircuitCreateType         INTEGER,
            ruijiefrExtCircuitMulticast          TruthValue,
            ruijiefrExtCircuitRoutedDlci         DlciNumber, 
            ruijiefrExtCircuitRoutedIf           InterfaceIndex,
            ruijiefrExtCircuitUncompressIns      Counter32,
            ruijiefrExtCircuitUncompressOuts     Counter32,
            ruijiefrExtCircuitFECNOuts           Counter32,  
            ruijiefrExtCircuitBECNOuts           Counter32,  
            ruijiefrExtCircuitMinThruputOut      Integer32,
            ruijiefrExtCircuitMinThruputIn       Integer32,
            ruijiefrExtCircuitBcastPktOuts       Counter32,
            ruijiefrExtCircuitBcastByteOuts      Counter32,
            ruijiefrExtCircuitBandwidth          Integer32,
            ruijiefrExtCircuitShapeByteLimit     Integer32,
            ruijiefrExtCircuitShapeInterval      Integer32,
            ruijiefrExtCircuitShapeByteIncrement Integer32,
            ruijiefrExtCircuitShapePkts          Counter32,
            ruijiefrExtCircuitShapeBytes         Counter32,
            ruijiefrExtCircuitShapePktsDelay     Counter32,
            ruijiefrExtCircuitShapeBytesDelay    Counter32,
            ruijiefrExtCircuitShapeActive        TruthValue,
            ruijiefrExtCircuitShapeAdapting      INTEGER,
            ruijiefrExtCircuitTxDataRate         INTEGER,
            ruijiefrExtCircuitTxPktRate          INTEGER,
            ruijiefrExtCircuitRcvDataRate        INTEGER,
            ruijiefrExtCircuitRcvPktRate         INTEGER 
        }

ruijiefrExtCircuitIfName  OBJECT-TYPE
        SYNTAX       DisplayString
        MAX-ACCESS   read-only
        STATUS       current
        DESCRIPTION
                "The textual name of the main interface or the 
                subinterface that this DLCI is associated with.
                This is the same name string of an interface used
                in the configuration and all console displays,
                such as 'serial 0', 'serial 3/0.3', etc."
        ::= { ruijiefrExtCircuitEntry 1 }

ruijiefrExtCircuitIfType  OBJECT-TYPE
        SYNTAX  INTEGER {
                  mainInterface(1),
                  pointToPoint(2),        -- subinterface
                  multipoint(3)           -- subinterface
                }
        MAX-ACCESS  read-only
        STATUS      current
        DESCRIPTION
                "Type of the subinterface this DLCI is associated
                with, if configured."
        ::= { ruijiefrExtCircuitEntry 2 }

ruijiefrExtCircuitSubifIndex OBJECT-TYPE
        SYNTAX      InterfaceIndex
        MAX-ACCESS  read-only
        STATUS      current
        DESCRIPTION
                "For value greater than zero (0), it indicates
                the network management interface index
                for the subinterface associated with
                this DLCI. Value 0 means the DLCI is not
                associated with any subinterface." 
        ::= { ruijiefrExtCircuitEntry 3 }

ruijiefrExtCircuitMapStatus OBJECT-TYPE
        SYNTAX      INTEGER (0..2047)
        MAX-ACCESS  read-only
        STATUS      current
        DESCRIPTION
                "The mapping protocols (internally considered as
                the 'link type') applied on this circuit.
                The value ranges from 0 to 2047.
                For point-to-point DLCI, the value stays zero.
                Otherwise, the value is a sum. It initially takes
                the value zero, then, for each type of Protocol,
                2 raised to a power is added to the sum.
                The following table presents respective power and
                equivalent value for each applicable type:

                        Protocol        Power    Value
                        --------        -----    -----
                        IP              0        1
                        IPX             1        2
                        Appletalk       2        4
                        XNS             3        8
                        VINES           4        16
                        DECnet          5        32
                        CLNS            6        64
                        Bridging        7        128
                        RSRB            8        256
                        STUN            9        512
                        LLC2            10       1024

                For example, value 3 means the circuit's mapping
                protocols include IP and IPX. (3 = 2**1 + 2**0,
                where 0 corresponds to IP and 1 to IPX.) Value 0
                means there is currently no mapping protocol for
                the circuit.
                See ruijiefrMapTable for more mapping information."
        ::= { ruijiefrExtCircuitEntry 4 }

ruijiefrExtCircuitCreateType OBJECT-TYPE
        SYNTAX  INTEGER
                {
                    dynamic(1),      -- PVC established through LMI
                                     -- or an SVC established through
                                     -- SVC signalling
                    static(2)        -- circuit was configured
                }
        MAX-ACCESS  read-only
        STATUS      current
        DESCRIPTION
                "Identify the last source of the circuit's creation."
        ::= { ruijiefrExtCircuitEntry 5 }

ruijiefrExtCircuitMulticast  OBJECT-TYPE
        SYNTAX      TruthValue
        MAX-ACCESS  read-only
        STATUS      current
        DESCRIPTION
                "Indicate if this DLCI is a multicast DLCI."
        ::= { ruijiefrExtCircuitEntry 6 }

ruijiefrExtCircuitRoutedDlci OBJECT-TYPE
        SYNTAX      DlciNumber
        MAX-ACCESS  read-only
        STATUS      current
        DESCRIPTION
                "The routed DLCI to pair up with this DLCI
                for switching function. NOTE: Value zero (0)
                indicates that there is no such routed DLCI
                corresponding to this DLCI."
        ::= { ruijiefrExtCircuitEntry 7 }

ruijiefrExtCircuitRoutedIf OBJECT-TYPE
        SYNTAX      InterfaceIndex
        MAX-ACCESS  read-only
        STATUS      current
        DESCRIPTION
                "The interface for the routed DLCI that pairs up
                with this DLCI for switching. Value greater than 0
                is the InterfaceIndex for that interface. Value
                zero (0) indicates that there is no such routed DLCI
                corresponding to this DLCI."
        ::= { ruijiefrExtCircuitEntry 8 }

ruijiefrExtCircuitUncompressIns OBJECT-TYPE
        SYNTAX      Counter32
        UNITS       "octets"
        MAX-ACCESS  read-only
        STATUS      current
        DESCRIPTION
                "Number of inbound octets of the data packets,
                accounted at Frame Relay level after FRF.9
                payload decompression is applied. In the case of
                non-FRF.9, this value could be identical to
                frCircuitReceivedOctets, unless otherwise noted."
        ::= { ruijiefrExtCircuitEntry 9 }

ruijiefrExtCircuitUncompressOuts OBJECT-TYPE
        SYNTAX      Counter32
        UNITS       "octets"
        MAX-ACCESS  read-only
        STATUS      current
        DESCRIPTION
                "Number of outbound octets of the data packets,
                accounted at Frame Relay level before FRF.9
                payload compression is applied. In the case of
                non-FRF.9, this value could be identical to
                frCircuitSentOctets, unless otherwise noted."
        ::= { ruijiefrExtCircuitEntry 10 }

ruijiefrExtCircuitFECNOuts OBJECT-TYPE
        SYNTAX      Counter32
        MAX-ACCESS  read-only
        STATUS      current
        DESCRIPTION
                "Total number of frames sent out to the network 
                indicating forward congestion."
        ::= { ruijiefrExtCircuitEntry 11 }

ruijiefrExtCircuitBECNOuts OBJECT-TYPE
        SYNTAX      Counter32
        MAX-ACCESS  read-only
        STATUS      current
        DESCRIPTION
                "Total number of frames sent out to the network 
                indicating backward congestion."
        ::= { ruijiefrExtCircuitEntry 12 }

ruijiefrExtCircuitMinThruputOut OBJECT-TYPE
        SYNTAX      Integer32 (9600..1544000)
        UNITS       "bits per second"
        MAX-ACCESS  read-only
        STATUS      current
        DESCRIPTION
                "Circuit's outgoing minimal Throughput based on 
                configuration."
        ::= { ruijiefrExtCircuitEntry 13 }

ruijiefrExtCircuitMinThruputIn  OBJECT-TYPE
        SYNTAX      Integer32 (9600..1544000)
        UNITS       "bits per second"
        MAX-ACCESS  read-only
        STATUS      current
        DESCRIPTION
                "Circuit's incoming minimal Throughput based on
                configuration."
        ::= { ruijiefrExtCircuitEntry 14 }

ruijiefrExtCircuitBcastPktOuts OBJECT-TYPE
        SYNTAX      Counter32
        MAX-ACCESS  read-only
        STATUS      current
        DESCRIPTION
                "Total number of broadcast packets sent out to the 
                 network."
        ::= { ruijiefrExtCircuitEntry 15 }

ruijiefrExtCircuitBcastByteOuts OBJECT-TYPE
        SYNTAX      Counter32
        MAX-ACCESS  read-only
        STATUS      current
        DESCRIPTION
                "Total number of bytes sent out to the network in 
                broadcast packets."
        ::= { ruijiefrExtCircuitEntry 16 }

ruijiefrExtCircuitBandwidth OBJECT-TYPE
        SYNTAX      Integer32 (0..16777215)
        UNITS       "bits per second"
        MAX-ACCESS  read-only
        STATUS      current
        DESCRIPTION
                "Bandwidth of the virtual circuit, acquired from 
                Ruijie typed LMI Full Status message."
        ::= { ruijiefrExtCircuitEntry 17 }

ruijiefrExtCircuitShapeByteLimit OBJECT-TYPE
        SYNTAX      Integer32 (125..2147483647)
        UNITS       "octets"
        MAX-ACCESS  read-only
        STATUS      current
        DESCRIPTION
                "Maximum number of tokens a token bucket can hold in any
                time interval in case of traffic shaping."
        ::= { ruijiefrExtCircuitEntry 18 }

ruijiefrExtCircuitShapeInterval OBJECT-TYPE
        SYNTAX      Integer32 (10..125)
        UNITS       "milliseconds"
        MAX-ACCESS  read-only
        STATUS      current
        DESCRIPTION
                "Committed rate measurement interval."
        ::= { ruijiefrExtCircuitEntry 19 }

ruijiefrExtCircuitShapeByteIncrement OBJECT-TYPE
        SYNTAX      Integer32 (125..2147483647)
        UNITS       "octets"
        MAX-ACCESS  read-only
        STATUS      current
        DESCRIPTION
                "Number of tokens added into the token bucket per time
                interval in case of traffic shaping."
        ::= { ruijiefrExtCircuitEntry 20 }

ruijiefrExtCircuitShapePkts OBJECT-TYPE
        SYNTAX      Counter32
        MAX-ACCESS  read-only
        STATUS      current
        DESCRIPTION
                "Total number of packets that went through traffic 
                shaping."
        ::= { ruijiefrExtCircuitEntry 21 }

ruijiefrExtCircuitShapeBytes OBJECT-TYPE
        SYNTAX      Counter32
        UNITS       "octets"
        MAX-ACCESS  read-only
        STATUS      current
        DESCRIPTION
                "Total number of bytes that went through traffic 
                shaping."
        ::= { ruijiefrExtCircuitEntry 22 }

ruijiefrExtCircuitShapePktsDelay OBJECT-TYPE
        SYNTAX      Counter32
        MAX-ACCESS  read-only
        STATUS      current
        DESCRIPTION
                "Total number of packets that were delayed by the 
                traffic shaper."
        ::= { ruijiefrExtCircuitEntry 23 }

ruijiefrExtCircuitShapeBytesDelay OBJECT-TYPE
        SYNTAX      Counter32
        UNITS       "octets"
        MAX-ACCESS  read-only
        STATUS      current
        DESCRIPTION
                "Total number of bytes that were delayed by the 
                traffic shaper."
        ::= { ruijiefrExtCircuitEntry 24 }

ruijiefrExtCircuitShapeActive OBJECT-TYPE
        SYNTAX      TruthValue
        MAX-ACCESS  read-only
        STATUS      current
        DESCRIPTION
                "Shows whether shaping is active or not."
        ::= { ruijiefrExtCircuitEntry 25 }

ruijiefrExtCircuitShapeAdapting  OBJECT-TYPE
        SYNTAX  INTEGER {
                  none(1),
                  becn(2),
                  foreSight(3)
                }
        MAX-ACCESS  read-only
        STATUS      current
        DESCRIPTION
                "Type of Adaptive Shaping configured.
                none(1)      - No adaptive shaping configured
                becn(2)      - Backward Explicit Congestion Notification
                foreSight(3) - ForeSight is the network traffic control 
                               software used in Ruijie WAN switches"
        ::= { ruijiefrExtCircuitEntry 26 }

ruijiefrExtCircuitTxDataRate OBJECT-TYPE
        SYNTAX       INTEGER (1..45000000)
        MAX-ACCESS   read-only
        STATUS       current
        DESCRIPTION
               "The average rate (bytes/second) at which data is 
               transmitted in this circuit. "
        ::= { ruijiefrExtCircuitEntry 27 }

ruijiefrExtCircuitTxPktRate OBJECT-TYPE
        SYNTAX       INTEGER (1..45000000)
        MAX-ACCESS   read-only
        STATUS       current
        DESCRIPTION
              "The average number of packets sent in a second in this 
              circuit."
        ::= { ruijiefrExtCircuitEntry 28 }

ruijiefrExtCircuitRcvDataRate OBJECT-TYPE
        SYNTAX       INTEGER (1..45000000)
        MAX-ACCESS   read-only
        STATUS       current
        DESCRIPTION
               "The average rate (bytes/second) at which data is 
               received in this circuit. "
        ::= { ruijiefrExtCircuitEntry 29 }

ruijiefrExtCircuitRcvPktRate OBJECT-TYPE
        SYNTAX       INTEGER (1..45000000)
        MAX-ACCESS   read-only
        STATUS       current
        DESCRIPTION
               "The average number of packets received in a second in 
               this circuit. "
       ::= { ruijiefrExtCircuitEntry 30 }

-- end circuit subgroup }

-- Mapping sub-group {

ruijiefrMapTable OBJECT-TYPE
        SYNTAX      SEQUENCE OF RuijiefrMapEntry
        MAX-ACCESS  not-accessible
        STATUS      current
        DESCRIPTION
                "Table of protocols and addresses mapping
                information of FR virtual circuit."
        ::= { ruijiefrMapObjs 1 }

ruijiefrMapEntry OBJECT-TYPE
        SYNTAX      RuijiefrMapEntry
        MAX-ACCESS  not-accessible
        STATUS     current
        DESCRIPTION
                "Each entry of the table contains one mapping 
                information of a Frame Relay virtual circuit."
        INDEX { frCircuitIfIndex, frCircuitDlci, ruijiefrMapIndex } 
        ::= { ruijiefrMapTable 1 }

RuijiefrMapEntry ::=
        SEQUENCE {
            ruijiefrMapIndex                 INTEGER,
            ruijiefrMapProtocol              RuijiefrMapProtocols,
            ruijiefrMapAddress               OCTET STRING (SIZE(0..64)),
            ruijiefrMapType                  INTEGER,
            ruijiefrMapEncaps                INTEGER,
            ruijiefrMapBroadcast             TruthValue,
            ruijiefrMapPayloadCompress       TruthValue,
            ruijiefrMapTcpHdrCompress        INTEGER,
            ruijiefrMapRtpHdrCompress        INTEGER,
            ruijiefrMapPayloadCompressType   INTEGER
        }

ruijiefrMapIndex OBJECT-TYPE
        SYNTAX      INTEGER (1..999)
        MAX-ACCESS  read-only
        STATUS      current
        DESCRIPTION
                "An arbitrary Index to the mapping information
                associated with a certain circuit. The maximum
                value is arbitrarily picked which is considered
                sufficient for usual configuration."
        ::= { ruijiefrMapEntry 1 }

ruijiefrMapProtocol OBJECT-TYPE
        SYNTAX      RuijiefrMapProtocols
        MAX-ACCESS  read-only
        STATUS      current
        DESCRIPTION
                "Mapping protocol for this circuit."
        ::= { ruijiefrMapEntry 2 }

ruijiefrMapAddress OBJECT-TYPE
        SYNTAX      OCTET STRING (SIZE(0..64))
        MAX-ACCESS  read-only
        STATUS      current
        DESCRIPTION
                "Mapping protocol address at remote end for
                this DLCI.
                NOTE: For point-to-point DLCI, the string is fixed
                to be point-to-point."
        ::= { ruijiefrMapEntry 3 }

ruijiefrMapType OBJECT-TYPE
        SYNTAX  INTEGER
                {
                    static(1),
                    dynamic(2),
                    svc(3)
                }
        MAX-ACCESS  read-only
        STATUS      current
        DESCRIPTION
                "Type for the map creation."
        ::= { ruijiefrMapEntry 4 }

ruijiefrMapEncaps OBJECT-TYPE
        SYNTAX  INTEGER
                {
                    ietf(1),    -- following IETF specifications
                                -- (RFC 1490 as up to date)
                    cisco(2)
                }
        MAX-ACCESS  read-only
        STATUS      current
        DESCRIPTION
                "Indication of the encapsulation type for this
                mapping protocol."
        ::= { ruijiefrMapEntry 5 }

ruijiefrMapBroadcast OBJECT-TYPE
        SYNTAX      TruthValue
        MAX-ACCESS  read-only
        STATUS      current
        DESCRIPTION
                "Broadcast enabled or disabled."
        ::= { ruijiefrMapEntry 6 }

ruijiefrMapPayloadCompress OBJECT-TYPE
        SYNTAX      TruthValue
        MAX-ACCESS  read-only
        STATUS      deprecated
                    -- obsoleted by ruijiefrMapPayloadCompressType
        DESCRIPTION
                "Indicate if payload compression is enabled."
        ::= { ruijiefrMapEntry 7 }

ruijiefrMapTcpHdrCompress OBJECT-TYPE
        SYNTAX  INTEGER
                {
                    inapplicable(1),
                    passive(2),
                    active(3)
                }
        MAX-ACCESS  read-only
        STATUS      current
        DESCRIPTION
                "TCP header compression type, if applicable."
        ::= { ruijiefrMapEntry 8 }

ruijiefrMapRtpHdrCompress OBJECT-TYPE
        SYNTAX  INTEGER
                {
                    inapplicable(1),
                    passive(2),
                    active(3)
                }
        MAX-ACCESS  read-only
        STATUS      current
        DESCRIPTION
                "RTP header compression type, if applicable.
                The value 'passive' means that the header of an
                outgoing RTP/IP packet is compressed only if an
                incoming RTP/IP packet had a compressed header.
                The value 'active' means the header of every outgoing
                RTP/IP packet is compressed."
        ::= { ruijiefrMapEntry 9 }

ruijiefrMapPayloadCompressType OBJECT-TYPE
        SYNTAX  INTEGER
             {
                inapplicable(1),
                cisco(2),         -- cisco proprietary FR packet-
                                  -- by-packet payload compression
                frf9Software(3),  -- FRF.9 software payload compression
                frf9Hardware(4)   -- FRF.9 hardware payload compression
             }
        MAX-ACCESS  read-only
        STATUS      current
        DESCRIPTION
                "FR payload compression type, if applicable.
                FRF.9 is the Frame Relay Forum Implementation Agreement
                on FR payload compression. The compression can be done
                by either software or hardware (when equipped with the
                supporting hardware), depending on configuration."
        REFERENCE
                "Frame Relay Forum document number FRF.9"
        ::= { ruijiefrMapEntry 10 }

-- end mapping subgroup }

-- SVC sub-group {
--        containing SVC spcific information

ruijiefrSvcTable OBJECT-TYPE
        SYNTAX      SEQUENCE OF RuijiefrSvcEntry
        MAX-ACCESS  not-accessible
        STATUS      current
        DESCRIPTION
                "Table of FR SVC specific, descriptive
                and statistics information."
        ::= { ruijiefrSvcObjs 1 }

ruijiefrSvcEntry OBJECT-TYPE
        SYNTAX      RuijiefrSvcEntry
        MAX-ACCESS  not-accessible
        STATUS      current
        DESCRIPTION
                "Each entry of the table contains circuit information
                specific to a Frame Relay Switched Virtual Circuit."
        INDEX { frCircuitIfIndex, frCircuitDlci } 
        ::= { ruijiefrSvcTable 1 }

RuijiefrSvcEntry ::=
        SEQUENCE {
            ruijiefrSvcAddrLocal           OCTET STRING (SIZE(0..64)),
            ruijiefrSvcAddrRemote          OCTET STRING (SIZE(0..64)),
            ruijiefrSvcThroughputIn        Integer32,
            ruijiefrSvcMinThruputOut       Integer32,
            ruijiefrSvcMinThruputIn        Integer32,
            ruijiefrSvcCommitBurstIn       Integer32,
            ruijiefrSvcExcessBurstIn       Integer32,
            ruijiefrSvcIdleTime            Integer32
        }

-- For circuit (DLCI) outbound throughput and outbound Committed 
-- and Excess Burst size, please refer to the following from
-- RFC1315 respectively:
--        frCircuitThroughput, 
--        frCircuitCommittedBurst, and
--        frCircuitExcessBurst


ruijiefrSvcAddrLocal OBJECT-TYPE
        SYNTAX      OCTET STRING (SIZE(0..64))
        MAX-ACCESS  read-only
        STATUS      current
        DESCRIPTION
                "Local E.164/X.125 address for the circuit."
        ::= { ruijiefrSvcEntry 1 }

ruijiefrSvcAddrRemote OBJECT-TYPE
        SYNTAX      OCTET STRING (SIZE(0..64))
        MAX-ACCESS  read-only
        STATUS      current
        DESCRIPTION
                "Remote E.164/X.125 address for the circuit."
        ::= { ruijiefrSvcEntry 2 }

ruijiefrSvcThroughputIn OBJECT-TYPE
        SYNTAX      Integer32 (9600..1544000)
        UNITS       "bits per second"
        MAX-ACCESS  read-only
        STATUS      current
        DESCRIPTION
                "Circuit's incoming throughput. For outgoing 
                throughput (commonly referred to as CIR) see
                frCircuitThroughput per RFC1315."
        ::= { ruijiefrSvcEntry 3 }

ruijiefrSvcMinThruputOut OBJECT-TYPE
        SYNTAX      Integer32 (9600..1544000)
        UNITS       "bits per second"
        MAX-ACCESS  read-only
        STATUS      deprecated -- deprecated by 
                               -- cfrExtCircuitMinThruputOut
        DESCRIPTION
                "Circuit's outgoing minimal Throughput."
        ::= { ruijiefrSvcEntry 4 }

ruijiefrSvcMinThruputIn  OBJECT-TYPE
        SYNTAX      Integer32 (9600..1544000)
        UNITS       "bits per second"
        MAX-ACCESS  read-only
        STATUS      deprecated -- deprecated by 
                               -- cfrExtCircuitMinThruputIn
        DESCRIPTION
                "Circuit's incoming minimal Throughput."
        ::= { ruijiefrSvcEntry 5 }

ruijiefrSvcCommitBurstIn OBJECT-TYPE
        SYNTAX      Integer32 (9600..1544000)
        MAX-ACCESS  read-only
        STATUS      current
        DESCRIPTION
                "Circuit's incoming Committed Burst Rate.
                See ANSI and/or ITU specifications for
                definition and calculations. For outgoing
                CBR, see frCircuitCommittedBurst per RFC 1315."
        ::= { ruijiefrSvcEntry 6 }

ruijiefrSvcExcessBurstIn OBJECT-TYPE
        SYNTAX      Integer32 (9600..2440000)
        MAX-ACCESS  read-only
        STATUS      current
        DESCRIPTION
                "Circuit's incoming Excess Burst Rate.
                See ANSI and/or ITU specifications for
                definition and calculations. For outgoing
                EBR, see frCircuitExcessBurst per RFC 1315."
        ::= { ruijiefrSvcEntry 7 }

ruijiefrSvcIdleTime      OBJECT-TYPE
        SYNTAX      Integer32
        UNITS       "seconds"
        MAX-ACCESS  read-only
        STATUS      current
        DESCRIPTION
                "Circuit's idle time period. If expires, the
                circuit is cleared."
        ::= { ruijiefrSvcEntry 8 }

-- end SVC subgroup }

-- Enhanced Link Management Interface(ELMI) sub-group {
-- ELMI is the protocol that learns QOS parameters(CIR,Bc,Be etc)
-- of a VC from the switch.
-- This sub group contains ELMI specific information.

ruijiefrElmiIpAddr      OBJECT-TYPE
        SYNTAX     IpAddress
        MAX-ACCESS read-only
        STATUS     current
        DESCRIPTION
                "This object represents the Management address of the
                 device used for address registration. 
                 Network management station can send management
                 messages to this IP address. This can be 
                 user configured address or the address of one of the
                 interfaces on the device. If address registration is
                 disabled then this will have a value of 0.0.0.0. 
                 This object is accessible only if the ELMI protocol 
                 is supported on the device"
        ::= { ruijiefrElmiObjs 1 }

ruijiefrElmiTable       OBJECT-TYPE
        SYNTAX     SEQUENCE OF RuijiefrElmiEntry
        MAX-ACCESS not-accessible
        STATUS     current
        DESCRIPTION
                "Table of RUIJIE Frame Relay ELMI information that is
                 specific to RUIJIE implementation"
        ::= { ruijiefrElmiObjs 2 }

ruijiefrElmiEntry       OBJECT-TYPE
        SYNTAX     RuijiefrElmiEntry
        MAX-ACCESS not-accessible
        STATUS     current
        DESCRIPTION
                "Each entry of the table contains information about a
                 physical interface. The table can be accessible only
                 if the device supports ELMI protocol and if LMI is
                 enabled on the interface."
        INDEX { ifIndex }
        ::= { ruijiefrElmiTable 1 }
  
RuijiefrElmiEntry ::=
        SEQUENCE {
            ruijiefrElmiLinkStatus
                INTEGER,
            ruijiefrElmiArStatus
                INTEGER,
            ruijiefrElmiRemoteStatus
                INTEGER
        }

ruijiefrElmiLinkStatus  OBJECT-TYPE
        SYNTAX     INTEGER {
                       enabled(1),
                       disabled(2)
                   }
        MAX-ACCESS read-only
        STATUS     current
        DESCRIPTION
                "This variable states whether Enhanced Link Management
                 Interface(ELMI) protocol is enabled or not on a 
                 frame relay interface."
        ::= { ruijiefrElmiEntry 1 }

ruijiefrElmiArStatus    OBJECT-TYPE
        SYNTAX     INTEGER {
                       enabled(1),
                       disabled(2)
                   }
        MAX-ACCESS read-only
        STATUS     current
        DESCRIPTION
                "This variable states whether the Enhanced Link
                 Management Interface(ELMI) address registration(AR)
                 mechanism is enabled or not on a frame relay 
                 interface. A value of 1 indicates ELMI AR is 
                 supported on the interface. A value of 2 indicates
                 ELMI AR is supported but the user disabled the
                 exchange of IP address and ifIndex with the
                 neighboring device. This object doesn't have any
                 significance if cfrElmiLinkStatus is disabled
                 on the interface."
        ::= { ruijiefrElmiEntry 2 }

ruijiefrElmiRemoteStatus OBJECT-TYPE
        SYNTAX      INTEGER {
                        enabled(1),
                        disabled(2)
                    }
        MAX-ACCESS  read-only
        STATUS      current
        DESCRIPTION
                "This variable states the Enhanced Link 
                 Management(ELMI) status on the other end of the
                 interface. If cfrElmiLinkStatus is enabled on the
                 other end a value of 1 will be returned,
                 else 2 will be returned. This object doesn't have any
                 significance if cfrElmiLinkStatus is disabled on the
                 interface"
        ::= { ruijiefrElmiEntry 3 }

ruijiefrElmiNeighborTable    OBJECT-TYPE
        SYNTAX          SEQUENCE OF RuijiefrElmiNeighborEntry
        MAX-ACCESS      not-accessible
        STATUS          current
        DESCRIPTION
                "Table of RUIJIE Frame Relay Neighbor ELMI information
                 that is specific to RUIJIE implementation."
        ::= { ruijiefrElmiObjs 3 }

ruijiefrElmiNeighborEntry OBJECT-TYPE
        SYNTAX       RuijiefrElmiNeighborEntry
        MAX-ACCESS   not-accessible
        STATUS       current
        DESCRIPTION
                "Each entry of the table contains information of the
                 neighboring device connected to a physical interface.
                 The entry will be present only if ELMI is enabled on
                 the neighboring device interface. If the value of the
                 ruijiefrElmiRemoteStatus in the ruijiefrElmiEntry is 1 then a 
                 valid entry exists for the interface. If ELMI is not 
                 supported on the remote end then, the neighbor 
                 information for the interface will not be present"
        INDEX { ifIndex }
        ::= { ruijiefrElmiNeighborTable 1 }

RuijiefrElmiNeighborEntry ::=
        SEQUENCE {
            ruijiefrElmiNeighborArStatus
                INTEGER,
            ruijiefrElmiNeighborIpAddress
                IpAddress,
            ruijiefrElmiNeighborIfIndex
                InterfaceIndex,
            ruijiefrElmiNeighborVendorName
                DisplayString,
            ruijiefrElmiNeighborPlatformName
                DisplayString,
            ruijiefrElmiNeighborDeviceName
                DisplayString
        }


ruijiefrElmiNeighborArStatus OBJECT-TYPE
        SYNTAX          INTEGER {
                            notsupported(1),
                            enabled(2),
                            disabled(3)
                        }
        MAX-ACCESS      read-only
        STATUS          current
        DESCRIPTION
                "This variable indicates the status of ELMI Address 
                 registration(AR) on the neighboring device. A value 
                 of 1 indicates ELMI AR is not supported on the 
                 neighboring device. A value of 2 indicates ELMI AR is
                 enabled on the interface. A value of 3 indicates AR is
                 supported, but user disabled the exchange of IP 
                 address and ifIndex with the neighbor."
        ::= { ruijiefrElmiNeighborEntry 1 }

ruijiefrElmiNeighborIpAddress OBJECT-TYPE
        SYNTAX           IpAddress
        MAX-ACCESS       read-only
        STATUS           current
        DESCRIPTION
                "The Management IP address of the neighboring device 
                 to which the other end of this interface is 
                 connected. Network management system can use this
                 address to send management messages to the device.
                 If address registration is not supported on the
                 remote end then the value will be 0.0.0.0.
                 NMS uses this object in the topology discovery of the
                 network."
        ::= { ruijiefrElmiNeighborEntry 2 }

ruijiefrElmiNeighborIfIndex   OBJECT-TYPE
        SYNTAX           InterfaceIndex
        MAX-ACCESS       read-only
        STATUS           current
        DESCRIPTION
                "The Interface index of the neighboring device to 
                 which this interface is connected. If the value of
                 ruijiefrElmiNeighborArStatus is 2 then this will have a
                 valid value. If the value of ruijiefrElmiNeighborArStatus
                 is 3 or 1 then value of this object will be 0. NMS
                 uses this object in the topology discovery of the
                 network."
        ::= { ruijiefrElmiNeighborEntry 3 }

ruijiefrElmiNeighborVendorName OBJECT-TYPE
        SYNTAX            DisplayString
        MAX-ACCESS        read-only
        STATUS            current
        DESCRIPTION
                "Vendor name of the neighboring device to which the
                 other end of this interface is connected."
        ::= { ruijiefrElmiNeighborEntry 4 }

ruijiefrElmiNeighborPlatformName OBJECT-TYPE
        SYNTAX              DisplayString
        MAX-ACCESS          read-only
        STATUS              current
        DESCRIPTION
                "Platform name of the neighboring device to which the
                 other end of this interface is connected."
        ::= { ruijiefrElmiNeighborEntry 5 }

ruijiefrElmiNeighborDeviceName   OBJECT-TYPE
        SYNTAX              DisplayString
        MAX-ACCESS          read-only
        STATUS              current
        DESCRIPTION
                "Device name of the neighboring device to which the
                 other end of this interface is connected."
        ::= { ruijiefrElmiNeighborEntry 6 }

-- end ELMI sub-group }

-- Fragmentation sub-group {

ruijiefrFragTable OBJECT-TYPE
        SYNTAX      SEQUENCE OF RuijiefrFragEntry
        MAX-ACCESS  not-accessible
        STATUS      current
        DESCRIPTION
                "Table of Frame Relay Fragmentation information. 
                These are specific to Ruijie's implementation."
        ::= { ruijiefrFragObjs 1 }

ruijiefrFragEntry OBJECT-TYPE
        SYNTAX      RuijiefrFragEntry
        MAX-ACCESS  not-accessible
        STATUS      current
        DESCRIPTION
                "Each entry of the table contains details of 
                fragmentation configured on  this circuit. "
        INDEX { frCircuitIfIndex, frCircuitDlci}
        ::= { ruijiefrFragTable 1 }

RuijiefrFragEntry ::=
        SEQUENCE {
            ruijiefrFragSize                       INTEGER,
            ruijiefrFragType                       DisplayString,
            ruijiefrFragInPkts                     Counter32,
            ruijiefrFragOutPkts                    Counter32,
            ruijiefrFragInOctets                   Counter32,
            ruijiefrFragOutOctets                  Counter32,
            ruijiefrFragNotInPkts                  Counter32,
            ruijiefrFragNotOutPkts                 Counter32,
            ruijiefrFragNotInOctets                Counter32,
            ruijiefrFragNotOutOctets               Counter32,
            ruijiefrFragAssembledInPkts            Counter32,
            ruijiefrFragAssembledInOctets          Counter32,
            ruijiefrFragPreOutPkts                 Counter32,
            ruijiefrFragPreOutOctets               Counter32,
            ruijiefrFragDroppedReAssembledInPkts   Counter32,
            ruijiefrFragDroppedFragmentedOutPkts   Counter32,
            ruijiefrFragTimeoutsIn                 INTEGER,
            ruijiefrFragOutOfSeqFragPkts           Counter32,
            ruijiefrFragUnexpectedBBitSetPkts      Counter32,
            ruijiefrFragSeqMissedPkts              Counter32,
            ruijiefrFragInterleavedOutPkts         Counter32
        }

ruijiefrFragSize OBJECT-TYPE
        SYNTAX      INTEGER (16..1600)
        UNITS       "octets"
        MAX-ACCESS  read-only
        STATUS      current
        DESCRIPTION
                "ruijiefrFragSize defines the payload size of a fragment 
                and it excludes the FR headers and any FR fragmentation
                header."

        ::= { ruijiefrFragEntry 1 }
ruijiefrFragType OBJECT-TYPE
        SYNTAX  DisplayString
        MAX-ACCESS  read-only
        STATUS      current
        DESCRIPTION
                "Fragmentation type configured by the user. The types
                supported are end-to-end, VoFR-ruijie and VoFR."
        ::= { ruijiefrFragEntry 2 }

ruijiefrFragInPkts  OBJECT-TYPE
        SYNTAX      Counter32
        UNITS       "packets"
        MAX-ACCESS  read-only
        STATUS      current
        DESCRIPTION
                "Total number of frames received that have a 
                fragmentation header."
        ::= { ruijiefrFragEntry 3 }

ruijiefrFragOutPkts OBJECT-TYPE
        SYNTAX      Counter32
        UNITS       "packets"
        MAX-ACCESS  read-only
        STATUS      current
        DESCRIPTION
                "Total number of fragments that are transmitted with a
                fragmenation header."
        ::= { ruijiefrFragEntry 4 }

ruijiefrFragInOctets OBJECT-TYPE
        SYNTAX      Counter32
        UNITS       "octets"
        MAX-ACCESS  read-only
        STATUS      current
        DESCRIPTION
                "Total number of bytes received in frames that have a 
                fragmentation header. The number of bytes include the
                FR header." 
        ::= { ruijiefrFragEntry 5}

ruijiefrFragOutOctets OBJECT-TYPE
        SYNTAX      Counter32
        UNITS       "octets"
        MAX-ACCESS  read-only
        STATUS      current
        DESCRIPTION
                "Total number of bytes that are transmitted in frames
                with a fragmenation header. The number of bytes also
                includes the FR header." 
        ::= { ruijiefrFragEntry 6}

ruijiefrFragNotInPkts OBJECT-TYPE
        SYNTAX      Counter32
        UNITS       "packets"
        MAX-ACCESS  read-only
        STATUS      current
        DESCRIPTION
                "Total number of frames received that do not require 
                reassembly and therefore will not contain the 
                fragmentation header. This counter is valid only when
                end-to-end fragmentation type is set." 
        ::= { ruijiefrFragEntry 7}

ruijiefrFragNotOutPkts  OBJECT-TYPE
        SYNTAX      Counter32
        UNITS       "packets"
        MAX-ACCESS  read-only
        STATUS      current
        DESCRIPTION
                "Total number of frames transmitted without fragmenting
                and therefore will not contain the fragmentation header.
                This counter is valid only when end-to-end fragmentation
                type is set." 
        ::= { ruijiefrFragEntry 8}

ruijiefrFragNotInOctets  OBJECT-TYPE
        SYNTAX      Counter32
        UNITS       "octets"
        MAX-ACCESS  read-only
        STATUS      current
        DESCRIPTION
                "Total number of bytes received in frames that do not 
                require reassembly and therefore will not contain the 
                fragmentation header. This counter is valid only when
                end-to-end fragmentation type is set." 
        ::= { ruijiefrFragEntry 9}

ruijiefrFragNotOutOctets OBJECT-TYPE
        SYNTAX      Counter32
        UNITS       "octets"
        MAX-ACCESS  read-only
        STATUS      current
        DESCRIPTION
                "Total number of bytes transmitted in frames that are
                not fragmented and therefore will not contain the 
                fragmentation header. This counter is valid only when 
                end-to-end fragmentation type is set." 
        ::= { ruijiefrFragEntry 10}

ruijiefrFragAssembledInPkts OBJECT-TYPE
        SYNTAX      Counter32
        UNITS       "packets"
        MAX-ACCESS  read-only
        STATUS      current
        DESCRIPTION
                "Total number of fully reassembled frames. It also 
                counts the number of packets received without FR 
                fragmentation header (i.e. in un-fragmentated pkts)."
        ::= { ruijiefrFragEntry 11}

ruijiefrFragAssembledInOctets OBJECT-TYPE
        SYNTAX      Counter32
        UNITS       "octets"
        MAX-ACCESS  read-only
        STATUS      current
        DESCRIPTION
                "Total number of bytes received in fully reassembled 
                frames. It also counts the number of packets received
                without FR fragmentation header (i.e.in un-fragmentated
                pkts)."
        ::= { ruijiefrFragEntry 12}

ruijiefrFragPreOutPkts OBJECT-TYPE
        SYNTAX      Counter32
        UNITS       "packets"
        MAX-ACCESS  read-only
        STATUS      current
        DESCRIPTION
                "Total number of frames fragmented and trasmitted. It 
                also counts the number of packets trasmitted without FR
                fragmentation header (i.e. in un-fragmentated pkts)."
        ::= { ruijiefrFragEntry 13}

ruijiefrFragPreOutOctets OBJECT-TYPE
        SYNTAX      Counter32
        UNITS       "octets"
        MAX-ACCESS  read-only
        STATUS      current
        DESCRIPTION
                "Total number of bytes transmitted in fragmented frames.
                It also counts the number of bytes trasmitted in frames
                without FR fragmentation header (i.e. in un-fragmentated
                pkts)."
        ::= { ruijiefrFragEntry 14}

ruijiefrFragDroppedReAssembledInPkts OBJECT-TYPE
        SYNTAX      Counter32
        UNITS       "packets"
        MAX-ACCESS  read-only
        STATUS      current
        DESCRIPTION
                "Number of received fragments dropped for reasons such
                as : running out of memory, receiving segments out of 
                sequence, receiving an unexpected frame with a B bit 
                set, timing out on a reassembling frame." 
        ::= { ruijiefrFragEntry 15}

ruijiefrFragDroppedFragmentedOutPkts OBJECT-TYPE
        SYNTAX      Counter32
        UNITS       "packets"
        MAX-ACCESS  read-only
        STATUS      current
        DESCRIPTION
                "Number of fragments dropped because of running 
                out of memory." 
        ::= { ruijiefrFragEntry 16}

ruijiefrFragTimeoutsIn OBJECT-TYPE
        SYNTAX      INTEGER (0..1000)
        MAX-ACCESS  read-only
        STATUS      current
        DESCRIPTION
                "Number of reassemble timer timeouts for this circuit.
                A frame requiring more than two minutes to fully 
                reassemble is dropped and timeout will be incremented
                by one." 
        ::= { ruijiefrFragEntry 17}

ruijiefrFragOutOfSeqFragPkts OBJECT-TYPE
        SYNTAX      Counter32
        UNITS       "packets"
        MAX-ACCESS  read-only
        STATUS      current
        DESCRIPTION
                "Indicates the total number of packets received with an
                unexpected sequence number. All fragments being 
                reassembled are dropped. Start a new packet with the
                received segment only if the B bit is set on the 
                segment. Otherwise the new segment is also dropped." 
        ::= { ruijiefrFragEntry 18}

ruijiefrFragUnexpectedBBitSetPkts OBJECT-TYPE
        SYNTAX      Counter32
        UNITS       "packets"
        MAX-ACCESS  read-only
        STATUS      current
        DESCRIPTION
                "Number of fragments received in this circuit with 
                a B bit set. All fragments being reassembled are dropped
                and a new packet is started with this segment." 
        ::= { ruijiefrFragEntry 19}

ruijiefrFragSeqMissedPkts OBJECT-TYPE
        SYNTAX      Counter32
        UNITS       "packets"
        MAX-ACCESS  read-only
        STATUS      current
        DESCRIPTION
                "Number of fragments received in this circuit with 
                skipped sequence number."
        ::= { ruijiefrFragEntry 20}

ruijiefrFragInterleavedOutPkts OBJECT-TYPE
        SYNTAX      Counter32
        UNITS       "packets"
        MAX-ACCESS  read-only
        STATUS      current
        DESCRIPTION
                "Number of packets that have been interleaved between 
                segments." 
        ::= { ruijiefrFragEntry 21}

-- end Fragmentation sub-group }


-- Connect sub-group {

ruijiefrConnectionTable OBJECT-TYPE
        SYNTAX      SEQUENCE OF RuijiefrConnectionEntry
        MAX-ACCESS  not-accessible
        STATUS      current
        DESCRIPTION
                "Table of Frame Relay/Frame Relay and Frame Relay/ATM
                Network/Service Interworking connection information. 
                These are specific to Ruijie's implementation."
        ::= { ruijiefrConnectionObjs 1 }

ruijiefrConnectionEntry OBJECT-TYPE
        SYNTAX      RuijiefrConnectionEntry
        MAX-ACCESS  not-accessible
        STATUS      current
        DESCRIPTION
                "Each entry of the table contains information of a
                connection that is established for Frame Relay/Frame 
                Relay and Frame Relay/ATM Network/Service Interworking."
        INDEX { frCircuitIfIndex, frCircuitDlci}
        ::= { ruijiefrConnectionTable 1 }

RuijiefrConnectionEntry ::=
        SEQUENCE {
            ruijiefrConnName               DisplayString,
            ruijiefrConnID                 INTEGER,
            ruijiefrConnState              DisplayString,
            ruijiefrConnSegment1Name       DisplayString,
            ruijiefrConnSegment1VCGroup    DisplayString,
            ruijiefrConnSegment1Dlci       DlciNumber,
            ruijiefrConnSegment2Name       DisplayString, 
            ruijiefrConnSegment2Vpi        INTEGER,
            ruijiefrConnSegment2Vci        INTEGER,
            ruijiefrConnServiceTranslation INTEGER,
            ruijiefrConnFrSscsDlci         DlciNumber,
            ruijiefrConnEfciBit            INTEGER,
            ruijiefrConnDeBit              INTEGER,
            ruijiefrConnClpBit             INTEGER
        }

ruijiefrConnName OBJECT-TYPE
        SYNTAX       DisplayString
        MAX-ACCESS   read-only
        STATUS       current        
        DESCRIPTION
               "The textual name of a for FR/FR or FR/ATM  
               Network/Service Interworking connection."
        ::= { ruijiefrConnectionEntry 1 }

ruijiefrConnID OBJECT-TYPE
        SYNTAX       INTEGER (1..2000)
        MAX-ACCESS   read-only
        STATUS       current
        DESCRIPTION
               "The numerical identifier of a FR/FR or FR/ATM  
               Network/Service Interworking connection."
        ::= { ruijiefrConnectionEntry 2 }

ruijiefrConnState OBJECT-TYPE
        SYNTAX      DisplayString
        MAX-ACCESS  read-only
        STATUS      current
        DESCRIPTION
                "Status of a FR/FR or FR/ATM  Network/Service 
                Interworking connection."
        ::= { ruijiefrConnectionEntry 3}

ruijiefrConnSegment1Name OBJECT-TYPE
        SYNTAX       DisplayString
        MAX-ACCESS   read-only
        STATUS       current
        DESCRIPTION
               "The textual name used to identify the first segment of 
               a FR/FR or FR/ATM  Network/Service Interworking 
               connection."
        ::= { ruijiefrConnectionEntry 4}

ruijiefrConnSegment1VCGroup OBJECT-TYPE
        SYNTAX       DisplayString
        MAX-ACCESS   read-only
        STATUS       current
        DESCRIPTION
               "The textual name used to identify the VC-Group in the
               first segment of a Frame Relay/ATM  Network Interworking
               (FRF.5)connection. 
               This field is not applicabe in case of,
                        FRF.8 (Frame Relay/ATM  Service Interworking)
                        and
                        FR-FR connectione. "
       ::= { ruijiefrConnectionEntry 5}

ruijiefrConnSegment1Dlci OBJECT-TYPE
        SYNTAX       DlciNumber
        MAX-ACCESS   read-only
        STATUS       current
        DESCRIPTION
               "The DLCI used as the first segment of a FR-FR or FR-ATM
               Network/Service Interworking connection."
        ::= { ruijiefrConnectionEntry 6}

ruijiefrConnSegment2Name OBJECT-TYPE
        SYNTAX       DisplayString
        MAX-ACCESS   read-only
        STATUS       current
        DESCRIPTION
               "The interface on which second segment of a FR-FR or 
               FR-ATM  Network/Service Interworking connection is 
               configured."
        ::= { ruijiefrConnectionEntry 7}

ruijiefrConnSegment2Vpi OBJECT-TYPE
        SYNTAX       INTEGER (0..4095)
        MAX-ACCESS   read-only
        STATUS       current
        DESCRIPTION
               "The value of  VPI, in the ATM connection, used as the
               second segment of a FR-ATM  Network/Service Interworking
               connection. In case of FR-FR connection, the same will 
               be used to display the DLCI used as the second segment."
        ::= { ruijiefrConnectionEntry 8}

ruijiefrConnSegment2Vci OBJECT-TYPE
        SYNTAX       INTEGER (0..4095)
        MAX-ACCESS   read-only
        STATUS       current
        DESCRIPTION
               "The value of  VCI, in the ATM connection, used as the
               second segment of a FR-ATM  Network/Service Interworking
               connection. In case of FR-FR connection, this is not 
               supported."
       ::= { ruijiefrConnectionEntry 9}

ruijiefrConnServiceTranslation OBJECT-TYPE
        SYNTAX       INTEGER {
                        serviceTranslationEnabled(1),
                        serviceTranslationNotEnabled(2)
                     }
        MAX-ACCESS   read-only
        STATUS       current
        DESCRIPTION
               "Shows whether Service Translation Mode is supported or
               not. Translation Mode is the interworking of 
               internetworking (routed and/or bridged) protocols used 
               in FR-ATM  Service PVC Interworking(FRF.8).
               This is not supported in case of FRF.5 (FR-ATM network
               Interworking) and FR-FR connections."
       ::= { ruijiefrConnectionEntry 10}

ruijiefrConnFrSscsDlci OBJECT-TYPE
        SYNTAX       DlciNumber
        MAX-ACCESS   read-only
        STATUS       current        
        DESCRIPTION
               "The DLCI value used at the FR-SSCS layer. This is one of
               connection multiplexing methods used in Frame Relay/ATM  
               Network Interworking.
               Not supported in case of FRF.8 (FR-ATM Service PVC 
               Interworking) and FR-FR connections"
        ::= { ruijiefrConnectionEntry 11}

ruijiefrConnEfciBit OBJECT-TYPE
        SYNTAX       INTEGER  {
                         mapFecn(1),
                         notMapFecn(2)
                     }
        MAX-ACCESS   read-only
        STATUS       current
        DESCRIPTION
               "Shows whether the FECN field in the FR frame is mapped 
               to the ATM EFCI field of every cell generated out of the 
               FR frame. This is used to indicate congestion in FR to
               ATM direction in case of Frame Relay/ATM  Service PVC 
               Interworking.
               Not supported in FRF.5 (Frame Relay/ATM Network 
               Interworking and FR-FR connections."
::= { ruijiefrConnectionEntry 12}

ruijiefrConnDeBit OBJECT-TYPE
        SYNTAX       INTEGER {
                         noMapClp(1),
                         mapClp(2),
                         setDe0(3),
                         setDe1(4)
                     }
        MAX-ACCESS   read-only
        STATUS       current
        DESCRIPTION
               "The method of operation for loss priority mapping in the
               B-ISDN to FR direction..
               Not supported in case of FR-FR connection."
        ::= { ruijiefrConnectionEntry 13}

ruijiefrConnClpBit OBJECT-TYPE
        SYNTAX  INTEGER {
                  setClpTo0AndCopyDeToFrsscsDe(1),
                  setClpTo1AndCopyDeToFrsscsDe(2),
                  copyDeToFrsscsDeAndClp(3),
                  copyDeToClp(4),
                  setClp1(5),
                  setClp0(6)
                }
        MAX-ACCESS   read-only
        STATUS       current
        DESCRIPTION
               "The method of operation used to map loss priority
               mapping in the FR to ATM direction.
               Not supported in case of FR-FR connection."
        ::= { ruijiefrConnectionEntry 14}

-- end Conn subgroup }

ruijieFrMIBConformance OBJECT IDENTIFIER ::= { ruijieFrameRelayMIB 3 }
ruijieFrMIBCompliances OBJECT IDENTIFIER ::= { ruijieFrMIBConformance 1 }
ruijieFrMIBGroups      OBJECT IDENTIFIER ::= { ruijieFrMIBConformance 2 }

ruijieFrMIBCompliance MODULE-COMPLIANCE
        STATUS  obsolete  -- obsoleted by ruijieFrMIBCompliancesRev2
        DESCRIPTION
                "The compliance statement for entities which implement
                this Ruijie Frame Relay MIB."
        MODULE  -- this module
                MANDATORY-GROUPS { ruijieFrMIBGroup }
        ::= { ruijieFrMIBCompliances 1 }

ruijieFrMIBCompliancesRev1 MODULE-COMPLIANCE
        STATUS  obsolete  -- obsoleted by ruijieFrMIBCompliancesRev2
        DESCRIPTION
                "The compliance statement for entities which implement
                this Ruijie Frame Relay MIB."
        MODULE  -- this module
                MANDATORY-GROUPS { ruijieFrMIBGroupRev1 }
        ::= { ruijieFrMIBCompliances 2 }

ruijieFrMIBCompliancesRev2 MODULE-COMPLIANCE
        STATUS  obsolete  -- obsoleted by ruijieFrMIBCompliancesRev3 
        DESCRIPTION
                "The compliance statement for entities which implement
                this Ruijie Frame Relay MIB."
        MODULE  -- this module
                MANDATORY-GROUPS { ruijieFrLmiMIBGroup, 
                                   ruijieFrCircuitMIBGroup,
                                   ruijieExtCircuitMIBGroup,
                                   ruijieFrTsMIBGroup,
                                   ruijieFrMapMIBGroup,
                                   ruijieFrSvcMIBGroup }
        ::= { ruijieFrMIBCompliances 3 }

ruijieFrMIBCompliancesRev3 MODULE-COMPLIANCE
        STATUS  deprecated  -- deprecated by ruijieFrMIBCompliancesRev4
        DESCRIPTION
                "The compliance statement for entities which implement
                this Ruijie Frame Relay MIB."
        MODULE  -- this module
                MANDATORY-GROUPS { ruijieFrLmiMIBGroup,
                                   ruijieFrCircuitMIBGroup,
                                   ruijieExtCircuitMIBGroup,
                                   ruijieFrTsMIBGroup,
                                   ruijieFrMapMIBGroup,
                                   ruijieFrSvcMIBGroup,
                                   ruijieFrElmiMIBGroup}
        ::= { ruijieFrMIBCompliances 4 }

ruijieFrMIBCompliancesRev4 MODULE-COMPLIANCE
        STATUS  current
        DESCRIPTION
                "The compliance statement for entities which implement
                this ruijie Frame Relay MIB."
        MODULE  -- this module
                MANDATORY-GROUPS { ruijieFrLmiMIBGroup,
                                   ruijieFrCircuitMIBGroup,
                                   ruijieExtCircuitMIBGroup1,
                                   ruijieFrTsMIBGroup,
                                   ruijieFrMapMIBGroup,
                                   ruijieFrSvcMIBGroup,
                                   ruijieFrElmiMIBGroup1,
                                   ruijieFrFragMIBGroup,
                                   ruijieFrConnMIBGroup}
        ::= { ruijieFrMIBCompliances 5 }

-- units of conformance:

ruijieFrMIBGroup OBJECT-GROUP
        OBJECTS {
            ruijiefrLmiLinkstatus,
            ruijiefrLmiLinkType,
            ruijiefrLmiEnquiryIns,
            ruijiefrLmiEnquiryOuts,
            ruijiefrLmiStatusIns,
            ruijiefrLmiStatusOuts,
            ruijiefrLmiUpdateStatusIns,
            ruijiefrLmiUpdateStatusOuts,
            ruijiefrLmiStatusTimeouts,
            ruijiefrLmiStatusEnqTimeouts,
            ruijiefrLmiN392Dce,
            ruijiefrLmiN393Dce,
            ruijiefrLmiT392Dce,
            ruijiefrCircuitDEins,
            ruijiefrCircuitDEouts,
            ruijiefrCircuitDropPktsOuts,
            ruijiefrCircuitType,
            ruijiefrExtCircuitIfName,
            ruijiefrExtCircuitIfType,
            ruijiefrExtCircuitSubifIndex,
            ruijiefrExtCircuitMapStatus,
            ruijiefrExtCircuitCreateType,
            ruijiefrExtCircuitMulticast,
            ruijiefrExtCircuitRoutedDlci,
            ruijiefrExtCircuitRoutedIf,
            ruijiefrMapIndex,
            ruijiefrMapProtocol,
            ruijiefrMapAddress,
            ruijiefrMapType,
            ruijiefrMapEncaps,
            ruijiefrMapBroadcast,
            ruijiefrMapPayloadCompress,
            ruijiefrMapTcpHdrCompress,
            ruijiefrSvcAddrLocal,
            ruijiefrSvcAddrRemote,
            ruijiefrSvcThroughputIn,
            ruijiefrSvcMinThruputOut,
            ruijiefrSvcMinThruputIn,
            ruijiefrSvcCommitBurstIn,
            ruijiefrSvcExcessBurstIn,
            ruijiefrSvcIdleTime
        }
        STATUS  deprecated       -- obsoleted by ruijieFrMIBGroupRev1
        DESCRIPTION
                "The compliance statement for entities which implement
                this Ruijie Frame Relay MIB."
        ::= { ruijieFrMIBGroups 1 }

ruijieFrMIBGroupRev1 OBJECT-GROUP
        OBJECTS {
            ruijiefrLmiLinkstatus,
            ruijiefrLmiLinkType,
            ruijiefrLmiEnquiryIns,
            ruijiefrLmiEnquiryOuts,
            ruijiefrLmiStatusIns,
            ruijiefrLmiStatusOuts,
            ruijiefrLmiUpdateStatusIns,
            ruijiefrLmiUpdateStatusOuts,
            ruijiefrLmiStatusTimeouts,
            ruijiefrLmiStatusEnqTimeouts,
            ruijiefrLmiN392Dce,
            ruijiefrLmiN393Dce,
            ruijiefrLmiT392Dce,
            ruijiefrCircuitDEins,
            ruijiefrCircuitDEouts,
            ruijiefrCircuitDropPktsOuts,
            ruijiefrCircuitType,
            ruijiefrExtCircuitIfName,
            ruijiefrExtCircuitIfType,
            ruijiefrExtCircuitSubifIndex,
            ruijiefrExtCircuitMapStatus,
            ruijiefrExtCircuitCreateType,
            ruijiefrExtCircuitMulticast,
            ruijiefrExtCircuitRoutedDlci,
            ruijiefrExtCircuitRoutedIf,
            ruijiefrExtCircuitUncompressIns,  
            ruijiefrExtCircuitUncompressOuts,
            ruijiefrMapIndex,
            ruijiefrMapProtocol,
            ruijiefrMapAddress,
            ruijiefrMapType,
            ruijiefrMapEncaps,
            ruijiefrMapBroadcast,
-- removed  ruijiefrMapPayloadCompress, obsoleted by ruijiefrMapPayloadCompressType
            ruijiefrMapTcpHdrCompress,
            ruijiefrMapRtpHdrCompress,          
            ruijiefrMapPayloadCompressType,    
            ruijiefrSvcAddrLocal,
            ruijiefrSvcAddrRemote,
            ruijiefrSvcThroughputIn,
            ruijiefrSvcMinThruputOut,
            ruijiefrSvcMinThruputIn,
            ruijiefrSvcCommitBurstIn,
            ruijiefrSvcExcessBurstIn,
            ruijiefrSvcIdleTime
        }
        STATUS  deprecated       
        DESCRIPTION
                "A collection of objects providing router's
                Frame Relay configuration and statistics
                information that are additional to the IETF
                standard Frame Relay DTE MIB."
        ::= { ruijieFrMIBGroups 2 }

ruijieFrLmiMIBGroup    OBJECT-GROUP
        OBJECTS { 
            ruijiefrLmiLinkstatus, ruijiefrLmiLinkType, ruijiefrLmiEnquiryIns,
            ruijiefrLmiEnquiryOuts, ruijiefrLmiStatusIns, ruijiefrLmiStatusOuts,
            ruijiefrLmiUpdateStatusIns, ruijiefrLmiUpdateStatusOuts,
            ruijiefrLmiStatusTimeouts, ruijiefrLmiStatusEnqTimeouts,
            ruijiefrLmiN392Dce, ruijiefrLmiN393Dce, ruijiefrLmiT392Dce
        }   
        STATUS current
        DESCRIPTION
                "A collection of objects providing router's
                 Frame Relay LMI configuration and statistics
                 information either supplemental to the 
                 frDlcmiTable of RFC 1315 or specific to ruijie's 
                 implementation."
        ::= { ruijieFrMIBGroups 3 }
 
ruijieFrCircuitMIBGroup    OBJECT-GROUP
        OBJECTS { 
            ruijiefrCircuitDEins, ruijiefrCircuitDEouts,
            ruijiefrCircuitDropPktsOuts, ruijiefrCircuitType
        }   
        STATUS current
        DESCRIPTION
                "A collection of objects providing information of a
                circuit that are not included in frCircuitTable of
                RFC1315 but are generic to Frame Relay."
        ::= { ruijieFrMIBGroups 4 }

ruijieExtCircuitMIBGroup    OBJECT-GROUP
        OBJECTS { 
            ruijiefrExtCircuitIfName, ruijiefrExtCircuitIfType,
            ruijiefrExtCircuitSubifIndex, ruijiefrExtCircuitMapStatus,
            ruijiefrExtCircuitCreateType, ruijiefrExtCircuitMulticast,
            ruijiefrExtCircuitRoutedDlci, ruijiefrExtCircuitRoutedIf,
            ruijiefrExtCircuitUncompressIns, ruijiefrExtCircuitUncompressOuts,
            ruijiefrExtCircuitFECNOuts, ruijiefrExtCircuitBECNOuts,
            ruijiefrExtCircuitMinThruputOut, ruijiefrExtCircuitMinThruputIn,
            ruijiefrExtCircuitBcastPktOuts, ruijiefrExtCircuitBcastByteOuts,
            ruijiefrExtCircuitBandwidth
        }   
        STATUS  deprecated       
        DESCRIPTION
                "A collection of objects that provide ruijie 
                implementation specific FR circuit information. 
                This is a ruijie extension for the frCircuitTable 
                of RFC 1315."
        ::= { ruijieFrMIBGroups 5 }

ruijieExtCircuitMIBGroup1    OBJECT-GROUP
        OBJECTS {
            ruijiefrExtCircuitIfName, ruijiefrExtCircuitIfType,
            ruijiefrExtCircuitSubifIndex, ruijiefrExtCircuitMapStatus,
            ruijiefrExtCircuitCreateType, ruijiefrExtCircuitMulticast,
            ruijiefrExtCircuitRoutedDlci, ruijiefrExtCircuitRoutedIf,
            ruijiefrExtCircuitUncompressIns, ruijiefrExtCircuitUncompressOuts,
            ruijiefrExtCircuitFECNOuts, ruijiefrExtCircuitBECNOuts,
            ruijiefrExtCircuitMinThruputOut, ruijiefrExtCircuitMinThruputIn,
            ruijiefrExtCircuitBcastPktOuts, ruijiefrExtCircuitBcastByteOuts,
            ruijiefrExtCircuitBandwidth, ruijiefrExtCircuitTxDataRate,
            ruijiefrExtCircuitTxPktRate, ruijiefrExtCircuitRcvDataRate,
            ruijiefrExtCircuitRcvPktRate
        }
        STATUS current
        DESCRIPTION
                "A collection of objects that provide ruijie
                implementation specific FR circuit information.
                This is a ruijie extension for the frCircuitTable
                of RFC 1315."
        ::= { ruijieFrMIBGroups 13 }


ruijieFrTsMIBGroup    OBJECT-GROUP
        OBJECTS { 
            ruijiefrExtCircuitShapeByteLimit, ruijiefrExtCircuitShapeInterval,
            ruijiefrExtCircuitShapeByteIncrement, ruijiefrExtCircuitShapePkts,
            ruijiefrExtCircuitShapeBytes, ruijiefrExtCircuitShapePktsDelay,
            ruijiefrExtCircuitShapeBytesDelay, ruijiefrExtCircuitShapeActive,
            ruijiefrExtCircuitShapeAdapting
        }   
        STATUS current
        DESCRIPTION
                "A collection of objects that provide information
                about Frame Relay Traffic Shaping. These are 
                additional to the IETF standard Frame Relay DTE MIB." 
        ::= { ruijieFrMIBGroups 6 }

ruijieFrMapMIBGroup    OBJECT-GROUP
        OBJECTS { 
            ruijiefrMapIndex, ruijiefrMapProtocol, ruijiefrMapAddress,
            ruijiefrMapType, ruijiefrMapEncaps, ruijiefrMapBroadcast,
            ruijiefrMapTcpHdrCompress, ruijiefrMapRtpHdrCompress,         
            ruijiefrMapPayloadCompressType  
        }   
        STATUS current
        DESCRIPTION
                "A collection of objects to provide mapping 
                information of a Frame Relay virtual circuit.
                These are additional to the IETF standard 
                Frame Relay DTE MIB."
        ::= { ruijieFrMIBGroups 7 }

ruijieFrSvcMIBGroup    OBJECT-GROUP
        OBJECTS { 
            ruijiefrSvcAddrLocal,
            ruijiefrSvcAddrRemote,
            ruijiefrSvcThroughputIn,
            ruijiefrSvcCommitBurstIn,
            ruijiefrSvcExcessBurstIn,
            ruijiefrSvcIdleTime
        }   
        STATUS current
        DESCRIPTION
                "A collection of objects to provide circuit
                information specific to a Frame Relay Switched
                Virtual Circuit.This is in addition to the IETF 
                standard Frame Relay DTE MIB."        
        ::= { ruijieFrMIBGroups 8 }

ruijieFrElmiMIBGroup    OBJECT-GROUP
        OBJECTS {
            ruijiefrElmiIpAddr, ruijiefrElmiArStatus, ruijiefrElmiRemoteStatus,
            ruijiefrElmiNeighborArStatus, ruijiefrElmiNeighborIpAddress,
            ruijiefrElmiNeighborIfIndex, ruijiefrElmiNeighborVendorName,
            ruijiefrElmiNeighborPlatformName, ruijiefrElmiNeighborDeviceName
        }
        STATUS deprecated
        DESCRIPTION
                "A collection of objects providing router's
                ELMI information."
        ::= { ruijieFrMIBGroups 9 }

ruijieFrElmiMIBGroup1    OBJECT-GROUP
        OBJECTS {
            ruijiefrElmiIpAddr, ruijiefrElmiArStatus, ruijiefrElmiRemoteStatus,
            ruijiefrElmiNeighborArStatus, ruijiefrElmiNeighborIpAddress,
            ruijiefrElmiNeighborIfIndex, ruijiefrElmiNeighborVendorName,
            ruijiefrElmiNeighborPlatformName, ruijiefrElmiNeighborDeviceName,
            ruijiefrElmiLinkStatus
        }
        STATUS current
        DESCRIPTION
                "A collection of objects providing router's
                ELMI information."
        ::= { ruijieFrMIBGroups 10 }

ruijieFrFragMIBGroup    OBJECT-GROUP
        OBJECTS {
            ruijiefrFragSize, ruijiefrFragType, ruijiefrFragInPkts, ruijiefrFragOutPkts,
            ruijiefrFragInOctets, ruijiefrFragOutOctets, ruijiefrFragNotInPkts,
            ruijiefrFragNotOutPkts, ruijiefrFragNotInOctets, ruijiefrFragNotOutOctets,
            ruijiefrFragAssembledInPkts, ruijiefrFragAssembledInOctets, 
            ruijiefrFragPreOutPkts, ruijiefrFragPreOutOctets,
            ruijiefrFragDroppedReAssembledInPkts, 
            ruijiefrFragDroppedFragmentedOutPkts,
            ruijiefrFragTimeoutsIn, ruijiefrFragOutOfSeqFragPkts,
            ruijiefrFragUnexpectedBBitSetPkts, ruijiefrFragSeqMissedPkts, 
            ruijiefrFragInterleavedOutPkts  
        }
        STATUS current
        DESCRIPTION
                "A collection of objects providing router's
                fragmentation information."
        ::= { ruijieFrMIBGroups 11 }
            
ruijieFrConnMIBGroup    OBJECT-GROUP
        OBJECTS {
            ruijiefrConnName, ruijiefrConnID, ruijiefrConnState, ruijiefrConnSegment1Name,
            ruijiefrConnSegment1VCGroup, ruijiefrConnSegment1Dlci,  
            ruijiefrConnSegment2Name, ruijiefrConnSegment2Vpi,
            ruijiefrConnSegment2Vci, ruijiefrConnServiceTranslation, 
            ruijiefrConnFrSscsDlci, ruijiefrConnEfciBit,
            ruijiefrConnDeBit, ruijiefrConnClpBit        
        }
        STATUS current
        DESCRIPTION
                "A collection of objects providing router's
                fragmentation information."
        ::= { ruijieFrMIBGroups 12 }
            

END
