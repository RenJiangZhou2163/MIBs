-- *****************************************************************
-- RUIJIE-CLUSTER-MIB.mib:  Ruijie CLUSTER MIB file
--
-- july 2012, sunxiaofeng
--
-- Copyright (c) 2012 by Ruijie Networks Co.,Ltd.
-- All rights reserved.
-- *****************************************************************

RUIJIE-CLUSTER-MIB DEFINITIONS ::= BEGIN

IMPORTS
    MODULE-IDENTITY,
    OBJECT-TYPE,
    NOTIFICATION-TYPE,
    Unsigned32
        FROM SNMPv2-SMI
    MacAddress,
    TimeStamp,
    DisplayString,
    RowStatus
        FROM SNMPv2-TC
    IpAddress
        FROM SNMPv2-SMI
    MODULE-COMPLIANCE,
    OBJECT-GROUP
        FROM SNMPv2-CONF
    EnabledStatus
        FROM P-BRIDGE-MIB
    ruijieMgmt
        FROM RUIJIE-SMI;

ruijieClusterMIB MODULE-IDENTITY
    LAST-UPDATED "201207010000Z"
    ORGANIZATION "Ruijie Networks Co.,Ltd."
    CONTACT-INFO
            "
            Tel: 4008-111-000

            E-mail: service@ruijie.com.cn"
    DESCRIPTION
            "The MIB module for the management of a group of
            devices called a 'cluster'.  A cluster comprises:

            1. A manager device, which is a device that can provide
               a single point of management (including SNMP, Web
               Console and CLI/Telnet Console) for the devices
               in the cluster;

            2. Zero or more expansion devicees, or called the
               cluster members throughout the context of this MIB,
               which are devices that can be managed via a manager
               device.  The manager device is also considered as a
               cluster member.  Thus it has an entry in the MIB tables
               defined below for cluster members.

            Only the manager device IP address, passwords, and SNMP
            community strings need to be configured in order to
            provide management access to members of the cluster.

            The Entity MIB is not cross-referenced from this MIB.

            To determine if a particular device can be a manager device
            or a member device please refer to the device's
            user's guide."
    REVISION  "201207010000Z"
    DESCRIPTION
            "Initial version of this mib."
    ::= { ruijieMgmt 31 }

ruijieClusterMIBObjects OBJECT IDENTIFIER ::= { ruijieClusterMIB 1 }

-- MIB contains 7 groups

ruijieClusterName OBJECT-TYPE
    SYNTAX        DisplayString (SIZE (0..31))
    MAX-ACCESS    read-write
    STATUS        current
    DESCRIPTION
            "The name of the cluster.  Cluster command switch
             functionality is only enabled if this object is
             a string. a NULL string will create the cluster named 'cluster',
             This object and ruijieClusterStatus in this MIB are
             the only objects that will be instantiated if the
             command switch functionality is not enabled.         
             This object in candidate switch is read-write, 
             and in candidate switch will return null
             string when retrive. But in member switch this object is
             read-only ."
    DEFVAL        { "" }
    ::= { ruijieClusterMIBObjects 1 }

ruijieClusterStatus OBJECT-TYPE
    SYNTAX    EnabledStatus
    MAX-ACCESS    read-write
    STATUS      current
    DESCRIPTION
            "if the role of device is manage device, the value set disable
             the manage device will delete the cluster,this command 
            can only be used on manage device delete cluster."
    DEFVAL { 1 }
   ::= { ruijieClusterMIBObjects 2 }
   
ruijieClusterCmdMacAddress OBJECT-TYPE
    SYNTAX      MacAddress
    MAX-ACCESS  read-only
    STATUS      current
    DESCRIPTION
            "The management MAC address of the manager device of the
             cluster, ie. the CPU MAC address.
             This object is not-accessible for candidate device."
    ::= { ruijieClusterMIBObjects 3 }

ruijieClusterCmdName OBJECT-TYPE
    SYNTAX        DisplayString
    MAX-ACCESS    read-only
    STATUS        current
    DESCRIPTION
            "The name of the manager device of the cluster.
            This object is not-accessible for candidate device."
    ::= { ruijieClusterMIBObjects 4 }

ruijieClusterVlan OBJECT-TYPE
    SYNTAX      INTEGER(0..4094)
    MAX-ACCESS  read-write
    STATUS      current
    DESCRIPTION
            "For the vlan created by a cluster. After this value is altered, 
            the previous cluster will be deleted and a new cluster will be created 
            according to the newly value of vlan, when the value is set 0 ,the vlan
            will be get a idle vlan between 2049 and 3000"
    ::= { ruijieClusterMIBObjects 5}

ruijieClusterHopsLimit OBJECT-TYPE
    SYNTAX        INTEGER(1..16)
    MAX-ACCESS    read-write
    STATUS        current
    DESCRIPTION
            "The hop counts between the farthest device and the manage device 
            in the topology discovery, namely, the scope of topology discovery. 
            Devices within this scope can be discovered by the manage device."
    DEFVAL        { 5}
    ::= { ruijieClusterMIBObjects 6}

ruijieClusterTimerTopo OBJECT-TYPE
    SYNTAX        INTEGER(10..300)
    MAX-ACCESS    read-write
    STATUS        current
    DESCRIPTION
            "Set the timer time for cluster topology collect. This value ranges 
            from 10 to 300 (60 by default), and the unit is second."
    DEFVAL        { 60}
    ::= { ruijieClusterMIBObjects 7}

ruijieClusterTimerHello OBJECT-TYPE
    SYNTAX        INTEGER(10..300)
    MAX-ACCESS    read-write
    STATUS        current
    DESCRIPTION
            "Set handshaking time administrator device and member device,This value ranges 
            from 10 to 300 (30 by default), and the unit is second."
    DEFVAL        { 30}
    ::= { ruijieClusterMIBObjects 8 }

ruijieClusterTimerHold OBJECT-TYPE
    SYNTAX        INTEGER(10..300)
    MAX-ACCESS    read-write
    STATUS        current
    DESCRIPTION
            "Set holdtime of administrator device in the cluster,This value ranges 
            from 10 to 300 (90 by default), and the unit is second."
    DEFVAL        { 90}
    ::= { ruijieClusterMIBObjects 9}

ruijieClusterTftpServer OBJECT-TYPE
    SYNTAX        IpAddress
    MAX-ACCESS    read-write
    STATUS        current
    DESCRIPTION
            "Set the shared TFTP server of the cluster. When the public network IP addresses
            are not set on member devices, use the TFTP agent service of the management device
            to upload or download files from the designated TFTP server."
    ::= { ruijieClusterMIBObjects 10 }

ruijieClusterNumberOfMembers OBJECT-TYPE
    SYNTAX        INTEGER(0..240)
    MAX-ACCESS    read-only
    STATUS        current
    DESCRIPTION
            "The number of cluster member devices,The manager device is considered as a cluster
             member also. "
    DEFVAL        { 0}
    ::= { ruijieClusterMIBObjects 11 }


ruijieClusterMaxNumberOfMembers OBJECT-TYPE
    SYNTAX        INTEGER(0..240)
    MAX-ACCESS    read-only
    STATUS        current
    DESCRIPTION
            "The maximum number of cluster member devices allowed in the
             cluster.  The manager device is considered as a cluster
             member also. "
    DEFVAL        { 0}
    ::= { ruijieClusterMIBObjects 12 }

ruijieClusterDevMaxCapicity OBJECT-TYPE
    SYNTAX        Unsigned32
    MAX-ACCESS    read-only
    STATUS        current
    DESCRIPTION
            "The maximum number of cluster dev allowed in the
             cluster. the max number of cluster members is 512"
    DEFVAL        { 0}
    ::= { ruijieClusterMIBObjects 13 }

ruijieClusterAutoAdd OBJECT-TYPE
    SYNTAX        INTEGER {
                            disable-with-def(0),
                            enable(1),
                            disabled-with-static(2),
                            disabled-with-del(3)
                          }
    MAX-ACCESS    read-write
    STATUS        current
    DESCRIPTION
            "Description the add Members method of Cluster.Set the value 1 to enable auto-add functionality.
            Set the value 0 or 3 to delete all auto-add Members by Cluster.
            The value 2 indicates that Cluster will change all Members to static."
    DEFVAL   { 1 }
    ::= { ruijieClusterMIBObjects 14}

ruijieClusterExplore OBJECT-TYPE
    SYNTAX       EnabledStatus
    MAX-ACCESS    read-write
    STATUS        current
    DESCRIPTION
            "Collect topology information manually. This command improves 
            the convergence of the cluster topology. And this command 
            can only be used on manage device."
    DEFVAL { 2 }
    ::= { ruijieClusterMIBObjects 15 }
  
ruijieClusterSpecifyAdmin       OBJECT IDENTIFIER ::= { ruijieClusterMIBObjects 16}

ruijieClusterSpecifyAdminAddress OBJECT-TYPE
    SYNTAX       MacAddress
    MAX-ACCESS    read-write
    STATUS        current
    DESCRIPTION
            "Specify the mac address of the cluster that the manage device ,
            And this command can only be used on member devices of the cluster 
            or the candidate devices of the cluster."
    ::= { ruijieClusterSpecifyAdmin 1 }

ruijieClusterSpecifyAdminName OBJECT-TYPE
    SYNTAX       DisplayString (SIZE (0..31))
    MAX-ACCESS    read-write
    STATUS        current
    DESCRIPTION
            "Specify the name of the manage device of the cluster,
            And this command can only be used on member devices of the cluster 
            or the candidate devices of the cluster."
    ::= { ruijieClusterSpecifyAdmin 2 }

-- The Cluster device info
ruijieClusterDeviceInfo                          OBJECT IDENTIFIER ::= { ruijieClusterMIBObjects 17}

ruijieClusterDeviceEnable OBJECT-TYPE
    SYNTAX    EnabledStatus
    MAX-ACCESS    read-write
    STATUS      current
    DESCRIPTION
            "Wether the device can be added to a cluster, if this device
            is already in a cluster, will be delete from cluster(if in the
            cluster) and will never be added to any cluster."
    DEFVAL { 1 }
   ::= { ruijieClusterDeviceInfo 1 }

ruijieClusterDeviceRole OBJECT-TYPE
    SYNTAX       INTEGER {
                           candidateDevice(1),
                           managerDevice(2),
                           memberDevice(3)
                          }
    MAX-ACCESS    read-only
    STATUS        current
    DESCRIPTION
            "The role of the device.  A device can become a member
             device only when it is added to the cluster at the manager
             device.  For devices that do not belong to any cluster,
             the ruijieStatusClusterMode is set to 'candidateDevice'."
     DEFVAL { 1 }
    ::= { ruijieClusterDeviceInfo 2 }

ruijieClusterDeviceIP OBJECT-TYPE
    SYNTAX       IpAddress
    MAX-ACCESS    read-only
    STATUS        current
    DESCRIPTION
            "The ip address of the device that specified by the manage device of the cluster"
    ::= { ruijieClusterDeviceInfo 3 }

ruijieClusterDeviceSn OBJECT-TYPE
    SYNTAX       INTEGER(1..240)
    MAX-ACCESS    read-only
    STATUS        current
    DESCRIPTION
            "the uniquely identifies of the device of the cluster."
    ::= { ruijieClusterDeviceInfo 4 }
    
    
    -- The Cluster Ip Pool table   
ruijieClusterIpPoolTable OBJECT-TYPE
    SYNTAX      SEQUENCE OF RuijieClusterIpPoolEntry
    MAX-ACCESS  not-accessible
    STATUS      current
    DESCRIPTION
            "The table is used config the cluster ip address pool."
    ::= { ruijieClusterMIBObjects 18 } 
    
ruijieClusterIpPoolEntry OBJECT-TYPE
    SYNTAX      RuijieClusterIpPoolEntry
    MAX-ACCESS  not-accessible
    STATUS      current
    DESCRIPTION
            "Entry items"
    INDEX { ruijieClusterIpPool, ruijieClusterIpMask }
    ::= { ruijieClusterIpPoolTable 1 } 
    
RuijieClusterIpPoolEntry ::=
      SEQUENCE {
               ruijieClusterIpPool                   IpAddress,
               ruijieClusterIpMask                     IpAddress,
               ruijieClusterIpPoolRowStatus         RowStatus
      } 
      
ruijieClusterIpPool OBJECT-TYPE
    SYNTAX      IpAddress
    MAX-ACCESS  read-only
    STATUS      current
    DESCRIPTION
            "As the management ip-pool configured by Cluster is altered, the cluster will be deleted. 
             A new cluster will be created according to the newly ip-pool. the management ip-pool must be private address of enterprises（10.0.0.0-10.255.255.255；172.16.0.0-172.37.255.255；192.168.0.0-192.168.255.255）"
    ::= { ruijieClusterIpPoolEntry 1 }  
    
ruijieClusterIpMask OBJECT-TYPE
    SYNTAX      IpAddress
    MAX-ACCESS  read-only
    STATUS      current
    DESCRIPTION
            "For the IP address mask created by a cluster. After this value is altered, 
            the previous cluster will be deleted and a new cluster will be created 
            according to the newly created cluster IP mask."
    ::= { ruijieClusterIpPoolEntry 2 } 
    
ruijieClusterIpPoolRowStatus OBJECT-TYPE
    SYNTAX      RowStatus
    MAX-ACCESS  read-create
    STATUS      current
    DESCRIPTION
        "The row status of this table."
    ::= { ruijieClusterIpPoolEntry 3 } 

--   The Cluster Member Add Table

ruijieClusterMemberAddTable OBJECT-TYPE
    SYNTAX      SEQUENCE OF RuijieClusterMemberAddEntry
    MAX-ACCESS  not-accessible
    STATUS      current
    DESCRIPTION
            "The table of manage the member device of the cluster or assign uniquely identifies
            of the clsuter to any device"
    ::= { ruijieClusterMIBObjects 19 }

ruijieClusterMemberAddEntry OBJECT-TYPE
    SYNTAX      RuijieClusterMemberAddEntry
    MAX-ACCESS  not-accessible
    STATUS      current
    DESCRIPTION
            " The table of member add configuration identified by its 
            mac address and the member id."
    INDEX { ruijieClusterMemberAddSn }
    ::= { ruijieClusterMemberAddTable 1 }

RuijieClusterMemberAddEntry ::=
      SEQUENCE {
                ruijieClusterMemberAddSn                     INTEGER,
                ruijieClusterMemberAddMacAddress               MacAddress,              
                ruijieClusterMemberAddRowStatus              RowStatus
      }

ruijieClusterMemberAddSn OBJECT-TYPE
    SYNTAX      INTEGER(0..240)
    MAX-ACCESS  read-only
    STATUS      current
    DESCRIPTION
            "An arbitrary value which uniquely identifies the
             cluster member device number. when the value set 0,
             the value of number will be specify a idle number beween 2 and 240,
             when the value set 1,the value is invalid."
    ::= { ruijieClusterMemberAddEntry 1 }
ruijieClusterMemberAddMacAddress OBJECT-TYPE
    SYNTAX      MacAddress
    MAX-ACCESS  read-create
    STATUS      current
    DESCRIPTION
            "The MAC address of the member device."
    ::= { ruijieClusterMemberAddEntry 2 }

ruijieClusterMemberAddRowStatus OBJECT-TYPE
    SYNTAX      RowStatus
    MAX-ACCESS  read-create
    STATUS      current
    DESCRIPTION
        "The row status of this table."
    ::= { ruijieClusterMemberAddEntry 3 }

--    The Cluster Member Table

ruijieClusterMemberTable OBJECT-TYPE
    SYNTAX      SEQUENCE OF RuijieClusterMemberEntry
    MAX-ACCESS  not-accessible
    STATUS      current
    DESCRIPTION
            "This table contains one row per cluster member,
            including the manager device."
    ::= { ruijieClusterMIBObjects 20}

ruijieClusterMemberEntry OBJECT-TYPE
    SYNTAX      RuijieClusterMemberEntry
    MAX-ACCESS  not-accessible
    STATUS      current
    DESCRIPTION
            "An entry containing cluster management information
            applicable to a particular cluster member. If the
            entry contain the manager device, this entry cannot
            be modified."
    INDEX { ruijieClusterMemberSn, ruijieClusterMemberUpMAC, ruijieClusterMemberLcIfx, ruijieClusterMemberUpIfx}
    ::= { ruijieClusterMemberTable 1 }

RuijieClusterMemberEntry ::=
      SEQUENCE {
                ruijieClusterMemberSn                       Unsigned32,
                ruijieClusterMemberUpMAC                    MacAddress,
                ruijieClusterMemberLcIfx                    Unsigned32,
                ruijieClusterMemberUpIfx                    Unsigned32,
                ruijieClusterMemberLcPort                   DisplayString,
                ruijieClusterMemberUpPort                   DisplayString,
                ruijieClusterMemberMacAddress               MacAddress,
                ruijieClusterMemberName                     DisplayString,
                ruijieClusterMemberIp                       IpAddress,
                ruijieClusterMemberHops                     Unsigned32,
                ruijieClusterMemberState                    DisplayString,      
                ruijieClusterMemberUpSn                     Unsigned32,              
                ruijieClusterMemberLastTopoUpdateTime       Unsigned32,
                ruijieClusterMemberLastUdpUpdateTime        Unsigned32,
                ruijieClusterMemberNoRecvTopoRspCount       Unsigned32,
                ruijieClusterMemberNoRecvUdpRspCount        Unsigned32,
                ruijieClusterMemberReload                   EnabledStatus
      }

ruijieClusterMemberSn OBJECT-TYPE
    SYNTAX      Unsigned32
    MAX-ACCESS  read-only
    STATUS      current
    DESCRIPTION
            "An arbitrary value which uniquely identifies the
             cluster member device number. It ranges from 0 to
             ruijieStatusMaxNumberOfMembers - 1. incluing the manager
             device."
    ::= { ruijieClusterMemberEntry 1 }
    
ruijieClusterMemberUpMAC OBJECT-TYPE
    SYNTAX      MacAddress
    MAX-ACCESS  read-only
    STATUS      current
    DESCRIPTION
            "The mac address of the uplink device of the cluster."
    ::= { ruijieClusterMemberEntry 2 }
    
ruijieClusterMemberLcIfx OBJECT-TYPE
    SYNTAX      Unsigned32
    MAX-ACCESS  read-only
    STATUS      current
    DESCRIPTION
            "The interface index of port of the member device of the cluster."
    ::= { ruijieClusterMemberEntry 3 }
    
ruijieClusterMemberUpIfx OBJECT-TYPE
    SYNTAX      Unsigned32
    MAX-ACCESS  read-only
    STATUS      current
    DESCRIPTION
            "The interface index of port of the uplink device of the cluster."
    ::= { ruijieClusterMemberEntry 4 }
    
ruijieClusterMemberLcPort OBJECT-TYPE
    SYNTAX      DisplayString
    MAX-ACCESS  read-only
    STATUS      current
    DESCRIPTION
            "The port member of the member device of the cluster."
    ::= { ruijieClusterMemberEntry 5 }

ruijieClusterMemberUpPort OBJECT-TYPE
    SYNTAX      DisplayString
    MAX-ACCESS  read-only
    STATUS      current
    DESCRIPTION
            "The port member of the uplink device of the cluster."
    ::= { ruijieClusterMemberEntry 6 }
    
ruijieClusterMemberMacAddress OBJECT-TYPE
    SYNTAX      MacAddress
    MAX-ACCESS  read-only
    STATUS      current
    DESCRIPTION
            "The management MAC address of the member device."
    ::= { ruijieClusterMemberEntry 7 }

ruijieClusterMemberName OBJECT-TYPE
    SYNTAX      DisplayString
    MAX-ACCESS  read-only
    STATUS      current
    DESCRIPTION
            "The name of the device."
    ::= { ruijieClusterMemberEntry 8 }

ruijieClusterMemberIp OBJECT-TYPE
    SYNTAX      IpAddress
    MAX-ACCESS  read-only
    STATUS      current
    DESCRIPTION
            "The private IP address of the member device of the cluster "
    ::= { ruijieClusterMemberEntry 9 }

ruijieClusterMemberHops OBJECT-TYPE
    SYNTAX      Unsigned32
    MAX-ACCESS  read-only
    STATUS      current
    DESCRIPTION
            "The hop counts between the device and the management device 
            in the topology discovery."
    ::= { ruijieClusterMemberEntry 10 }

ruijieClusterMemberState OBJECT-TYPE
    SYNTAX      DisplayString
    MAX-ACCESS  read-only
    STATUS      current
    DESCRIPTION
            "The status of cluster management connectivity between
            the manage device and a cluster member. Cluster management
            connectivity is determined by the exchange of cluster
            management messages between the manage device and a
            cluster member. A member that has failed to exchange
            cluster management messages with the manage device is
            deemed to be inactive. Otherwise, it is deemed to be active."
    ::= { ruijieClusterMemberEntry 11 }

ruijieClusterMemberUpSn OBJECT-TYPE
    SYNTAX      Unsigned32
    MAX-ACCESS  read-only
    STATUS      current
    DESCRIPTION
            "The uniquely identifies of the uplink device of the member device,
             if the uplink device of the member device is null,
             the ruijieClusterMemberUpSn vlaue is 0."
    ::= { ruijieClusterMemberEntry 12 }

ruijieClusterMemberLastTopoUpdateTime OBJECT-TYPE
    SYNTAX      Unsigned32
    MAX-ACCESS  read-only
    STATUS      current
    DESCRIPTION
            "The last time of the device for cluster topology collect."
    ::= { ruijieClusterMemberEntry 13 }

ruijieClusterMemberLastUdpUpdateTime OBJECT-TYPE
    SYNTAX      Unsigned32
    MAX-ACCESS  read-only
    STATUS      current
    DESCRIPTION
            "The last update time of the member device of the cluster."
    ::= { ruijieClusterMemberEntry 14 }

ruijieClusterMemberNoRecvTopoRspCount OBJECT-TYPE
    SYNTAX      Unsigned32
    MAX-ACCESS  read-only
    STATUS      current
    DESCRIPTION
            "The count that no receive the response of the topology collect of the member device."
    ::= { ruijieClusterMemberEntry 15 }

ruijieClusterMemberNoRecvUdpRspCount OBJECT-TYPE
    SYNTAX      Unsigned32
    MAX-ACCESS  read-only
    STATUS      current
    DESCRIPTION
            "The count that no receive the response package of the hello time of the member device."
    ::= { ruijieClusterMemberEntry 16 }
    
ruijieClusterMemberReload OBJECT-TYPE
    SYNTAX      EnabledStatus
    MAX-ACCESS  read-write
    STATUS      current
    DESCRIPTION
            "when the value is set enable,the member device will reboot."
    ::= { ruijieClusterMemberEntry 17 }
--      The Cluster Candidate Table

ruijieClusterCandidateTable OBJECT-TYPE
    SYNTAX      SEQUENCE OF RuijieClusterCandidateEntry
    MAX-ACCESS  not-accessible
    STATUS      current
    DESCRIPTION
            "This table contains one row per cluster candidate,
             A cluster candidate is a device that is currently
             eligible to be added to the cluster of a manager
             device.  A device is eligible if it satisfies the
             following conditions:
             1. It supports the cluster management protocol.


             The entries in this table and the entries in
             ruijieMemberTable are mutually exclusive at all
             times.  That is, any device that is a cluster
             member never shows up in the ruijieCandidateTable
             or is never a candidate at the same time .  Also, any
             candidate that shows up in ruijieCandidateTable should not
             appear in ruijieMemberTable."
    ::= { ruijieClusterMIBObjects 21 }

ruijieClusterCandidateEntry       OBJECT-TYPE
    SYNTAX      RuijieClusterCandidateEntry
    MAX-ACCESS  not-accessible
    STATUS      current
    DESCRIPTION
            "An entry pertaining to a single candidate device."
    INDEX { ruijieClusterCandidateMacAddress, ruijieClusterCandidateUpMAC, ruijieClusterCandidateLcIfx, ruijieClusterCandidateUpIfx}
    ::= { ruijieClusterCandidateTable 1 }

RuijieClusterCandidateEntry ::= SEQUENCE {
        ruijieClusterCandidateMacAddress            MacAddress,
        ruijieClusterCandidateUpMAC                 MacAddress,
        ruijieClusterCandidateLcIfx                 Unsigned32,
        ruijieClusterCandidateUpIfx                 Unsigned32, 
        ruijieClusterCandidateLcPort                DisplayString,
        ruijieClusterCandidateUpPort                DisplayString,
        ruijieClusterCandidateUpSn                  Unsigned32,    
        ruijieClusterCandidateHops                  Unsigned32,
        ruijieClusterCandidateState                 DisplayString
}

ruijieClusterCandidateMacAddress OBJECT-TYPE
    SYNTAX      MacAddress
    MAX-ACCESS  read-only
    STATUS      current
    DESCRIPTION
            "The management MAC address of a device qualified to
             to be a cluster member of the manager device
             cluster."
    ::= { ruijieClusterCandidateEntry 1 }
    
ruijieClusterCandidateUpMAC OBJECT-TYPE
    SYNTAX      MacAddress
    MAX-ACCESS  read-only
    STATUS      current
    DESCRIPTION
            "The mac address of the uplink device of the candidate device."
    ::= { ruijieClusterCandidateEntry 2 }
    
ruijieClusterCandidateLcIfx OBJECT-TYPE
    SYNTAX      Unsigned32
    MAX-ACCESS  read-only
    STATUS      current
    DESCRIPTION
            "The interface index of port of the candidate device of the cluster."
    ::= { ruijieClusterCandidateEntry 3 }
    
ruijieClusterCandidateUpIfx OBJECT-TYPE
    SYNTAX      Unsigned32
    MAX-ACCESS  read-only
    STATUS      current
    DESCRIPTION
            "The interface index of port of the uplink device of the candidate device."
    ::= { ruijieClusterCandidateEntry 4 }    

ruijieClusterCandidateLcPort OBJECT-TYPE
    SYNTAX      DisplayString
    MAX-ACCESS  read-only
    STATUS      current
    DESCRIPTION
            "The port number of the candidate device of the cluster."
    ::= { ruijieClusterCandidateEntry 5 }

ruijieClusterCandidateUpPort OBJECT-TYPE
    SYNTAX      DisplayString
    MAX-ACCESS  read-only
    STATUS      current
    DESCRIPTION
            "The port number of the uplink device of the candidate device."
    ::= { ruijieClusterCandidateEntry 6 }
    
ruijieClusterCandidateUpSn OBJECT-TYPE
    SYNTAX      Unsigned32
    MAX-ACCESS  read-only
    STATUS      current
    DESCRIPTION
            "The port number of the uplink device of the candidate device."
    ::= { ruijieClusterCandidateEntry 7 }   
    
ruijieClusterCandidateHops OBJECT-TYPE
    SYNTAX      Unsigned32
    MAX-ACCESS  read-only
    STATUS      current
    DESCRIPTION
            "The hop counts between the candidate device and the management device 
            in the topology discovery."
    ::= { ruijieClusterCandidateEntry 8 }
    
ruijieClusterCandidateState OBJECT-TYPE
    SYNTAX      DisplayString
    MAX-ACCESS  read-only
    STATUS      current
    DESCRIPTION
            "The status of cluster management connectivity between
            the manage device and a cluster candidate. Cluster management
            connectivity is determined by the exchange of cluster
            management messages between the manage device and a
            cluster candidate member. A candidate member that has failed to exchange
            cluster management messages with the manage device is
            deemed to be inactive. Otherwise, it is deemed to be active."
    ::= { ruijieClusterCandidateEntry 9 }
    
--    The Cluster blacklist Table

ruijieClusterBlacklistTable OBJECT-TYPE
    SYNTAX      SEQUENCE OF RuijieClusterBlacklistEntry
    MAX-ACCESS  not-accessible
    STATUS      current
    DESCRIPTION
            "This table contains one row per cluster blacklist,
            the device is not permitted to join in any cluster
            in the black list table"
    ::= { ruijieClusterMIBObjects 22}

ruijieClusterBlacklistEntry       OBJECT-TYPE
    SYNTAX      RuijieClusterBlacklistEntry
    MAX-ACCESS  not-accessible
    STATUS      current
    DESCRIPTION
            "An entry pertaining to a single device in blacklist table."
    INDEX { ruijieClusterBlacklistMacAddress }
    ::= { ruijieClusterBlacklistTable 1 }

RuijieClusterBlacklistEntry ::= SEQUENCE {
      ruijieClusterBlacklistMacAddress                MacAddress,
      ruijieClusterBlackListRowStatus                 RowStatus
}

ruijieClusterBlacklistMacAddress OBJECT-TYPE
    SYNTAX      MacAddress
    MAX-ACCESS  read-only
    STATUS      current
    DESCRIPTION
            "The management MAC address of a device which is
            in blacklist table ."
    ::= { ruijieClusterBlacklistEntry 1 }

ruijieClusterBlackListRowStatus OBJECT-TYPE
    SYNTAX      RowStatus
    MAX-ACCESS  read-create
    STATUS      current
    DESCRIPTION
        "The status of the table."
    ::= { ruijieClusterBlacklistEntry 2 }

--     The Cluster Password Auth Pool Table

ruijieClusterPasswordAuth                    OBJECT IDENTIFIER ::= { ruijieClusterMIBObjects 23}

ruijieClusterPasswordAuthPoolTable OBJECT-TYPE
    SYNTAX      SEQUENCE OF RuijieClusterPasswordAuthPoolEntry
    MAX-ACCESS  not-accessible
    STATUS      current
    DESCRIPTION
            "This table shows current configurations for the password pool of the cluster."
    ::= { ruijieClusterPasswordAuth 1 }

ruijieClusterPasswordAuthPoolEntry       OBJECT-TYPE
    SYNTAX      RuijieClusterPasswordAuthPoolEntry
    MAX-ACCESS  not-accessible
    STATUS      current
    DESCRIPTION
            "Entry items"
    INDEX { ruijieClusterPasswordSn }
    ::= { ruijieClusterPasswordAuthPoolTable 1 }

RuijieClusterPasswordAuthPoolEntry ::= SEQUENCE {
      ruijieClusterPasswordSn                    INTEGER,
      ruijieClusterPassword                      DisplayString,
      ruijieClusterPasswordAuthRowStatus        RowStatus
}

ruijieClusterPasswordSn OBJECT-TYPE
    SYNTAX      INTEGER(1..16)
    MAX-ACCESS  read-only
    STATUS      current
    DESCRIPTION
            "The uniquely identifies of the password pool of the cluster."
    ::= { ruijieClusterPasswordAuthPoolEntry 1 }

ruijieClusterPassword OBJECT-TYPE
    SYNTAX      DisplayString (SIZE (1..126))
    MAX-ACCESS  read-create
    STATUS      current
    DESCRIPTION
            "The password of the password pool."
    ::= { ruijieClusterPasswordAuthPoolEntry 2 }

ruijieClusterPasswordAuthRowStatus OBJECT-TYPE
    SYNTAX      RowStatus
    MAX-ACCESS  read-create
    STATUS      current
    DESCRIPTION
        "The status of the table."
    ::= { ruijieClusterPasswordAuthPoolEntry 3}

--  The Cluster device auth password Tables

ruijieClusterDeviceAuthPasswordTable OBJECT-TYPE
    SYNTAX      SEQUENCE OF RuijieClusterDeviceAuthPasswordEntry
    MAX-ACCESS  not-accessible
    STATUS      current
    DESCRIPTION
            "This table shows current configurations for the password of the cluster devices."
    ::= { ruijieClusterPasswordAuth 2 }

ruijieClusterDeviceAuthPasswordEntry       OBJECT-TYPE
    SYNTAX      RuijieClusterDeviceAuthPasswordEntry
    MAX-ACCESS  not-accessible
    STATUS      current
    DESCRIPTION
            "Entry items"
    INDEX { ruijieClusterDeviceMacAddress }
    ::= { ruijieClusterDeviceAuthPasswordTable 1 }

RuijieClusterDeviceAuthPasswordEntry ::= SEQUENCE {
      ruijieClusterDeviceMacAddress                MacAddress,
      ruijieClusterDevicePassword                DisplayString ,
      ruijieClusterDevicePasswordRowStatus        RowStatus
}

ruijieClusterDeviceMacAddress OBJECT-TYPE
    SYNTAX      MacAddress
    MAX-ACCESS  read-only
    STATUS      current
    DESCRIPTION
            "The mac address of the device."
    ::= { ruijieClusterDeviceAuthPasswordEntry 1 }

ruijieClusterDevicePassword OBJECT-TYPE
    SYNTAX      DisplayString (SIZE (1..126))
    MAX-ACCESS  read-create
    STATUS      current
    DESCRIPTION
            " The auth password of the device."
    ::= { ruijieClusterDeviceAuthPasswordEntry 2 }

ruijieClusterDevicePasswordRowStatus OBJECT-TYPE
    SYNTAX      RowStatus
    MAX-ACCESS  read-create
    STATUS      current
    DESCRIPTION
        "The status of the table."
    ::= { ruijieClusterDeviceAuthPasswordEntry 3}

-- traps definition

ruijieClusterTraps OBJECT IDENTIFIER ::= { ruijieClusterMIB 2 }

ruijieClusterMemberStateChangeTrap    NOTIFICATION-TYPE
                OBJECTS { ruijieClusterMemberSn,ruijieClusterMemberState}
                STATUS  current
                DESCRIPTION
                    "While the state of member device changed, then this trap will be sent.
                    The ruijieClusterMemberState node is as follow, 1 indicates Ready status, 
                    2 indicates Active status, 3 indicates Connect status, 
                    and 4 indicates Disconnect status. The node value is as follow."
            ::= { ruijieClusterTraps 1}

ruijieClusterMemberFailureTrap    NOTIFICATION-TYPE
                OBJECTS {ruijieClusterCandidateMacAddress}
                STATUS  current
                DESCRIPTION
                    "When a device add cluster failure, send a snmp trap to the network
                    management. then this trap will be sent."
            ::= { ruijieClusterTraps 2}


ruijieClusterDevMaximumAllowedTrap    NOTIFICATION-TYPE
                STATUS  current
                DESCRIPTION
                    "The number of cluster devices including candidates and members reaches the maximum allowed,
                    then this trap will be sent."
            ::= { ruijieClusterTraps 3}
            
ruijieClusterMemberMaximumAllowedTrap    NOTIFICATION-TYPE
                STATUS  current
                DESCRIPTION
                    "The number of cluster member including members reaches the maximum allowed,
                    then this trap will be sent."
            ::= { ruijieClusterTraps 4}

-- Conformance Information

ruijieClusterMIBConformance OBJECT IDENTIFIER ::= { ruijieClusterMIB 3 }
ruijieClusterMIBCompliances OBJECT IDENTIFIER
            ::= { ruijieClusterMIBConformance 1 }
ruijieClusterMIBGroups      OBJECT IDENTIFIER
            ::= { ruijieClusterMIBConformance 2 }

-- Compliance statements

ruijieClusterCompliance MODULE-COMPLIANCE
    STATUS  current
    DESCRIPTION
            "The compliance statement for the CLUSTER MIB."
    MODULE  -- this module
    MANDATORY-GROUPS { ruijieClusterStatusGroup,
                        ruijieClusterMemberStatusGroup,
                        ruijieClusterMemberGroup,
                        ruijieClusterCandidateGroup,
                        ruijieClusterMemberAddGroup,
                        ruijieClusterBlackListGroup,
                        ruijieClusterPasswordAuthPoolGroup,
                        ruijieClsuterDeviceAuthPasswordGroup,
                        ruijieClusterCandidateStatusGroup
                       }
    ::= { ruijieClusterMIBCompliances 1 }

-- MIB groupings

ruijieClusterStatusGroup  OBJECT-GROUP
    OBJECTS {
             ruijieClusterName,
             ruijieClusterCmdMacAddress,
             ruijieClusterIpPool,
             ruijieClusterIpMask,
             ruijieClusterVlan,
             ruijieClusterHopsLimit,
             ruijieClusterHopsLimit,
             ruijieClusterTimerTopo,
             ruijieClusterTimerHello,
             ruijieClusterTimerHold,
             ruijieClusterTftpServer,
             ruijieClusterNumberOfMembers,
             ruijieClusterMaxNumberOfMembers,
             ruijieClusterDevMaxCapicity
            }
    STATUS  current
    DESCRIPTION
            "The collection of objects which are used to represent
             the status of the cluster."
    ::= { ruijieClusterMIBGroups 1 }

ruijieClusterMemberStatusGroup OBJECT-GROUP
    OBJECTS {
            ruijieClusterName,
            ruijieClusterDeviceEnable,
            ruijieClusterDeviceRole,
            ruijieClusterDeviceIP,
            ruijieClusterDeviceSn
            }
    STATUS  current
    DESCRIPTION
            "The collection of objects which are used to represent
             the status of the cluster member.  These objects are accessible
             on the cluster members and the manager device."
    ::= { ruijieClusterMIBGroups 2 }

ruijieClusterCandidateStatusGroup OBJECT-GROUP
    OBJECTS {
             ruijieClusterName,
             ruijieClusterDeviceRole,
             ruijieClusterDeviceEnable
            }
    STATUS  current
    DESCRIPTION
            "The collection of objects which are used to represent
             the status of single devices which are not in any cluster.
             These objects are accessible on any single device."
    ::= { ruijieClusterMIBGroups 3 }

ruijieClusterMemberGroup    OBJECT-GROUP
    OBJECTS {
                ruijieClusterMemberSn,
                ruijieClusterMemberMacAddress,
                ruijieClusterMemberLcIfx ,
                ruijieClusterMemberUpIfx ,
                ruijieClusterMemberLcPort,
                ruijieClusterMemberUpPort,
                ruijieClusterMemberName,
                ruijieClusterMemberIp,
                ruijieClusterMemberHops,
                ruijieClusterMemberState,                
                ruijieClusterMemberUpSn,
                ruijieClusterMemberUpMAC,                
                ruijieClusterMemberLastTopoUpdateTime,
                ruijieClusterMemberLastUdpUpdateTime,
                ruijieClusterMemberNoRecvTopoRspCount,
                ruijieClusterMemberNoRecvUdpRspCount,
                ruijieClusterMemberReload
            }
    STATUS  current
    DESCRIPTION
            "The collection of objects which are used to represent
             the members of a cluster."
    ::= { ruijieClusterMIBGroups 4 }

ruijieClusterCandidateGroup    OBJECT-GROUP
    OBJECTS {
                ruijieClusterCandidateMacAddress,
                ruijieClusterCandidateUpMAC,
                ruijieClusterCandidateLcIfx,
                ruijieClusterCandidateUpIfx, 
                ruijieClusterCandidateLcPort,
                ruijieClusterCandidateUpPort,
                ruijieClusterCandidateHops,               
                ruijieClusterCandidateUpSn,                   
                ruijieClusterCandidateState                  
            }
    STATUS  current
    DESCRIPTION
            "The collection of objects which are used to represent
             cluster candidates.  These objects are accessible
             on the manager device only."
    ::= { ruijieClusterMIBGroups 5 }

ruijieClusterMemberAddGroup    OBJECT-GROUP
    OBJECTS {
             ruijieClusterMemberAddMacAddress,
             ruijieClusterMemberAddSn,
             ruijieClusterMemberAddRowStatus
            }
    STATUS  current
    DESCRIPTION
            "The collection of objects which are used to represent
             cluster Member add operate.  These objects are accessible
             on the manager device only."
    ::= { ruijieClusterMIBGroups 6 }

ruijieClusterBlackListGroup    OBJECT-GROUP
    OBJECTS {
             ruijieClusterBlacklistMacAddress
            }
    STATUS  current
    DESCRIPTION
            "The collection of objects which are used to represent
             cluster blackList.  These objects are accessible
             on the manager device only."
    ::= { ruijieClusterMIBGroups 7 }

ruijieClusterPasswordAuthPoolGroup    OBJECT-GROUP
    OBJECTS {
             ruijieClusterPasswordSn,
             ruijieClusterPassword
            }
    STATUS  current
    DESCRIPTION
            "The collection of objects which are used to represent
             cluster auth password pool.  These objects are accessible
             on the manager device only."
    ::= { ruijieClusterMIBGroups 8 }

ruijieClsuterDeviceAuthPasswordGroup    OBJECT-GROUP
    OBJECTS {
             ruijieClusterDeviceMacAddress,
             ruijieClusterDevicePassword
            }
    STATUS  current
    DESCRIPTION
            "The collection of objects which are used to represent
             cluster device auth Password.  These objects are accessible
             on the manager device only."
    ::= { ruijieClusterMIBGroups 9 }

END
