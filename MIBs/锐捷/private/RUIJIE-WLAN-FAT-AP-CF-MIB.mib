-- *******************************************************************
-- RUIJIE-WLAN-FAT-AP-CF-MIB.mib : Ruijie MIB
-- May 2010, ruanyucheng
--
-- Copyright (c) 2010 by Ruijie Networks Co.,Ltd.
-- All rights reserved.
-- *******************************************************************
RUIJIE-WLAN-FAT-AP-CF-MIB DEFINITIONS ::= BEGIN
    IMPORTS
        MODULE-IDENTITY,
        OBJECT-TYPE,
        Integer32,
        IpAddress,
        Unsigned32,
        Counter32,
        Counter64,
        TimeTicks
            FROM SNMPv2-SMI
        TruthValue,
        DisplayString,
        MacAddress,
        RowStatus,
        TAddress
            FROM SNMPv2-TC
        Gauge
            FROM RFC1155-SMI
        MODULE-COMPLIANCE,
        NOTIFICATION-GROUP,
        OBJECT-GROUP
            FROM SNMPv2-CONF
        ruijieApgWlanId
            FROM RUIJIE-AC-MGMT-MIB
        ifIndex
            FROM RFC1213-MIB
        IANAifType
            FROM IANAifType-MIB        
        ruijieMgmt
            FROM RUIJIE-SMI;
        
--*******************************************
--* module definition
--*******************************************
apStandardmibmodule MODULE-IDENTITY
    LAST-UPDATED    "201002260000Z"
    ORGANIZATION
        "Ruijie Networks Co.,Ltd."
    CONTACT-INFO
        "Tel: 4008-111-000
           E-mail: service@ruijie.com.cn "

    DESCRIPTION
       "
       Wlan software private MIB for Ruijie SNC according to the China
       Mobile standard. This is device manage MIB.
       "
    REVISION      "201002280000Z"
    DESCRIPTION
       "Initial version of this MIB module."

    ::= { ruijieMgmt  80 }
    
    
                                                                                      
apStandardSysTraps                  OBJECT IDENTIFIER  ::= { apStandardmibmodule 0 }
apStandardSysTrapsObjects           OBJECT IDENTIFIER  ::= { apStandardmibmodule 1 }
                                                                                      
apStandardRadioTraps                OBJECT IDENTIFIER  ::= { apStandardmibmodule 2 }
apStandardRadioTrapsObjects         OBJECT IDENTIFIER  ::= { apStandardmibmodule 3 }
                                                                                      
apStandardTerminalTraps             OBJECT IDENTIFIER  ::= { apStandardmibmodule 4 }
apStandardTerminalTrapsObjects      OBJECT IDENTIFIER  ::= { apStandardmibmodule 5 }
                                                                                      
apStandardAuthSvrTraps              OBJECT IDENTIFIER  ::= { apStandardmibmodule 6 }


apStandardWapiScrTraps             OBJECT IDENTIFIER  ::= { apStandardmibmodule 7 }
--cmApStandardWapiScrTrapsObjects      OBJECT IDENTIFIER  ::= { apStandardmibmodule 8 }






--**************************************************
--* apStandardSysTraps begin here
--**************************************************

apConfigurationErrorTrap NOTIFICATION-TYPE
    STATUS  current
    DESCRIPTION
            " This trap will be sent when the config file is wrong."
    ::= { apStandardSysTraps 1 }
    
apCPUusageTooHighTrap NOTIFICATION-TYPE
    STATUS  current
    DESCRIPTION
            " This trap will be sent when the CPU usage is too high."
    ::= { apStandardSysTraps 2 }
    
apCPUusageTooHighRecovTrap NOTIFICATION-TYPE
    STATUS  current
    DESCRIPTION
            " This trap is used to clear CPU high usage traps."
    ::= { apStandardSysTraps 3 }
    
apMemUsageTooHighTrap NOTIFICATION-TYPE
    STATUS  current
    DESCRIPTION
            " This trap will be sent when memory usage is too high."
    ::= { apStandardSysTraps 4 }
    
apMemUsageTooHighRecovTrap NOTIFICATION-TYPE
    STATUS  current
    DESCRIPTION
            " This trap will be used to clear high memory usage trap."
    ::= { apStandardSysTraps 5 }
    
apSystmColdStartTrap NOTIFICATION-TYPE
    STATUS  current
    DESCRIPTION
            " This trap will be sent when the AP cold start."
    ::= { apStandardSysTraps 6 }
    
apIPAddrChangeTrap NOTIFICATION-TYPE
    OBJECTS {
        apOriginalIpAddr,
        apCurrentIpAddr
    }
    STATUS  current
    DESCRIPTION
            " This trap will be sent when the AP address changes."
    ::= { apStandardSysTraps 7 }
    
apAPMtWorkModeChgTrap NOTIFICATION-TYPE
    STATUS  current
    DESCRIPTION
            " This trap will be sent when the AP radio monitor working mode changes."
    ::= { apStandardSysTraps 8 }  
    
apAPSWUpdateFailTrap NOTIFICATION-TYPE

    STATUS  current
    DESCRIPTION
            " This trap will be sent when the AP software update failed."
    ::= { apStandardSysTraps 9 }    
    
apSSIDkeyConflictTrap NOTIFICATION-TYPE
    OBJECTS {
				apAPMac,
				apWorkingAPRadioIfInfo,
				apSSIDKey,
				apSSIDKeyConflict,
				apCyperIndex
    }
    STATUS  current
    DESCRIPTION
            " This trap will be sent when the SSID key conflict."
    ::= { apStandardSysTraps 10 } 
    
apFatAPHeartbeatTrap NOTIFICATION-TYPE
    OBJECTS {
        apIpAddr,
        apTimeStamp
    }
    STATUS  current
    DESCRIPTION
            " This trap will be sent when a heartbeat periode pass."
    ::= { apStandardSysTraps 11 }     
 
 
apOriginalIpAddr OBJECT-TYPE
    SYNTAX IpAddress
    MAX-ACCESS read-only
    STATUS current
    DESCRIPTION
        "Original IP address of the AP"
    ::= { apStandardSysTrapsObjects 1 }   
    
apCurrentIpAddr OBJECT-TYPE
    SYNTAX IpAddress
    MAX-ACCESS read-only
    STATUS current
    DESCRIPTION
        "Current IP address of the AP"
    ::= { apStandardSysTrapsObjects 2 }      
        
apIpAddr OBJECT-TYPE
    SYNTAX IpAddress
    MAX-ACCESS read-only
    STATUS current
    DESCRIPTION
        "IP address of the AP"
    ::= { apStandardSysTrapsObjects 3 }
    
apTimeStamp OBJECT-TYPE
    SYNTAX TimeTicks
    MAX-ACCESS read-only
    STATUS current
    DESCRIPTION
        "Time stamp of the AP"
    ::= { apStandardSysTrapsObjects 4 }
    
apAPMac OBJECT-TYPE
    SYNTAX MacAddress
    MAX-ACCESS read-only
    STATUS current
    DESCRIPTION
        "AP mac address"
    ::= { apStandardSysTrapsObjects 5 }
    
apSSIDKey OBJECT-TYPE
    SYNTAX DisplayString
    MAX-ACCESS read-only
    STATUS current
    DESCRIPTION
        "Key SSID"
    ::= { apStandardSysTrapsObjects 6 }
    
apSSIDKeyConflict OBJECT-TYPE
    SYNTAX DisplayString
    MAX-ACCESS read-only
    STATUS current
    DESCRIPTION
        "Key SSID"
    ::= { apStandardSysTrapsObjects 7 }
 
apCyperIndex OBJECT-TYPE
    SYNTAX INTEGER
    MAX-ACCESS read-only
    STATUS current
    DESCRIPTION
        "Key SSID"
    ::= { apStandardSysTrapsObjects 8 } 


--**************************************************
--* apStandardSysTraps end here
--**************************************************

--**************************************************
--* apStandardRadioTraps begin here
--**************************************************

apAPCoInterfDetectedTrap NOTIFICATION-TYPE
    OBJECTS {
        apWorkingAPRadioIfInfo,
        apWorkingAPChannel,
        apInterfAPBSSID
    }
    STATUS  current
    DESCRIPTION
            " This trap will be sent when 
            the AP is interupted by coherence AP."
    ::= { apStandardRadioTraps 1 }  
    
   
apAPCoInterfClearTrap NOTIFICATION-TYPE
    OBJECTS {
        apWorkingAPRadioIfInfo,
        apWorkingAPChannel,
        apInterfAPBSSID
    }
    STATUS  current
    DESCRIPTION
            " This trap is used to clear AP cohererence 
            interference traps."
    ::= { apStandardRadioTraps 2 }   
    
apAPNerborInterfDetectedTrap NOTIFICATION-TYPE
    OBJECTS {
        apWorkingAPRadioIfInfo,
        apWorkingAPChannel,
        apInterfAPBSSID,
        apInterfAPChannel
    }
    STATUS  current
    DESCRIPTION
            " This trap is used when 
            the AP is interfere by neibor AP."
    ::= { apStandardRadioTraps 3 }

apAPNeiborInterfClearTrap NOTIFICATION-TYPE
    OBJECTS {
        apWorkingAPRadioIfInfo,
        apWorkingAPChannel,
        apInterfAPBSSID,
        apInterfAPChannel
    }
    STATUS  current
    DESCRIPTION
            " This trap is used to clear AP neibor 
            interference traps."
    ::= { apStandardRadioTraps 4 } 
    
apStaInterfDetectedTrap NOTIFICATION-TYPE
    OBJECTS {
        apWorkingAPRadioIfInfo,
        apWorkingAPChannel,
				apInterfStaMac
    }
    STATUS  current
    DESCRIPTION
            " This trap is used when 
            the AP is interfere by terminal."
    ::= { apStandardRadioTraps 5 }
    
apStaInterfClearTrap NOTIFICATION-TYPE
    OBJECTS {
        apWorkingAPRadioIfInfo,
        apWorkingAPChannel,
				apInterfStaMac
    }
    STATUS  current
    DESCRIPTION
            " This trap is used to clear AP terminal 
            interference traps."
    ::= { apStandardRadioTraps 6 } 
    
apOtherDeviceInterfDetectedTrap NOTIFICATION-TYPE
    OBJECTS {
        apWorkingAPRadioIfInfo,
        apWorkingAPChannel
    }
    STATUS  current
    DESCRIPTION
            " This trap is used when 
            the AP is interfere by other device."
    ::= { apStandardRadioTraps 7 } 
    
apOtherDevInterfClearTrap NOTIFICATION-TYPE
    OBJECTS {
        apWorkingAPRadioIfInfo,
        apWorkingAPChannel
    }
    STATUS  current
    DESCRIPTION
            " This trap is used to clear other device 
              interference traps."
    ::= { apStandardRadioTraps 8 } 
    
apRadioDownTrap NOTIFICATION-TYPE
    OBJECTS {
        apWorkingAPRadioIfInfo,
        apInterruptReason 
    }
    STATUS  current
    DESCRIPTION
            " This trap is sent when 
            radio link is disrupted."
    ::= { apStandardRadioTraps 9 }
    
apRadioDownRecovTrap NOTIFICATION-TYPE
    OBJECTS {
        apWorkingAPRadioIfInfo,
        apInterruptReason 
    }
    STATUS  current
    DESCRIPTION
            " This trap is used to clear other wireless link 
            interrupt traps."
    ::= { apStandardRadioTraps 10 }  
    
apAPStaFullTrap NOTIFICATION-TYPE
    OBJECTS {
				apPermitAssoUser,
				apAssoFailReason    
		}
    STATUS  current
    DESCRIPTION
            " This trap is sent when it can't 
            add a mobile user to the AP."
    ::= { apStandardRadioTraps 11 }   
      
apAPStaFullRecoverTrap NOTIFICATION-TYPE
    OBJECTS {
				apPermitAssoUser,
				apAssoFailReason    
		}
    STATUS  current
    DESCRIPTION
            " This trap is used to clear APStaFullRecoverTrap."
    ::= { apStandardRadioTraps 12 }    
    
apAPMtRdoChanlChgTrap NOTIFICATION-TYPE
    OBJECTS {
				apWorkingAPRadioIfInfo,
				apChannelBeforeChange,
				apChannelAfterChange,
				apChanChangeMode		
    }
    STATUS  current
    DESCRIPTION
            " This trap is sent when radio channel changes."
    ::= { apStandardRadioTraps 13 }        
    
    
apInterruptReason OBJECT-TYPE
    SYNTAX DisplayString
    MAX-ACCESS read-only
    STATUS current
    DESCRIPTION
        "The interrupt reason of the wireless link"
    ::= { apStandardRadioTrapsObjects 1} 
    
apWorkingAPRadioIfInfo OBJECT-TYPE
    SYNTAX MacAddress
    MAX-ACCESS read-only
    STATUS current
    DESCRIPTION
        "radio interface infomation."
    ::= { apStandardRadioTrapsObjects 2} 
 
apWorkingAPChannel OBJECT-TYPE
    SYNTAX INTEGER
    MAX-ACCESS read-only
    STATUS current
    DESCRIPTION
        "Channel of working AP"
    ::= { apStandardRadioTrapsObjects 3}  
    
apInterfAPChannel OBJECT-TYPE
    SYNTAX INTEGER
    MAX-ACCESS read-only
    STATUS current
    DESCRIPTION
        "Channel of inteference AP"
    ::= { apStandardRadioTrapsObjects 4}  
    
apInterfAPBSSID OBJECT-TYPE
    SYNTAX MacAddress
    MAX-ACCESS read-only
    STATUS current
    DESCRIPTION
        "BSSID of inteference AP"
    ::= { apStandardRadioTrapsObjects 5}
    
apInterfStaMac OBJECT-TYPE
    SYNTAX MacAddress
    MAX-ACCESS read-only
    STATUS current
    DESCRIPTION
        "mac of inteference STA"
    ::= { apStandardRadioTrapsObjects 6}   

  
apPermitAssoUser OBJECT-TYPE
    SYNTAX INTEGER
    MAX-ACCESS read-only
    STATUS current
    DESCRIPTION
        "mac of inteference STA"
    ::= { apStandardRadioTrapsObjects 7}   
    
apAssoFailReason OBJECT-TYPE
    SYNTAX DisplayString
    MAX-ACCESS read-only
    STATUS current
    DESCRIPTION
        "Association fail reason."
    ::= { apStandardRadioTrapsObjects 8} 
    
apChannelBeforeChange OBJECT-TYPE
    SYNTAX INTEGER
    MAX-ACCESS read-only
    STATUS current
    DESCRIPTION
        "radio channel before channel change."
    ::= { apStandardRadioTrapsObjects 9} 

apChannelAfterChange OBJECT-TYPE
    SYNTAX INTEGER
    MAX-ACCESS read-only
    STATUS current
    DESCRIPTION
        "radio channel after channel change."
    ::= { apStandardRadioTrapsObjects 10}  
    
apChanChangeMode OBJECT-TYPE
    SYNTAX INTEGER
    MAX-ACCESS read-only
    STATUS current
    DESCRIPTION
        "radio channel change mode."
    ::= { apStandardRadioTrapsObjects 11}     
    

    
--**************************************************
--* apStandardRadioTraps end here
--**************************************************


--**************************************************
--* apStandardTerminalTraps begin here
--**************************************************

apStaAuthErrorTrap NOTIFICATION-TYPE
    OBJECTS {
        apWorkingAPRadioIfInfo,        
        apWorkingAPBSSID,
        apWorkingAPSSID,
        apStaMacAddr,
        apAuthMode,
        apAuthFailReason     
    }
    STATUS  current
    DESCRIPTION
            " This trap is sent when 
            terminal authentication failed."
    ::= { apStandardTerminalTraps 1 }
    
apStAssociationFailTrap NOTIFICATION-TYPE
    OBJECTS {
        apWorkingAPRadioIfInfo,        
        apWorkingAPBSSID,
        apWorkingAPSSID,
        apStaMacAddr,
        apAssoFailReason  
    }
    STATUS  current
    DESCRIPTION
            " This trap is sent when 
            terminal association failed."
    ::= { apStandardTerminalTraps 2 }
    
apWorkingAPBSSID OBJECT-TYPE
    SYNTAX MacAddress
    MAX-ACCESS read-only
    STATUS current
    DESCRIPTION
        "AP BSSID"
    ::= { apStandardTerminalTrapsObjects 1} 

apWorkingAPSSID OBJECT-TYPE
    SYNTAX MacAddress
    MAX-ACCESS read-only
    STATUS current
    DESCRIPTION
        "AP SSID"
    ::= { apStandardTerminalTrapsObjects 2}        
    
apStaMacAddr OBJECT-TYPE
    SYNTAX MacAddress
    MAX-ACCESS read-only
    STATUS current
    DESCRIPTION
        "MAC address of the STA"
    ::= { apStandardTerminalTrapsObjects 3}     

apAuthMode OBJECT-TYPE
    SYNTAX INTEGER
    MAX-ACCESS read-only
    STATUS current
    DESCRIPTION
        "auth mode"
    ::= { apStandardTerminalTrapsObjects 4}   
    
apAuthFailReason OBJECT-TYPE
    SYNTAX DisplayString
    MAX-ACCESS read-only
    STATUS current
    DESCRIPTION
        "Reason of the 	 failure"
    ::= { apStandardTerminalTrapsObjects 5}   
    
    
--**************************************************
--* apStandardTerminalTraps end here
--**************************************************


--**************************************************
--* apStandardAuthSvrTraps begin here
--**************************************************

apRadiusAuthServerUnavailableTrap NOTIFICATION-TYPE
    STATUS  current
    DESCRIPTION
            " This trap will be sent when Radius 
            authentication server is unavailable."
    ::= { apStandardAuthSvrTraps 1 }
    
apRadiusAuthServerAvailableTrap NOTIFICATION-TYPE
    STATUS  current
    DESCRIPTION
            " This trap was used to clear 
            RadiusAuthServerUnavailableTrap."
    ::= { apStandardAuthSvrTraps 2 } 
    
apRadioAccServerUnavailableTrap NOTIFICATION-TYPE
    STATUS  current
    DESCRIPTION
            " This trap will be sent when Radius 
            charge server is unavailable."
    ::= { apStandardAuthSvrTraps 3 } 

apRadiusAccServerAvailableTrap NOTIFICATION-TYPE
    STATUS  current
    DESCRIPTION
            " This trap was used to clear 
            apRadioAccServerUnavailableTrap."
    ::= { apStandardAuthSvrTraps 4 } 
    

--**************************************************
--* apStandardAuthSvrTraps end here
--**************************************************



--**************************************************
--* apStandardWapiScrTraps begin here
--**************************************************

apUserWithInvalidCerficationInbreakNetworkTrap NOTIFICATION-TYPE
    OBJECTS {
        apWorkingAPRadioIfInfo,        
        apWorkingAPBSSID,
        apWorkingAPSSID,
        apStaMacAddr
    }
    STATUS  current
    DESCRIPTION
            " This trap will be sent when
            the network is invaded by user with invalid cerfication."
    ::= { apStandardWapiScrTraps 1 } 
    
apStationRepititiveAttackTrap NOTIFICATION-TYPE
    OBJECTS {
        apWorkingAPRadioIfInfo,        
        apWorkingAPBSSID,
        apWorkingAPSSID,
        apStaMacAddr
    }
    STATUS  current
    DESCRIPTION
            " This trap will be sent when
            the client station re-attack."
    ::= { apStandardWapiScrTraps 2 } 

apTamperAttackTrap NOTIFICATION-TYPE
    OBJECTS {
        apWorkingAPRadioIfInfo,        
        apWorkingAPBSSID,
        apWorkingAPSSID,
        apStaMacAddr
    }
    STATUS  current
    DESCRIPTION
            " This trap will be sent when
             attack modifies."
    ::= { apStandardWapiScrTraps 3 } 

apLowSafeLevelAttackTrap NOTIFICATION-TYPE
    OBJECTS {
        apWorkingAPRadioIfInfo,        
        apWorkingAPBSSID,
        apWorkingAPSSID,
        apStaMacAddr
    }
    STATUS  current
    DESCRIPTION
            " This trap will be sent when
            low save level attack."
    ::= { apStandardWapiScrTraps 4 } 
    
 apAddressRedirectionAttackTrap NOTIFICATION-TYPE
    OBJECTS {
        apWorkingAPRadioIfInfo,        
        apWorkingAPBSSID,
        apWorkingAPSSID,
        apStaMacAddr
    }
    STATUS  current
    DESCRIPTION
            " This trap will be sent when
            address redirection attack."
    ::= { apStandardWapiScrTraps 5 } 
    
    
apConfigInfoObjects  OBJECT IDENTIFIER  ::= { apStandardmibmodule 8 }  
apPerformanceStatObjects  OBJECT IDENTIFIER  ::= { apStandardmibmodule 9 }  

                                                    
apSysInfoObjects       OBJECT IDENTIFIER  ::= { apConfigInfoObjects 1 }
apPhyInterfaceConfig   OBJECT IDENTIFIER  ::= { apConfigInfoObjects 2 }
apRadioInterfaceCfg    OBJECT IDENTIFIER  ::= { apConfigInfoObjects 3 }
apSSIDCfg              OBJECT IDENTIFIER  ::= { apConfigInfoObjects 4 }
apSecurityCfg          OBJECT IDENTIFIER  ::= { apConfigInfoObjects 5 }
apTerminalCfg          OBJECT IDENTIFIER  ::= { apConfigInfoObjects 6 }
apQosCfg               OBJECT IDENTIFIER  ::= { apConfigInfoObjects 7 }
apWapiCfg              OBJECT IDENTIFIER  ::= { apConfigInfoObjects 8 }
apSyslogCfg            OBJECT IDENTIFIER  ::= { apConfigInfoObjects 9 }
apSoftwareUpdate       OBJECT IDENTIFIER  ::= { apConfigInfoObjects 10 }
apCfgFileDistribute    OBJECT IDENTIFIER  ::= { apConfigInfoObjects 11 }
apAccessControl        OBJECT IDENTIFIER  ::= { apConfigInfoObjects 12 }
apTrapConfig           OBJECT IDENTIFIER  ::= { apConfigInfoObjects 13 }
apVlanConfig           OBJECT IDENTIFIER  ::= { apConfigInfoObjects 14 }
apHeartbeatConfig      OBJECT IDENTIFIER  ::= { apConfigInfoObjects 15 }

apSysPerformanceStat   OBJECT IDENTIFIER  ::= { apPerformanceStatObjects 1 }
apConInfoStat          OBJECT IDENTIFIER  ::= { apPerformanceStatObjects 2 }
apIfPeformanceStat     OBJECT IDENTIFIER  ::= { apPerformanceStatObjects 3 }
apSSIDPeformanceStat   OBJECT IDENTIFIER  ::= { apPerformanceStatObjects 4 }
apTermPeformanceStat   OBJECT IDENTIFIER  ::= { apPerformanceStatObjects 5 }
apWAPIPeformanceStat   OBJECT IDENTIFIER  ::= { apPerformanceStatObjects 6 }
apQOSPeformanceStat    OBJECT IDENTIFIER  ::= { apPerformanceStatObjects 7 }


--**************************************************
--* apSysInfoObjects start here
--************************************************** 
apSysNetID OBJECT-TYPE
    SYNTAX DisplayString (SIZE(16..255))
    MAX-ACCESS read-write
    STATUS current
    DESCRIPTION
        "Network elements encoding of AP, unifiedly defined by
        China Mobile. It's length is not less than 16."
    ::= { apSysInfoObjects 1 }

apSysHostName OBJECT-TYPE
    SYNTAX DisplayString (SIZE(40..255))
    MAX-ACCESS read-write
    STATUS current
    DESCRIPTION
        "The AP device name, in line with the naming
        convention of China Mobile. It's length will not be
        shorter than 40."
    ::= { apSysInfoObjects 2 } 
    
apSysDescr OBJECT-TYPE
    SYNTAX DisplayString
    MAX-ACCESS read-only
    STATUS current
    DESCRIPTION
        "The discription of AP device information"
    ::= { apSysInfoObjects 3 }  
     
    
apManufacturer OBJECT-TYPE
    SYNTAX DisplayString
    MAX-ACCESS read-only
    STATUS current
    DESCRIPTION
        "The manufactureer of the ap device."
    ::= { apSysInfoObjects 4 }
    
apSerialNumber OBJECT-TYPE
    SYNTAX DisplayString
    MAX-ACCESS read-only
    STATUS current
    DESCRIPTION
        "The serial number of the ap device."
    ::= { apSysInfoObjects 5 } 
    
apSysModel OBJECT-TYPE
    SYNTAX DisplayString
    MAX-ACCESS read-only
    STATUS current
    DESCRIPTION
        "The type of the ap device."
    ::= { apSysInfoObjects 6 } 
    
apSysTime OBJECT-TYPE
    SYNTAX DisplayString
    MAX-ACCESS read-write
    STATUS current
    DESCRIPTION
        "The system time displayed on the ap device."
    ::= { apSysInfoObjects 7 } 
    
apSysUpTime OBJECT-TYPE
    SYNTAX TimeTicks
    MAX-ACCESS read-only
    STATUS current
    DESCRIPTION
        "The run time of the AP."
    ::= { apSysInfoObjects 8 }  
    
apSysIPAddress OBJECT-TYPE
    SYNTAX IpAddress
    MAX-ACCESS read-write
    STATUS current                
    DESCRIPTION                
        "The ip of AP."                
    ::= { apSysInfoObjects 9 } 
    
apSysIPNetMask OBJECT-TYPE
    SYNTAX IpAddress
    MAX-ACCESS read-write
    STATUS current
    DESCRIPTION
        "The netmask of the AP ip."
    ::= { apSysInfoObjects 10 }
    
apSysGWAddr OBJECT-TYPE
    SYNTAX IpAddress
    MAX-ACCESS read-write
    STATUS current
    DESCRIPTION
        "The gateway address of the AP."
    ::= { apSysInfoObjects 11 }                   
                
apPrimDNSServerIPAdd OBJECT-TYPE
    SYNTAX IpAddress
    MAX-ACCESS read-write
    STATUS current
    DESCRIPTION
        "The prime DNS server address of the AP."
    ::= { apSysInfoObjects 12 }    
    
apSeconDNSServerIPAdd OBJECT-TYPE
    SYNTAX IpAddress
    MAX-ACCESS read-write
    STATUS current
    DESCRIPTION
        "The second DNS server address of the AP."
    ::= { apSysInfoObjects 13 }   
    
apSysMacAddress OBJECT-TYPE
    SYNTAX MacAddress
    MAX-ACCESS read-only
    STATUS current
    DESCRIPTION
        "The MAC address of the AP."
    ::= { apSysInfoObjects 14 }   
    
apReadCommunityName OBJECT-TYPE
    SYNTAX DisplayString
    MAX-ACCESS read-write
    STATUS current
    DESCRIPTION
        "The  community name used when reading."
    ::= { apSysInfoObjects 15 }    
    
apWriteCommunityName OBJECT-TYPE
    SYNTAX DisplayString
    MAX-ACCESS read-write
    STATUS current
    DESCRIPTION
        "The  community name used when writing."
    ::= { apSysInfoObjects 16 }   
    
apStatWindowTime OBJECT-TYPE
    SYNTAX TimeTicks
    MAX-ACCESS read-write
    STATUS current
    DESCRIPTION
        "The  statistic time of sliding window."
    ::= { apSysInfoObjects 17 }  
    
apSampleTime OBJECT-TYPE
    SYNTAX Integer32
    MAX-ACCESS read-write
    STATUS current
    DESCRIPTION
        "The  sampling time of AP device."
    ::= { apSysInfoObjects 18 }   
    
apSysRestart OBJECT-TYPE
    SYNTAX INTEGER
    MAX-ACCESS read-write
    STATUS current
    DESCRIPTION
        "Restart the device."
    ::= { apSysInfoObjects 19 }   
    
apSysReset OBJECT-TYPE
    SYNTAX INTEGER
    MAX-ACCESS read-write
    STATUS current
    DESCRIPTION
        "reset the device to default."
    ::= { apSysInfoObjects 20 }  
 
apSoftwareName OBJECT-TYPE
    SYNTAX DisplayString
    MAX-ACCESS read-only
    STATUS current
    DESCRIPTION
        "The software name of the ap system."
    ::= { apSysInfoObjects 21 } 
    
apSoftwareVersion OBJECT-TYPE
    SYNTAX DisplayString
    MAX-ACCESS read-only
    STATUS current
    DESCRIPTION
        "The software version of the ap system."
    ::= { apSysInfoObjects 22 } 
    
apSoftwareVendor OBJECT-TYPE
    SYNTAX DisplayString
    MAX-ACCESS read-only
    STATUS current
    DESCRIPTION
        "The software vendor of the ap system."
    ::= { apSysInfoObjects 23 }   
    
apCPUType OBJECT-TYPE
    SYNTAX DisplayString
    MAX-ACCESS read-only
    STATUS current
    DESCRIPTION
        "The CPU information including CPU Type,dominant frequency and so on."
    ::= { apSysInfoObjects 24 }  
    
apMemoryType OBJECT-TYPE
    SYNTAX DisplayString
    MAX-ACCESS read-only
    STATUS current
    DESCRIPTION
        "The memory type of ap."
    ::= { apSysInfoObjects 25 }
    
apMemorySize OBJECT-TYPE
    SYNTAX Gauge
    MAX-ACCESS read-only
    STATUS current
    DESCRIPTION
        "The memory size of ap."
    ::= { apSysInfoObjects 26 }

apFlashSize OBJECT-TYPE
    SYNTAX Gauge
    MAX-ACCESS read-only
    STATUS current
    DESCRIPTION
        "The flash size of ap."
    ::= { apSysInfoObjects 27 }

--**************************************************
--* apSysInfoObjects end here
--************************************************** 

--**************************************************
--* apPhyInterfaceConfig start here
--**************************************************
apIfNumber OBJECT-TYPE
    SYNTAX Integer32
    MAX-ACCESS read-only
    STATUS current
    DESCRIPTION
        "The count of the physical interfaces of ap."
    ::= { apPhyInterfaceConfig 1 }
    
--**************************************************
--* cmApWiredInterfaceCfgTable begins
--**************************************************

apWiredInterfaceCfgTable OBJECT-TYPE
    SYNTAX SEQUENCE OF ApWiredInterfaceCfgEntry
    MAX-ACCESS not-accessible
    STATUS current
    DESCRIPTION
        "The table discribe wired interface configuration."
    ::= { apPhyInterfaceConfig 2 }

apWiredInterfaceCfgEntry OBJECT-TYPE
    SYNTAX ApWiredInterfaceCfgEntry
    MAX-ACCESS not-accessible
    STATUS current
    DESCRIPTION
        "The entry of apWiredInterfaceCfgTable."
    INDEX { ifIndex }
    ::= { apWiredInterfaceCfgTable 1 }

ApWiredInterfaceCfgEntry ::=
    SEQUENCE {
        apIfDescr                           DisplayString,
        apIfType                            IANAifType,
        apIfMTU                             Integer32,
        apIfSpeed                           Integer32,
        apIfPhysAddress                     MacAddress,
        apIfAdminStatus                     INTEGER,
        apIfOperStatus                      INTEGER,
        apIfLastChange                      TimeTicks
    }
    
apIfDescr OBJECT-TYPE
    SYNTAX DisplayString
    MAX-ACCESS read-only
    STATUS current
    DESCRIPTION
        "The description of the ap interfaces."
    ::= { apWiredInterfaceCfgEntry 1 }

apIfType OBJECT-TYPE
    SYNTAX IANAifType
    MAX-ACCESS read-only
    STATUS current
    DESCRIPTION
        "The style of the ap interfaces."
    ::= { apWiredInterfaceCfgEntry 2 }

apIfMTU OBJECT-TYPE
    SYNTAX Integer32
    MAX-ACCESS read-only
    STATUS current
    DESCRIPTION
        "The max mtu of the ap interfaces."
    ::= { apWiredInterfaceCfgEntry 3 }

apIfSpeed OBJECT-TYPE
    SYNTAX Integer32
    MAX-ACCESS read-only
    STATUS current
    DESCRIPTION
        "The speed of the ap interfaces."
    ::= { apWiredInterfaceCfgEntry 4 }

apIfPhysAddress OBJECT-TYPE
    SYNTAX MacAddress
    MAX-ACCESS read-only
    STATUS current
    DESCRIPTION
        "The MAC address of the ap interfaces."
    ::= { apWiredInterfaceCfgEntry 5 }
    
apIfAdminStatus OBJECT-TYPE
    SYNTAX INTEGER
    MAX-ACCESS read-write
    STATUS current
    DESCRIPTION
        "The status admin of the interface."
    ::= { apWiredInterfaceCfgEntry 6 }
    
apIfOperStatus OBJECT-TYPE
    SYNTAX INTEGER
    MAX-ACCESS read-only
    STATUS current
    DESCRIPTION
        "The operation status of the interface."
    ::= { apWiredInterfaceCfgEntry 7 }
    
apIfLastChange OBJECT-TYPE
    SYNTAX TimeTicks
    MAX-ACCESS read-only
    STATUS current
    DESCRIPTION
        "The last time of current status."
    ::= { apWiredInterfaceCfgEntry 8 }        
    

--**************************************************
--* apWiredInterfaceCfgTable ends
--**************************************************
    
--**************************************************
--* apPhyInterfaceConfig end here
--**************************************************

--**************************************************
--* apRadioInterfaceCfg start here
--**************************************************

--**************************************************
--* cmApradioInterfaceInfoTable begins
--**************************************************
apRadioInterfaceInfoTable OBJECT-TYPE
    SYNTAX SEQUENCE OF ApRadioInterfaceInfoEntry
    MAX-ACCESS not-accessible
    STATUS current
    DESCRIPTION
        "The table inluding radio interface information Of the AP."
    ::= { apRadioInterfaceCfg 1 }

apRadioInterfaceInfoEntry OBJECT-TYPE
    SYNTAX ApRadioInterfaceInfoEntry
    MAX-ACCESS not-accessible
    STATUS current
    DESCRIPTION
        "The entry of apRadioInterfaceInfoTable."
    INDEX
    { ifIndex }
    ::= { apRadioInterfaceInfoTable 1 }

ApRadioInterfaceInfoEntry ::=
    SEQUENCE {
        apRadioIfDescr                      DisplayString,
        apRadioIfType                       IANAifType,
        apRadioIfMTU                        Integer32,
        apRadioIfSpeed                      Integer32,
        apRadioIfMacAddress                 MacAddress,
        apRadioIfDiversity									INTEGER,
        apRadioIfAdminStatus                INTEGER,
        apRadioIfOperStatus                 INTEGER,
        apRadioIfLastChange                 TimeTicks,
        apRadioChannelAutoSelectEnable      INTEGER,
        apRadioChannelConfig                INTEGER,
        apRadioChannelUsing                 INTEGER,
        apCurrRadioModeSupport              Integer32,
        apRadioModeConfig                   Integer32,
        apTransmitSpeedConfig               DisplayString,
        apMaxTxPwrLvl                       DisplayString,
        apTxPwr															INTEGER,
        apPwrAttRange                       INTEGER,
        apPwrAttValue                       INTEGER,
        apAntennaGain                       INTEGER,
        apPowerMgmtEnable                   TruthValue,
        apMaxStationNumPermitted            Integer32,
        apAMPDUEnabled                      INTEGER,
        apBWMode                            INTEGER,
        apShortGIEnabled                    INTEGER,
        apIs11nOnly                         TruthValue 
    }
    
    
apRadioIfDescr OBJECT-TYPE
    SYNTAX DisplayString
    MAX-ACCESS read-only
    STATUS current
    DESCRIPTION
        "The discription of radio interface information"
    ::= { apRadioInterfaceInfoEntry 1 }

apRadioIfType OBJECT-TYPE
    SYNTAX IANAifType
    MAX-ACCESS read-only
    STATUS current
    DESCRIPTION
        "Radio interface type"
    ::= { apRadioInterfaceInfoEntry 2 }
    
apRadioIfMTU OBJECT-TYPE
    SYNTAX Integer32
    MAX-ACCESS read-only
    STATUS current
    DESCRIPTION
        "The max tramsform unit of the interface"
    ::= { apRadioInterfaceInfoEntry 3 }
    
apRadioIfSpeed OBJECT-TYPE
    SYNTAX Integer32
    MAX-ACCESS read-only
    STATUS current
    DESCRIPTION
        "The speed of the interface"
    ::= { apRadioInterfaceInfoEntry 4 }
    
apRadioIfMacAddress OBJECT-TYPE
    SYNTAX MacAddress
    MAX-ACCESS read-only
    STATUS current
    DESCRIPTION
        "The MAC address of the interface."
    ::= { apRadioInterfaceInfoEntry 5 }

apRadioIfDiversity OBJECT-TYPE
    SYNTAX INTEGER {
         no(0),
         yes(1)
    }
    MAX-ACCESS read-only
    STATUS current
    DESCRIPTION
        "Is diversity supported."
    ::= { apRadioInterfaceInfoEntry 6 }
    
apRadioIfAdminStatus OBJECT-TYPE
    SYNTAX INTEGER {
         up(1),
         down(2),
         admindown(3)
    }
    MAX-ACCESS read-write
    STATUS current
    DESCRIPTION
        "the administration of interface status."
    ::= { apRadioInterfaceInfoEntry 7 }  
    
apRadioIfOperStatus OBJECT-TYPE
    SYNTAX INTEGER {
         up(1),
         down(2),
         admindown(3)
    }
    MAX-ACCESS read-only
    STATUS current
    DESCRIPTION
        "Current status of the interface ."
    ::= { apRadioInterfaceInfoEntry 8 }      
      
apRadioIfLastChange OBJECT-TYPE
    SYNTAX TimeTicks
    MAX-ACCESS read-only
    STATUS current
    DESCRIPTION
        "The last time of current status."
    ::= { apRadioInterfaceInfoEntry 9 }  
    
apRadioChannelAutoSelectEnable OBJECT-TYPE
    SYNTAX INTEGER
    MAX-ACCESS read-write
    STATUS current
    DESCRIPTION
        "Decide wether to auto-select radio channel."
    ::= { apRadioInterfaceInfoEntry 10 }        
    
apRadioChannelConfig OBJECT-TYPE
    SYNTAX INTEGER
    MAX-ACCESS read-write
    STATUS current
    DESCRIPTION
        "Set radio channel by hand."
    ::= { apRadioInterfaceInfoEntry 11 }   
           
apRadioChannelUsing OBJECT-TYPE
    SYNTAX INTEGER
    MAX-ACCESS read-only
    STATUS current
    DESCRIPTION
        "The current using radio channel."
    ::= { apRadioInterfaceInfoEntry 12 } 

apCurrRadioModeSupport OBJECT-TYPE
    SYNTAX Integer32
    MAX-ACCESS read-only
    STATUS current
    DESCRIPTION
        "The radio model supported."
    ::= { apRadioInterfaceInfoEntry 13 }      

apRadioModeConfig OBJECT-TYPE
    SYNTAX Integer32
    MAX-ACCESS read-write
    STATUS current
    DESCRIPTION
        "config radio channel."
    ::= { apRadioInterfaceInfoEntry 14 }      

apTransmitSpeedConfig OBJECT-TYPE
    SYNTAX DisplayString
    MAX-ACCESS read-write
    STATUS current
    DESCRIPTION
        "transmit speed config"
    ::= { apRadioInterfaceInfoEntry 15 } 
    
apMaxTxPwrLvl OBJECT-TYPE
    SYNTAX DisplayString
    MAX-ACCESS read-only
    STATUS current
    DESCRIPTION
        "The max transmit power"
    ::= { apRadioInterfaceInfoEntry 16 }
    
apTxPwr OBJECT-TYPE
    SYNTAX INTEGER
    MAX-ACCESS read-write
    STATUS current
    DESCRIPTION
        "Transmit power setup."
    ::= { apRadioInterfaceInfoEntry 17 }
     
apPwrAttRange OBJECT-TYPE
    SYNTAX INTEGER
    MAX-ACCESS read-only
    STATUS current
    DESCRIPTION
        "The range of power attenuation."
    ::= { apRadioInterfaceInfoEntry 18 } 
    
apPwrAttValue OBJECT-TYPE
    SYNTAX INTEGER
    MAX-ACCESS read-write
    STATUS current
    DESCRIPTION
        "config power attenuation."
    ::= { apRadioInterfaceInfoEntry 19 }     
    
apAntennaGain OBJECT-TYPE
    SYNTAX INTEGER
    MAX-ACCESS read-only
    STATUS current
    DESCRIPTION
        "Antenna Gain."
    ::= { apRadioInterfaceInfoEntry 20 }      
    
apPowerMgmtEnable OBJECT-TYPE
    SYNTAX TruthValue
    MAX-ACCESS read-write
    STATUS current
    DESCRIPTION
        "whether to open auto power control."
    ::= { apRadioInterfaceInfoEntry 21 }        
    
apMaxStationNumPermitted OBJECT-TYPE
    SYNTAX Integer32
    MAX-ACCESS read-write
    STATUS current
    DESCRIPTION
        "The max number of terminal the interface can suopport."
    ::= { apRadioInterfaceInfoEntry 22 }     
    
apAMPDUEnabled OBJECT-TYPE
    SYNTAX INTEGER
    MAX-ACCESS read-write
    STATUS current
    DESCRIPTION
        "A-MPDU Switch."
    ::= { apRadioInterfaceInfoEntry 23 }   
    
apBWMode OBJECT-TYPE
    SYNTAX INTEGER
    MAX-ACCESS read-write
    STATUS current
    DESCRIPTION
        "Bandwidth mode select."
    ::= { apRadioInterfaceInfoEntry 24 }     
    
apShortGIEnabled OBJECT-TYPE
    SYNTAX INTEGER
    MAX-ACCESS read-write
    STATUS current
    DESCRIPTION
        "Short GI switch."
    ::= { apRadioInterfaceInfoEntry 25 } 
    
apIs11nOnly OBJECT-TYPE
    SYNTAX TruthValue
    MAX-ACCESS read-write
    STATUS current
    DESCRIPTION
        "whether access 11n terminal."
    ::= { apRadioInterfaceInfoEntry 26 } 
    
    
--**************************************************
--* apRadioInterfaceInfoTable ends
--**************************************************
    
    

--**************************************************
--* cmApradioInterfacePhyParaTable begins
--**************************************************

apRadioInterfacePhyParaTable OBJECT-TYPE
    SYNTAX SEQUENCE OF ApRadioInterfacePhyParaEntry
    MAX-ACCESS not-accessible
    STATUS current
    DESCRIPTION
        "The table describe the physical parameter cofiguration of radio interface."
    ::= { apRadioInterfaceCfg 2 }

apRadioInterfacePhyParaEntry OBJECT-TYPE
    SYNTAX ApRadioInterfacePhyParaEntry
    MAX-ACCESS not-accessible
    STATUS current
    DESCRIPTION
        "The entry of apRadioInterfacePhyParaTable."
    INDEX
    { ifIndex }
    ::= { apRadioInterfacePhyParaTable 1 }

ApRadioInterfacePhyParaEntry ::=
    SEQUENCE {
        apBeaconIntvl                       Integer32,
        apDtimIntvl                         Integer32,
        apRtsThreshold                      Integer32,
        apFragThreshlod                     Integer32,
        apPreambleLen                       INTEGER
    } 
  
apBeaconIntvl OBJECT-TYPE
    SYNTAX Integer32
    MAX-ACCESS read-write
    STATUS current
    DESCRIPTION
        "The interval of beacon."
    ::= { apRadioInterfacePhyParaEntry 1 } 
    

apDtimIntvl OBJECT-TYPE
    SYNTAX Integer32
    MAX-ACCESS read-write
    STATUS current
    DESCRIPTION
        "The interval of DTIM."
    ::= { apRadioInterfacePhyParaEntry 2 }  
    
apRtsThreshold OBJECT-TYPE
    SYNTAX Integer32
    MAX-ACCESS read-write
    STATUS current
    DESCRIPTION
        "Rts Threshold."
    ::= { apRadioInterfacePhyParaEntry 3 }     
    
apFragThreshlod OBJECT-TYPE
    SYNTAX Integer32
    MAX-ACCESS read-write
    STATUS current
    DESCRIPTION
        "Frag Threshold."
    ::= { apRadioInterfacePhyParaEntry 4 }  
    
apPreambleLen OBJECT-TYPE
    SYNTAX INTEGER
    MAX-ACCESS read-write
    STATUS current
    DESCRIPTION
        "Preamb Length."
    ::= { apRadioInterfacePhyParaEntry 5 } 
    
    
--**************************************************
--* apRadioInterfacePhyParaTable ends
--**************************************************     
    
--**************************************************
--* apRadioInterfaceCfg end here
--**************************************************


--**************************************************
--* apSSIDCfg start here
--************************************************** 

apConfigBSSIDNum OBJECT-TYPE
    SYNTAX Integer32
    MAX-ACCESS read-only
    STATUS current
    DESCRIPTION
        "The current bssid number of the AP device."
    ::= { apSSIDCfg 1 }

    
    
--**************************************************
--* cmApRadioIfSSIDCfgTable begins
--**************************************************

apRadioIfSSIDCfgTable OBJECT-TYPE
    SYNTAX SEQUENCE OF ApRadioIfSSIDCfgEntry
    MAX-ACCESS not-accessible
    STATUS current
    DESCRIPTION
        "The table describe the SSID cofiguration of radio interface."
    ::= { apSSIDCfg 2 }

apRadioIfSSIDCfgEntry OBJECT-TYPE
    SYNTAX ApRadioIfSSIDCfgEntry
    MAX-ACCESS not-accessible
    STATUS current
    DESCRIPTION
        "The entry of cmApSSIDCfgTable."
    INDEX
    { ifIndex,apWlanId }
    ::= { apRadioIfSSIDCfgTable 1 }

ApRadioIfSSIDCfgEntry ::=
    SEQUENCE {
        apBSSID         MacAddress
    } 
  
apBSSID OBJECT-TYPE
    SYNTAX MacAddress
    MAX-ACCESS read-only
    STATUS current
    DESCRIPTION
        "virtual BSSID."
    ::= { apRadioIfSSIDCfgEntry 1 }   
    
    
--**************************************************
--* apRadioIfSSIDCfgTable ends
--**************************************************

--**************************************************
--* apSSIDCfgTable begins
--**************************************************
apSSIDCfgTable OBJECT-TYPE
    SYNTAX SEQUENCE OF ApSSIDCfgEntry
    MAX-ACCESS not-accessible
    STATUS current
    DESCRIPTION
        "The table describe the SSID cofiguration of radio interface."
    ::= { apSSIDCfg 3 }

apSSIDCfgEntry OBJECT-TYPE
    SYNTAX ApSSIDCfgEntry
    MAX-ACCESS not-accessible
    STATUS current
    DESCRIPTION
        "The entry of apSSIDCfgTable."
    INDEX { apWlanId }
    ::= { apSSIDCfgTable 1 }

ApSSIDCfgEntry ::=
    SEQUENCE {
        apWlanId								INTEGER,
        apSSIDName              DisplayString,
        apSSIDEnabled           TruthValue,
        apSSIDHidden            TruthValue,
        apStaIsolate            TruthValue,
        apDot11Auth             INTEGER,
        apSecurity              INTEGER,
        apAuthenMode            INTEGER,
        apSecurityCiphers       INTEGER,
        apVlanId                INTEGER,
        apMaxSimultUsers        Integer32,
        apStaUplinkMaxRate      Integer32,
        apStaDwlinkMaxRate      Integer32,
        apSSIDCfgStatus		RowStatus
    } 
    
apWlanId OBJECT-TYPE               
    SYNTAX INTEGER               
    MAX-ACCESS read-only               
    STATUS current               
    DESCRIPTION               
        "The index of the table."               
    ::= { apSSIDCfgEntry 1 }   
      
apSSIDName OBJECT-TYPE               
    SYNTAX DisplayString               
    MAX-ACCESS read-create               
    STATUS current               
    DESCRIPTION               
        "SSID Name."               
    ::= { apSSIDCfgEntry 2 }   
    
apSSIDEnabled OBJECT-TYPE         
    SYNTAX TruthValue       
    MAX-ACCESS read-create       
    STATUS current             
    DESCRIPTION                
        "whether to enable SSID."           
    ::= { apSSIDCfgEntry 3 } 

apSSIDHidden OBJECT-TYPE         
    SYNTAX TruthValue 
    MAX-ACCESS read-create       
    STATUS current             
    DESCRIPTION                
        "Whether to broadcast SSID."           
    ::= { apSSIDCfgEntry 4 } 
            
apStaIsolate OBJECT-TYPE         
    SYNTAX TruthValue       
    MAX-ACCESS read-create       
    STATUS current             
    DESCRIPTION                
        "Whether to isolate SSID."           
    ::= { apSSIDCfgEntry 5 }
    
apDot11Auth OBJECT-TYPE         
    SYNTAX INTEGER       
    MAX-ACCESS read-create       
    STATUS current             
    DESCRIPTION                
        "802.11 authentication."           
    ::= { apSSIDCfgEntry 6 }   
    
apSecurity OBJECT-TYPE         
    SYNTAX INTEGER       
    MAX-ACCESS read-create       
    STATUS current             
    DESCRIPTION                
        "security type."           
    ::= { apSSIDCfgEntry 7 } 
    
apAuthenMode OBJECT-TYPE         
    SYNTAX INTEGER       
    MAX-ACCESS read-create       
    STATUS current             
    DESCRIPTION                
        "authentication mode."           
    ::= { apSSIDCfgEntry 8 }          
    
apSecurityCiphers OBJECT-TYPE         
    SYNTAX INTEGER {       
          none(0),
          wep40(1),
          wep104(2),
          tkip(3),
          aesccmp(4),
          wapisms4(5)
    }
    MAX-ACCESS read-create       
    STATUS current             
    DESCRIPTION                
        "encryption type."           
    ::= { apSSIDCfgEntry 9 }          
    
apVlanId OBJECT-TYPE         
    SYNTAX INTEGER       
    MAX-ACCESS read-create       
    STATUS current             
    DESCRIPTION                
        "vlan id."           
    ::= { apSSIDCfgEntry 10 } 
    
apMaxSimultUsers OBJECT-TYPE         
    SYNTAX Integer32       
    MAX-ACCESS read-create       
    STATUS current             
    DESCRIPTION                
        "The max supported users."           
    ::= { apSSIDCfgEntry 11 }     
        
apStaUplinkMaxRate OBJECT-TYPE         
    SYNTAX Integer32       
    MAX-ACCESS read-create       
    STATUS current             
    DESCRIPTION                
        "The max up-lind speed for terminal."           
    ::= { apSSIDCfgEntry 12 }     

apStaDwlinkMaxRate OBJECT-TYPE         
    SYNTAX Integer32       
    MAX-ACCESS read-create       
    STATUS current             
    DESCRIPTION                
        "The max down-lind speed for terminal."           
    ::= { apSSIDCfgEntry 13 } 
    
apSSIDCfgStatus OBJECT-TYPE         
    SYNTAX RowStatus       
    MAX-ACCESS read-create       
    STATUS current             
    DESCRIPTION                
        "The status column used for creating and
         deleting instances of the columnar objects in the table."           
    ::= { apSSIDCfgEntry 14 }    
                          
    

--**************************************************
--* apSSIDCfgTable ends
--**************************************************

    
--**************************************************
--* apSSIDCfg end here
--************************************************** 



--**************************************************
--* apSecurityCfg start here
--************************************************** 

--**************************************************
--* cmApSecurityCfgTable begins
--**************************************************
apSecurityCfgTable OBJECT-TYPE
    SYNTAX SEQUENCE OF ApSecurityCfgEntry
    MAX-ACCESS not-accessible
    STATUS current
    DESCRIPTION
        "The table discribe the security configuration of the AP"
    ::= { apSecurityCfg 1 }

apSecurityCfgEntry OBJECT-TYPE
    SYNTAX ApSecurityCfgEntry
    MAX-ACCESS not-accessible
    STATUS current
    DESCRIPTION
        "The entry of apSecurityCfgTable."
    INDEX
    { apWlanId }
    ::= { apSecurityCfgTable 1 }

ApSecurityCfgEntry ::=
    SEQUENCE {
        apWEPCipherKeyIndex              INTEGER,
        apWEPCipherKeyValue              DisplayString,
        apWEPCipherKeyCharType           INTEGER,
        apPSKCipherKeyValue              DisplayString,
        apPSKCipherKeyCharType           INTEGER,
        apWAPIASIPAddress                IpAddress,
        apWAPIIsInstalledCer             TruthValue
    } 
  
apWEPCipherKeyIndex OBJECT-TYPE               
    SYNTAX INTEGER               
    MAX-ACCESS read-write              
    STATUS current               
    DESCRIPTION               
        "WEP cipher key index."               
    ::= { apSecurityCfgEntry 1 } 
    
apWEPCipherKeyValue OBJECT-TYPE               
    SYNTAX DisplayString               
    MAX-ACCESS read-write              
    STATUS current               
    DESCRIPTION               
        "WEP Cipher key value."               
    ::= { apSecurityCfgEntry 2 }     
    
apWEPCipherKeyCharType OBJECT-TYPE               
    SYNTAX INTEGER               
    MAX-ACCESS read-write              
    STATUS current               
    DESCRIPTION               
        "WEP Cipher key char type."               
    ::= { apSecurityCfgEntry 3 } 
    
apPSKCipherKeyValue OBJECT-TYPE               
    SYNTAX DisplayString               
    MAX-ACCESS read-write              
    STATUS current               
    DESCRIPTION               
        "PSK Cipher key value."               
    ::= { apSecurityCfgEntry 4 }
    
apPSKCipherKeyCharType OBJECT-TYPE               
    SYNTAX INTEGER               
    MAX-ACCESS read-write              
    STATUS current               
    DESCRIPTION               
        "PSK Cipher key value."               
    ::= { apSecurityCfgEntry 5}
    
apWAPIASIPAddress OBJECT-TYPE               
    SYNTAX IpAddress               
    MAX-ACCESS read-write              
    STATUS current               
    DESCRIPTION               
        "IP address of WAPI AS."               
    ::= { apSecurityCfgEntry 6}        
    
apWAPIIsInstalledCer OBJECT-TYPE               
    SYNTAX TruthValue               
    MAX-ACCESS read-only              
    STATUS current               
    DESCRIPTION               
        "Is Certificate installed."               
    ::= { apSecurityCfgEntry 7} 
         
       
--**************************************************
--* apSecurityCfgTable end here
--************************************************** 


--**************************************************
--* apSecurityCfg end here
--************************************************** 


--**************************************************
--* apTerminalCfg start here
--************************************************** 

--**************************************************
--* cmApTerminalInfoTable begins
--**************************************************
apTerminalInfoTable OBJECT-TYPE
    SYNTAX SEQUENCE OF ApTerminalInfoEntry
    MAX-ACCESS not-accessible
    STATUS current
    DESCRIPTION
        "The table discribe the security configuration of the AP"
    ::= { apTerminalCfg 1 }

apTerminalInfoEntry OBJECT-TYPE
    SYNTAX ApTerminalInfoEntry
    MAX-ACCESS not-accessible
    STATUS current
    DESCRIPTION
        "The entry of apSecurityCfgTable."
    INDEX { apStaMAC }
    ::= { apTerminalInfoTable 1 }

ApTerminalInfoEntry ::=
    SEQUENCE {
        apStaMAC                         MacAddress,
        apStaWMMAttr										 INTEGER,
        apStaIPAddress                   IpAddress,
        apStaRadioMode                   INTEGER,
        apStaRadioChannel                INTEGER,
        apStaTxRates                     INTEGER,
        apStaPowerSaveMode               INTEGER,
        apStaVlanId                      Integer32,
        apStaSSIDName                    DisplayString,
        apStaDot11Auth                   INTEGER,
        apStaSecurity                    INTEGER,
        apStaAuthenMode                  INTEGER,
        apStaSecurityCiphers             INTEGER
    } 
    
apStaMAC OBJECT-TYPE               
    SYNTAX MacAddress               
    MAX-ACCESS read-only              
    STATUS current               
    DESCRIPTION               
        "The MAC address of the termal."               
    ::= { apTerminalInfoEntry 1 } 
    
apStaWMMAttr OBJECT-TYPE               
    SYNTAX INTEGER               
    MAX-ACCESS read-only              
    STATUS current               
    DESCRIPTION               
        "VMM attribute of the terminal."               
    ::= { apTerminalInfoEntry 2 }    
    
apStaIPAddress OBJECT-TYPE               
    SYNTAX IpAddress               
    MAX-ACCESS read-only              
    STATUS current               
    DESCRIPTION               
        "IP address of the terminal."               
    ::= { apTerminalInfoEntry 3 }  
    
apStaRadioMode OBJECT-TYPE               
    SYNTAX INTEGER               
    MAX-ACCESS read-only              
    STATUS current               
    DESCRIPTION               
        "radio mode of the terminal."               
    ::= { apTerminalInfoEntry 4 }
    
apStaRadioChannel OBJECT-TYPE               
    SYNTAX INTEGER               
    MAX-ACCESS read-only              
    STATUS current               
    DESCRIPTION               
        "Radio channel of the terminal."               
    ::= { apTerminalInfoEntry 5 }         
        
apStaTxRates OBJECT-TYPE               
    SYNTAX INTEGER               
    MAX-ACCESS read-only              
    STATUS current               
    DESCRIPTION               
        "Current rate of the terminal."               
    ::= { apTerminalInfoEntry 6 }  
    
apStaPowerSaveMode OBJECT-TYPE               
    SYNTAX INTEGER               
    MAX-ACCESS read-only              
    STATUS current               
    DESCRIPTION               
        "Power save mode of the terminal"               
    ::= { apTerminalInfoEntry 7 } 
    
apStaVlanId OBJECT-TYPE               
    SYNTAX Integer32               
    MAX-ACCESS read-only              
    STATUS current               
    DESCRIPTION               
        "Vlan id where the terminal located."               
    ::= { apTerminalInfoEntry 8 }   
    
apStaSSIDName OBJECT-TYPE               
    SYNTAX DisplayString               
    MAX-ACCESS read-only              
    STATUS current               
    DESCRIPTION               
        "SSID name."               
    ::= { apTerminalInfoEntry 9 }  
    
    
apStaDot11Auth OBJECT-TYPE               
    SYNTAX INTEGER               
    MAX-ACCESS read-only              
    STATUS current               
    DESCRIPTION               
        "802.11 authentication."               
    ::= { apTerminalInfoEntry 10 }     
    
apStaSecurity OBJECT-TYPE               
    SYNTAX INTEGER               
    MAX-ACCESS read-only              
    STATUS current               
    DESCRIPTION               
        "Security type."               
    ::= { apTerminalInfoEntry 11 }      
      
apStaAuthenMode OBJECT-TYPE               
    SYNTAX INTEGER               
    MAX-ACCESS read-only              
    STATUS current               
    DESCRIPTION               
        "authentication mdoe."               
    ::= { apTerminalInfoEntry 12 }
    
    
apStaSecurityCiphers OBJECT-TYPE               
    SYNTAX INTEGER               
    MAX-ACCESS read-only              
    STATUS current               
    DESCRIPTION               
        "Encryption mode."               
    ::= { apTerminalInfoEntry 13 } 
    
    
--**************************************************
--* apTerminalInfoTable ends
--**************************************************
    
                                   
--**************************************************
--* apTerminalCfg end here
--************************************************** 

--**************************************************
--* apQosCfg begin here
--**************************************************


 
--**************************************************
--* cmApQosRadioIfCfgTable begins
--**************************************************
apQosRadioIfCfgTable OBJECT-TYPE
    SYNTAX SEQUENCE OF ApQosRadioIfCfgEntry
    MAX-ACCESS not-accessible
    STATUS current
    DESCRIPTION
        "The table discribe radio interface configuration information of QOS"
    ::= { apQosCfg 1 }

apQosRadioIfCfgEntry OBJECT-TYPE
    SYNTAX ApQosRadioIfCfgEntry
    MAX-ACCESS not-accessible
    STATUS current
    DESCRIPTION
        "The entry of apQosRadioIfCfgTable."
    INDEX { ifIndex, apQoSTrafficClassIndex}
    ::= { apQosRadioIfCfgTable 1 }

ApQosRadioIfCfgEntry ::=
    SEQUENCE {
        apQoSTrafficClassIndex                 INTEGER,
        apQosAIFS			          							 INTEGER,
        apQoSCWmin                             INTEGER,
        apQoSCWmax                             INTEGER,
        apQoSTXOPLim                           INTEGER
        }                                    
  
apQoSTrafficClassIndex OBJECT-TYPE               
    SYNTAX INTEGER {
        bestEffort(0),
        background(1),
        video(2),
        voice(3)
    }
    MAX-ACCESS read-only              
    STATUS current               
    DESCRIPTION               
        "ap QOS Service type 0:bestEffort  1:background  2:video  3:voice."               
    ::= { apQosRadioIfCfgEntry 1 } 
 
apQosAIFS OBJECT-TYPE               
    SYNTAX INTEGER               
    MAX-ACCESS read-write              
    STATUS current               
    DESCRIPTION               
        "AIFS."               
    ::= { apQosRadioIfCfgEntry 2 } 
    
apQoSCWmin OBJECT-TYPE               
    SYNTAX INTEGER               
    MAX-ACCESS read-write              
    STATUS current               
    DESCRIPTION               
        "CW Min."               
    ::= { apQosRadioIfCfgEntry 3 } 

apQoSCWmax OBJECT-TYPE               
    SYNTAX INTEGER               
    MAX-ACCESS read-write              
    STATUS current               
    DESCRIPTION               
        "CW Max."               
    ::= { apQosRadioIfCfgEntry 4 } 
    
apQoSTXOPLim OBJECT-TYPE               
    SYNTAX INTEGER               
    MAX-ACCESS read-write              
    STATUS current               
    DESCRIPTION               
        "TXOP Limit."               
    ::= { apQosRadioIfCfgEntry 5 } 

--**************************************************
--* apQosRadioIfCfgTable ends
--**************************************************



--**************************************************
--* apQosBaseCfgTable begins
--**************************************************
apQosBaseCfgTable OBJECT-TYPE
    SYNTAX SEQUENCE OF ApQosBaseCfgEntry
    MAX-ACCESS not-accessible
    STATUS current
    DESCRIPTION
        "The table discribe basic performance configuration information of QOS"
    ::= { apQosCfg 2 }

apQosBaseCfgEntry OBJECT-TYPE
    SYNTAX ApQosBaseCfgEntry
    MAX-ACCESS not-accessible
    STATUS current
    DESCRIPTION
        "The entry of apQosBaseCfgTable."
    INDEX { ifIndex }
    ::= { apQosBaseCfgTable 1 }

ApQosBaseCfgEntry ::=
    SEQUENCE {
        apQoSBaseTrafficClass                  INTEGER,
        apQoSEnabled													 TruthValue,
        apQoSBW																 Integer32,
        apQoSResPercent                        Integer32,
        apQoSsharedBW                          Integer32,
        apQoSsharedBWPercent                   Integer32,
        apSchedAlgName                         DisplayString,
        apResPolicyEnabled                     TruthValue,
        apResPolicyName                        DisplayString,
        apBackgroundSvcAvgSpeed                Integer32,
        apBackgroundSvcMaxBurst                Integer32,
        apBackgroundSvcPriority                Integer32,
        apBackgroundSvcResPriority             Integer32,
        apBestEffortSvcAvgSpeed                Integer32,
        apBestEffortSvcMaxBurst                Integer32,
        apBestEffortSvcPriority                Integer32,
        apBestEffortSvcResPriority             Integer32,
        apVoiceSvcAvgSpeed                     Integer32,
        apVoiceSvcMaxBurst                     Integer32,
        apVoiceSvcPriority                     Integer32,
        apVoiceSvcResPriority                  Integer32,
        apVideoSvcAvgSpeed                     Integer32,
        apVideoSvcMaxBurst                     Integer32,
        apVideoSvcPriority                     Integer32,
        apVideoSvcResPriority                  Integer32
        } 
  
apQoSBaseTrafficClass OBJECT-TYPE               
    SYNTAX INTEGER               
    MAX-ACCESS read-write              
    STATUS current               
    DESCRIPTION               
        "Provide QoS service type."               
    ::= { apQosBaseCfgEntry 1 } 
    
apQoSEnabled OBJECT-TYPE               
    SYNTAX TruthValue               
    MAX-ACCESS read-write              
    STATUS current               
    DESCRIPTION               
        "Is QoS enabled."               
    ::= { apQosBaseCfgEntry 2 }     
        
apQoSBW OBJECT-TYPE          
    SYNTAX Integer32               
    MAX-ACCESS read-write           
    STATUS current                  
    DESCRIPTION                     
        "Total bandwidth of QoS server." 
    ::= { apQosBaseCfgEntry 3 }   
    
apQoSResPercent OBJECT-TYPE          
    SYNTAX Integer32               
    MAX-ACCESS read-write           
    STATUS current                  
    DESCRIPTION                     
        "Qos resource percentage." 
    ::= { apQosBaseCfgEntry 4 }       
    
apQoSsharedBW OBJECT-TYPE          
    SYNTAX Integer32               
    MAX-ACCESS read-write           
    STATUS current                  
    DESCRIPTION                     
        "Qos shared bandwidth." 
    ::= { apQosBaseCfgEntry 5 }     
    
apQoSsharedBWPercent OBJECT-TYPE          
    SYNTAX Integer32               
    MAX-ACCESS read-write           
    STATUS current                  
    DESCRIPTION                     
        "Qos shared bandwidth percentage" 
    ::= { apQosBaseCfgEntry 6 }         													 
        																 
apSchedAlgName OBJECT-TYPE          
    SYNTAX DisplayString               
    MAX-ACCESS read-write           
    STATUS current                  
    DESCRIPTION                     
        "The scheduling algorithm between different Qos service." 
    ::= { apQosBaseCfgEntry 7 } 
    
apResPolicyEnabled OBJECT-TYPE          
    SYNTAX TruthValue               
    MAX-ACCESS read-write           
    STATUS current                  
    DESCRIPTION                     
        "Is resource Policy enabled." 
    ::= { apQosBaseCfgEntry 8 }                                  
                           
apResPolicyName OBJECT-TYPE          
    SYNTAX DisplayString               
    MAX-ACCESS read-write           
    STATUS current                  
    DESCRIPTION                     
        "the name of resource occupy policy." 
    ::= { apQosBaseCfgEntry 9 }                                   
                             
apBackgroundSvcAvgSpeed OBJECT-TYPE          
    SYNTAX Integer32               
    MAX-ACCESS read-write           
    STATUS current                  
    DESCRIPTION                     
        "Avearage speed of background service." 
    ::= { apQosBaseCfgEntry 10 } 
    
apBackgroundSvcMaxBurst OBJECT-TYPE          
    SYNTAX Integer32               
    MAX-ACCESS read-write           
    STATUS current                  
    DESCRIPTION                     
        "The max burst of background service." 
    ::= { apQosBaseCfgEntry 11 }     
    
apBackgroundSvcPriority OBJECT-TYPE          
    SYNTAX Integer32               
    MAX-ACCESS read-write           
    STATUS current                  
    DESCRIPTION                     
        "Schedule priority of background service." 
    ::= { apQosBaseCfgEntry 12 }
    
apBackgroundSvcResPriority OBJECT-TYPE          
    SYNTAX Integer32               
    MAX-ACCESS read-write           
    STATUS current                  
    DESCRIPTION                     
        "Resource occupy priority of background service." 
    ::= { apQosBaseCfgEntry 13 }    
                                        
apBestEffortSvcAvgSpeed OBJECT-TYPE          
    SYNTAX Integer32               
    MAX-ACCESS read-write           
    STATUS current                  
    DESCRIPTION                     
        "Avearage speed of BestEffort service." 
    ::= { apQosBaseCfgEntry 14 } 

apBestEffortSvcMaxBurst OBJECT-TYPE          
    SYNTAX Integer32               
    MAX-ACCESS read-write           
    STATUS current                  
    DESCRIPTION                     
        "The max burst of BestEffort service." 
    ::= { apQosBaseCfgEntry 15 } 
    
apBestEffortSvcPriority OBJECT-TYPE          
    SYNTAX Integer32               
    MAX-ACCESS read-write           
    STATUS current                  
    DESCRIPTION                     
        "Schedule priority of BestEffort service." 
    ::= { apQosBaseCfgEntry 16 } 
    
apBestEffortSvcResPriority OBJECT-TYPE          
    SYNTAX Integer32               
    MAX-ACCESS read-write           
    STATUS current                  
    DESCRIPTION                     
        "Resource occupy priority of BestEffort service." 
    ::= { apQosBaseCfgEntry 17 }  
    
    
apVoiceSvcAvgSpeed OBJECT-TYPE          
    SYNTAX Integer32               
    MAX-ACCESS read-write           
    STATUS current                  
    DESCRIPTION                     
        "Avearage speed of voice service." 
    ::= { apQosBaseCfgEntry 18 }     
    
apVoiceSvcMaxBurst OBJECT-TYPE          
    SYNTAX Integer32               
    MAX-ACCESS read-write           
    STATUS current                  
    DESCRIPTION                     
        "The max burst of voice service." 
    ::= { apQosBaseCfgEntry 19 }   
    
apVoiceSvcPriority OBJECT-TYPE          
    SYNTAX Integer32               
    MAX-ACCESS read-write           
    STATUS current                  
    DESCRIPTION                     
        "Schedule priority of voice service." 
    ::= { apQosBaseCfgEntry 20 }      
    
    
apVoiceSvcResPriority OBJECT-TYPE          
    SYNTAX Integer32               
    MAX-ACCESS read-write           
    STATUS current                  
    DESCRIPTION                     
        "Resource occupy priority of voice service." 
    ::= { apQosBaseCfgEntry 21 }  
    
apVideoSvcAvgSpeed OBJECT-TYPE          
    SYNTAX Integer32               
    MAX-ACCESS read-write           
    STATUS current                  
    DESCRIPTION                     
        "Avearage speed of Video service." 
    ::= { apQosBaseCfgEntry 22 }      
       
apVideoSvcMaxBurst OBJECT-TYPE          
    SYNTAX Integer32               
    MAX-ACCESS read-write           
    STATUS current                  
    DESCRIPTION                     
        "The max burst of Video service." 
    ::= { apQosBaseCfgEntry 23 }   
    
    
apVideoSvcPriority OBJECT-TYPE          
    SYNTAX Integer32               
    MAX-ACCESS read-write           
    STATUS current                  
    DESCRIPTION                     
        "Schedule priority of Video service." 
    ::= { apQosBaseCfgEntry 24 }
    
apVideoSvcResPriority OBJECT-TYPE          
    SYNTAX Integer32               
    MAX-ACCESS read-write           
    STATUS current                  
    DESCRIPTION                     
        "Resource occupy priority of Video service." 
    ::= { apQosBaseCfgEntry 25 }      
                                
    
--**************************************************
--* apQosBaseCfgTable ends
--**************************************************

--**************************************************
--* cmApQosBackgroundCfgTable begins
--**************************************************
apQosBackgroundCfgTable OBJECT-TYPE
    SYNTAX SEQUENCE OF ApQosBackgroundCfgEntry
    MAX-ACCESS not-accessible
    STATUS current
    DESCRIPTION
        "The table discribe the QoS performance 
        configuration of Background QoS service."
    ::= { apQosCfg 3 }

apQosBackgroundCfgEntry OBJECT-TYPE
    SYNTAX ApQosBackgroundCfgEntry
    MAX-ACCESS not-accessible
    STATUS current
    DESCRIPTION
        "The entry of apQosBackgroundCfgTable."
    INDEX
    { ifIndex }
    ::= { apQosBackgroundCfgTable 1 }

ApQosBackgroundCfgEntry ::=
    SEQUENCE {
        apBgMaxSvcCnt                 Integer32,
        apBgSvcBW                     Integer32,
        apBgSvcBWPercent              Integer32,  
        apBgIsUseWREDAlg              TruthValue,
        apBgIsUseTrafficShaping       TruthValue
        }                             
  
apBgMaxSvcCnt OBJECT-TYPE               
    SYNTAX Integer32               
    MAX-ACCESS read-write              
    STATUS current               
    DESCRIPTION               
        "The max Concurrence of the service."               
    ::= { apQosBackgroundCfgEntry 1 } 

apBgSvcBW OBJECT-TYPE               
    SYNTAX Integer32               
    MAX-ACCESS read-write              
    STATUS current               
    DESCRIPTION               
        "The bandwidth distributed by the service."               
    ::= { apQosBackgroundCfgEntry 2 } 
    
apBgSvcBWPercent OBJECT-TYPE               
    SYNTAX Integer32               
    MAX-ACCESS read-write              
    STATUS current               
    DESCRIPTION               
        "The service-distribute bandwidth percentage."               
    ::= { apQosBackgroundCfgEntry 3 } 

apBgIsUseWREDAlg OBJECT-TYPE               
    SYNTAX TruthValue               
    MAX-ACCESS read-write              
    STATUS current               
    DESCRIPTION               
        "Is WRED algorithm used?"               
    ::= { apQosBackgroundCfgEntry 4 }
    
apBgIsUseTrafficShaping OBJECT-TYPE               
    SYNTAX TruthValue               
    MAX-ACCESS read-write              
    STATUS current               
    DESCRIPTION               
        "Is traffic shaping used?"               
    ::= { apQosBackgroundCfgEntry 5 }
     
    
    
--**************************************************
--* apQosBackgroundCfgTable ends
--**************************************************

--**************************************************
--* apQosBestEffortCfgTable begins
--**************************************************
apQosBestEffortCfgTable OBJECT-TYPE
    SYNTAX SEQUENCE OF ApQosBestEffortCfgEntry
    MAX-ACCESS not-accessible
    STATUS current
    DESCRIPTION
        "The table discribe the QoS performance 
        configuration of BestEffort QoS service."
    ::= { apQosCfg 4 }

apQosBestEffortCfgEntry OBJECT-TYPE
    SYNTAX ApQosBestEffortCfgEntry
    MAX-ACCESS not-accessible
    STATUS current
    DESCRIPTION
        "The entry of apQosBestEffortCfgTable."
    INDEX
    { ifIndex }
    ::= { apQosBestEffortCfgTable 1 }

ApQosBestEffortCfgEntry ::=
    SEQUENCE {
        apBeMaxSvcCnt                 Integer32,
        apBeSvcBW                     Integer32,
        apBeSvcBWPercent              Integer32,  
        apBeIsUseWREDAlg              TruthValue,
        apBeIsUseTrafficShaping       TruthValue
        }                             
  
apBeMaxSvcCnt OBJECT-TYPE               
    SYNTAX Integer32               
    MAX-ACCESS read-write              
    STATUS current               
    DESCRIPTION               
        "The max Concurrence of the service."               
    ::= { apQosBestEffortCfgEntry 1 } 

apBeSvcBW OBJECT-TYPE               
    SYNTAX Integer32               
    MAX-ACCESS read-write              
    STATUS current               
    DESCRIPTION               
        "The bandwidth distributed by the service."               
    ::= { apQosBestEffortCfgEntry 2 } 
    
apBeSvcBWPercent OBJECT-TYPE               
    SYNTAX Integer32               
    MAX-ACCESS read-write              
    STATUS current               
    DESCRIPTION               
        "The service-distribute bandwidth percentage."               
    ::= { apQosBestEffortCfgEntry 3 } 

apBeIsUseWREDAlg OBJECT-TYPE               
    SYNTAX TruthValue               
    MAX-ACCESS read-write              
    STATUS current               
    DESCRIPTION               
        "Is WRED algorithm used?"               
    ::= { apQosBestEffortCfgEntry 4 }
    
apBeIsUseTrafficShaping OBJECT-TYPE               
    SYNTAX TruthValue               
    MAX-ACCESS read-write              
    STATUS current               
    DESCRIPTION               
        "Is traffic shaping used?"               
    ::= { apQosBestEffortCfgEntry 5 }


--**************************************************
--* apQosBestEffortCfgTable ends
--**************************************************

--**************************************************
--* cmApQosVoiceCfgTable begins
--**************************************************
apQosVoiceCfgTable OBJECT-TYPE
    SYNTAX SEQUENCE OF ApQosVoiceCfgEntry
    MAX-ACCESS not-accessible
    STATUS current
    DESCRIPTION
        "The table discribe the QoS performance 
        configuration of Voice QoS service."
    ::= { apQosCfg 5 }

apQosVoiceCfgEntry OBJECT-TYPE
    SYNTAX ApQosVoiceCfgEntry
    MAX-ACCESS not-accessible
    STATUS current
    DESCRIPTION
        "The entry of apQosVoiceCfgTable."
    INDEX
    { ifIndex }
    ::= { apQosVoiceCfgTable 1 }

ApQosVoiceCfgEntry ::=
    SEQUENCE {
        apVoiceMaxSvcCnt                 Integer32,
        apVoiceSvcBW                     Integer32,
        apVoiceSvcBWPercent              Integer32, 
        apVoiceIsUseStreamBasedQueue       TruthValue,
        apVoiceStreamMaxQueueLen           Integer32,
        apVoiceStreamAvgSpeed              Integer32,
        apVoiceStreamMaxBurst              Integer32,
        apVoiceIsUseWREDAlg                TruthValue,
        apVoiceIsUseTrafficShaping         TruthValue
        }                             
  
apVoiceMaxSvcCnt OBJECT-TYPE               
    SYNTAX Integer32               
    MAX-ACCESS read-write              
    STATUS current               
    DESCRIPTION               
        "The max Concurrence of the service."               
    ::= { apQosVoiceCfgEntry 1 } 

apVoiceSvcBW OBJECT-TYPE               
    SYNTAX Integer32               
    MAX-ACCESS read-write              
    STATUS current               
    DESCRIPTION               
        "The bandwidth distributed by the service."               
    ::= { apQosVoiceCfgEntry 2 } 
    
apVoiceSvcBWPercent OBJECT-TYPE               
    SYNTAX Integer32               
    MAX-ACCESS read-write              
    STATUS current               
    DESCRIPTION               
        "The service-distribute bandwidth percentage."               
    ::= { apQosVoiceCfgEntry 3 } 

apVoiceIsUseStreamBasedQueue OBJECT-TYPE               
    SYNTAX TruthValue               
    MAX-ACCESS read-write              
    STATUS current               
    DESCRIPTION               
        "Is stream baseed queue used?"               
    ::= { apQosVoiceCfgEntry 4 }
    
apVoiceStreamMaxQueueLen OBJECT-TYPE               
    SYNTAX Integer32               
    MAX-ACCESS read-write              
    STATUS current               
    DESCRIPTION               
        "Is stream max queue used?"               
    ::= { apQosVoiceCfgEntry 5 }
    
apVoiceStreamAvgSpeed OBJECT-TYPE               
    SYNTAX Integer32               
    MAX-ACCESS read-write              
    STATUS current               
    DESCRIPTION               
        "The avearage speed of the stream"               
    ::= { apQosVoiceCfgEntry 6 }
   
apVoiceStreamMaxBurst OBJECT-TYPE               
    SYNTAX Integer32               
    MAX-ACCESS read-write              
    STATUS current               
    DESCRIPTION               
        "The max burst of the stream"               
    ::= { apQosVoiceCfgEntry 7 }
    
apVoiceIsUseWREDAlg OBJECT-TYPE               
    SYNTAX TruthValue               
    MAX-ACCESS read-write              
    STATUS current               
    DESCRIPTION               
        "Is WRED algorithm used?"               
    ::= { apQosVoiceCfgEntry 8 }
    
apVoiceIsUseTrafficShaping OBJECT-TYPE               
    SYNTAX TruthValue               
    MAX-ACCESS read-write              
    STATUS current               
    DESCRIPTION               
        "Is traffic shaping used?"               
    ::= { apQosVoiceCfgEntry 9 }
    
--**************************************************
--* apQosVoiceCfgTable ends
--**************************************************

--**************************************************
--* apQosVedioCfgTable begins
--**************************************************
apQosVedioCfgTable OBJECT-TYPE
    SYNTAX SEQUENCE OF ApQosVedioCfgEntry
    MAX-ACCESS not-accessible
    STATUS current
    DESCRIPTION
        "The table discribe the QoS performance 
        configuration of Vedio QoS service."
    ::= { apQosCfg 6 }

apQosVedioCfgEntry OBJECT-TYPE
    SYNTAX ApQosVedioCfgEntry
    MAX-ACCESS not-accessible
    STATUS current
    DESCRIPTION
        "The entry of apQosVedioCfgTable."
    INDEX
    { ifIndex }
    ::= { apQosVedioCfgTable 1 }

ApQosVedioCfgEntry ::=
    SEQUENCE {
        apVedioMaxSvcCnt                 Integer32,
        apVedioSvcBW                     Integer32,
        apVedioSvcBWPercent              Integer32, 
        apVedioIsUseStreamBasedQueue       TruthValue,
        apVedioStreamMaxQueueLen           Integer32,
        apVedioStreamAvgSpeed              Integer32,
        apVedioStreamMaxBurst              Integer32,
        apVedioIsUseWREDAlg                TruthValue,
        apVedioIsUseTrafficShaping         TruthValue
        }                             
  
apVedioMaxSvcCnt OBJECT-TYPE               
    SYNTAX Integer32               
    MAX-ACCESS read-write              
    STATUS current               
    DESCRIPTION               
        "The max Concurrence of the service."               
    ::= { apQosVedioCfgEntry 1 } 

apVedioSvcBW OBJECT-TYPE               
    SYNTAX Integer32               
    MAX-ACCESS read-write              
    STATUS current               
    DESCRIPTION               
        "The bandwidth distributed by the service."               
    ::= { apQosVedioCfgEntry 2 } 
    
apVedioSvcBWPercent OBJECT-TYPE               
    SYNTAX Integer32               
    MAX-ACCESS read-write              
    STATUS current               
    DESCRIPTION               
        "The service-distribute bandwidth percentage."               
    ::= { apQosVedioCfgEntry 3 } 

apVedioIsUseStreamBasedQueue OBJECT-TYPE               
    SYNTAX TruthValue               
    MAX-ACCESS read-write              
    STATUS current               
    DESCRIPTION               
        "Is stream baseed queue used?"               
    ::= { apQosVedioCfgEntry 4 }
    
apVedioStreamMaxQueueLen OBJECT-TYPE               
    SYNTAX Integer32               
    MAX-ACCESS read-write              
    STATUS current               
    DESCRIPTION               
        "Is stream max queue used?"               
    ::= { apQosVedioCfgEntry 5 }
    
apVedioStreamAvgSpeed OBJECT-TYPE               
    SYNTAX Integer32               
    MAX-ACCESS read-write              
    STATUS current               
    DESCRIPTION               
        "The avearage speed of the stream"               
    ::= { apQosVedioCfgEntry 6 }
   
apVedioStreamMaxBurst OBJECT-TYPE               
    SYNTAX Integer32               
    MAX-ACCESS read-write              
    STATUS current               
    DESCRIPTION               
        "The max burst of the stream"               
    ::= { apQosVedioCfgEntry 7 }
    
apVedioIsUseWREDAlg OBJECT-TYPE               
    SYNTAX TruthValue               
    MAX-ACCESS read-write              
    STATUS current               
    DESCRIPTION               
        "Is WRED algorithm used?"               
    ::= { apQosVedioCfgEntry 8 }
    
apVedioIsUseTrafficShaping OBJECT-TYPE               
    SYNTAX TruthValue               
    MAX-ACCESS read-write              
    STATUS current               
    DESCRIPTION               
        "Is traffic shaping used?"               
    ::= { apQosVedioCfgEntry 9 }
    
--**************************************************
--* apQosVedioCfgTable ends
--**************************************************

--**************************************************
--* apQosCfg end here
--************************************************** 


--**************************************************
--* apWapiCfg start here
--************************************************** 

--**************************************************
--* apWapiProtocolCfgTable begins
--**************************************************
apWapiProtocolCfgTable OBJECT-TYPE
    SYNTAX SEQUENCE OF ApWapiProtocolCfgEntry
    MAX-ACCESS not-accessible
    STATUS current
    DESCRIPTION
        "The table discribe the WAPI protocol configuration of the AP"
    ::= { apWapiCfg 1 }

apWapiProtocolCfgEntry OBJECT-TYPE
    SYNTAX ApWapiProtocolCfgEntry
    MAX-ACCESS not-accessible
    STATUS current
    DESCRIPTION
        "The entry of apWapiProtocolCfgTable."
    INDEX
    { apWlanId }
    ::= { apWapiProtocolCfgTable 1 }

ApWapiProtocolCfgEntry ::=
    SEQUENCE {
        apConfigVersion                 Integer32,
        apControlledAuthControl         TruthValue,
        apControlledPortControl         INTEGER,
        apWapiOptionImplemented         TruthValue,
        apWapiPreauthImplemented        TruthValue,
        apWapiEnabled                   TruthValue,
        apWapiPreauthEnabled            TruthValue,
        apUnicastKeysSupported          Unsigned32,
        apUnicastRekeyMethod            INTEGER,
        apUnicastRekeyTime              Unsigned32,
        apUnicastRekeyPackets           Unsigned32,        
        apMulticastCipher               OCTET STRING,   
        apMulticastRekeyMethod          INTEGER,
        apMulticastRekeyTime            Unsigned32,
        apMulticastRekeyPackets					Unsigned32,
        apMulticastRekeyStrict					TruthValue,
        apPSKValue											OCTET STRING,
        apPSKPassPhrase									DisplayString,
        apCertificateUpdateCount				Unsigned32,
        apMulticastUpdateCount					Unsigned32,
        apUnicastUpdateCount						Unsigned32,
        apMulticastCipherSize						Unsigned32,
        apBKLifetime										Unsigned32,
        apBKReauthThreshold							Unsigned32,
        apSATimeout											Unsigned32,
        apAuthSuiteSelected							OCTET STRING,
        apUnicastCipherSelected					OCTET STRING,
        apMulticastCipherSelected       OCTET STRING,
        apBKIDUsed                      OCTET STRING,
        apAuthSuiteRequested            OCTET STRING,
        apUnicastCipherRequested        OCTET STRING,
        apMulticastCipherRequested      OCTET STRING       
        } 
  
apConfigVersion OBJECT-TYPE               
    SYNTAX Integer32               
    MAX-ACCESS read-only              
    STATUS current               
    DESCRIPTION               
        "The highest version the WAPI can support."               
    ::= { apWapiProtocolCfgEntry 1 } 
    
apControlledAuthControl OBJECT-TYPE               
    SYNTAX TruthValue               
    MAX-ACCESS read-only              
    STATUS current               
    DESCRIPTION               
        "Whether to invocate authentication."               
    ::= { apWapiProtocolCfgEntry 2 } 
    
apControlledPortControl OBJECT-TYPE               
    SYNTAX INTEGER               
    MAX-ACCESS read-only              
    STATUS current               
    DESCRIPTION               
        "The control type of the port."               
    ::= { apWapiProtocolCfgEntry 3 } 
    
apWapiOptionImplemented OBJECT-TYPE               
    SYNTAX TruthValue               
    MAX-ACCESS read-only              
    STATUS current               
    DESCRIPTION               
        "Is WAPI supported."               
    ::= { apWapiProtocolCfgEntry 4 } 
    
apWapiPreauthImplemented OBJECT-TYPE               
    SYNTAX TruthValue               
    MAX-ACCESS read-only              
    STATUS current               
    DESCRIPTION               
        "Is WAPI authentication supported."               
    ::= { apWapiProtocolCfgEntry 5 }     
    
apWapiEnabled OBJECT-TYPE               
    SYNTAX TruthValue               
    MAX-ACCESS read-write              
    STATUS current               
    DESCRIPTION               
        "Is WAPI enabled."               
    ::= { apWapiProtocolCfgEntry 6 }   
    
apWapiPreauthEnabled OBJECT-TYPE               
    SYNTAX TruthValue               
    MAX-ACCESS read-write              
    STATUS current               
    DESCRIPTION               
        "Is WAPI authentication enabled."               
    ::= { apWapiProtocolCfgEntry 7 }   
    
apUnicastKeysSupported OBJECT-TYPE               
    SYNTAX Unsigned32               
    MAX-ACCESS read-only              
    STATUS current               
    DESCRIPTION               
        "Unicast key number supported."               
    ::= { apWapiProtocolCfgEntry 8 }  
    
apUnicastRekeyMethod OBJECT-TYPE               
    SYNTAX INTEGER               
    MAX-ACCESS read-write              
    STATUS current               
    DESCRIPTION               
        "Unicast key update method."               
    ::= { apWapiProtocolCfgEntry 9 }      
    
apUnicastRekeyTime OBJECT-TYPE               
    SYNTAX Unsigned32               
    MAX-ACCESS read-write              
    STATUS current               
    DESCRIPTION               
        "The effective time of Unicast key."               
    ::= { apWapiProtocolCfgEntry 10 }   
        
apUnicastRekeyPackets OBJECT-TYPE               
    SYNTAX Unsigned32               
    MAX-ACCESS read-write              
    STATUS current               
    DESCRIPTION               
        "The effective package number of unicast key."               
    ::= { apWapiProtocolCfgEntry 11 }     
    
apMulticastCipher OBJECT-TYPE               
    SYNTAX OCTET STRING               
    MAX-ACCESS read-write              
    STATUS current               
    DESCRIPTION               
        "Multicast encryption "               
    ::= { apWapiProtocolCfgEntry 12 } 
    
apMulticastRekeyMethod OBJECT-TYPE               
    SYNTAX INTEGER               
    MAX-ACCESS read-write              
    STATUS current               
    DESCRIPTION               
        "Multicast key update method."               
    ::= { apWapiProtocolCfgEntry 13 } 
    
apMulticastRekeyTime OBJECT-TYPE               
    SYNTAX Unsigned32               
    MAX-ACCESS read-write              
    STATUS current               
    DESCRIPTION               
        "The effective time of multicast key."               
    ::= { apWapiProtocolCfgEntry 14 } 
    
apMulticastRekeyPackets OBJECT-TYPE               
    SYNTAX Unsigned32               
    MAX-ACCESS read-write              
    STATUS current               
    DESCRIPTION               
        "The effective package number of multicast key."               
    ::= { apWapiProtocolCfgEntry 15 } 
    
apMulticastRekeyStrict OBJECT-TYPE               
    SYNTAX TruthValue               
    MAX-ACCESS read-write              
    STATUS current               
    DESCRIPTION               
        "Whether to invocate multicast key when terminal leaves from BSS."               
    ::= { apWapiProtocolCfgEntry 16 }  
    
apPSKValue OBJECT-TYPE               
    SYNTAX OCTET STRING               
    MAX-ACCESS read-write              
    STATUS current               
    DESCRIPTION               
        "PSK value."               
    ::= { apWapiProtocolCfgEntry 17 } 
    
apPSKPassPhrase OBJECT-TYPE               
    SYNTAX DisplayString               
    MAX-ACCESS read-write              
    STATUS current               
    DESCRIPTION               
        "PSK pass phrase."               
    ::= { apWapiProtocolCfgEntry 18 }     
        
apCertificateUpdateCount OBJECT-TYPE               
    SYNTAX Unsigned32               
    MAX-ACCESS read-write              
    STATUS current               
    DESCRIPTION               
        "Retry time of Certification."               
    ::= { apWapiProtocolCfgEntry 19 } 
    
apMulticastUpdateCount OBJECT-TYPE               
    SYNTAX Unsigned32               
    MAX-ACCESS read-write              
    STATUS current               
    DESCRIPTION               
        "Retry time of MSK."               
    ::= { apWapiProtocolCfgEntry 20 }      
       
apUnicastUpdateCount OBJECT-TYPE               
    SYNTAX Unsigned32               
    MAX-ACCESS read-write              
    STATUS current               
    DESCRIPTION               
        "Retry time of unicast key."               
    ::= { apWapiProtocolCfgEntry 21 }      

apMulticastCipherSize OBJECT-TYPE               
    SYNTAX Unsigned32               
    MAX-ACCESS read-only              
    STATUS current               
    DESCRIPTION               
        "Bit length of multicast key."               
    ::= { apWapiProtocolCfgEntry 22 } 

apBKLifetime OBJECT-TYPE               
    SYNTAX Unsigned32               
    MAX-ACCESS read-write              
    STATUS current               
    DESCRIPTION               
        "The life time of broadcast key."               
    ::= { apWapiProtocolCfgEntry 23 } 

apBKReauthThreshold OBJECT-TYPE               
    SYNTAX Unsigned32               
    MAX-ACCESS read-write              
    STATUS current               
    DESCRIPTION               
        "Threshold of reauthentucation."               
    ::= { apWapiProtocolCfgEntry 24 }
     

apSATimeout OBJECT-TYPE               
    SYNTAX Unsigned32               
    MAX-ACCESS read-write              
    STATUS current               
    DESCRIPTION               
        "Time out of safe conection."               
    ::= { apWapiProtocolCfgEntry 25 } 

apAuthSuiteSelected OBJECT-TYPE               
    SYNTAX OCTET STRING               
    MAX-ACCESS read-only              
    STATUS current               
    DESCRIPTION               
        "AKM selected."               
    ::= { apWapiProtocolCfgEntry 26 } 
    
apUnicastCipherSelected OBJECT-TYPE               
    SYNTAX OCTET STRING               
    MAX-ACCESS read-only              
    STATUS current               
    DESCRIPTION               
        "Encryption type selected by last unicast."               
    ::= { apWapiProtocolCfgEntry 27 }  
    
apMulticastCipherSelected OBJECT-TYPE               
    SYNTAX OCTET STRING               
    MAX-ACCESS read-only              
    STATUS current               
    DESCRIPTION               
        "ncryption type selected by last multicast."               
    ::= { apWapiProtocolCfgEntry 28 }      
    
apBKIDUsed OBJECT-TYPE               
    SYNTAX OCTET STRING               
    MAX-ACCESS read-only              
    STATUS current               
    DESCRIPTION               
        "BKID used."               
    ::= { apWapiProtocolCfgEntry 29 }         
    
apAuthSuiteRequested OBJECT-TYPE               
    SYNTAX OCTET STRING               
    MAX-ACCESS read-only              
    STATUS current               
    DESCRIPTION               
        "The selection requested by last AKM."               
    ::= { apWapiProtocolCfgEntry 30 } 
    
apUnicastCipherRequested OBJECT-TYPE               
    SYNTAX OCTET STRING               
    MAX-ACCESS read-only              
    STATUS current               
    DESCRIPTION               
        "The selection requested by last unicast."               
    ::= { apWapiProtocolCfgEntry 31 } 
    
apMulticastCipherRequested OBJECT-TYPE               
    SYNTAX OCTET STRING               
    MAX-ACCESS read-only              
    STATUS current               
    DESCRIPTION               
        "The selection requested by last multicast."               
    ::= { apWapiProtocolCfgEntry 32 } 
    
--**************************************************
--* apWapiProtocolCfgTable ends
--**************************************************


--**************************************************
--* apWapiUnicastCfgTable begins
--**************************************************
apWapiUnicastCfgTable OBJECT-TYPE
    SYNTAX SEQUENCE OF ApWapiUnicastCfgEntry
    MAX-ACCESS not-accessible
    STATUS current
    DESCRIPTION
        "The table discribe the WAPI unicast encryption configuration of the AP"
    ::= { apWapiCfg 2 }

apWapiUnicastCfgEntry OBJECT-TYPE
    SYNTAX ApWapiUnicastCfgEntry
    MAX-ACCESS not-accessible
    STATUS current
    DESCRIPTION
        "The entry of apWapiUnicastCfgTable."
    INDEX
    { apWlanId }
    ::= { apWapiUnicastCfgTable 1 }

ApWapiUnicastCfgEntry ::=
    SEQUENCE {
        apUnicastCipher                 OCTET STRING,
        apUnicastCipherEnabled					TruthValue,
        apUnicastCipherSize							Unsigned32 
        } 
  
apUnicastCipher OBJECT-TYPE               
    SYNTAX OCTET STRING               
    MAX-ACCESS read-only              
    STATUS current               
    DESCRIPTION               
        "The unicast encryption selected."               
    ::= { apWapiUnicastCfgEntry 1 } 
    
apUnicastCipherEnabled OBJECT-TYPE               
    SYNTAX TruthValue               
    MAX-ACCESS read-write              
    STATUS current               
    DESCRIPTION               
        "Wether to enable unicast encryption."               
    ::= { apWapiUnicastCfgEntry 2 } 
    
apUnicastCipherSize OBJECT-TYPE               
    SYNTAX Unsigned32               
    MAX-ACCESS read-only              
    STATUS current               
    DESCRIPTION               
        "The bit length of unicase key."               
    ::= { apWapiUnicastCfgEntry 3 } 

--**************************************************
--* apWapiUnicastCfgTable ends
--**************************************************


--**************************************************
--* apWapiAKMCfgTable begins
--**************************************************
apWapiAKMCfgTable OBJECT-TYPE
    SYNTAX SEQUENCE OF ApWapiAKMCfgEntry
    MAX-ACCESS not-accessible
    STATUS current
    DESCRIPTION
        "The table discribe the AKM configuration of the AP"
    ::= { apWapiCfg 3 }

apWapiAKMCfgEntry OBJECT-TYPE
    SYNTAX ApWapiAKMCfgEntry
    MAX-ACCESS not-accessible
    STATUS current
    DESCRIPTION
        "The entry of apWapiAKMCfgTable."
    INDEX
    { apWlanId }
    ::= { apWapiAKMCfgTable 1 }

ApWapiAKMCfgEntry ::=
    SEQUENCE {
        apAuthenticationSuite                 OCTET STRING,
        apAuthenticationSuiteEnabled					TruthValue
        } 
  
apAuthenticationSuite OBJECT-TYPE               
    SYNTAX OCTET STRING               
    MAX-ACCESS read-only              
    STATUS current               
    DESCRIPTION               
        "The AKM selected."               
    ::= { apWapiAKMCfgEntry 1 } 
    
apAuthenticationSuiteEnabled OBJECT-TYPE               
    SYNTAX TruthValue               
    MAX-ACCESS read-write              
    STATUS current               
    DESCRIPTION               
        "Wether to enable AKM."               
    ::= { apWapiAKMCfgEntry 2 } 
    

--**************************************************
--* apWapiAKMCfgTable ends
--**************************************************

         
--**************************************************
--* apWapiCfg end here
--************************************************** 

--**************************************************
--* apSyslogCfg start here
--************************************************** 

apSyslogSvcEnable OBJECT-TYPE
    SYNTAX TruthValue
    MAX-ACCESS read-write
    STATUS current
    DESCRIPTION
        "Whether to open syslog service"
    ::= { apSyslogCfg 1 }

apSyslogReportEventLevel OBJECT-TYPE
    SYNTAX INTEGER
    MAX-ACCESS read-write
    STATUS current
    DESCRIPTION
        "Report event level"
    ::= { apSyslogCfg 2 }

--**************************************************
--* apSyslogCfg end here
--**************************************************


--**************************************************
--* apSyslogSvrCfgTable begins
--**************************************************

apSyslogSvrCfgTable OBJECT-TYPE
    SYNTAX SEQUENCE OF ApSyslogSvrCfgEntry
    MAX-ACCESS not-accessible
    STATUS current
    DESCRIPTION
        "The table discribe the system log configuration of the AP."
    ::= { apSyslogCfg 3 }

apSyslogSvrCfgEntry OBJECT-TYPE
    SYNTAX ApSyslogSvrCfgEntry
    MAX-ACCESS not-accessible
    STATUS current
    DESCRIPTION
        "The entry of apSyslogSvrCfgTable."
    INDEX
    { apSyslogSvrIndex }
    ::= { apSyslogSvrCfgTable 1 }

ApSyslogSvrCfgEntry ::=
    SEQUENCE {
        apSyslogSvrIndex	INTEGER,
        apSyslogServerAddr	TAddress,
        apSyslogStatus		RowStatus
        } 
  
apSyslogSvrIndex OBJECT-TYPE               
    SYNTAX INTEGER               
    MAX-ACCESS read-only              
    STATUS current               
    DESCRIPTION               
        "The index of the table."               
    ::= { apSyslogSvrCfgEntry 1 } 
    
apSyslogServerAddr OBJECT-TYPE               
    SYNTAX TAddress               
    MAX-ACCESS read-create              
    STATUS current               
    DESCRIPTION               
        "Address of syslog server."               
    ::= { apSyslogSvrCfgEntry 2 } 

apSyslogStatus OBJECT-TYPE               
    SYNTAX RowStatus               
    MAX-ACCESS read-create              
    STATUS current               
    DESCRIPTION               
        "Address of syslog server."               
    ::= { apSyslogSvrCfgEntry 3 } 
    
    
--**************************************************
--* apSyslogSvrCfgTable ends
--**************************************************

--**************************************************
--* apSoftwareUpdate start here
--************************************************** 

apLoadFlag OBJECT-TYPE
    SYNTAX INTEGER
    MAX-ACCESS read-write
    STATUS current
    DESCRIPTION
        "File send type"
    ::= { apSoftwareUpdate 1 }

apFileName OBJECT-TYPE
    SYNTAX DisplayString
    MAX-ACCESS read-write
    STATUS current
    DESCRIPTION
        "File name"
    ::= { apSoftwareUpdate 2 }
    
apFileType OBJECT-TYPE
    SYNTAX INTEGER
    MAX-ACCESS read-write
    STATUS current
    DESCRIPTION
        "File type"
    ::= { apSoftwareUpdate 3 }   
    
apTransProtocol OBJECT-TYPE
    SYNTAX INTEGER
    MAX-ACCESS read-write
    STATUS current
    DESCRIPTION
        "File transmit protocol"
    ::= { apSoftwareUpdate 4 } 
    
apServerAddr OBJECT-TYPE
    SYNTAX IpAddress
    MAX-ACCESS read-write
    STATUS current
    DESCRIPTION
        "Address of remote server"
    ::= { apSoftwareUpdate 5 } 
    
apServerPort OBJECT-TYPE
    SYNTAX INTEGER
    MAX-ACCESS read-write
    STATUS current
    DESCRIPTION
        "Port of remote server"
    ::= { apSoftwareUpdate 6 } 
    
apServerUsername OBJECT-TYPE
    SYNTAX DisplayString
    MAX-ACCESS read-write
    STATUS current
    DESCRIPTION
        "Port of remote server"
    ::= { apSoftwareUpdate 7 }   
    
apServerPasswd OBJECT-TYPE
    SYNTAX DisplayString
    MAX-ACCESS read-write
    STATUS current
    DESCRIPTION
        "Encryption of remote server."
    ::= { apSoftwareUpdate 8 }  
    
apTransStatus OBJECT-TYPE
    SYNTAX INTEGER
    MAX-ACCESS read-only
    STATUS current
    DESCRIPTION
        "Running status of the AP."
    ::= { apSoftwareUpdate 9 }   
    
    
apFailReason OBJECT-TYPE
    SYNTAX DisplayString
    MAX-ACCESS read-only
    STATUS current
    DESCRIPTION
        "Fail reason."
    ::= { apSoftwareUpdate 10 }   

--**************************************************
--* apSoftwareUpdate end here
--************************************************** 


--**************************************************
--* apCfgFileDistribute start here
--************************************************** 

apCfgFileLoadFlag OBJECT-TYPE
    SYNTAX INTEGER
    MAX-ACCESS read-write
    STATUS current
    DESCRIPTION
        "File send type."
    ::= { apCfgFileDistribute 1 }

apCfgFileFileName OBJECT-TYPE
    SYNTAX DisplayString
    MAX-ACCESS read-write
    STATUS current
    DESCRIPTION
        "File name"
    ::= { apCfgFileDistribute 2 }
    
apCfgFileFileType OBJECT-TYPE
    SYNTAX INTEGER
    MAX-ACCESS read-write
    STATUS current
    DESCRIPTION
        "File type"
    ::= { apCfgFileDistribute 3 }   
    
apCfgFileTransProtocol OBJECT-TYPE
    SYNTAX INTEGER
    MAX-ACCESS read-write
    STATUS current
    DESCRIPTION
        "File transmit protocol"
    ::= { apCfgFileDistribute 4 } 
    
apCfgFileServerAddr OBJECT-TYPE
    SYNTAX IpAddress
    MAX-ACCESS read-write
    STATUS current
    DESCRIPTION
        "Address of remote server"
    ::= { apCfgFileDistribute 5 } 
    
apCfgFileServerPort OBJECT-TYPE
    SYNTAX INTEGER
    MAX-ACCESS read-write
    STATUS current
    DESCRIPTION
        "Port of remote server"
    ::= { apCfgFileDistribute 6 } 
    
apCfgFileServerUsername OBJECT-TYPE
    SYNTAX DisplayString
    MAX-ACCESS read-write
    STATUS current
    DESCRIPTION
        "Port of remote server"
    ::= { apCfgFileDistribute 7 }   
    
apCfgFileServerPasswd OBJECT-TYPE
    SYNTAX DisplayString
    MAX-ACCESS read-write
    STATUS current
    DESCRIPTION
        "Encryption of remote server."
    ::= { apCfgFileDistribute 8 }  
    
apCfgFileTransStatus OBJECT-TYPE
    SYNTAX INTEGER
    MAX-ACCESS read-only
    STATUS current
    DESCRIPTION
        "Running status of the AP."
    ::= { apCfgFileDistribute 9 }   
    
  
apCfgFileFailReason OBJECT-TYPE
    SYNTAX DisplayString
    MAX-ACCESS read-write
    STATUS current
    DESCRIPTION
        "Fail reason."
    ::= { apCfgFileDistribute 10 }   

--**************************************************
--* apCfgFileDistribute end here
--************************************************** 


--**************************************************
--* apAccessControl start here
--************************************************** 



--**************************************************
--* cmApTerminalPermitTable begins
--**************************************************
apTerminalPermitTable OBJECT-TYPE
    SYNTAX SEQUENCE OF ApTerminalPermitEntry
    MAX-ACCESS not-accessible
    STATUS current
    DESCRIPTION
        "Terminal white list"
    ::= { apAccessControl 1 }

apTerminalPermitEntry OBJECT-TYPE
    SYNTAX ApTerminalPermitEntry
    MAX-ACCESS not-accessible
    STATUS current
    DESCRIPTION
        "The entry of apTerminalPermitTable."
    INDEX
    { apWhiteListIndex }
    ::= { apTerminalPermitTable 1 }

ApTerminalPermitEntry ::=
    SEQUENCE {
        apWhiteListIndex	INTEGER,
        apPermitMAC             MacAddress,
        apWhiteListStatus	RowStatus
        } 
apWhiteListIndex OBJECT-TYPE               
    SYNTAX INTEGER               
    MAX-ACCESS read-only              
    STATUS current               
    DESCRIPTION               
        "The index of the table."               
    ::= { apTerminalPermitEntry 1 }   
apPermitMAC OBJECT-TYPE               
    SYNTAX MacAddress               
    MAX-ACCESS read-create              
    STATUS current               
    DESCRIPTION               
        "The permited MAC address."               
    ::= { apTerminalPermitEntry 2 } 
    
apWhiteListStatus OBJECT-TYPE               
    SYNTAX RowStatus               
    MAX-ACCESS read-create              
    STATUS current               
    DESCRIPTION               
        "The status column used for creating and
         deleting instances of the columnar objects in the table."               
    ::= { apTerminalPermitEntry 3 } 
    
    


--**************************************************
--* apTerminalPermitTable ends
--**************************************************


--**************************************************
--* apTerminalDeniedTable begins
--**************************************************
apTerminalDeniedTable OBJECT-TYPE
    SYNTAX SEQUENCE OF ApTerminalDeniedEntry
    MAX-ACCESS not-accessible
    STATUS current
    DESCRIPTION
        "Terminal black list"
    ::= { apAccessControl 2 }

apTerminalDeniedEntry OBJECT-TYPE
    SYNTAX ApTerminalDeniedEntry
    MAX-ACCESS not-accessible
    STATUS current
    DESCRIPTION
        "The entry of apTerminalDeniedTable."
    INDEX
    { apBlackListIndex }
    ::= { apTerminalDeniedTable 1 }

ApTerminalDeniedEntry ::=
    SEQUENCE {
        apBlackListIndex								INTEGER,
        apAttackDeviceMAC               MacAddress,
        apBlackListStatus		RowStatus
        } 
apBlackListIndex OBJECT-TYPE               
    SYNTAX INTEGER               
    MAX-ACCESS read-only              
    STATUS current               
    DESCRIPTION               
        "The index of the table."               
    ::= { apTerminalDeniedEntry 1 } 
      
apAttackDeviceMAC OBJECT-TYPE               
    SYNTAX MacAddress               
    MAX-ACCESS read-create              
    STATUS current               
    DESCRIPTION               
        "The Denied MAC address."               
    ::= { apTerminalDeniedEntry 2 } 
    
apBlackListStatus OBJECT-TYPE               
    SYNTAX RowStatus               
    MAX-ACCESS read-create              
    STATUS current               
    DESCRIPTION               
        "The status column used for creating and
         deleting instances of the columnar objects in the table."               
    ::= { apTerminalDeniedEntry 3 } 


--**************************************************
--* apTerminalDeniedTable ends
--**************************************************

--**************************************************
--* apAccessControl end here
--************************************************** 



--**************************************************
--* apTrapConfig start here
--************************************************** 

apTrapResendWaitingTime OBJECT-TYPE
    SYNTAX INTEGER
    MAX-ACCESS read-write
    STATUS current
    DESCRIPTION
        "waiting time for trap resend."
    ::= { apTrapConfig 1 }
    
apCPUusageThreshhd OBJECT-TYPE
    SYNTAX INTEGER
    MAX-ACCESS read-write
    STATUS current
    DESCRIPTION
        "CUP usage threshold."
    ::= { apTrapConfig 2 } 
    
apMemUsageThreshhd OBJECT-TYPE
    SYNTAX INTEGER
    MAX-ACCESS read-write
    STATUS current
    DESCRIPTION
        "Memory usage threshold."
    ::= { apTrapConfig 3 }    

apAPCoInterfThreshhd OBJECT-TYPE
    SYNTAX INTEGER
    MAX-ACCESS read-write
    STATUS current
    DESCRIPTION
        "AP cointerference threshold."
    ::= { apTrapConfig 4 } 
     
apAPNeiborInterfThreshhd OBJECT-TYPE
    SYNTAX INTEGER
    MAX-ACCESS read-write
    STATUS current
    DESCRIPTION
        "AP neibor interference threshold."
    ::= { apTrapConfig 5 }      
    
apStaInterfNumThreshhd OBJECT-TYPE
    SYNTAX INTEGER
    MAX-ACCESS read-write
    STATUS current
    DESCRIPTION
        "Terminal interference threshold."
    ::= { apTrapConfig 6 }   
    
apHeartbeatOnOff OBJECT-TYPE
    SYNTAX INTEGER
    MAX-ACCESS read-write
    STATUS current
    DESCRIPTION
        "Heartbeat detect switch."
    ::= { apTrapConfig 7 } 
     
apHeartbeatPeriod OBJECT-TYPE
    SYNTAX INTEGER
    MAX-ACCESS read-write
    STATUS current
    DESCRIPTION
        "Heartbeat detect periode."
    ::= { apTrapConfig 8 }  
    
 --**************************************************
--* apTrapAddrTable begins
--**************************************************
apTrapAddrTable OBJECT-TYPE
    SYNTAX SEQUENCE OF ApTrapAddrEntry
    MAX-ACCESS not-accessible
    STATUS current
    DESCRIPTION
        "Configuration of trap address"
    ::= { apTrapConfig 9 }

apTrapAddrEntry OBJECT-TYPE
    SYNTAX ApTrapAddrEntry
    MAX-ACCESS not-accessible
    STATUS current
    DESCRIPTION
        "The entry of apTrapAddrTable."
    INDEX
    { apTrapDesAddrIndex }
    ::= { apTrapAddrTable 1 }

ApTrapAddrEntry ::=
    SEQUENCE {
        apTrapDesAddrIndex							 INTEGER,
        apTrapDesIPAddress               IpAddress,
        apTrapAddrStatus		 RowStatus
        } 
apTrapDesAddrIndex OBJECT-TYPE               
    SYNTAX INTEGER               
    MAX-ACCESS read-only              
    STATUS current               
    DESCRIPTION               
        "The index of the table."               
    ::= { apTrapAddrEntry 1 } 
    
apTrapDesIPAddress OBJECT-TYPE               
    SYNTAX IpAddress               
    MAX-ACCESS read-create              
    STATUS current               
    DESCRIPTION               
        "Trap address."               
    ::= { apTrapAddrEntry 2 } 
      
apTrapAddrStatus OBJECT-TYPE               
    SYNTAX RowStatus               
    MAX-ACCESS read-create              
    STATUS current               
    DESCRIPTION               
        "The status column used for creating and
         deleting instances of the columnar objects in the table."               
    ::= { apTrapAddrEntry 3 } 


--**************************************************
--* apTrapAddrTable ends
--**************************************************


--**************************************************
--* apTrapEnabledTable begins
--**************************************************
apTrapEnabledTable OBJECT-TYPE
    SYNTAX SEQUENCE OF ApTrapEnabledEntry
    MAX-ACCESS not-accessible
    STATUS current
    DESCRIPTION
        "Configuration of trap enabled"
    ::= { apTrapConfig 10 }

apTrapEnabledEntry OBJECT-TYPE
    SYNTAX ApTrapEnabledEntry
    MAX-ACCESS not-accessible
    STATUS current
    DESCRIPTION
        "The entry of apTrapEnabledTable."
    INDEX
    { apTrapEnabledIndex }
    ::= { apTrapEnabledTable 1 }

ApTrapEnabledEntry ::=
    SEQUENCE {
        apTrapEnabledIndex                 INTEGER,
        apTrapName               					 DisplayString,
        apTrapDescr												 DisplayString,
        apTrapOnOff												 INTEGER
        } 
  
apTrapEnabledIndex OBJECT-TYPE               
    SYNTAX INTEGER               
    MAX-ACCESS read-only              
    STATUS current               
    DESCRIPTION               
        "index of apTrapEnabledTable."               
    ::= { apTrapEnabledEntry 1 } 
    
apTrapName OBJECT-TYPE               
    SYNTAX DisplayString               
    MAX-ACCESS read-only              
    STATUS current               
    DESCRIPTION               
        "Trap name."               
    ::= { apTrapEnabledEntry 2 } 
    
apTrapDescr OBJECT-TYPE               
    SYNTAX DisplayString               
    MAX-ACCESS read-write              
    STATUS current               
    DESCRIPTION               
        "Trap description."               
    ::= { apTrapEnabledEntry 3 } 
    
apTrapOnOff OBJECT-TYPE               
    SYNTAX INTEGER               
    MAX-ACCESS read-write              
    STATUS current               
    DESCRIPTION               
        "Trap switch."               
    ::= { apTrapEnabledEntry 4 } 


--**************************************************
--* apTrapEnabledTable ends
--**************************************************
   
        
--**************************************************
--* apTrapConfig end here
--************************************************** 



--**************************************************
--* apVlanConfig begins here
--**************************************************


--**************************************************
--* cmApVlanConfigTable begins
--**************************************************
apVlanConfigTable OBJECT-TYPE
    SYNTAX SEQUENCE OF ApVlanConfigEntry
    MAX-ACCESS not-accessible
    STATUS current
    DESCRIPTION
        "Configuration of vlan"
    ::= { apVlanConfig 10 }

apVlanConfigEntry OBJECT-TYPE
    SYNTAX ApVlanConfigEntry
    MAX-ACCESS not-accessible
    STATUS current
    DESCRIPTION
        "The entry of apVlanConfigTable."
    INDEX
    { apWlanId}
    ::= { apVlanConfigTable 1 }

ApVlanConfigEntry ::=
    SEQUENCE {
        apVlanCfgVlanId                 INTEGER,
        apVlanCfgStatus			RowStatus
        } 
  
apVlanCfgVlanId OBJECT-TYPE               
    SYNTAX INTEGER               
    MAX-ACCESS read-create             
    STATUS current               
    DESCRIPTION               
        "Vlan ID."               
    ::= { apVlanConfigEntry 1 } 
    
apVlanCfgStatus OBJECT-TYPE               
    SYNTAX RowStatus               
    MAX-ACCESS read-create             
    STATUS current               
    DESCRIPTION               
        "The status column used for creating and
         deleting instances of the columnar objects in the table."               
    ::= { apVlanConfigEntry 2 } 
        
--**************************************************
--* apVlanConfigTable ends
--**************************************************



--**************************************************
--* apVlanConfig ends here
--**************************************************


-- apHeartBeatConfig 
apHeartbeatCycle OBJECT-TYPE
    SYNTAX Integer32
    MAX-ACCESS read-write
    STATUS current
    DESCRIPTION
        "Timespace of heartbeat."
    ::= { apHeartbeatConfig 1 }


--**************************************************
--* apSysPerformanceStat begins here
--**************************************************

apCPURTUsage OBJECT-TYPE
    SYNTAX INTEGER
    MAX-ACCESS read-only
    STATUS current
    DESCRIPTION
        "Real-time use ratio of CPU."
    ::= { apSysPerformanceStat 1 }

apCPUAvgUsage OBJECT-TYPE
    SYNTAX INTEGER
    MAX-ACCESS read-only
    STATUS current
    DESCRIPTION
        "Avearage use ratio of CPU."
    ::= { apSysPerformanceStat 2 }

apMemRTUsage OBJECT-TYPE
    SYNTAX INTEGER
    MAX-ACCESS read-only
    STATUS current
    DESCRIPTION
        "Real-time use ratio of memory."
    ::= { apSysPerformanceStat 3 }
    
apMemAvgUsage OBJECT-TYPE
    SYNTAX INTEGER
    MAX-ACCESS read-only
    STATUS current
    DESCRIPTION
        "Avearage use ratio of memory."
    ::= { apSysPerformanceStat 4 }   
         
--**************************************************
--* apSysPerformanceStat ends here
--**************************************************




--**************************************************
--* apConInfoStat begins here
--**************************************************

apApStationAssocSum OBJECT-TYPE
    SYNTAX INTEGER
    MAX-ACCESS read-only
    STATUS current
    DESCRIPTION
        "The number of terminal that connect to AP."
    ::= { apConInfoStat 1 }

apApStationOnlineSum OBJECT-TYPE
    SYNTAX INTEGER
    MAX-ACCESS read-only
    STATUS current
    DESCRIPTION
        "The number of terminal on line."
    ::= { apConInfoStat 2 }

apAssocTimes OBJECT-TYPE
    SYNTAX Counter32
    MAX-ACCESS read-only
    STATUS current
    DESCRIPTION
        "Total association times."
    ::= { apConInfoStat 3 }
    
apAssocFailTimes OBJECT-TYPE
    SYNTAX Counter32
    MAX-ACCESS read-only
    STATUS current
    DESCRIPTION
        "Total failure times of association"
    ::= { apConInfoStat 4 }   
    
apReassocTimes OBJECT-TYPE
    SYNTAX Counter32
    MAX-ACCESS read-only
    STATUS current
    DESCRIPTION
        "Reassociation times."
    ::= { apConInfoStat 5 }   
    
apPreAssCannotShiftDeassocFailSum OBJECT-TYPE
    SYNTAX Counter32
    MAX-ACCESS read-only
    STATUS current
    DESCRIPTION
        "."
    ::= { apConInfoStat 6 }    
    
apApStatsDisassociated OBJECT-TYPE
    SYNTAX Counter32
    MAX-ACCESS read-only
    STATUS current
    DESCRIPTION
        "."
    ::= { apConInfoStat 7 } 
    
apAssocRejectSum OBJECT-TYPE
    SYNTAX Counter32
    MAX-ACCESS read-only
    STATUS current
    DESCRIPTION
        "."
    ::= { apConInfoStat 8 }   
    
apBSSNotSupportAssocFailSum OBJECT-TYPE
    SYNTAX Counter32
    MAX-ACCESS read-only
    STATUS current
    DESCRIPTION
        "."
    ::= { apConInfoStat 9 }     
            
--**************************************************
--* apConInfoStat ends here
--**************************************************



--**************************************************
--* apIfPeformanceStat begins here
--**************************************************

--**************************************************
--* cmApWiredIfPfmStatTable begins
--**************************************************
apWiredIfPfmStatTable OBJECT-TYPE
    SYNTAX SEQUENCE OF ApWiredIfPfmStatEntry
    MAX-ACCESS not-accessible
    STATUS current
    DESCRIPTION
        "Statistic of wired interface performance."
    ::= { apIfPeformanceStat 1 }

apWiredIfPfmStatEntry OBJECT-TYPE
    SYNTAX ApWiredIfPfmStatEntry
    MAX-ACCESS not-accessible
    STATUS current
    DESCRIPTION
        "The entry of apWiredIfPfmStatTable."
    INDEX
    { ifIndex }
    ::= { apWiredIfPfmStatTable 1 }

ApWiredIfPfmStatEntry ::=
    SEQUENCE {
        apIfInUcastPkts                 Counter32,      
        apIfInNUcastPkts                Counter32,
        apIfInOctets                    Counter32,
        apIfInDiscardPkts               Counter32,
        apIfInErrors                    Counter32,
        apIfOutUcastPkts                Counter32,
        apIfOutNUcastPkts               Counter32,
        apIfOutOctets                   Counter32,
        apIfOutDiscardPkts              Counter32,
        apIfOutErrors                   Counter32,
        apIfUpDwnTimes                  Counter32      									  
       } 
         
apIfInUcastPkts OBJECT-TYPE               
    SYNTAX Counter32               
    MAX-ACCESS read-only             
    STATUS current               
    DESCRIPTION               
        "Unicast packages received by the port."               
    ::= { apWiredIfPfmStatEntry 1 } 
    
apIfInNUcastPkts OBJECT-TYPE               
    SYNTAX Counter32               
    MAX-ACCESS read-only             
    STATUS current               
    DESCRIPTION               
        "Non-Unicast packages received by the port."               
    ::= { apWiredIfPfmStatEntry 2 }     
    
apIfInOctets OBJECT-TYPE               
    SYNTAX Counter32               
    MAX-ACCESS read-only             
    STATUS current               
    DESCRIPTION               
        " Total bytes received by the port."               
    ::= { apWiredIfPfmStatEntry 3 } 
    
apIfInDiscardPkts OBJECT-TYPE               
    SYNTAX Counter32               
    MAX-ACCESS read-only             
    STATUS current               
    DESCRIPTION               
        "Packages discarded by the port."               
    ::= { apWiredIfPfmStatEntry 4 }     
    
apIfInErrors OBJECT-TYPE               
    SYNTAX Counter32               
    MAX-ACCESS read-only             
    STATUS current               
    DESCRIPTION               
        "Error packages received by the port."               
    ::= { apWiredIfPfmStatEntry 5 }        
    
    
apIfOutUcastPkts OBJECT-TYPE               
    SYNTAX Counter32               
    MAX-ACCESS read-only             
    STATUS current               
    DESCRIPTION               
        "Unicast packages sent by the port."               
    ::= { apWiredIfPfmStatEntry 6 }     
    
apIfOutNUcastPkts OBJECT-TYPE               
    SYNTAX Counter32               
    MAX-ACCESS read-only             
    STATUS current               
    DESCRIPTION               
        "Non-unicast packages sent by the port.."               
    ::= { apWiredIfPfmStatEntry 7 }  
    
apIfOutOctets OBJECT-TYPE               
    SYNTAX Counter32               
    MAX-ACCESS read-only             
    STATUS current               
    DESCRIPTION               
        "total bytes sent by the port."               
    ::= { apWiredIfPfmStatEntry 8 }    
    
apIfOutDiscardPkts OBJECT-TYPE               
    SYNTAX Counter32               
    MAX-ACCESS read-only             
    STATUS current               
    DESCRIPTION               
        "Packages discarded by the port."               
    ::= { apWiredIfPfmStatEntry 9 }     
    
apIfOutErrors OBJECT-TYPE               
    SYNTAX Counter32               
    MAX-ACCESS read-only             
    STATUS current               
    DESCRIPTION               
        "Error packages received by the port."               
    ::= { apWiredIfPfmStatEntry 10 } 
    
apIfUpDwnTimes OBJECT-TYPE               
    SYNTAX Counter32               
    MAX-ACCESS read-only             
    STATUS current               
    DESCRIPTION               
        "Updown times of the port."               
    ::= { apWiredIfPfmStatEntry 11 }     
    

--**************************************************
--* apWiredIfPfmStatTable ends
--**************************************************


--**************************************************
--* apRadioIfPfmStatTable begins
--**************************************************
apRadioIfPfmStatTable OBJECT-TYPE
    SYNTAX SEQUENCE OF ApRadioIfPfmStatEntry
    MAX-ACCESS not-accessible
    STATUS current
    DESCRIPTION
        "Statistic of wireless interface performance."
    ::= { apIfPeformanceStat 2 }

apRadioIfPfmStatEntry OBJECT-TYPE
    SYNTAX ApRadioIfPfmStatEntry
    MAX-ACCESS not-accessible
    STATUS current
    DESCRIPTION
        "The entry of apRadioIfPfmStatTable."
    INDEX
    { ifIndex }
    ::= { apRadioIfPfmStatTable 1 }

ApRadioIfPfmStatEntry ::=
    SEQUENCE {
        apAvgRxSignalStrength                         Integer32,
        apHighestRxSignalStrength		      						Integer32,
        apLowestRxSignalStrength		      						Integer32,
        apUpdownTimes				      										Counter32,
        apTxDataPkts                                  Counter32,
        apRxDataPkts                                  Counter32,
        apUplinkDataOctets                            Counter64,
        apDwlinkDataOctets                            Counter64,
        apChStatsDwlinkTotRetryPkts                   Counter32,
        apChStatsPhyErrPkts                           Counter32,
        apChStatsMacFcsErrPkts                        Counter32,
        apChStatsMacMicErrPkts                        Counter32,
        apChStatsMacDecryptErrPkts                    Counter32,
        apChStatsTotalErrPkts                         Counter32,
        apRxMgmtFrameCnt			      									Counter32,
        apRxCtrlFrameCnt                              Counter32,
        apRxDataFrameCnt                              Counter32,
        apTxMgmtFrameCnt                              Counter32,
        apTxCtrlFrameCnt                              Counter32,
        apTxDataFrameCnt                              Counter32,
        apChStatsFrameErrorCnt												Counter32,
        apRetryCnt                                    Counter32,
        apCurTxPwr				      											Integer32,
        apAPNeighborSSIDList 			      							DisplayString,
        apChanStaNum																	Counter32,
        apChDownUnicastFrame                          Counter32,
        apChDownNonUnicastFrame                       Counter32,
        apChRxAuthFrame                               Counter32,
        apChRxAssoFrame                               Counter32,
        apChTxAuthFrame                               Counter32,
        apChTxAssoFrame                               Counter32
       } 
         
apAvgRxSignalStrength OBJECT-TYPE               
    SYNTAX Integer32               
    MAX-ACCESS read-only             
    STATUS current               
    DESCRIPTION               
        "Avearage receive signal strength."               
    ::= { apRadioIfPfmStatEntry 1 }
    
apHighestRxSignalStrength OBJECT-TYPE               
    SYNTAX Integer32               
    MAX-ACCESS read-only             
    STATUS current               
    DESCRIPTION               
        "Highest received signal strength."               
    ::= { apRadioIfPfmStatEntry 2 }
    
apLowestRxSignalStrength OBJECT-TYPE               
    SYNTAX Integer32               
    MAX-ACCESS read-only             
    STATUS current               
    DESCRIPTION               
        "Lowest received signal strength."               
    ::= { apRadioIfPfmStatEntry 3 }
    
apUpdownTimes OBJECT-TYPE               
    SYNTAX Counter32               
    MAX-ACCESS read-only             
    STATUS current               
    DESCRIPTION               
        "Updown times of wireless port."               
    ::= { apRadioIfPfmStatEntry 4 }    
    
apTxDataPkts OBJECT-TYPE               
    SYNTAX Counter32               
    MAX-ACCESS read-only             
    STATUS current               
    DESCRIPTION               
        "Data package number transmited."               
    ::= { apRadioIfPfmStatEntry 5 }      
    
apRxDataPkts OBJECT-TYPE               
    SYNTAX Counter32               
    MAX-ACCESS read-only             
    STATUS current               
    DESCRIPTION               
        "Data package number received."               
    ::= { apRadioIfPfmStatEntry 6 } 
    
apUplinkDataOctets OBJECT-TYPE               
    SYNTAX Counter64               
    MAX-ACCESS read-only             
    STATUS current               
    DESCRIPTION               
        "Data package bytes received."               
    ::= { apRadioIfPfmStatEntry 7 }   
    
apDwlinkDataOctets OBJECT-TYPE               
    SYNTAX Counter64               
    MAX-ACCESS read-only             
    STATUS current               
    DESCRIPTION               
        "Data package bytes transmited."               
    ::= { apRadioIfPfmStatEntry 8 } 
                                          
apChStatsDwlinkTotRetryPkts OBJECT-TYPE               
    SYNTAX Counter32               
    MAX-ACCESS read-only             
    STATUS current               
    DESCRIPTION               
        "Retry packages of downlink."               
    ::= { apRadioIfPfmStatEntry 9 }  
    
apChStatsPhyErrPkts OBJECT-TYPE               
    SYNTAX Counter32               
    MAX-ACCESS read-only             
    STATUS current               
    DESCRIPTION               
        "Error physical packages received by channel."               
    ::= { apRadioIfPfmStatEntry 10 }     
    
apChStatsMacFcsErrPkts OBJECT-TYPE               
    SYNTAX Counter32               
    MAX-ACCESS read-only             
    STATUS current               
    DESCRIPTION               
        "Error FCS MAC packages received by channel."               
    ::= { apRadioIfPfmStatEntry 11 } 

apChStatsMacMicErrPkts OBJECT-TYPE               
    SYNTAX Counter32               
    MAX-ACCESS read-only             
    STATUS current               
    DESCRIPTION               
        "Error MIC MAC packages received by channel."               
    ::= { apRadioIfPfmStatEntry 12 } 

apChStatsMacDecryptErrPkts OBJECT-TYPE               
    SYNTAX Counter32               
    MAX-ACCESS read-only             
    STATUS current               
    DESCRIPTION               
        "Error Decrypted MAC packages received by channel."               
    ::= { apRadioIfPfmStatEntry 13 } 
    
apChStatsTotalErrPkts OBJECT-TYPE               
    SYNTAX Counter32               
    MAX-ACCESS read-only             
    STATUS current               
    DESCRIPTION               
        "Total error packages received by channel."               
    ::= { apRadioIfPfmStatEntry 14 } 

apRxMgmtFrameCnt OBJECT-TYPE               
    SYNTAX Counter32               
    MAX-ACCESS read-only             
    STATUS current               
    DESCRIPTION               
        "Number of RX management frames."               
    ::= { apRadioIfPfmStatEntry 15 } 
    
apRxCtrlFrameCnt OBJECT-TYPE               
    SYNTAX Counter32               
    MAX-ACCESS read-only             
    STATUS current               
    DESCRIPTION               
        "Number of RX control frames."               
    ::= { apRadioIfPfmStatEntry 16 } 
    
apRxDataFrameCnt OBJECT-TYPE               
    SYNTAX Counter32               
    MAX-ACCESS read-only             
    STATUS current               
    DESCRIPTION               
        "Number of RX data frames."               
    ::= { apRadioIfPfmStatEntry 17 }     
    
apTxMgmtFrameCnt OBJECT-TYPE               
    SYNTAX Counter32               
    MAX-ACCESS read-only             
    STATUS current               
    DESCRIPTION               
        "Number of TX management frames."               
    ::= { apRadioIfPfmStatEntry 18 }     
        
apTxCtrlFrameCnt OBJECT-TYPE               
    SYNTAX Counter32               
    MAX-ACCESS read-only             
    STATUS current               
    DESCRIPTION               
        "Number of TX control frames."               
    ::= { apRadioIfPfmStatEntry 19 } 
    
apTxDataFrameCnt OBJECT-TYPE               
    SYNTAX Counter32               
    MAX-ACCESS read-only             
    STATUS current               
    DESCRIPTION               
        "Number of TX data frames."               
    ::= { apRadioIfPfmStatEntry 20 }   
    
apChStatsFrameErrorCnt OBJECT-TYPE               
    SYNTAX Counter32               
    MAX-ACCESS read-only             
    STATUS current               
    DESCRIPTION               
        "Received error frames."               
    ::= { apRadioIfPfmStatEntry 21 } 
           
apRetryCnt OBJECT-TYPE               
    SYNTAX Counter32               
    MAX-ACCESS read-only             
    STATUS current               
    DESCRIPTION               
        "retry count."               
    ::= { apRadioIfPfmStatEntry 22 }
    
apCurTxPwr OBJECT-TYPE               
    SYNTAX Integer32               
    MAX-ACCESS read-only             
    STATUS current               
    DESCRIPTION               
        "TX power of AP."               
    ::= { apRadioIfPfmStatEntry 23 }    
    
apAPNeighborSSIDList OBJECT-TYPE               
    SYNTAX DisplayString               
    MAX-ACCESS read-only             
    STATUS current               
    DESCRIPTION               
        "SSID list around AP."               
    ::= { apRadioIfPfmStatEntry 24 }  
    
    
apChanStaNum OBJECT-TYPE               
    SYNTAX Counter32               
    MAX-ACCESS read-only             
    STATUS current               
    DESCRIPTION               
        "The associated sta number of the channel."               
    ::= { apRadioIfPfmStatEntry 25 }   
    
apChDownUnicastFrame OBJECT-TYPE               
    SYNTAX Counter32               
    MAX-ACCESS read-only             
    STATUS current               
    DESCRIPTION               
        "Down link unicast frames."               
    ::= { apRadioIfPfmStatEntry 26 }      
    
apChDownNonUnicastFrame OBJECT-TYPE               
    SYNTAX Counter32               
    MAX-ACCESS read-only             
    STATUS current               
    DESCRIPTION               
        "Down link non-unicast frames."               
    ::= { apRadioIfPfmStatEntry 27 }    
    
apChRxAuthFrame OBJECT-TYPE               
    SYNTAX Counter32               
    MAX-ACCESS read-only             
    STATUS current               
    DESCRIPTION               
        "Receive auth frames."               
    ::= { apRadioIfPfmStatEntry 28 }          
    
apChRxAssoFrame OBJECT-TYPE               
    SYNTAX Counter32               
    MAX-ACCESS read-only             
    STATUS current               
    DESCRIPTION               
        "Receive association frames."               
    ::= { apRadioIfPfmStatEntry 29 }  
    
apChTxAuthFrame OBJECT-TYPE               
    SYNTAX Counter32               
    MAX-ACCESS read-only             
    STATUS current               
    DESCRIPTION               
        "transmit auth frames."               
    ::= { apRadioIfPfmStatEntry 30 }  
    
apChTxAssoFrame OBJECT-TYPE               
    SYNTAX Counter32               
    MAX-ACCESS read-only             
    STATUS current               
    DESCRIPTION               
        "transmit association frames."               
    ::= { apRadioIfPfmStatEntry 31 }      
    
--**************************************************
--* apRadioIfPfmStatTable ends
--**************************************************


--**************************************************
--* apIfPeformanceStat ends here
--**************************************************



--**************************************************
--* apSSIDPeformanceStat starts here
--**************************************************

--**************************************************
--* apRadioIfPfmStatTable begins
--**************************************************
apSSIDPfmStatTable OBJECT-TYPE
    SYNTAX SEQUENCE OF ApSSIDPfmStatEntry
    MAX-ACCESS not-accessible
    STATUS current
    DESCRIPTION
        "Statistic of wireless SSID performance."
    ::= { apSSIDPeformanceStat 1 }

apSSIDPfmStatEntry OBJECT-TYPE
    SYNTAX ApSSIDPfmStatEntry
    MAX-ACCESS not-accessible
    STATUS current
    DESCRIPTION
        "The entry of apSSIDPfmStatTable."
    INDEX
    { apWlanId }
    ::= { apSSIDPfmStatTable 1 }

ApSSIDPfmStatEntry ::=
    SEQUENCE {
        apSSIDTxDataPkts                            Counter32,
        apSSIDRxDataPkts														Counter32,
        apSSIDUplinkDataOctets											Counter64,
        apSSIDDwlinkDataOctets											Counter64,
        apSSIDChStatsDwlinkTotRetryPkts							Counter32,
        apSSIDApChStatsNumStations   								Integer32            
       } 
         
apSSIDTxDataPkts OBJECT-TYPE                   
    SYNTAX Counter32                       
    MAX-ACCESS read-only                   
    STATUS current               
    DESCRIPTION               
        "Data packages transmited."               
    ::= { apSSIDPfmStatEntry 1 }
    
apSSIDRxDataPkts OBJECT-TYPE                   
    SYNTAX Counter32                       
    MAX-ACCESS read-only                   
    STATUS current               
    DESCRIPTION               
        "Data packages received."               
    ::= { apSSIDPfmStatEntry 2 }    
    
apSSIDUplinkDataOctets OBJECT-TYPE                   
    SYNTAX Counter64                       
    MAX-ACCESS read-only                   
    STATUS current               
    DESCRIPTION               
        "Data packages bytes received."               
    ::= { apSSIDPfmStatEntry 3 } 
    
apSSIDDwlinkDataOctets OBJECT-TYPE                   
    SYNTAX Counter64                       
    MAX-ACCESS read-only                   
    STATUS current               
    DESCRIPTION               
        "Data packages bytes transmited."               
    ::= { apSSIDPfmStatEntry 4 }     
         
apSSIDChStatsDwlinkTotRetryPkts OBJECT-TYPE                   
    SYNTAX Counter32                       
    MAX-ACCESS read-only                   
    STATUS current               
    DESCRIPTION               
        "Downlink retransmit packages."               
    ::= { apSSIDPfmStatEntry 5 } 
    
apSSIDApChStatsNumStations OBJECT-TYPE                   
    SYNTAX Integer32                       
    MAX-ACCESS read-only                   
    STATUS current               
    DESCRIPTION               
        "Terminal number connected to the SSID."               
    ::= { apSSIDPfmStatEntry 6 }     
    


--**************************************************
--* apRadioIfPfmStatTable ends
--**************************************************

--**************************************************
--* apSSIDPeformanceStat ends here
--**************************************************



--**************************************************
--* apTermPeformanceStat starts here
--**************************************************


--**************************************************
--* apTermPfmStatTable begins
--**************************************************

apTermPfmStatTable OBJECT-TYPE      
    SYNTAX SEQUENCE OF ApTermPfmStatEntry
    MAX-ACCESS not-accessible      
    STATUS current      
    DESCRIPTION      
        "Statistic of  Terminal performance."
    ::= { apTermPeformanceStat 1 }    
      
apTermPfmStatEntry OBJECT-TYPE      
    SYNTAX ApTermPfmStatEntry      
    MAX-ACCESS not-accessible      
    STATUS current      
    DESCRIPTION      
        "The entry of apTermPfmStatTable."
    INDEX      
    { apStaAddress }      
    ::= { apTermPfmStatTable 1 }      

ApTermPfmStatEntry ::=
    SEQUENCE {
        apStaAddress                           MacAddress,               
        apStaUpTime                            TimeTicks,
        apAPReceivedStaSignalStrength          Counter32,
        apAPReceiveStaSNR											 Counter32,				
        apStaTxPkts                            Counter32,
        apStaTxBytes                           Counter32,
        apStaRxPkts														 Counter32,
        apStaRxBytes													 Counter32
       } 
                       
apStaAddress OBJECT-TYPE                   
    SYNTAX MacAddress                       
    MAX-ACCESS read-only                   
    STATUS current               
    DESCRIPTION               
        "MAC address of the terminal."               
    ::= { apTermPfmStatEntry 1 }
    
apStaUpTime OBJECT-TYPE                   
    SYNTAX TimeTicks                       
    MAX-ACCESS read-only                   
    STATUS current               
    DESCRIPTION               
        "Up time of the terminal."               
    ::= { apTermPfmStatEntry 2 } 
    
apAPReceivedStaSignalStrength OBJECT-TYPE                   
    SYNTAX Counter32                       
    MAX-ACCESS read-only                   
    STATUS current               
    DESCRIPTION               
        "Current signal strength of the terminal."               
    ::= { apTermPfmStatEntry 3 } 
    
apAPReceiveStaSNR OBJECT-TYPE                   
    SYNTAX Counter32                       
    MAX-ACCESS read-only                   
    STATUS current               
    DESCRIPTION               
        "SNR of the terminal."               
    ::= { apTermPfmStatEntry 4 } 
      
apStaTxPkts OBJECT-TYPE                   
    SYNTAX Counter32                       
    MAX-ACCESS read-only                   
    STATUS current               
    DESCRIPTION               
        "Total packages transmited to the terminal."               
    ::= { apTermPfmStatEntry 5 } 
    
apStaTxBytes OBJECT-TYPE                   
    SYNTAX Counter32                       
    MAX-ACCESS read-only                   
    STATUS current               
    DESCRIPTION               
        "Total bytes transmited to the terminal."               
    ::= { apTermPfmStatEntry 6 } 
    
    
apStaRxPkts OBJECT-TYPE                   
    SYNTAX Counter32                       
    MAX-ACCESS read-only                   
    STATUS current               
    DESCRIPTION               
        "Total packages receive from the terminal."               
    ::= { apTermPfmStatEntry 7 } 
    
apStaRxBytes OBJECT-TYPE                   
    SYNTAX Counter32                       
    MAX-ACCESS read-only                   
    STATUS current               
    DESCRIPTION               
        "Total bytes receive from the terminal."               
    ::= { apTermPfmStatEntry 8 } 

--**************************************************
--* apTermPfmStatTable ends
--**************************************************

--**************************************************
--* apTermPeformanceStat ends here
--**************************************************


--**************************************************
--* apWAPIPeformanceStat starts here
--**************************************************

--**************************************************
--* apWAPIPfmStatTable begins
--**************************************************

apWAPIPfmStatTable OBJECT-TYPE      
    SYNTAX SEQUENCE OF ApWAPIPfmStatEntry
    MAX-ACCESS not-accessible      
    STATUS current      
    DESCRIPTION      
        "Statistic of  WAPI performance."
    ::= { apWAPIPeformanceStat 1 }    
      
apWAPIPfmStatEntry OBJECT-TYPE      
    SYNTAX ApWAPIPfmStatEntry      
    MAX-ACCESS not-accessible      
    STATUS current      
    DESCRIPTION      
        "The entry of apWAPIPfmStatTable."
    INDEX      
    { apSTAAddress }      
    ::= { apWAPIPfmStatTable 1 }      

ApWAPIPfmStatEntry ::=
    SEQUENCE {
        apSTAAddress                             MacAddress, 
        apVersion                                Unsigned32,
        apControlledPortStatus                   TruthValue,
        apSelectedUnicastCipher									 OCTET STRING,
        apWPIReplayCounters                      Counter32,
        apWPIDecryptableErrors                   Counter32,
        apWPIMICErrors                           Counter32,
        apWAISignatureErrors                     Counter32,   
        apWAIHMACErrors                          Counter32,
        apWAIAuthResultFailures                  Counter32,
        apWAIDiscardCounters                     Counter32,
        apWAITimeoutCounters                     Counter32,
        apWAIFormatErrors                        Counter32,
        apWAICertificateHandshakeFailures        Counter32,
        apWAIUnicastHandshakeFailures            Counter32,
        apWAIMulticastHandshakeFailures          Counter32
       } 
                       
apSTAAddress OBJECT-TYPE                   
    SYNTAX MacAddress                       
    MAX-ACCESS read-only                   
    STATUS current               
    DESCRIPTION               
        "MAC address of the terminal."               
    ::= { apWAPIPfmStatEntry 1 }
    
apVersion OBJECT-TYPE                   
    SYNTAX Unsigned32                       
    MAX-ACCESS read-only                   
    STATUS current               
    DESCRIPTION               
        "WAPI version of the terminal."               
    ::= { apWAPIPfmStatEntry 2 }

apControlledPortStatus OBJECT-TYPE                   
    SYNTAX TruthValue                       
    MAX-ACCESS read-only                   
    STATUS current               
    DESCRIPTION               
        "Status of auhen control port."               
    ::= { apWAPIPfmStatEntry 3 }
    
apSelectedUnicastCipher OBJECT-TYPE                   
    SYNTAX OCTET STRING                       
    MAX-ACCESS read-only                   
    STATUS current               
    DESCRIPTION               
        "Unicast Encryption selected."               
    ::= { apWAPIPfmStatEntry 4 }    
    
apWPIReplayCounters OBJECT-TYPE                   
    SYNTAX Counter32                       
    MAX-ACCESS read-only                   
    STATUS current               
    DESCRIPTION               
        "MPDU number discarded."               
    ::= { apWAPIPfmStatEntry 5 }  
    
apWPIDecryptableErrors OBJECT-TYPE                   
    SYNTAX Counter32                       
    MAX-ACCESS read-only                   
    STATUS current               
    DESCRIPTION               
        "MPDU number discarded."               
    ::= { apWAPIPfmStatEntry 6 }  
    
apWPIMICErrors OBJECT-TYPE                   
    SYNTAX Counter32                       
    MAX-ACCESS read-only                   
    STATUS current               
    DESCRIPTION               
        "MPDU number discarded."               
    ::= { apWAPIPfmStatEntry 7 }     
    
apWAISignatureErrors OBJECT-TYPE                   
    SYNTAX Counter32                       
    MAX-ACCESS read-only                   
    STATUS current               
    DESCRIPTION               
        "WAI packages due to signature error."               
    ::= { apWAPIPfmStatEntry 8 } 
    
apWAIHMACErrors OBJECT-TYPE                   
    SYNTAX Counter32                       
    MAX-ACCESS read-only                   
    STATUS current               
    DESCRIPTION               
        "WAI packages due to MIC certificate failure."               
    ::= { apWAPIPfmStatEntry 9 }     
    
apWAIAuthResultFailures OBJECT-TYPE                   
    SYNTAX Counter32                       
    MAX-ACCESS read-only                   
    STATUS current               
    DESCRIPTION               
        "WAI number for authen failure."               
    ::= { apWAPIPfmStatEntry 10 } 

apWAIDiscardCounters OBJECT-TYPE                   
    SYNTAX Counter32                       
    MAX-ACCESS read-only                   
    STATUS current               
    DESCRIPTION               
        "Packages number discarded by WAI."               
    ::= { apWAPIPfmStatEntry 11 } 

apWAITimeoutCounters OBJECT-TYPE                   
    SYNTAX Counter32                       
    MAX-ACCESS read-only                   
    STATUS current               
    DESCRIPTION               
        "WAI packages number for time out."               
    ::= { apWAPIPfmStatEntry 12 }   
    
apWAIFormatErrors OBJECT-TYPE                   
    SYNTAX Counter32                       
    MAX-ACCESS read-only                   
    STATUS current               
    DESCRIPTION               
        "Number of WAI packages for format error."               
    ::= { apWAPIPfmStatEntry 13 }   
    
apWAICertificateHandshakeFailures OBJECT-TYPE                   
    SYNTAX Counter32                       
    MAX-ACCESS read-only                   
    STATUS current               
    DESCRIPTION               
        "Number of WAI packages for hand shake failure."               
    ::= { apWAPIPfmStatEntry 14 }      
        
apWAIUnicastHandshakeFailures OBJECT-TYPE                   
    SYNTAX Counter32                       
    MAX-ACCESS read-only                   
    STATUS current               
    DESCRIPTION               
        "Number of WAI packages for unicast hand shake failure."               
    ::= { apWAPIPfmStatEntry 15 }  
    
apWAIMulticastHandshakeFailures OBJECT-TYPE                   
    SYNTAX Counter32                       
    MAX-ACCESS read-only                   
    STATUS current               
    DESCRIPTION               
        "Number of WAI packages for multicast key failure."               
    ::= { apWAPIPfmStatEntry 16 }  
    

--**************************************************
--* apWAPIPfmStatTable ends
--**************************************************

--**************************************************
--* apWAPIPeformanceStat ends here
--**************************************************



--**************************************************
--* apQOSPeformanceStat starts here
--**************************************************

--**************************************************
--* cmApQosBasePfmStatTable begins
--**************************************************

apQosBasePfmStatTable OBJECT-TYPE      
    SYNTAX SEQUENCE OF ApQosBasePfmStatEntry
    MAX-ACCESS not-accessible      
    STATUS current      
    DESCRIPTION      
        "Statistic of  QOS basic performance."
    ::= { apQOSPeformanceStat 1 }    
      
apQosBasePfmStatEntry OBJECT-TYPE      
    SYNTAX ApQosBasePfmStatEntry      
    MAX-ACCESS not-accessible      
    STATUS current      
    DESCRIPTION      
        "The entry of apQosBasePfmStatTable."
    INDEX      
    { ifIndex }      
    ::= { apQosBasePfmStatTable 1 }      

ApQosBasePfmStatEntry ::=
    SEQUENCE {
        apQoSSvcQueAvgLen                          INTEGER, 
        apQoSSvcPktLossRatio                       INTEGER,
        apAvgTransSpeed                            INTEGER
       } 
                       
apQoSSvcQueAvgLen OBJECT-TYPE                   
    SYNTAX INTEGER                       
    MAX-ACCESS read-only                   
    STATUS current               
    DESCRIPTION               
        "Avearage queue length of QOS service."               
    ::= { apQosBasePfmStatEntry 1 }
    
apQoSSvcPktLossRatio OBJECT-TYPE                   
    SYNTAX INTEGER                       
    MAX-ACCESS read-only                   
    STATUS current               
    DESCRIPTION               
        "Total loss ratio of QoS."               
    ::= { apQosBasePfmStatEntry 2 }
 
apAvgTransSpeed OBJECT-TYPE                   
    SYNTAX INTEGER                       
    MAX-ACCESS read-only                   
    STATUS current               
    DESCRIPTION               
        "Avearage transmit speed."               
    ::= { apQosBasePfmStatEntry 3 }
    
--**************************************************
--* apQosBasePfmStatTable ends
--**************************************************

--**************************************************
--* apBackgroundQosPfmStatTable begins
--**************************************************

apBackgroundQosPfmStatTable OBJECT-TYPE      
    SYNTAX SEQUENCE OF ApBackgroundQosPfmStatEntry
    MAX-ACCESS not-accessible      
    STATUS current      
    DESCRIPTION      
        "Statistic of Background QOS performance."
    ::= { apQOSPeformanceStat 2 }    
      
apBackgroundQosPfmStatEntry OBJECT-TYPE      
    SYNTAX ApBackgroundQosPfmStatEntry      
    MAX-ACCESS not-accessible      
    STATUS current      
    DESCRIPTION      
        "The entry of apBackgroundQosPfmStatTable."
    INDEX      
    { ifIndex }      
    ::= { apBackgroundQosPfmStatTable 1 }      

ApBackgroundQosPfmStatEntry ::=
    SEQUENCE {
        apBgQueAvgLen                                INTEGER,
        apBgAvgBurst                                 INTEGER,
        apBgPktLossRatio                             INTEGER,
        apBgAvgTransSpeed                            INTEGER,                          
        apBgSvcLoss                                  INTEGER
       } 
                       
apBgQueAvgLen OBJECT-TYPE                   
    SYNTAX INTEGER                       
    MAX-ACCESS read-only                   
    STATUS current               
    DESCRIPTION               
        "Avearage queue length of QOS service."               
    ::= { apBackgroundQosPfmStatEntry 1 }
    
apBgAvgBurst OBJECT-TYPE                   
    SYNTAX INTEGER                       
    MAX-ACCESS read-only                   
    STATUS current               
    DESCRIPTION               
        "Avearage burst."               
    ::= { apBackgroundQosPfmStatEntry 2 }
 
apBgPktLossRatio OBJECT-TYPE                   
    SYNTAX INTEGER                       
    MAX-ACCESS read-only                   
    STATUS current               
    DESCRIPTION               
        "Package lost ratio."               
    ::= { apBackgroundQosPfmStatEntry 3 }
    
 apBgAvgTransSpeed OBJECT-TYPE                   
    SYNTAX INTEGER                       
    MAX-ACCESS read-only                   
    STATUS current               
    DESCRIPTION               
        "Avearage transmit speed."               
    ::= { apBackgroundQosPfmStatEntry 4 }
 
apBgSvcLoss OBJECT-TYPE                   
    SYNTAX INTEGER                       
    MAX-ACCESS read-only                   
    STATUS current               
    DESCRIPTION               
        "Service loss."               
    ::= { apBackgroundQosPfmStatEntry 5 }
    
--**************************************************
--* apBackgroundQosPfmStatTable ends
--**************************************************

--**************************************************
--* apBestEffortQosPfmStatTable begins
--**************************************************

apBestEffortQosPfmStatTable OBJECT-TYPE      
    SYNTAX SEQUENCE OF ApBestEffortQosPfmStatEntry
    MAX-ACCESS not-accessible      
    STATUS current      
    DESCRIPTION      
        "Statistic of BestEffort QOS performance."
    ::= { apQOSPeformanceStat 3 }    
      
apBestEffortQosPfmStatEntry OBJECT-TYPE      
    SYNTAX ApBestEffortQosPfmStatEntry      
    MAX-ACCESS not-accessible      
    STATUS current      
    DESCRIPTION      
        "The entry of apBestEffortQosPfmStatTable."
    INDEX      
    { ifIndex }      
    ::= { apBestEffortQosPfmStatTable 1 }      

ApBestEffortQosPfmStatEntry ::=
    SEQUENCE {
        apBeQueAvgLen                                INTEGER,
        apBeAvgBurst                                 INTEGER,
        apBePktLossRatio                             INTEGER,
        apBeAvgTransSpeed                            INTEGER,                          
        apBeSvcLoss                                  INTEGER
       } 
                       
apBeQueAvgLen OBJECT-TYPE                   
    SYNTAX INTEGER                       
    MAX-ACCESS read-only                   
    STATUS current               
    DESCRIPTION               
        "Avearage queue length of QOS service."               
    ::= { apBestEffortQosPfmStatEntry 1 }
    
apBeAvgBurst OBJECT-TYPE                   
    SYNTAX INTEGER                       
    MAX-ACCESS read-only                   
    STATUS current               
    DESCRIPTION               
        "Avearage burst."               
    ::= { apBestEffortQosPfmStatEntry 2 }
 
apBePktLossRatio OBJECT-TYPE                   
    SYNTAX INTEGER                       
    MAX-ACCESS read-only                   
    STATUS current               
    DESCRIPTION               
        "Package lost ratio."               
    ::= { apBestEffortQosPfmStatEntry 3 }
    
 apBeAvgTransSpeed OBJECT-TYPE                   
    SYNTAX INTEGER                       
    MAX-ACCESS read-only                   
    STATUS current               
    DESCRIPTION               
        "Avearage transmit speed."               
    ::= { apBestEffortQosPfmStatEntry 4 }
 
apBeSvcLoss OBJECT-TYPE                   
    SYNTAX INTEGER                       
    MAX-ACCESS read-only                   
    STATUS current               
    DESCRIPTION               
        "Service loss."               
    ::= { apBestEffortQosPfmStatEntry 5 }
    
    
       
--**************************************************
--* apBestEffortQosPfmStatTable ends
--**************************************************

--**************************************************
--* apVoiceQosPfmStatTable begins
--**************************************************

apVoiceQosPfmStatTable OBJECT-TYPE      
    SYNTAX SEQUENCE OF ApVoiceQosPfmStatEntry
    MAX-ACCESS not-accessible      
    STATUS current      
    DESCRIPTION      
        "Statistic of Voice QOS performance."
    ::= { apQOSPeformanceStat 4 }    
      
apVoiceQosPfmStatEntry OBJECT-TYPE      
    SYNTAX ApVoiceQosPfmStatEntry      
    MAX-ACCESS not-accessible      
    STATUS current      
    DESCRIPTION      
        "The entry of apVoiceQosPfmStatTable."
    INDEX      
    { ifIndex }      
    ::= { apVoiceQosPfmStatTable 1 }      

ApVoiceQosPfmStatEntry ::=
    SEQUENCE {
        apVoiceQueAvgLen                                INTEGER,
        apVoiceAvgBurst                                 INTEGER,
        apVoicePktLossRatio                             INTEGER,
        apVoiceAvgTransSpeed                            INTEGER,                          
        apVoicePutThroughRatio                          INTEGER,
        apVoiceDropRatio																INTEGER,
        apVoiceSvcLoss																	INTEGER,									
        apVoiceExceedMaxUsersRequest										INTEGER						
       } 
                       
apVoiceQueAvgLen OBJECT-TYPE                   
    SYNTAX INTEGER                       
    MAX-ACCESS read-only                   
    STATUS current               
    DESCRIPTION               
        "Avearage queue length of QOS service."               
    ::= { apVoiceQosPfmStatEntry 1 }
    
apVoiceAvgBurst OBJECT-TYPE                   
    SYNTAX INTEGER                       
    MAX-ACCESS read-only                   
    STATUS current               
    DESCRIPTION               
        "Avearage burst."               
    ::= { apVoiceQosPfmStatEntry 2 }
 
apVoicePktLossRatio OBJECT-TYPE                   
    SYNTAX INTEGER                       
    MAX-ACCESS read-only                   
    STATUS current               
    DESCRIPTION               
        "Package lost ratio."               
    ::= { apVoiceQosPfmStatEntry 3 }
    
 apVoiceAvgTransSpeed OBJECT-TYPE                   
    SYNTAX INTEGER                       
    MAX-ACCESS read-only                   
    STATUS current               
    DESCRIPTION               
        "Avearage transmit speed."               
    ::= { apVoiceQosPfmStatEntry 4 }
 
apVoicePutThroughRatio OBJECT-TYPE                    
    SYNTAX INTEGER                                    
    MAX-ACCESS read-only                              
    STATUS current                               
    DESCRIPTION                               
        "Put through ratio of the service."               
    ::= { apVoiceQosPfmStatEntry 5 }                
    
apVoiceDropRatio OBJECT-TYPE                    
    SYNTAX INTEGER                                    
    MAX-ACCESS read-only                              
    STATUS current                               
    DESCRIPTION                               
        "Drop ratio of the voice service."               
    ::= { apVoiceQosPfmStatEntry 6 }    
    
apVoiceSvcLoss OBJECT-TYPE                    
    SYNTAX INTEGER                                    
    MAX-ACCESS read-only                              
    STATUS current                               
    DESCRIPTION                               
        "loss service."               
    ::= { apVoiceQosPfmStatEntry 7 }   
    
apVoiceExceedMaxUsersRequest OBJECT-TYPE                    
    SYNTAX INTEGER                                    
    MAX-ACCESS read-only                              
    STATUS current                               
    DESCRIPTION                               
        "voice exceed max users request."               
    ::= { apVoiceQosPfmStatEntry 8 }     
  
       
--**************************************************
--* apVoiceQosPfmStatTable ends
--**************************************************


--**************************************************
--* apVedioQosPfmStatTable begins
--**************************************************

apVedioQosPfmStatTable OBJECT-TYPE      
    SYNTAX SEQUENCE OF ApVedioQosPfmStatEntry
    MAX-ACCESS not-accessible      
    STATUS current      
    DESCRIPTION      
        "Statistic of Voice QOS performance."
    ::= { apQOSPeformanceStat 5 }    
      
apVedioQosPfmStatEntry OBJECT-TYPE      
    SYNTAX ApVedioQosPfmStatEntry      
    MAX-ACCESS not-accessible      
    STATUS current      
    DESCRIPTION      
        "The entry of apVedioQosPfmStatTable."
    INDEX      
    { ifIndex }      
    ::= { apVedioQosPfmStatTable 1 }      

ApVedioQosPfmStatEntry ::=
    SEQUENCE {
        apVedioQueAvgLen                                INTEGER,
        apVedioAvgBurst                                 INTEGER,
        apVedioPktLossRatio                             INTEGER,
        apVedioAvgTransSpeed                            INTEGER,                          
        apVedioPutThroughRatio                          INTEGER,
        apVedioDropRatio																INTEGER,
        apVedioSvcLoss																	INTEGER,									
        apVedioExceedMaxUsersRequest										INTEGER						
       } 
                       
apVedioQueAvgLen OBJECT-TYPE                   
    SYNTAX INTEGER                       
    MAX-ACCESS read-only                   
    STATUS current               
    DESCRIPTION               
        "Avearage queue length of QOS service."               
    ::= { apVedioQosPfmStatEntry 1 }
    
apVedioAvgBurst OBJECT-TYPE                   
    SYNTAX INTEGER                       
    MAX-ACCESS read-only                   
    STATUS current               
    DESCRIPTION               
        "Avearage burst."               
    ::= { apVedioQosPfmStatEntry 2 }
 
apVedioPktLossRatio OBJECT-TYPE                   
    SYNTAX INTEGER                       
    MAX-ACCESS read-only                   
    STATUS current               
    DESCRIPTION               
        "Package lost ratio."               
    ::= { apVedioQosPfmStatEntry 3 }
    
 apVedioAvgTransSpeed OBJECT-TYPE                   
    SYNTAX INTEGER                       
    MAX-ACCESS read-only                   
    STATUS current               
    DESCRIPTION               
        "Avearage transmit speed."               
    ::= { apVedioQosPfmStatEntry 4 }
 
apVedioPutThroughRatio OBJECT-TYPE                    
    SYNTAX INTEGER                                    
    MAX-ACCESS read-only                              
    STATUS current                               
    DESCRIPTION                               
        "Put through ratio of the service."               
    ::= { apVedioQosPfmStatEntry 5 }                
    
apVedioDropRatio OBJECT-TYPE                    
    SYNTAX INTEGER                                    
    MAX-ACCESS read-only                              
    STATUS current                               
    DESCRIPTION                               
        "Drop ratio of the voice service."               
    ::= { apVedioQosPfmStatEntry 6 }    
    
apVedioSvcLoss OBJECT-TYPE                    
    SYNTAX INTEGER                                    
    MAX-ACCESS read-only                              
    STATUS current                               
    DESCRIPTION                               
        "loss service."               
    ::= { apVedioQosPfmStatEntry 7 }   
    
apVedioExceedMaxUsersRequest OBJECT-TYPE                    
    SYNTAX INTEGER                                    
    MAX-ACCESS read-only                              
    STATUS current                               
    DESCRIPTION                               
        "voice exceed max users request."               
    ::= { apVedioQosPfmStatEntry 8 }     
  
       
--**************************************************
--* apVedioQosPfmStatTable ends
--**************************************************

--**************************************************
--* apQOSPeformanceStat ends here
--**************************************************

END
