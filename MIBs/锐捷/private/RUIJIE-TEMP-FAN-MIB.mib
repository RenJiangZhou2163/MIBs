-- *****************************************************************
-- RUIJIE-SYSTEM-MIB.mib:  Ruijie System MIB file
--
-- Feb 2012, HuangY
--
-- Copyright (c) 2012 by Ruijie Networks Co.,Ltd.
-- All rights reserved.
-- 
-- *****************************************************************
--

RUIJIE-TEMP-FAN-MIB DEFINITIONS ::= BEGIN

IMPORTS
        MODULE-IDENTITY,
        OBJECT-TYPE,
        NOTIFICATION-TYPE,
        Integer32
               FROM SNMPv2-SMI
        MODULE-COMPLIANCE
               FROM SNMPv2-CONF
        ruijieMgmt
                FROM RUIJIE-SMI
        ruijieSystemTemperatureCurrent
                FROM RUIJIE-SYSTEM-MIB;

ruijieTempFanMIB MODULE-IDENTITY
        LAST-UPDATED "200203200000Z"
        ORGANIZATION "Ruijie Networks Co.,Ltd."
        CONTACT-INFO
                " 
                Tel: 4008-111-000 

                E-mail: service@ruijie.com.cn"
        DESCRIPTION
                "This module defines ruijie system mibs."
        REVISION      "200203200000Z"
        DESCRIPTION
                "Initial version of this MIB module."
        ::= { ruijieMgmt 109}

ruijieTempFanTraps OBJECT IDENTIFIER ::= { ruijieTempFanMIB 1 }

--Temperature Too High Trap
temperatureTooHighTrap NOTIFICATION-TYPE
        OBJECTS   {ruijieSystemTemperatureCurrent}
        STATUS     current
        DESCRIPTION
                "Temperature Too High warning and report the current temperature."
        ::= { ruijieTempFanTraps 1 }   
           
--Temperature Too High Recover Trap 
temperTooHighRecovTrap NOTIFICATION-TYPE
        OBJECTS   {ruijieSystemTemperatureCurrent}
        STATUS     current
        DESCRIPTION
                "Clear the warning of temperature too high and report the current temperature."
        ::= { ruijieTempFanTraps 2 }

--Fan Failure Trap
fanFailure NOTIFICATION-TYPE
        STATUS     current
        DESCRIPTION
                "Fan stopped warning."
        ::= { ruijieTempFanTraps 3 }
  
END
