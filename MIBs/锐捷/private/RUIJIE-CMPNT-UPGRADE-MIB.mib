-- *****************************************************************
-- RUIJIE-CMPNT-UPGRADE-MIB.mib:  Ruijie Component upgrade MIB file
--
-- Sep 2019, liweibin
--
-- Copyright (c) 2019 by Ruijie Networks Co.,Ltd.
-- All rights reserved.
-- 
-- *****************************************************************
--

RUIJIE-CMPNT-UPGRADE-MIB DEFINITIONS ::= BEGIN

IMPORTS
        MODULE-IDENTITY,
        OBJECT-TYPE,
        Integer32,
        Unsigned32,
        Counter64,
        IpAddress
                FROM SNMPv2-SMI
        TruthValue,
        DisplayString,
        RowStatus,
        MacAddress
                FROM SNMPv2-TC
        MODULE-COMPLIANCE,
        OBJECT-GROUP
                FROM SNMPv2-CONF
        IfIndex,
        ConfigStatus
                FROM RUIJIE-TC        
        ruijieMgmt
                FROM RUIJIE-SMI;
				
ruijieCmpntPatchMIB MODULE-IDENTITY
        LAST-UPDATED "201906180000Z"
        ORGANIZATION "Ruijie Networks Co.,Ltd."
        CONTACT-INFO
                " 
                Tel: 4008-111-000 

                E-mail: service@ruijie.com.cn"
        DESCRIPTION
                "This module defines ruijie system component patch mibs."
        REVISION      "201906180000Z"
        DESCRIPTION
                "Initial version of this MIB module."
        ::= { ruijieMgmt 162}

ruijieCmpntPatchMIBObjects OBJECT IDENTIFIER ::= { ruijieCmpntPatchMIB 1 }

ruijieCmpntPatchTable OBJECT-TYPE
        SYNTAX SEQUENCE OF RuijieCmpntPatchEntry
        MAX-ACCESS not-accessible
        STATUS current
        DESCRIPTION
               "A table of component patch entries."
        ::= { ruijieCmpntPatchMIBObjects 1 }

ruijieCmpntPatchEntry OBJECT-TYPE
        SYNTAX RuijieCmpntPatchEntry
        MAX-ACCESS not-accessible
        STATUS current
        DESCRIPTION
                "Entry contains component patch details."  
        INDEX { ruijieCmpntDevIndex,
                ruijieCmpntPatchIndex }
        ::= { ruijieCmpntPatchTable 1 }

RuijieCmpntPatchEntry ::=
        SEQUENCE {
                ruijieCmpntDevIndex Integer32,
                ruijieCmpntPatchIndex Integer32,
                ruijieCmpntPatchDevId Integer32,
                ruijieCmpntPatchSlotId Integer32,
                ruijieCmpntPatchCpuId Integer32,
                ruijieCmpntPatchName DisplayString,
                ruijieCmpntPatchStatus DisplayString,
                ruijieCmpntPatchFlag DisplayString,
                ruijieCmpntPatchDesc DisplayString
        }

ruijieCmpntDevIndex OBJECT-TYPE
        SYNTAX        Integer32
        MAX-ACCESS read-only
        STATUS current
        DESCRIPTION
            "An index that represents a Devices."
        ::= { ruijieCmpntPatchEntry 1 }
		
ruijieCmpntPatchIndex OBJECT-TYPE
        SYNTAX        Integer32
        MAX-ACCESS read-only
        STATUS current
        DESCRIPTION
            "An index that represents a component patch."
        ::= { ruijieCmpntPatchEntry 2 }

ruijieCmpntPatchDevId OBJECT-TYPE
        SYNTAX        Integer32
        MAX-ACCESS read-only
        STATUS current
        DESCRIPTION
            "Device Identification."
        ::= { ruijieCmpntPatchEntry 3 }
		
ruijieCmpntPatchSlotId OBJECT-TYPE
        SYNTAX        Integer32
        MAX-ACCESS read-only
        STATUS current
        DESCRIPTION
            "Slot Identification."
        ::= { ruijieCmpntPatchEntry 4 }
		
ruijieCmpntPatchCpuId OBJECT-TYPE
        SYNTAX        Integer32
        MAX-ACCESS read-only
        STATUS current
        DESCRIPTION
            "Cpu Identification."
        ::= { ruijieCmpntPatchEntry 5 }

ruijieCmpntPatchName OBJECT-TYPE
        SYNTAX        DisplayString
        MAX-ACCESS    read-only
        STATUS        current
        DESCRIPTION
            "Currtent Name of the component patch."
        ::= { ruijieCmpntPatchEntry 6 }
		
ruijieCmpntPatchStatus OBJECT-TYPE
        SYNTAX        DisplayString
        MAX-ACCESS    read-only
        STATUS        current
        DESCRIPTION
            "Currtent status of the component patch."
        ::= { ruijieCmpntPatchEntry 7 }
		
ruijieCmpntPatchFlag OBJECT-TYPE
        SYNTAX        DisplayString
        MAX-ACCESS    read-only
        STATUS        current
        DESCRIPTION
            "Currtent hot and cold sign of the component patch."
        ::= { ruijieCmpntPatchEntry 8 }
		
ruijieCmpntPatchDesc OBJECT-TYPE
        SYNTAX        DisplayString
        MAX-ACCESS    read-only
        STATUS        current
        DESCRIPTION
            "The component patch description."
        ::= { ruijieCmpntPatchEntry 9 }

END
