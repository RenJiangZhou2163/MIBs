-- *****************************************************************
-- RUIJIE-CPP-MIB.mib:  Ruijie CPP MIB file
--
-- Dec 2014, Linxiaojie
--
-- Copyright (c) 2012 by Ruijie Networks Co.,Ltd.
-- All rights reserved.
-- 
-- *****************************************************************
--

RUIJIE-CPP-MIB DEFINITIONS ::= BEGIN

IMPORTS
        MODULE-IDENTITY,
        OBJECT-TYPE,
        NOTIFICATION-TYPE,
        Integer32,
        OBJECT-TYPE
                FROM SNMPv2-SMI
        TruthValue,
        DisplayString
                FROM SNMPv2-TC
        MODULE-COMPLIANCE,
        OBJECT-GROUP
                FROM SNMPv2-CONF
        ruijieMgmt
                FROM RUIJIE-SMI;

ruijieCPPMIB MODULE-IDENTITY
        LAST-UPDATED "201412192100Z"
        ORGANIZATION "Ruijie Networks Co.,Ltd."
        CONTACT-INFO
                " 
                Tel: 4008-111-000 

                E-mail: service@ruijie.com.cn"
        DESCRIPTION
                "This module defines ruijie cpp mibs."
        REVISION      "201412192100Z"
        DESCRIPTION
                "Add a table about cpp."
        REVISION      "201412192100Z"
        DESCRIPTION
                "Initial version of this MIB module."
        ::= { ruijieMgmt 132 }

ruijieCPPMIBObjects OBJECT IDENTIFIER ::= { ruijieCPPMIB 1 }

ruijieCPPTable OBJECT-TYPE
        SYNTAX 			SEQUENCE OF RuijieCPPEntry
        MAX-ACCESS 	not-accessible
        STATUS 			current
        DESCRIPTION
            " "
        ::= { ruijieCPPMIBObjects 1 }

ruijieCPPEntry OBJECT-TYPE
        SYNTAX 			RuijieCPPEntry
        MAX-ACCESS 	not-accessible
        STATUS 			current
        DESCRIPTION
            " "
        INDEX { cppIndex }
        ::= { ruijieCPPTable 1 }

RuijieCPPEntry ::=
        SEQUENCE {
            cppIndex			Integer32,
            cppDeviceId			Integer32,
            cppSlotId			Integer32,
            cppCardIndex		DisplayString,
            cppPacketType		DisplayString,
            cppTrafficClass		Integer32,
            cppBandwidth		Integer32,
            cppRate			Integer32,
            cppDrop			Integer32,
            cppTotal			Integer32,
            cppTotalDrop		Integer32
        }
cppIndex OBJECT-TYPE
        SYNTAX 			Integer32 (1..2147483647)
        MAX-ACCESS 	read-only
        STATUS 			current
        DESCRIPTION
            " "
        ::= { ruijieCPPEntry 1 }

cppDeviceId OBJECT-TYPE
        SYNTAX 			Integer32 (1..2147483647)
        MAX-ACCESS 	read-only
        STATUS 			current
        DESCRIPTION
            " "
        ::= { ruijieCPPEntry 2 }

cppSlotId OBJECT-TYPE
        SYNTAX 			Integer32 (1..2147483647)
        MAX-ACCESS 	read-only
        STATUS 			current
        DESCRIPTION
            " "
        ::= { ruijieCPPEntry 3 }

cppCardIndex OBJECT-TYPE
        SYNTAX DisplayString(SIZE (1..32))
        MAX-ACCESS read-only
        STATUS current
        DESCRIPTION
            " "
        ::= { ruijieCPPEntry 4 }

cppPacketType OBJECT-TYPE
        SYNTAX DisplayString(SIZE (1..32))
        MAX-ACCESS read-only
        STATUS current
        DESCRIPTION
            " "
        ::= { ruijieCPPEntry 5 }

cppTrafficClass OBJECT-TYPE
        SYNTAX 			Integer32 (1..2147483647)
        MAX-ACCESS 	read-only
        STATUS 			current
        DESCRIPTION
            " "
        ::= { ruijieCPPEntry 6 }

cppBandwidth OBJECT-TYPE
        SYNTAX 			Integer32 (1..2147483647)
        MAX-ACCESS 	read-only
        STATUS 			current
        DESCRIPTION
            " "
        ::= { ruijieCPPEntry 7 }

cppRate OBJECT-TYPE
        SYNTAX 			Integer32 (1..2147483647)
        MAX-ACCESS 	read-only
        STATUS 			current
        DESCRIPTION
            " "
        ::= { ruijieCPPEntry 8 }

cppDrop OBJECT-TYPE
        SYNTAX 			Integer32 (1..2147483647)
        MAX-ACCESS 	read-only
        STATUS 			current
        DESCRIPTION
            " "
        ::= { ruijieCPPEntry 9 }

cppTotal OBJECT-TYPE
        SYNTAX 			Integer32 (1..2147483647)
        MAX-ACCESS 	read-only
        STATUS 			current
        DESCRIPTION
            " "
        ::= { ruijieCPPEntry 10 }

cppTotalDrop OBJECT-TYPE
        SYNTAX 			Integer32 (1..2147483647)
        MAX-ACCESS 	read-only
        STATUS 			current
        DESCRIPTION
            " "
        ::= { ruijieCPPEntry 11 }
		

ruijieCPPTcTable OBJECT-TYPE
        SYNTAX 			SEQUENCE OF RuijieCPPTcEntry
        MAX-ACCESS 	not-accessible
        STATUS 			current
        DESCRIPTION
            " "
        ::= { ruijieCPPMIBObjects 2 }

ruijieCPPTcEntry OBJECT-TYPE
        SYNTAX 			RuijieCPPTcEntry
        MAX-ACCESS 	not-accessible
        STATUS 			current
        DESCRIPTION
            " "
        INDEX { cppTcIndex }
        ::= { ruijieCPPTcTable 1 }

RuijieCPPTcEntry ::=
        SEQUENCE {
            cppTcIndex			Integer32,
            cppTcDeviceId	        Integer32,
            cppTcSlotId			Integer32,
            cppTcTrafficClass		Integer32,
            cppTcCardIndex		DisplayString,
            cppTcBandwidth		Integer32,
            cppTcRate			Integer32,
            cppTcDrop			Integer32
        }
		
cppTcIndex OBJECT-TYPE
        SYNTAX 			Integer32 (1..2147483647)
        MAX-ACCESS 	read-only
        STATUS 			current
        DESCRIPTION
            " "
        ::= { ruijieCPPTcEntry 1 }

cppTcDeviceId OBJECT-TYPE
        SYNTAX 			Integer32 (1..2147483647)
        MAX-ACCESS 	read-only
        STATUS 			current
        DESCRIPTION
            " "
        ::= { ruijieCPPTcEntry 2 }

cppTcSlotId OBJECT-TYPE
        SYNTAX 			Integer32 (1..2147483647)
        MAX-ACCESS 	read-only
        STATUS 			current
        DESCRIPTION
            " "
        ::= { ruijieCPPTcEntry 3 }

cppTcTrafficClass OBJECT-TYPE
        SYNTAX 			Integer32 (1..2147483647)
        MAX-ACCESS 	read-only
        STATUS 			current
        DESCRIPTION
            " "
        ::= { ruijieCPPTcEntry 4 }

cppTcCardIndex OBJECT-TYPE
        SYNTAX DisplayString(SIZE (1..32))
        MAX-ACCESS read-only
        STATUS current
        DESCRIPTION
            " "
        ::= { ruijieCPPTcEntry 5 }
		
cppTcBandwidth OBJECT-TYPE
        SYNTAX 			Integer32 (1..2147483647)
        MAX-ACCESS 	read-only
        STATUS 			current
        DESCRIPTION
            " "
        ::= { ruijieCPPTcEntry 6 }

cppTcRate OBJECT-TYPE
        SYNTAX 			Integer32 (1..2147483647)
        MAX-ACCESS 	read-only
        STATUS 			current
        DESCRIPTION
            " "
        ::= { ruijieCPPTcEntry 7 }

cppTcDrop OBJECT-TYPE
        SYNTAX 			Integer32 (1..2147483647)
        MAX-ACCESS 	read-only
        STATUS 			current
        DESCRIPTION
            " "
        ::= { ruijieCPPTcEntry 8 }
	
ruijieCPPMessageContent OBJECT-TYPE
        SYNTAX OCTET STRING(SIZE(0..512))
        MAX-ACCESS accessible-for-notify
        STATUS current
        DESCRIPTION
          "CPP Message Content"
        ::= { ruijieCPPMIBObjects 3}
        
ruijieCPPMessagePortContent OBJECT-TYPE
        SYNTAX OCTET STRING(SIZE(0..512))
        MAX-ACCESS accessible-for-notify
        STATUS current
        DESCRIPTION
          "CPP Port Attack Content"
        ::= { ruijieCPPMIBObjects 4}
        
-- notifications

ruijieCPPMIBNotifications OBJECT IDENTIFIER ::= { ruijieCPPMIB 2 }

ruijieCPPMessageGenerated NOTIFICATION-TYPE
	OBJECTS   {ruijieCPPMessageContent}
	STATUS	   current
	DESCRIPTION
	       "When CPP Event Occur, this message is Generated."
	::= { ruijieCPPMIBNotifications 1 }
    
ruijieCPPMIBPortNotifications OBJECT IDENTIFIER ::= { ruijieCPPMIB 3 }
    
ruijieCPPMessagePort NOTIFICATION-TYPE
	OBJECTS   {ruijieCPPMessagePortContent}
	STATUS	   current
	DESCRIPTION
	       "When CPP Port Attack Occur, this message is Generated."
	::= { ruijieCPPMIBPortNotifications 1 }
	
END
