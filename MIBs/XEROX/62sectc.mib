XEROX-SECURITY-TC DEFINITIONS ::= BEGIN
--  Module: Security Textual Conventions
--  Author: Ira McDonald, Rob Sklut, and Rob Westfall
--  File:   62sectc.mib
--  Date:   28 April 2000 - Version 4.00.int

--  Textual Conventions companion to the Security MIB

IMPORTS
--  MODULE-IDENTITY, OBJECT-TYPE
--          FROM SNMPv2-SMI             -  IETF RFC 1442/1902/2578
--  TEXTUAL-CONVENTION
--          FROM SNMPv2-TC              -  IETF RFC 1443/1903/2579
--  xeroxCommonMIB
--          FROM XEROX-COMMON-MIB/
    xeroxCommonMIB
        FROM    XEROX-COMMON-MIB
    OBJECT-TYPE
        FROM    RFC-1212
    ;

xcmSecTC OBJECT IDENTIFIER
--  LAST-UPDATED "0004280000Z" -  28 April 2000
--  ORGANIZATION "Xerox Corporation - XCMI Working Group"
--  CONTACT-INFO
--      "           XCMI Editors
--      Email:      xcmieditors@cp10.es.xerox.com
--
--      - 
--      -  BEGIN XEROX PRIVATE DATA
--      - 
--                  Ira McDonald
--      Postal:     High North Inc
--                  221 Ridge Ave
--                  Grand Marais, MI  49839
--      Voice:      906-494-2434 or 906-494-2697
--      Email:      imcdonal@sdsp.mc.xerox.com
--
--                  Rob Sklut
--      Postal:     Xerox Corporation, MS 801-36D
--                  1350 Jefferson Rd
--                  Rochester, NY  14623
--      Voice:      716-427-5706
--      Email:      Robert_Sklut@.mc.xerox.com
--
--                  Robert Westfall
--      Postal:     Xerox Corporation, MS 834-03E
--                  300 Canalview Blvd
--                  Rochester, NY  14623
--      Voice:      716-231-0976
--      Email:      robert_westfall@mc.xerox.com
--      - 
--      -  ENDOF XEROX PRIVATE DATA
--      - 
--      "
--  DESCRIPTION
--      "Version:   4.00.int
--
--      The TC module for textual conventions, enumerated types, OIDs,
--      and other volatile elements of the companion Security MIB
--      ('xcmSecMIB'), which supports both basic configuration and
--      active management of security information for network accessible
--      host systems, including authentication, authorization, and
--      accounting.
--
--      See:    OSI Reference Model - Part 4:  Systems Management
--              (CCITT X.700:1992 | ISO 7498-4:1992).
--      See:    OSI Reference Model - Part 2:  Security Architecture
--              (CCITT X.800:1992 | ISO 7498-2:1992).
--
--      Copyright (C) 2000 Xerox Corporation. All Rights Reserved."
    ::= { xeroxCommonMIB 71 }

--
--          The Security TC
--
--          Textual Conventions

--.ts 'XcmSecAuditSupport'
XcmSecAuditSupport ::= 
--  STATUS      current
--  DESCRIPTION
--      "Terse conformance statement of security 'audit' methods
--      supported by this management agent implementation (ie, version)
--      on this host system, specified in a bit-mask.
--
--      The current set of values (which may be extended in the future)
--      is given below:
--
--            1 : auditLoginAndLogoutAccess
--            2 : auditFileAndObjectAccess
--            4 : auditAccountAndUserAccess
--            8 : auditPolicyAccess
--           16 : auditKeyAndProtocolAccess
--           32 : auditServiceAndProfileAccess
--           64 : auditGeneralAndFindAccess
--          128 : auditConfigAndViewAccess
--          256 : auditLoginAndLogoutChange
--          512 : auditFileAndObjectChange
--         1024 : auditAccountAndUserChange
--         2048 : auditPolicyChange
--         4096 : auditKeyAndProtocolChange
--         8192 : auditServiceAndProfileChange
--        16384 : auditGeneralAndFindChange
--        32768 : auditConfigAndViewChange
--        65536 : auditSystemStartupAndShutdown
--       131072 : auditSessionStartupAndShutdown
--
--      Usage:  Conforming management agents shall ALWAYS accurately
--      report their support for security 'audit' methods."
    INTEGER (0..2147483647)  -- biggest int = 2**31-1

--.ts 'XcmSecFacilitySupport'
XcmSecFacilitySupport ::= 
--  STATUS      current
--  DESCRIPTION
--      "Terse conformance statement of secure session 'facilities'
--      supported by this management agent implementation (ie, version)
--      on this host system, specified in a bit-mask.
--
--      The current set of values (which may be extended in the future)
--      is given below:
--
--      -   Session level operations
--            1 : sessionSupport        -  open, close
--            2 : sessionManage         -  manage
--      -   Bracket level operations
--            4 : bracketSupport        -  open, close, commit
--            8 : bracketUndo
--           16 : bracketSync
--           32 : bracketResync
--      -   Trace level operations
--           64 : traceSupport          -  open, close
--          128 : traceEncrypt          -  encrypt, decrypt
--
--      Usage:  Conforming management agents shall ALWAYS accurately
--      report their support for secure session 'facilities'."
    INTEGER (0..2147483647)  -- biggest int = 2**31-1

--.ts 'XcmSecFeatureSupport'
XcmSecFeatureSupport ::= 
--  STATUS      current
--  DESCRIPTION
--      "Terse conformance statement of Security MIB 'features'
--      supported by this management agent implementation (ie, version)
--      on this host system, specified in a bit-mask.
--
--      The current set of values (which may be extended in the future)
--      is given below:
--
--            1 : secFeatureAccountName
--            2 : secFeatureAccountAlias
--            4 : secFeatureAccountRole
--            8 : secFeatureAccountSkill
--           16 : secFeaturePolicyServiceTypeOID
--           32 : secFeatureUserName
--           64 : secFeatureUserAlias
--          128 : secFeatureUserRole
--          256 : secFeatureUserSkill
--          512 : secFeaturePosixRights
--         1024 : secFeaturePosixVerbs
--         2048 : secFeatureObjectSubtree
--         4096 : secFeatureConciseMode
--         8192 : secFeatureExcludeMode
--
--      Usage:  Conforming management agents shall ALWAYS accurately
--      report their support for Security MIB 'features'."
    INTEGER (0..2147483647)  -- biggest int = 2**31-1

--.ts 'XcmSecGroupSupport'
XcmSecGroupSupport ::= 
--  STATUS      current
--  DESCRIPTION
--      "Terse conformance statement of Security MIB object groups
--      supported by this management agent implementation (ie, version)
--      on this host system, specified in a bit-mask.
--
--      The current set of values (which may be extended in the future)
--      is given below:
--
--            1 : secGeneralGroup           -  Mandatory
--            2 : secConfigGroup            -  Mandatory
--            4 : secConfigAccessGroup      -  Mandatory
--            8 : secConfigProtocolGroup    -  Conditionally Mandatory
--           16 : secConfigViewGroup        -  Conditionally Mandatory
--           32 : secAccountGroup           -  Conditionally Mandatory
--           64 : secAccountExtGroup        -  Conditionally Mandatory
--          128 : secEventGroup             -  Conditionally Mandatory
--          256 : secFindIntegerGroup       -  Conditionally Mandatory
--          512 : secFindOIDGroup           -  Conditionally Mandatory
--         1024 : secFindParentGroup        -  Conditionally Mandatory
--         2048 : secFindStringGroup        -  Conditionally Mandatory
--         4096 : secKeyGroup               -  Conditionally Mandatory
--         8192 : secLinkGroup              -  Conditionally Mandatory
--        16384 : secPolicyGroup            -  Conditionally Mandatory
--        32768 : secPolicyLimitGroup       -  Conditionally Mandatory
--        65536 : secPolicyUsageGroup       -  Conditionally Mandatory
--       131072 : secPolicyVerbGroup        -  Conditionally Mandatory
--       262144 : secProfileGroup           -  Conditionally Mandatory
--       524288 : secProfileDetailGroup     -  Conditionally Mandatory
--      1048576 : secServiceGroup           -  Conditionally Mandatory
--      2097152 : secSessionGroup           -  Conditionally Mandatory
--      4194304 : secSessionExtGroup        -  Conditionally Mandatory
--      8388608 : secTeamGroup              -  Conditionally Mandatory
--     16777216 : secTimestampGroup         -  Conditionally Mandatory
--     33554432 : secTokenGroup             -  Conditionally Mandatory
--     67108864 : secUserGroup              -  Conditionally Mandatory
--    134217728 : secUserExtGroup           -  Conditionally Mandatory
--
--      Usage:  Conforming management agents shall ALWAYS accurately
--      report their support for Security MIB object groups."
    INTEGER (0..2147483647)  -- biggest int = 2**31-1

--.ts 'XcmSecSecuritySupport'
XcmSecSecuritySupport ::= 
--  STATUS      current
--  DESCRIPTION
--      "Terse conformance statement of security 'AAA' methods
--      supported by this management agent implementation (ie, version)
--      on this host system, specified in a bit-mask.
--
--      The current set of values (which may be extended in the future)
--      is given below:
--
--            1 : userIdentifyByIndex
--            2 : userIdentifyByName
--            4 : userAuthenticateByPassword
--            8 : userAuthenticateByPasscode
--           16 : userPerformAuthorization -  authorize user
--           32 : userPerformAccounting -  policy usage accounting
--           64 : userPerformLogging -  reliable accounting logs
--          128 : userPerformAuditing -  security activities/events
--          256 : accountIdentifyByIndex
--          512 : accountIdentifyByName
--         1024 : accountAuthenticateByPassword
--         2048 : accountAuthenticateByPasscode
--         4096 : accountPerformAuthorization -  authorize account
--         8192 : accountPerformAccounting -  policy usage accounting
--        16384 : accountPerformLogging -  reliable accounting logs
--        32768 : accountPerformAuditing -  security activities/events
--        65536 : modeDirectAuthentication  -  via password every Set
--       131072 : modeSourceAuthentication  -  via source transport addr
--       262144 : modeSessionAuthentication -  via session/token index
--       524288 : portHrDevMgmtCommandData -  'single-port' authenticate
--      1048576 : portSecConfigMgmtData    -  'single-port' authenticate
--      2097152 : portSecAccountMgmtData   -  'multi-port' authenticate
--      4194304 : portSecUserMgmtData      -  'multi-port' authenticate
--      8388608 : traceExceptions
--
--      Usage:  Conforming management agents shall ALWAYS accurately
--      report their support for security 'AAA' methods."
    INTEGER (0..2147483647)  -- biggest int = 2**31-1

--.ts 'XcmSecAccountScope'
XcmSecAccountScope ::= 
--  STATUS      current
--  DESCRIPTION
--      "A description of the relative 'scope' of an account (ie, the
--      realm of accessibility of the account).  Used to show whether
--      one user, one or more teams of users, all authenticated users,
--      or guest (ie, anonymous) users have access to the account.
--
--      The standard account scopes are specified below:
--
--            1 : private
--            2 : group
--            4 : world
--            8 : guest
--
--      Usage:  A given account shall always have EXACTLY one scope.
--      A given user may have access to one or more account scopes."
    INTEGER (0..2147483647)  -- biggest int = 2**31-1

--.ts 'XcmSecConfigMgmtOperation'
XcmSecConfigMgmtOperation ::= 
--  STATUS      current
--  DESCRIPTION
--      "The most recent security management operation specified for
--      this conceptual row in the 'xcmSec[Config|Account|User]Table'.
--
--      Usage:  The operations specified in this textual convention are
--      derived from the 'object' and 'server' operations specified in
--      the POSIX.3 standard."
--  REFERENCE
--      "See:   Section 4 'Print Utilities' (pages 71 to 212) of
--              POSIX Sys Admin (IEEE 1387.4 / Draft 8, October 1994)."
    INTEGER  -- left brace delay
--      none(0),                        -  zero enums illegal in SMIv1
        {
        other(1),                       -- Other operation
        unknown(2),                     -- Unknown operation
        --  POSIX - Security level operations (on host system)
        securityCreate(1601),           -- 'pdcreate' (create object)
        securityDelete(1602),           -- 'pddelete' (delete object)
        securityList(1603),             -- 'pdls' (list obj attribute)
        securitySet(1604),              -- 'pdset' (set obj attribute)
        --  XCMI - Security level extensions (on host system)
        securityManage(2601),           -- manage security object(s)
        securityInstall(2621),          -- install security object(s)
        securityUpgrade(2622),          -- upgrade security object(s)
        securityBackup(2623),           -- backup security object(s)
        securityRestore(2624),          -- restore security object(s)
        securityConfigure(2625),        -- configure security object(s)
        securityDiagnose(2626),         -- diagnose security object(s)
        securityResetCounters(2631),    -- reset security counters
        securityResetWarm(2632),        -- warm reset (no power cycle)
        securityResetCold(2633),        -- cold reset (w/ power cycle)
        securityResetFactory(2634),     -- factory defaults reset
        securityLogin(2641),            -- login w/ authentication
        securityLogout(2642)            -- logout w/ authentication
    }

--.ts 'XcmSecConfigMgmtData'
XcmSecConfigMgmtData ::= 
--  STATUS      current
--  DESCRIPTION
--      "The most recent security management data specified for
--      this conceptual row in the 'xcmSec[Config|Account|User]Table'."
--  REFERENCE
--      "See:   Section 4 'Print Utilities' (pages 71 to 212) of
--              POSIX Sys Admin (IEEE 1387.4 / Draft 8, October 1994)."
    OCTET STRING (SIZE (0..255))

--.ts 'XcmSecEventTypeCode'
XcmSecEventTypeCode ::= 
--  STATUS      current
--  DESCRIPTION
--      "The (numeric) type code of the security event which is
--      recorded in this conceptual row in the 'xcmSecEventTable'."
    INTEGER  -- left brace delay
--      none(0),                        -  zero enums illegal in SMIv1
        {
        other(1),
        unknown(2),
        eventLoginOrLogoutAccess(3),
        eventFileOrObjectAccess(4),
        eventAccountOrUserAccess(5),
        eventPolicyAccess(6),
        eventKeyOrProtocolAccess(7),
        eventServiceOrProfileAccess(8),
        eventGeneralOrFindAccess(9),
        eventConfigOrViewAccess(10),
        eventLoginOrLogoutChange(11),
        eventFileOrObjectChange(12),
        eventAccountOrUserChange(13),
        eventPolicyChange(14),
        eventKeyOrProtocolChange(15),
        eventServiceOrProfileChange(16),
        eventGeneralOrFindChange(17),
        eventConfigOrViewChange(18),
        eventSystemStartup(19),
        eventSystemShutdown(20),
        eventSystemError(21),
        eventSessionStartup(22),
        eventSessionShutdown(23),
        eventSessionError(24)
    }

--.ts 'XcmSecFindIntegerKeyType'
XcmSecFindIntegerKeyType ::= 
--  STATUS      current
--  DESCRIPTION
--      "The type of the key integer to use for a table index lookup."
    INTEGER  -- left brace delay
        {
        other(1),
        unknown(2),
        highestConfigAccessIndex(3),
        highestConfigProtocolIndex(4),
        highestConfigViewIndex(5),
        highestAccountIndex(6),
        highestEventIndex(7),
        highestKeyIndex(8),
        highestLinkIndex(9),
        highestPolicyIndex(10),
        highestProfileIndex(11),
        highestProfileDetailIndex(12),
        highestServiceIndex(13),
        highestSessionIndex(14),
        highestTeamIndex(15),
        highestTimestampIndex(16),
        highestUserIndex(17),
        accountRole(18),
        accountScope(19),
        accountTeamIndex(20),
        accountUserIndex(21),
        userRole(22),
        userScopes(23),
        userTeamIndex(24),
        userAccountIndex(25),
        configViewOwnerRole(26),
        serviceOwnerRole(27)
    }

--.ts 'XcmSecFindOIDKeyType'
XcmSecFindOIDKeyType ::= 
--  STATUS      current
--  DESCRIPTION
--      "The type of the key OID to use for a table index lookup."
    INTEGER  -- left brace delay
        {
        other(1),
        unknown(2),
        policyServiceTypeOID(3),
        policyVerbTypeOID(4),
        profileEventTypeOID(5),
        serviceTypeOID(6)
    }

--.ts 'XcmSecFindStringKeyType'
XcmSecFindStringKeyType ::= 
--  STATUS      current
--  DESCRIPTION
--      "The type of the key string to use for a table index lookup."
    INTEGER  -- left brace delay
        {
        other(1),
        unknown(2),
        accountAlias(3),                -- unbounded text
        accountName(4),                 -- display text
        accountPassword(5),             -- display text
        accountPasscode(6),             -- numeric text (ie, PIN)
        userAlias(7),                   -- unbounded text
        userName(8),                    -- display text
        userPassword(9),                -- display text
        userPasscode(10),               -- numeric text (ie, PIN)
        sessionID(11)
    }

--.ts 'XcmSecGuestJobPolicy'
XcmSecGuestJobPolicy ::= 
--  STATUS      current
--  DESCRIPTION
--      "The current policy for jobs submitted with 'guest' (empty)
--      user/account identification info, on this host system."
    INTEGER  -- left brace delay
        {
        other(1),                       -- other
        unknown(2),                     -- unknown
        jobCreateGuestUser(3),          -- create job for guest user
        jobCreateGuestAccount(4),       -- create job for guest account
        jobCreateWorldAccount(5),       -- create job for world account
        jobDelete(6),                   -- delete job w/out accounting
        jobHold(7),                     -- hold job until user walkup
        jobRemove(8)                    -- cancel job with accounting
    }

--.ts 'XcmSecKeyProtocolType'
XcmSecKeyProtocolType ::= 
--  STATUS      current
--  DESCRIPTION
--      "The type of security protocol which is currently associated
--      with this security key entry (ie, conceptual row in the
--      'xcmSecKeyTable')."
    INTEGER  -- left brace delay
--      none(0),                        -  zero enums illegal in SMIv1
        {
        other(1),
        unknown(2),
        integrityNone(100),
        integrityOther(101),
        integrityUnknown(102),
        integrityMD5(103),
        privacyNone(200),
        privacyOther(201),
        privacyUnknown(202),
        privacyDES(203)
    }

--.ts 'XcmSecKeyScope'
XcmSecKeyScope ::= 
--  STATUS      current
--  DESCRIPTION
--      "A description of the relative 'scope' of a security key (ie,
--      the realm of accessibility of the key).
--
--      The standard security key scopes are specified below:
--
--            1 : private               -  asymmetric private key
--            2 : public                -  asymmetric public key
--            4 : shared                -  symmetric key
--            8 : unique                -  one-time key
--           16 : lifetime              -  permanent key
--           32 : lease                 -  negotiated lease key
--           64 : session               -  current session key
--          128 : transaction           -  current transaction key
--          256 : operation             -  current operation key
--          512 : packet                -  current packet key
--
--      Usage:  A given key may have restricted scope (eg, 'shared
--      session' or 'private session')."
    INTEGER (0..2147483647)  -- biggest int = 2**31-1

--.ts 'XcmSecPosixRights'
XcmSecPosixRights ::= 
--  STATUS      current
--  DESCRIPTION
--      "The set of owner, group, AND world POSIX.1/2 access permissions
--      for a given managed, protected, and (optionally) audit trailed
--      service class OR service instance OR service operation, or
--      resource class OR resource instance OR resource operation
--      which is instantiated/supported directly on this managed system
--      OR (optionally) on any accessible remote managed system.
--
--      The standard POSIX.1/2 access permissions are specified below
--      (values EXACTLY match traditional UNIX and GNU implementations
--      of shell command 'chmod' - POSIX does NOT define bit values):
--
--          -   Mandatory for all conforming implementations
--            1 : worldExecute  -  Execute file or Search directory
--            2 : worldWrite    -  Write file or directory
--            4 : worldRead     -  Read file or directory
--            8 : groupExecute  -  Execute file or Search directory
--           16 : groupWrite    -  Write file or directory
--           32 : groupRead     -  Read file or directory
--           64 : ownerExecute  -  Execute file or Search directory
--          128 : ownerWrite    -  Write file or directory
--          256 : ownerRead     -  Read file or directory
--          -   Optional for all conforming implementations (special)
--          512 : saveTextImage -  Save text image (qualifies Execute)
--         1024 : setGroupID    -  Set group ID (qualifies Execute)
--         2048 : setUserID     -  Set user ID (qualifies Execute)
--          -   Optional for all conforming implementations (anonymous)
--         4096 : guestExecute  -  Execute file or Search directory
--         8192 : guestWrite    -  Write file or directory
--        16384 : guestRead     -  Read file or directory
--
--      Usage:  Owner/group/world permissions shall ALWAYS be treated as
--      mandatory and NOT as advisory.  Conforming implementations shall
--      NOT 'waive' system administrator configured access restrictions
--      which are currently in force (ie, '...RowStatus' of 'active').
--
--      Usage:  Set user/group ID and save text image permissions need
--      NOT be supported by conforming implementations (ie, they are
--      optional).
--
--      Usage:  Guest (anonymous) permissions need NOT be supported by
--      conforming implementations (ie, they are optional)."
--  REFERENCE
--      "See:   Section 5.6.4 'chmod()' in POSIX.1 (ISO 9945-1:1990),
--              section 4.7 'chmod' in POSIX.2 (ISO 9945-2:1992), and
--              GNU manual page for 'chmod' shell command in CHMOD(1L)."
    INTEGER (0..2147483647)  -- biggest int = 2**31-1

--.ts 'XcmSecPosixVerbs'
XcmSecPosixVerbs ::= 
--  STATUS      current
--  DESCRIPTION
--      "The set of POSIX.3 system management verbs supported or ready
--      for a given managed, protected, and (optionally) audit trailed
--      system, view, service, or policy and any of its associated jobs.
--
--      The POSIX.3 standard job management verbs are specified below:
--
--          -   Mandatory POSIX.3 job management verbs
--            1 : jobCreate             -  'pdpr' (submit job)
--            2 : jobDelete             -  'pddelete' (destroy job)
--            4 : jobInterrupt          -  'pdinterrupt' (interrupt job)
--            8 : jobList               -  'pdls' (list job attributes)
--           16 : jobModify             -  'pdmod' (set job attributes)
--           32 : jobPause              -  'pdpause' (hold job)
--           64 : jobPromote            -  'pdpromote' (set priority)
--          128 : jobQueueList          -  'pdq' (list job queue)
--          256 : jobRemove             -  'pdrm' (cancel job)
--          512 : jobResubmit           -  'pdresubmit' (resubmit job)
--         1024 : jobResume             -  'pdresume' (release job)
--
--          -   Optional XCMI job management verbs
--         2048 : jobManage             -  for future XCMI extensions
--
--      The POSIX.3 standard system management verb classes are
--      specified below:
--
--          -    Mandatory POSIX.3 system management verb classes
--         4096 : systemMgmt            -  all system mgmt verbs
--         8192 : commsList             -  list comms attributes
--        16384 : commsMgmt             -  all comms mgmt verbs
--        32768 : commsConcise          -  concise comms mgmt verbs
--        65536 : objectList            -  list object attributes
--       131072 : objectMgmt            -  all object mgmt verbs
--       262144 : objectConcise         -  concise object mgmt verbs
--       524288 : serviceList           -  list service attributes
--      1048576 : serviceMgmt           -  all service mgmt verbs
--      2097152 : serviceConcise        -  concise service mgmt verbs
--      4194304 : deviceList            -  list device attributes
--      8388608 : deviceMgmt            -  all device mgmt verbs
--     16777216 : deviceConcise         -  concise device mgmt verbs
--     33554432 : jobReserved           -  reserved
--     67108864 : jobMgmt               -  all job/doc mgmt verbs
--    134217728 : jobConcise            -  concise job/doc mgmt verbs
--    268435456 : securityList          -  list security attributes
--    536870912 : securityMgmt          -  all security mgmt verbs
--   1073741824 : securityConcise       -  concise security mgmt verbs
--
--      -  2**31 not used, due to 'Integer32|Cardinal32' semantics
--
--      Usage:  Conforming implementations shall ALWAYS support access
--      control to ALL of the POSIX.3 standard job management verbs.
--
--      Usage:  Conforming implementations shall ALWAYS support access
--      control to ALL of the POSIX.3 standard system management verb
--      classes.
--
--      Usage:  Conforming implementations need NOT support access
--      control to ANY of the XCMI extension job management verbs
--      (ie, they are optional)."
--  REFERENCE
--      "See:   POSIX System Administration - Part 4: Print Interfaces
--              (IEEE 1387.4 / Draft 8, October 1994).
--      See:    Document Printing Application - Part 1: Abstract Service
--              (ISO/IEC 10175-1 / Final Text, March 1996).
--      See:    'xcmSimpleJobMgmtOperation' in Simple Job Mgmt
--              group of XCMI Simple Job Mgmt MIB.
--      See:    'xcmSimpleSvcMgmtOperation' in Simple Service Mgmt
--              group of XCMI Simple Service Mgmt MIB.
--      See:    'xcmSysAdminRequestOperationOID' in System Admin Request
--              group of XCMI System Admin Mgmt MIB.
--      See:    'xcmHrDevMgmtCommandRequest' in Device Mgmt
--              group of XCMI Host Resources Extensions MIB.
--      See:    'xcmCommsMgmtCommandRequest' in Comms Mgmt
--              group of XCMI Comms Engine MIB."
    INTEGER (0..2147483647)  -- biggest int = 2**31-1

--.ts 'XcmSecSessionRequestOperation'
XcmSecSessionRequestOperation ::= 
--  STATUS      current
--  DESCRIPTION
--      "A write of this object by an (authorized) management station
--      invokes a secure admin session request.
--      A read of this object by an (authorized) management station
--      returns the most recent previous secure admin session request.
--
--    * 'none' - NO action(s) shall be taken.
--    * 'secSessionCreate' - new secure admin session
--      shall be created, if valid authentication and authorization
--      information is presented in '...RequestData' AND the management
--      agent is able to support a new (possibly concurrent) secure
--      admin session at this time.
--    * 'secSessionDelete' - existing secure admin session
--      shall be deleted, if valid authentication and authorization
--      information is presented in '...RequestData' AND the management
--      agent is able to delete the existing secure admin
--      session at this time.
--    * 'secSessionManage' - it is a local matter (to each system)
--      how this request is processed/ however, the associated
--      '...RequestData' object shall ALWAYS be specified.
--    * all other requests - the requested operation shall be performed,
--      if valid authentication and authorization information is also
--      presented in '...RequestData' AND a valid token is presented AND
--      the management agent is able to perform the requested secure
--      admin operation at this time."
--  REFERENCE
--      "See:   'dot5Commands' in IEEE 802.5 Token Ring MIB (RFC 1748)
--      and 'hrDeviceStatus' in IETF Host Resources MIB (RFC 2790).
--      Compare:    'ifOperStatus' (current) and 'ifAdminStatus'
--      (desired) in the Interfaces Group of IETF MIB-II (RFC 1213)/
--      'RowStatus' textual convention in IETF SMIv2 (RFC 1902/2578).
--      See:    'XcmSysAdminRequestOperation' in the XCMI Sys Admin TC
--      for system admin requests which may be performed during an
--      authenticated secure admin session.  Always present a valid
--      token when writing to a command/request object in any other MIB
--      module, during a secure admin session."
    INTEGER  -- left brace delay
--      none(0),                        -  zero enums illegal in SMIv1
        {
        other(1),                       -- other operation ??
        unknown(2),                     -- unknown operation ??
        --  Session level operations
        secSessionCreate(10),           -- create secure admin session
                                        -- (start token generation)
        secSessionDelete(11),           -- delete secure admin session
                                        -- (end token generation)
        secSessionManage(12),           -- manage secure admin session
                                        -- (for future extension)
        --  Bracket level operations
        secBracketOpen(20),             -- open transaction bracket
                                        -- (start deferred transactions)
        secBracketClose(21),            -- close transaction bracket
                                        -- (end deferred transactions)
        secBracketCommit(22),           -- commit transaction bracket
                                        -- (commit all transactions)
        secBracketUndo(23),             -- undo transaction bracket
                                        -- (undo all transactions)
        secBracketSync(24),             -- sync transaction bracket
                                        -- (checkpoint last transaction)
        secBracketResync(25),           -- resync transaction bracket
                                        -- (undo to last checkpoint)
        --  Trace level operations
        secTraceOpen(30),               -- open security trace
                                        -- (start transaction trace)
        secTraceClose(31),              -- close security trace
                                        -- (end transaction trace)
        secTraceEncrypt(33),            -- encrypt security trace
                                        -- (archive transaction trace)
        secTraceDecrypt(34)             -- decrypt security trace
                                        -- (recover transaction trace)
    }

--.ts 'XcmSecSessionRequestData'
XcmSecSessionRequestData ::= 
--  STATUS      current
--  DESCRIPTION
--      "A write of this object by an (authorized) management station
--      invokes a secure admin session request data.
--      A read of this object by an (authorized) management station
--      returns the last secure admin session request data."
--  REFERENCE
--      "See:   Appropriate product specs for further information."
    OCTET STRING (SIZE (0..255))

--.ts 'XcmSecUserRole'
XcmSecUserRole ::= 
--  STATUS      current
--  DESCRIPTION
--      "The explicit role of a given individual user or the default
--      role associated with a team of users.
--
--      Usage:  The special roles 'any...' shall NOT be specified in
--      'xcmSec[Account|User]Role', or 'xcmSec...OwnerRole' objects, but
--      MAY be specified in 'xcmSecConfigAccessRole' and
--      MAY be specified in 'xcmSecConfigViewOwnerRole'
--      to grant broad privileges in a terse manner.
--
--      Usage:  The role 'alien' (invalid) user shall NOT be specified
--      in 'xcmSec[Account|User]Role'.  Requests and jobs submitted to a
--      management agent with invalid user/account identification data
--      shall be labelled as 'alien' - they shall ALWAYS be handled via
--      the current value of 'xcmSecConfigAlienJobPolicy' in the
--      'xcmSecConfigTable' - if accepted, they shall ALWAYS be assigned
--      to a selected 'guest' user or account - with inheritance of all
--      of its configured capabilities and permissions, for all aspects
--      of authentication, authorization, accounting (and audit trail) -
--      via 'xcmSecConfig[GuestUser|GuestAccount|WorldAccount]Index'."
    INTEGER  -- left brace delay
--      none(0),                        -  zero enums illegal in SMIv1
        {
        other(1),
        unknown(2),
        system(100),                    -- 'system' role (generic)
        systemAdministrator(101),       -- System Manager (overall)
        systemHelpDesk(102),            -- Information Desk
        systemOperator(103),            -- Key Operator
        systemPlanningAdmin(104),       -- Capacity Planner
        systemAssetAdmin(105),          -- Asset Manager
        systemAccountingAdmin(106),     -- Accounting Manager
        systemSecurityAdmin(107),       -- Security Officer
        systemSuppliesSource(108),      -- Supplies (vendor/customer)
        systemInstaller(109),           -- Installer (vendor/customer)
        systemTrainer(110),             -- Trainer (vendor/customer)
        technician(200),                -- 'technician' role (generic)
        technicianManufacturer(201),    -- Service (manufacturer)
        technicianThirdParty(202),      -- Service (third party)
        technicianCustomer(203),        -- Service (customer)
        anyEffectiveOwner(250),         -- Any effective object owner
        anyMemberOfOwnersTeam(260),     -- Any member of owner's team
        user(300),                      -- 'user' role (end user)
        anyAuthenticatedUser(350),      -- Any authenticated user
        guest(400),                     -- 'guest' role (anonymous user)
        anyIdentifiedUser(450),         -- Any identified user
        alien(500)                      -- 'alien' role (invalid user)
    }

--.ts 'XcmSecUserSkill'
XcmSecUserSkill ::= 
--  STATUS      current
--  DESCRIPTION
--      "The explicit skill of a given individual user or the default
--      skill associated with a team of users.  Skill indicates 'level
--      of training' and/or 'level of experience', and is specified as
--      follows:
--
--      a)  One (1) indicates the lowest possible skill/ and
--      b)  One-hundred (100) indicates the highest possible skill."
    INTEGER (1..100)

--.ts 'Dummy Group (to suppress compiler warnings)'
--
--          The Security TC Dummy Group (DO NOT USE)
--
--          DO NOT USE - Present to suppress compiler warnings ONLY!
--
--          Note:  The following objects have 'odd' use of case in their
--          names (ie, 'xCm...'), in order to make obvious their related
--          textual conventions

xCmSecDummy         OBJECT IDENTIFIER ::= { xcmSecTC 999 }

xCmSecAuditSupport OBJECT-TYPE
    SYNTAX      XcmSecAuditSupport
    ACCESS      read-only
    STATUS      mandatory
    DESCRIPTION "Dummy - DO NOT USE"
    ::= { xCmSecDummy 1 }

xCmSecFacilitySupport OBJECT-TYPE
    SYNTAX      XcmSecFacilitySupport
    ACCESS      read-only
    STATUS      mandatory
    DESCRIPTION "Dummy - DO NOT USE"
    ::= { xCmSecDummy 2 }

xCmSecFeatureSupport OBJECT-TYPE
    SYNTAX      XcmSecFeatureSupport
    ACCESS      read-only
    STATUS      mandatory
    DESCRIPTION "Dummy - DO NOT USE"
    ::= { xCmSecDummy 3 }

xCmSecGroupSupport OBJECT-TYPE
    SYNTAX      XcmSecGroupSupport
    ACCESS      read-only
    STATUS      mandatory
    DESCRIPTION "Dummy - DO NOT USE"
    ::= { xCmSecDummy 4 }

xCmSecSecuritySupport OBJECT-TYPE
    SYNTAX      XcmSecSecuritySupport
    ACCESS      read-only
    STATUS      mandatory
    DESCRIPTION "Dummy - DO NOT USE"
    ::= { xCmSecDummy 5 }

xCmSecAccountScope OBJECT-TYPE
    SYNTAX      XcmSecAccountScope
    ACCESS      read-only
    STATUS      mandatory
    DESCRIPTION "Dummy - DO NOT USE"
    ::= { xCmSecDummy 6 }

xCmSecConfigMgmtOperation OBJECT-TYPE
    SYNTAX      XcmSecConfigMgmtOperation
    ACCESS      read-only
    STATUS      mandatory
    DESCRIPTION "Dummy - DO NOT USE"
    ::= { xCmSecDummy 7 }

xCmSecConfigMgmtData OBJECT-TYPE
    SYNTAX      XcmSecConfigMgmtData
    ACCESS      read-only
    STATUS      mandatory
    DESCRIPTION "Dummy - DO NOT USE"
    ::= { xCmSecDummy 8 }

xCmSecEventTypeCode OBJECT-TYPE
    SYNTAX      XcmSecEventTypeCode
    ACCESS      read-only
    STATUS      mandatory
    DESCRIPTION "Dummy - DO NOT USE"
    ::= { xCmSecDummy 9 }

xCmSecFindIntegerKeyType OBJECT-TYPE
    SYNTAX      XcmSecFindIntegerKeyType
    ACCESS      read-only
    STATUS      mandatory
    DESCRIPTION "Dummy - DO NOT USE"
    ::= { xCmSecDummy 10 }

xCmSecFindOIDKeyType OBJECT-TYPE
    SYNTAX      XcmSecFindOIDKeyType
    ACCESS      read-only
    STATUS      mandatory
    DESCRIPTION "Dummy - DO NOT USE"
    ::= { xCmSecDummy 11 }

xCmSecFindStringKeyType OBJECT-TYPE
    SYNTAX      XcmSecFindStringKeyType
    ACCESS      read-only
    STATUS      mandatory
    DESCRIPTION "Dummy - DO NOT USE"
    ::= { xCmSecDummy 12 }

xCmSecGuestJobPolicy OBJECT-TYPE
    SYNTAX      XcmSecGuestJobPolicy
    ACCESS      read-only
    STATUS      mandatory
    DESCRIPTION "Dummy - DO NOT USE"
    ::= { xCmSecDummy 13 }

xCmSecKeyProtocolType OBJECT-TYPE
    SYNTAX      XcmSecKeyProtocolType
    ACCESS      read-only
    STATUS      mandatory
    DESCRIPTION "Dummy - DO NOT USE"
    ::= { xCmSecDummy 14 }

xCmSecPosixRights OBJECT-TYPE
    SYNTAX      XcmSecPosixRights
    ACCESS      read-only
    STATUS      mandatory
    DESCRIPTION "Dummy - DO NOT USE"
    ::= { xCmSecDummy 15 }

xCmSecPosixVerbs OBJECT-TYPE
    SYNTAX      XcmSecPosixVerbs
    ACCESS      read-only
    STATUS      mandatory
    DESCRIPTION "Dummy - DO NOT USE"
    ::= { xCmSecDummy 16 }

xCmSecSessionRequestOperation OBJECT-TYPE
    SYNTAX      XcmSecSessionRequestOperation
    ACCESS      read-only
    STATUS      mandatory
    DESCRIPTION "Dummy - DO NOT USE"
    ::= { xCmSecDummy 17 }

xCmSecSessionRequestData OBJECT-TYPE
    SYNTAX      XcmSecSessionRequestData
    ACCESS      read-only
    STATUS      mandatory
    DESCRIPTION "Dummy - DO NOT USE"
    ::= { xCmSecDummy 18 }

xCmSecUserRole OBJECT-TYPE
    SYNTAX      XcmSecUserRole
    ACCESS      read-only
    STATUS      mandatory
    DESCRIPTION "Dummy - DO NOT USE"
    ::= { xCmSecDummy 19 }

xCmSecUserSkill OBJECT-TYPE
    SYNTAX      XcmSecUserSkill
    ACCESS      read-only
    STATUS      mandatory
    DESCRIPTION "Dummy - DO NOT USE"
    ::= { xCmSecDummy 20 }

xCmSecKeyScope OBJECT-TYPE
    SYNTAX      XcmSecKeyScope
    ACCESS      read-only
    STATUS      mandatory
    DESCRIPTION "Dummy - DO NOT USE"
    ::= { xCmSecDummy 21 }

END
