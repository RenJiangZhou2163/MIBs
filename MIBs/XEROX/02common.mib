XEROX-COMMON-MIB DEFINITIONS ::= BEGIN

-- Module:  Common
-- Editors: Paul Gloger and Gary Padlipsky
-- File:    02common.txt
-- Date:    August 09, 1997
-- Version: 2.32.int

IMPORTS
--  enterprises, OBJECT-IDENTITY, MODULE-IDENTITY
--  FROM SNMPv2-SMI/                            -  IETF RFC 1442
    enterprises
        FROM    RFC1155-SMI
    ;

xerox OBJECT IDENTIFIER
--  LAST-UPDATED "9708090000Z"
--  ORGANIZATION "Xerox Corporation -
--                Xerox Common Management Interface Working Group"
--  CONTACT-INFO "
--                   XCMI Editors
--      E-Mail       xcmieditors@cp10.es.xerox.com
--
--      - 
--      -  BEGIN XEROX PRIVATE DATA
--      - 
--                   XCMI Working Group
--      WebPage:     http://www.cp10.es.xerox.com/adss/xcmiwg
--      E-Mail:      xcmiwg@cp10.es.xerox.com
--
--                   Paul Gloger
--                   CR&T/ADSTC/Enterprise Management
--      Mailstop:    ESAE-231
--      Voice:       8*823-6820 / 310-333-6820
--      E-Mail:      pgloger@cp10.es.xerox.com
--
--                   Gary Padlipsky
--                   CR&T/ADSTC/Enterprise Management
--      Mailstop:    ESAE-231
--      Voice:       8*823-7653 / 310-333-7653
--      E-Mail:      gpadlipsky@cp10.es.xerox.com
--
--      - 
--      -  ENDOF XEROX PRIVATE DATA
--      - 
--  "
--  DESCRIPTION
--      "Xerox Common MIB Root Module, Version 2.32.int.
--
--      Copyright (C) 1997 Xerox Corporation. All Rights Reserved.
--      Copyright protection claimed includes all forms and matters
--      of copyrightable material and information now allowed by
--      statutory or judicial law or hereinafter granted,
--      including without limitation, material generated from the
--      software programs which are displayed on the screen such as
--      icons, screen display looks, etc."
    ::= { enterprises 253 }

xeroxCommonMIB OBJECT IDENTIFIER
--  STATUS      current
--  DESCRIPTION
--      "The root of the Xerox Common MIB module.
--
--       xeroxCommonMIB ::= { iso(1) org(3) dod(6) internet(1)
--                            private(4) enterprises(1) Xerox(253) 8 }"
    ::= { xerox 8 }

END
