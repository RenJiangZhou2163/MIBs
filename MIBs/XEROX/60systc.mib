XEROX-SYS-ADMIN-TC DEFINITIONS ::= BEGIN
--  Module: System Administration TC
--  Author: Ira McDonald, Rob Sklut
--  File    60systc.mib
--  Date:   28 April 2000 - Version 4.00.int

--  Textual Conventions companion to the XCMI System Admin MIB
--  Contains the REGISTRY of XCMI System Admin Service Types

IMPORTS
--  MODULE-IDENTITY, OBJECT-IDENTITY,
--      OBJECT-TYPE
--          FROM SNMPv2-SMI             -  IETF RFC 1442/1902/2578
--  TEXTUAL-CONVENTION
--          FROM SNMPv2-TC              -  IETF RFC 1443/1903/2579
--  xeroxCommonMIB
--          FROM XEROX-COMMON-MIB/
    xeroxCommonMIB
        FROM    XEROX-COMMON-MIB
    OBJECT-TYPE
        FROM    RFC-1212
    ;

xcmSysAdminTC OBJECT IDENTIFIER
--  LAST-UPDATED "0004280000Z" -  28 April 2000
--  ORGANIZATION "Xerox Corporation - XCMI Working Group"
--  CONTACT-INFO
--      "           XCMI Editors
--      Email:      xcmieditors@cp10.es.xerox.com
--
--      - 
--      -  BEGIN XEROX PRIVATE DATA
--      - 
--                  Ira McDonald
--      Postal:     High North Inc
--                  221 Ridge Ave
--                  Grand Marais, MI  49839
--      Voice:      906-494-2434 or 906-494-2697
--      Email:      imcdonal@sdsp.mc.xerox.com
--
--                  Rob Sklut
--      Postal:     Xerox Corporation
--                  200 Cross Keys Office Park
--                  Rochester, NY  14623
--      Voice:      716-425-6601
--      Email:      Robert_Sklut@.mc.xerox.com
--      - 
--      -  ENDOF XEROX PRIVATE DATA
--      - 
--      "
--  DESCRIPTION
--      "Version:   4.00.int
--
--      Textual Conventions companion to the XCMI System Admin MIB,
--      the MIB module for performing POSIX system admin of jobs and
--      other system objects in network accessible host systems.
--
--      See:    Document Printing Application - Part 1: Abstract Service
--              (ISO/IEC 10175-1 / Final Text, March 1996).
--      See:    POSIX System Administration - Part 4: Print Interfaces
--              (IEEE 1387.4 / Draft 8, October 1994).
--      See:    OSI Reference Model - Part 1:  Basic Reference Model
--              (CCITT X.200:1992 | ISO 7498-1:1992).
--
--      Copyright (C) 2000 Xerox Corporation. All Rights Reserved."
    ::= { xeroxCommonMIB 69 }

--
--          The System Admin TC
--

--.ts 'REGISTRY of XCMI System Admin Operation Types'
--          REGISTRY of XCMI System Admin Operation Types
--          (used in the 'xcmSysAdminRequestOperationOID' object
--          in the companion XCMI System Admin MIB
--          and the 'xcmSec[Master|Policy]VerbTypeOID' objects
--          in the closely related XCMI Security MIB).

xcmSysAdminOperationTypes OBJECT IDENTIFIER
--  STATUS      current
--  DESCRIPTION
--      "The root of all system admin operation types defined in
--      the System Admin TC."
--  REFERENCE
--      "See:   Document Printing Application - Part 1: Abstract Service
--              (ISO/IEC 10175-1 / Final Text, March 1996).
--      See:    POSIX System Administration - Part 4: Print Interfaces
--              (IEEE 1387.4 / Draft 8, October 1994)."
    ::= { xcmSysAdminTC 2 }

--
--  POSIX - Object level operations (host system objects)
--

xcmSysAdminObjectOperations OBJECT IDENTIFIER
--  STATUS      current
--  DESCRIPTION
--      "POSIX - Object level operations"
--  REFERENCE
--      "Section 4 'Printing Utilities' in POSIX IEEE 1387.4."
    ::= { xcmSysAdminOperationTypes 1100 }

xcmSysAdminObjectCreate OBJECT IDENTIFIER
--  STATUS      current
--  DESCRIPTION
--      "Create a host system object."
--  REFERENCE
--      "Section 4.2 'pdcreate' in POSIX IEEE 1387.4."
    ::= { xcmSysAdminOperationTypes 1101 }

xcmSysAdminObjectDelete OBJECT IDENTIFIER
--  STATUS      current
--  DESCRIPTION
--      "Delete a host system object."
--  REFERENCE
--      "Section 4.3 'pddelete' in POSIX IEEE 1387.4."
    ::= { xcmSysAdminOperationTypes 1102 }

xcmSysAdminObjectList OBJECT IDENTIFIER
--  STATUS      current
--  DESCRIPTION
--      "List attributes of a host system object."
--  REFERENCE
--      "Section 4.7 'pdls' in POSIX IEEE 1387.4."
    ::= { xcmSysAdminOperationTypes 1103 }

xcmSysAdminObjectSet OBJECT IDENTIFIER
--  STATUS      current
--  DESCRIPTION
--      "Set attributes of a host system object."
--  REFERENCE
--      "Section 4.16 'pdset' in POSIX IEEE 1387.4."
    ::= { xcmSysAdminOperationTypes 1104 }

--
--  XCMI - Object level operations (host system objects)
--

xcmSysAdminXCMIObjectOperations OBJECT IDENTIFIER
--  STATUS      current
--  DESCRIPTION
--      "XCMI - Object level operations"
--  REFERENCE
--      "Section 4 'Printing Utilities' in POSIX IEEE 1387.4."
    ::= { xcmSysAdminOperationTypes 2100 }

xcmSysAdminObjectManage OBJECT IDENTIFIER
--  SYNTAX      xcmSysAdminObjectManage (...)
--
--  For future extensions
--  STATUS      current
--  DESCRIPTION
--      "XCMI - Manage a host system object."
--  REFERENCE
--      "Section 4 'Printing Utilities' in POSIX IEEE 1387.4."
    ::= { xcmSysAdminOperationTypes 2101 }

xcmSysAdminObjectInstall OBJECT IDENTIFIER
--  STATUS      current
--  DESCRIPTION
--      "XCMI - Install a host system object."
    ::= { xcmSysAdminOperationTypes 2121 }

xcmSysAdminObjectUpgrade OBJECT IDENTIFIER
--  STATUS      current
--  DESCRIPTION
--      "XCMI - Upgrade a host system object."
    ::= { xcmSysAdminOperationTypes 2122 }

xcmSysAdminObjectBackup OBJECT IDENTIFIER
--  STATUS      current
--  DESCRIPTION
--      "XCMI - Backup a host system object."
    ::= { xcmSysAdminOperationTypes 2123 }

xcmSysAdminObjectRestore OBJECT IDENTIFIER
--  STATUS      current
--  DESCRIPTION
--      "XCMI - Restore a host system object."
    ::= { xcmSysAdminOperationTypes 2124 }

xcmSysAdminObjectConfigure OBJECT IDENTIFIER
--  STATUS      current
--  DESCRIPTION
--      "XCMI - Configure a host system object."
    ::= { xcmSysAdminOperationTypes 2125 }

xcmSysAdminObjectDiagnose OBJECT IDENTIFIER
--  STATUS      current
--  DESCRIPTION
--      "XCMI - Diagnose a host system object."
    ::= { xcmSysAdminOperationTypes 2126 }

xcmSysAdminObjectResetCounters OBJECT IDENTIFIER
--  STATUS      current
--  DESCRIPTION
--      "XCMI - Reset counters on a host system object."
    ::= { xcmSysAdminOperationTypes 2131 }

xcmSysAdminObjectResetWarm OBJECT IDENTIFIER
--  STATUS      current
--  DESCRIPTION
--      "XCMI - Reset warm (w/out power cycle) a host system object."
    ::= { xcmSysAdminOperationTypes 2132 }

xcmSysAdminObjectResetCold OBJECT IDENTIFIER
--  STATUS      current
--  DESCRIPTION
--      "XCMI - Reset cold (w/ power cycle) a host system object."
    ::= { xcmSysAdminOperationTypes 2133 }

xcmSysAdminObjectResetFactory OBJECT IDENTIFIER
--  STATUS      current
--  DESCRIPTION
--      "XCMI - Reset to factory defaults a host system object."
    ::= { xcmSysAdminOperationTypes 2134 }

--
--  POSIX - Server level operations (host system servers)
--

xcmSysAdminServerOperations OBJECT IDENTIFIER
--  STATUS      current
--  DESCRIPTION
--      "POSIX - Server level operations"
--  REFERENCE
--      "Section 4 'Printing Utilities' in POSIX IEEE 1387.4."
    ::= { xcmSysAdminOperationTypes 1200 }

xcmSysAdminServerCreate OBJECT IDENTIFIER
--  SYNTAX      xcmSysAdminServerCreate (...)
--
--  INPUT General Arguments:
--  For software which is currently installed on the local host system:
--  From 'hrSWInstalledTable' in the IETF Host Resources MIB
--  hrSWInstalledIndex          Ordinal32                    - choice
--                              <OR>
--  From 'xcmHrSWInstalledTable' in the XCMI Host Resources Ext MIB
--  xcmHrSWInstalledAdminName   XcmFixedLocaleDisplayString  - choice
--
--  For software which is NOT installed on the local host system:
--  From 'hrSWRunTable' in the IETF Host Resources MIB
--  hrSWRunIndex                Ordinal32                    - choice
--                              <OR>
--  From 'xcmHrSWRunTable' in the XCMI Host Resources Ext MIB
--  xcmHrSWRunAdminName         XcmFixedLocaleDisplayString  - choice
--
--  INPUT Create Arguments:
--  From 'hrSWRunTable' in the IETF Host Resources MIB (RFC 2790)
--  hrSWRunIndex                Ordinal32                    - mandatory
--  hrSWRunPath                 InternationalDisplayString   - optional
--  hrSWRunParameters           InternationalDisplayString   - optional
--  hrSWRunType                 INTEGER                      - optional
--  From 'xcmHrSWRunTable' in the XCMI Host Resources Ext MIB
--  xcmHrSWRunRowStatus         RowStatus                    - mandatory
--  xcmHrSWRunAdminName         XcmFixedLocaleDisplayString  - mandatory
--  xcmHrSWRunPhysicalDeviceIndex       Cardinal32           - optional
--  xcmHrSWRunLogicalDeviceIndex        Cardinal32           - optional
--
--  OUTPUT Responses:
--  [See OUTPUT Responses from 'xcmSysAdminServerList']
--  STATUS      current
--  DESCRIPTION
--      "Create (ie, load and run) a host system server
--      (ie, a software-based system service which MAY support jobs)."
--  REFERENCE
--      "Section 4.2 'pdcreate' in POSIX IEEE 1387.4."
    ::= { xcmSysAdminOperationTypes 1201 }

xcmSysAdminServerDelete OBJECT IDENTIFIER
--  SYNTAX      xcmSysAdminServerDelete (...)
--
--  INPUT General Arguments:
--  For software which is currently running on the local host system:
--  From 'hrSWRunTable' in the IETF Host Resources MIB
--  hrSWRunIndex                Ordinal32                    - choice
--                              <OR>
--  From 'xcmHrSWRunTable' in the XCMI Host Resources Ext MIB
--  xcmHrSWRunAdminName         XcmFixedLocaleDisplayString  - choice
--
--  For software which is currently installed on the local host system:
--  From 'hrSWInstalledTable' in the IETF Host Resources MIB
--  hrSWInstalledIndex          Ordinal32                    - choice
--                              <OR>
--  From 'xcmHrSWInstalledTable' in the XCMI Host Resources Ext MIB
--  xcmHrSWInstalledAdminName   XcmFixedLocaleDisplayString  - choice
--
--  OUTPUT Responses:
--  [See OUTPUT Responses from 'xcmSysAdminServerList']
--  STATUS      current
--  DESCRIPTION
--      "Delete (ie, stop and unload) a host system server
--      (ie, a software-based system service which MAY support jobs)
--      <OR>
--      Delete installed software on this host system."
--  REFERENCE
--      "Section 4.3 'pddelete' in POSIX IEEE 1387.4."
    ::= { xcmSysAdminOperationTypes 1202 }

xcmSysAdminServerList OBJECT IDENTIFIER
--  SYNTAX      xcmSysAdminServerList (...)
--
--  INPUT General Arguments:
--  For software which is currently running on the local host system:
--  From 'hrSWRunTable' in the IETF Host Resources MIB
--  hrSWRunIndex                Ordinal32                    - choice
--                              <OR>
--  From 'xcmHrSWRunTable' in the XCMI Host Resources Ext MIB
--  xcmHrSWRunAdminName         XcmFixedLocaleDisplayString  - choice
--
--  For software which is currently installed on the local host system:
--  From 'hrSWInstalledTable' in the IETF Host Resources MIB
--  hrSWInstalledIndex          Ordinal32                    - choice
--                              <OR>
--  From 'xcmHrSWInstalledTable' in the XCMI Host Resources Ext MIB
--  xcmHrSWInstalledAdminName   XcmFixedLocaleDisplayString  - choice
--
--  INPUT List Filters:
--  From ANY Software level table in the IETF Host Resources MIB
--  From ANY Software level table in the XCMI Host Resources Ext MIB
--  either simple filters OR filter expressions
--
--  OUTPUT Responses:
--  For software which is currently running on the local host system:
--  [Argument of 'xcmSysAdminRequestedNone']
--  From 'xcmSysAdminRequestTable' in the XCMI System Admin MIB
--  xcmSysAdminRequestErrorStatus   XcmGenSNMPv2ErrorStatus  - mandatory
--  [Argument of 'xcmSysAdminRequestedBrief' - DEFAULT]
--  From 'hrSWRunTable' in the IETF Host Resources MIB (RFC 2790)
--  hrSWRunIndex                Cardinal32                   - mandatory
--  hrSWRunStatus               INTEGER                      - mandatory
--  From 'xcmHrSWRunTable' in the XCMI Host Resources Ext MIB
--  xcmHrSWRunRowStatus         RowStatus                    - mandatory
--  xcmHrSWRunAdminName         XcmFixedLocaleDisplayString  - mandatory
--  [Argument of 'xcmSysAdminRequestedVerbose', additions to 'Brief']
--  From 'xcmHrSWRunTable' in the XCMI Host Resources Ext MIB
--  xcmHrSWRunXStatus           XcmHrSWRunXStatus            - mandatory
--  xcmHrSWRunPhysicalDeviceIndex       Cardinal32           - mandatory
--  xcmHrSWRunLogicalDeviceIndex        Cardinal32           - mandatory
--  [Argument of 'xcmSysAdminRequestedAll']
--                              <OR>
--  [Argument of 'xcmSysAdminRequestedAttributes']
--  From ANY Software level table in the IETF Host Resources MIB
--  hrSWRun...                  [syntax]                     - cond mand
--  From ANY Software level table in the XCMI Host Resources Ext MIB
--  xcmHrSWRun...               [syntax]                     - cond mand
--
--  For software which is currently installed on the local host system:
--  [Argument of 'xcmSysAdminRequestedNone']
--  From 'xcmSysAdminRequestTable' in the XCMI System Admin MIB
--  xcmSysAdminRequestErrorStatus   XcmGenSNMPv2ErrorStatus  - mandatory
--  [Argument of 'xcmSysAdminRequestedBrief' - DEFAULT]
--  From 'hrSWInstalledTable' in the IETF Host Resources MIB (RFC 2790)
--  hrSWInstalledIndex          Cardinal32                   - mandatory
--  From 'xcmHrSWInstalledTable' in the XCMI Host Resources Ext MIB
--  xcmHrSWInstalledRowStatus   RowStatus                    - mandatory
--  xcmHrSWInstalledAdminName   XcmFixedLocaleDisplayString  - mandatory
--  [Argument of 'xcmSysAdminRequestedVerbose', additions to 'Brief']
--  From 'xcmHrSWInstalledTable' in the XCMI Host Resources Ext MIB
--  hrSWInstalledType           INTEGER                      - mandatory
--  hrSWInstalledName           InternationalDisplayString   - mandatory
--  hrSWInstalledID             ProductID                    - mandatory
--  [Argument of 'xcmSysAdminRequestedAll']
--                              <OR>
--  [Argument of 'xcmSysAdminRequestedAttributes']
--  From ANY Software level table in the IETF Host Resources MIB
--  hrSWInstalled...            [syntax]                     - cond mand
--  From ANY Software level table in the XCMI Host Resources Ext MIB
--  xcmHrSWInstalled...         [syntax]                     - cond mand
--  STATUS      current
--  DESCRIPTION
--      "List attributes of a host system server
--      (ie, a software-based system service which MAY support jobs)."
--  REFERENCE
--      "Section 4.7 'pdls' in POSIX IEEE 1387.4."
    ::= { xcmSysAdminOperationTypes 1203 }

xcmSysAdminServerSet OBJECT IDENTIFIER
--  SYNTAX      xcmSysAdminServerSet (...)
--
--  INPUT General Arguments:
--  For software which is currently running on the local host system:
--  From 'hrSWRunTable' in the IETF Host Resources MIB
--  hrSWRunIndex                Ordinal32                    - choice
--                              <OR>
--  From 'xcmHrSWRunTable' in the XCMI Host Resources Ext MIB
--  xcmHrSWRunAdminName         XcmFixedLocaleDisplayString  - choice
--
--  For software which is currently installed on the local host system:
--  From 'hrSWInstalledTable' in the IETF Host Resources MIB
--  hrSWInstalledIndex          Ordinal32                    - choice
--                              <OR>
--  From 'xcmHrSWInstalledTable' in the XCMI Host Resources Ext MIB
--  xcmHrSWInstalledAdminName   XcmFixedLocaleDisplayString  - choice
--
--  INPUT Set Assignments:
--  From ANY Software level table in the IETF Host Resources MIB
--  From ANY Software level table in the XCMI Host Resources Ext MIB
--  either simple assignments OR assignment expressions
--
--  INPUT Set Filters:
--  From ANY Software level table in the IETF Host Resources MIB
--  From ANY Software level table in the XCMI Host Resources Ext MIB
--  either simple filters OR filter expressions
--
--  OUTPUT Responses:
--  [See OUTPUT Responses from 'xcmSysAdminServerList']
--  STATUS      current
--  DESCRIPTION
--      "Set attributes of a host system server
--      (ie, a software-based system service which MAY support jobs)."
--  REFERENCE
--      "Section 4.16 'pdset' in POSIX IEEE 1387.4."
    ::= { xcmSysAdminOperationTypes 1204 }

xcmSysAdminServerClean OBJECT IDENTIFIER
--  SYNTAX      xcmSysAdminServerClean (...)
--
--  See:        xcmSysAdminServerDelete (identical arguments)
--  STATUS      current
--  DESCRIPTION
--      "Remove all jobs from a host system server
--      (ie, a software-based system service which MAY support jobs)."
--  REFERENCE
--      "Section 4.1 'pdclean' in POSIX IEEE 1387.4."
    ::= { xcmSysAdminOperationTypes 1205 }

xcmSysAdminServerDisable OBJECT IDENTIFIER
--  SYNTAX      xcmSysAdminServerDisable (...)
--
--  See:        xcmSysAdminServerDelete (identical arguments)
--  STATUS      current
--  DESCRIPTION
--      "Stop acceptance of jobs by a host system server
--      (ie, a software-based system service which MAY support jobs)."
--  REFERENCE
--      "Section 4.4 'pddisable' in POSIX IEEE 1387.4."
    ::= { xcmSysAdminOperationTypes 1206 }

xcmSysAdminServerEnable OBJECT IDENTIFIER
--  SYNTAX      xcmSysAdminServerEnable (...)
--
--  See:        xcmSysAdminServerDelete (identical arguments)
--  STATUS      current
--  DESCRIPTION
--      "Allow acceptance of jobs by a host system server
--      (ie, a software-based system service which MAY support jobs)."
--  REFERENCE
--      "Section 4.5 'pdenable' in POSIX IEEE 1387.4."
    ::= { xcmSysAdminOperationTypes 1207 }

xcmSysAdminServerPause OBJECT IDENTIFIER
--  SYNTAX      xcmSysAdminServerPause (...)
--
--  See:        xcmSysAdminServerDelete (identical arguments)
--  STATUS      current
--  DESCRIPTION
--      "Pause a host system server
--      (ie, a software-based system service which MAY support jobs)."
--  REFERENCE
--      "Section 4.9 'pdpause' in POSIX IEEE 1387.4."
    ::= { xcmSysAdminOperationTypes 1208 }

xcmSysAdminServerResume OBJECT IDENTIFIER
--  SYNTAX      xcmSysAdminServerResume (...)
--
--  See:        xcmSysAdminServerDelete (identical arguments)
--  STATUS      current
--  DESCRIPTION
--      "Resume a paused host system server
--      (ie, a software-based system service which MAY support jobs)."
--  REFERENCE
--      "Section 4.14 'pdresume' in POSIX IEEE 1387.4."
    ::= { xcmSysAdminOperationTypes 1209 }

xcmSysAdminServerShutdown OBJECT IDENTIFIER
--  SYNTAX      xcmSysAdminServerShutdown (...)
--
--  See:        xcmSysAdminServerDelete (identical arguments)
--
--  Note:       NO delete of 'hrSWRunTable' and 'xcmHrSWRunTable' rows
--  STATUS      current
--  DESCRIPTION
--      "Shutdown a host system server
--      (ie, a software-based system service which MAY support jobs)."
--  REFERENCE
--      "Section 4.17 'pdshutdown' in POSIX IEEE 1387.4."
    ::= { xcmSysAdminOperationTypes 1210 }

--
--  XCMI - Server level operations (host system servers)
--

xcmSysAdminXCMIServerOperations OBJECT IDENTIFIER
--  STATUS      current
--  DESCRIPTION
--      "XCMI - Server level operations"
--  REFERENCE
--      "Section 4 'Printing Utilities' in POSIX IEEE 1387.4."
    ::= { xcmSysAdminOperationTypes 2200 }

xcmSysAdminServerManage OBJECT IDENTIFIER
--  SYNTAX      xcmSysAdminServerManage (...)
--
--  For future extensions
--  STATUS      current
--  DESCRIPTION
--      "XCMI - Manage a host system server
--      (ie, a software-based system service which MAY support jobs)."
--  REFERENCE
--      "Section 4 'Printing Utilities' in POSIX IEEE 1387.4."
    ::= { xcmSysAdminOperationTypes 2201 }

xcmSysAdminServerRestart OBJECT IDENTIFIER
--  SYNTAX      xcmSysAdminServerRestart (...)
--
--  See:        xcmSysAdminServerDelete (identical arguments)
--  STATUS      current
--  DESCRIPTION
--      "XCMI - Restart a host system server
--      (ie, a software-based system service which MAY support jobs)."
--  REFERENCE
--      "Section 4.17 'pdshutdown' in POSIX IEEE 1387.4."
    ::= { xcmSysAdminOperationTypes 2202 }

xcmSysAdminServerInstall OBJECT IDENTIFIER
--  SYNTAX      xcmSysAdminServerInstall (...)
--
--  INPUT General Arguments:
--  From 'hrSWInstalledTable' in the IETF Host Resources MIB
--  hrSWInstalledIndex          Ordinal32                    - mandatory
--  hrSWInstalledName           InternationalDisplayString   - mandatory
--  hrSWInstalledID             ProductID                    - mandatory
--  hrSWInstalledType           Ordinal32                    - mandatory
--  From 'xcmHrSWInstalledTable' in the XCMI Host Resources Ext MIB
--  xcmHrSWInstalledRowStatus   RowStatus                    - mandatory
--  xcmHrSWInstalledAdminName   XcmFixedLocaleDisplayString  - mandatory
--
--  OUTPUT Responses:
--  [See OUTPUT Responses from 'xcmSysAdminServerList']
--
--  Note:       May involve file transfer, in addition to explicit
--              host system server attributes.
--  STATUS      current
--  DESCRIPTION
--      "XCMI - Install (but do NOT load and run) a host system server
--      (ie, a software-based system service which MAY support jobs)."
    ::= { xcmSysAdminOperationTypes 2221 }

xcmSysAdminServerUpgrade OBJECT IDENTIFIER
--  SYNTAX      xcmSysAdminServerUpgrade (...)
--
--  See:        xcmSysAdminServerInstall (identical arguments)
--
--  Note:       May involve file transfer, in addition to explicit
--              host system server attributes.
--  STATUS      current
--  DESCRIPTION
--      "XCMI - Upgrade (but do NOT load and run) a host system server
--      (ie, a software-based system service which MAY support jobs)."
    ::= { xcmSysAdminOperationTypes 2222 }

xcmSysAdminServerBackup OBJECT IDENTIFIER
--  SYNTAX      xcmSysAdminServerBackup (...)
--
--  INPUT General Arguments:
--  From 'hrSWInstalledTable' in the IETF Host Resources MIB
--  hrSWInstalledIndex          Ordinal32                    - choice
--                              <OR>
--  From 'xcmHrSWInstalledTable' in the XCMI Host Resources Ext MIB
--  xcmHrSWInstalledAdminName   XcmFixedLocaleDisplayString  - choice
--
--  INPUT Backup Filters:
--  From ANY Software level table in the IETF Host Resources MIB
--  From ANY Software level table in the XCMI Host Resources Ext MIB
--  either simple filters OR filter expressions
--
--  OUTPUT Responses:
--  [See OUTPUT Responses from 'xcmSysAdminServerList']
--
--  Note:       May involve file transfer, in addition to explicit
--              host system server attributes.
--  STATUS      current
--  DESCRIPTION
--      "XCMI - Backup a host system server
--      (ie, a software-based system service which MAY support jobs)."
    ::= { xcmSysAdminOperationTypes 2223 }

xcmSysAdminServerRestore OBJECT IDENTIFIER
--  SYNTAX      xcmSysAdminServerRestore (...)
--
--  See:        xcmSysAdminServerBackup (identical arguments)
--
--  Note:       May involve file transfer, in addition to explicit
--              host system server attributes.
--  STATUS      current
--  DESCRIPTION
--      "XCMI - Restore a host system server
--      (ie, a software-based system service which MAY support jobs)."
    ::= { xcmSysAdminOperationTypes 2224 }

xcmSysAdminServerConfigure OBJECT IDENTIFIER
--  SYNTAX      xcmSysAdminServerConfigure (...)
--
--  See:        xcmSysAdminServerSet (identical arguments)
--
--  Note:       May involve file transfer, in addition to explicit
--              host system server attributes.
--  STATUS      current
--  DESCRIPTION
--      "XCMI - Configure a host system server
--      (ie, a software-based system service which MAY support jobs)."
    ::= { xcmSysAdminOperationTypes 2225 }

xcmSysAdminServerDiagnose OBJECT IDENTIFIER
--  SYNTAX      xcmSysAdminServerDiagnose (...)
--
--  See:        xcmSysAdminServerBackup (identical arguments)
--
--  Note:       May involve file transfer, in addition to explicit
--              host system server attributes.
--  STATUS      current
--  DESCRIPTION
--      "XCMI - Diagnose a host system server
--      (ie, a software-based system service which MAY support jobs)."
    ::= { xcmSysAdminOperationTypes 2226 }

xcmSysAdminServerResetCounters OBJECT IDENTIFIER
--  SYNTAX      xcmSysAdminServerResetCounters (...)
--
--  See:        xcmSysAdminServerDelete (identical arguments)
--  STATUS      current
--  DESCRIPTION
--      "XCMI - Reset counters on a host system server
--      (ie, a software-based system service which MAY support jobs)."
    ::= { xcmSysAdminOperationTypes 2231 }

xcmSysAdminServerResetWarm OBJECT IDENTIFIER
--  SYNTAX      xcmSysAdminServerResetWarm (...)
--
--  See:        xcmSysAdminServerDelete (identical arguments)
--  STATUS      current
--  DESCRIPTION
--      "XCMI - Reset warm (w/out power cycle) a host system server
--      (ie, a software-based system service which MAY support jobs)."
    ::= { xcmSysAdminOperationTypes 2232 }

xcmSysAdminServerResetCold OBJECT IDENTIFIER
--  SYNTAX      xcmSysAdminServerResetCold (...)
--
--  See:        xcmSysAdminServerDelete (identical arguments)
--  STATUS      current
--  DESCRIPTION
--      "XCMI - Reset cold (w/ power cycle) a host system server
--      (ie, a software-based system service which MAY support jobs)."
    ::= { xcmSysAdminOperationTypes 2233 }

xcmSysAdminServerResetFactory OBJECT IDENTIFIER
--  SYNTAX      xcmSysAdminServerResetFactory (...)
--
--  See:        xcmSysAdminServerDelete (identical arguments)
--  STATUS      current
--  DESCRIPTION
--      "XCMI - Reset to factory defaults a host system server
--      (ie, a software-based system service which MAY support jobs)."
    ::= { xcmSysAdminOperationTypes 2234 }

--
--  POSIX - Device level operations (host system devices)
--

xcmSysAdminDeviceOperations OBJECT IDENTIFIER
--  STATUS      current
--  DESCRIPTION
--      "POSIX - Device level operations"
--  REFERENCE
--      "Section 4 'Printing Utilities' in POSIX IEEE 1387.4."
    ::= { xcmSysAdminOperationTypes 1300 }

xcmSysAdminDeviceCreate OBJECT IDENTIFIER
--  SYNTAX      xcmSysAdminDeviceCreate (...)
--
--  INPUT General Arguments:
--  From 'hrDeviceTable' in the IETF Host Resources MIB (RFC 2790)
--  hrDeviceIndex               Ordinal32                    - mandatory
--  hrDeviceType                OBJECT IDENTIFIER            - mandatory
--  hrDeviceDescr               DisplayString                - mandatory
--  hrDeviceID                  ProductID                    - mandatory
--  From 'xcmHrDevInfoTable' in the XCMI Host Resources Ext MIB
--  xcmHrDevInfoRowStatus       RowStatus                    - mandatory
--  xcmHrDevInfoName            XcmFixedLocaleDisplayString  - mandatory
--  xcmHrDevInfoSerialNumber    XcmFixedLocaleDisplayString  - optional
--  xcmHrDevInfoRealization     XcmHrDevInfoRealization      - mandatory
--  xcmHrDevInfoNextDeviceIndex         Cardinal32           - optional
--  xcmHrDevInfoPreviousDeviceIndex     Cardinal32           - optional
--  xcmHrDevInfoPhysicalDeviceIndex     Cardinal32           - optional
--  From 'xcmHrDevHelpTable' in the XCMI Host Resources Ext MIB
--  xcmHrDevHelp...             [syntax]                     - optional
--  From 'xcmHrDevMgmtTable' in the XCMI Host Resources Ext MIB
--  xcmHrDevMgmt...             [syntax]                     - optional
--  From 'xcmHrDevPowerTable' in the XCMI Host Resources Ext MIB
--  xcmHrDevPower...            [syntax]                     - optional
--  From 'xcmHrDevTrafficTable' in the XCMI Host Resources Ext MIB
--  xcmHrDevTraffic...          [syntax]                     - optional
--
--  INPUT Processor Device Arguments:
--  ONLY for devices of type 'hrDeviceProcessor'
--  From 'hrProcessorTable' in the IETF Host Resources MIB (RFC 2790)
--  hrProcessorFrwID            ProductID                    - mandatory
--
--  INPUT Network Device Arguments:
--  ONLY for devices of type 'hrDevice[Network|ParallelPort|SerialPort]'
--  From 'hrNetworkTable' in the IETF Host Resources MIB (RFC 2790)
--  hrNetworkIfIndex            Ordinal32                    - mandatory
--
--  INPUT Printer Device Arguments:
--  ONLY for devices of type 'hrDevicePrinter'
--  From various tables in the IETF Printer MIB (RFC 1759)
--  prt...                      [syntax]                     - optional
--
--  INPUT Disk Storage Device Arguments:
--  ONLY for devices of type 'hrDeviceDiskStorage'
--  From 'hrDiskStorageTable' in the IETF Host Resources MIB (RFC 2790)
--  hrDiskStorageAccess         Ordinal32                    - mandatory
--  hrDiskStorageMedia          Ordinal32                    - mandatory
--  hrDiskStorageRemoveble      TruthValue                   - mandatory
--  hrDiskStorageCapacity       Cardinal32                   - mandatory
--  From 'hrPartitionTable' in the IETF Host Resources MIB (RFC 2790)
--  hrPartitionIndex            Ordinal32                    - optional
--  hrPartitionLabel            InternationalDisplayString   - optional
--  hrPartitionID               OCTET STRING                 - optional
--  hrPartitionSize             Cardinal32                   - optional
--  hrPartitionFSIndex          Cardinal32                   - optional
--  From 'hrFSTable' in the IETF Host Resources MIB (RFC 2790)
--  hrFSIndex                   Ordinal32                    - optional
--  hrFSMountPoint              InternationalDisplayString   - optional
--  hrFSRemoteMountPoint        InternationalDisplayString   - optional
--  hrFSType                    OBJECT IDENTIFIER            - optional
--  hrFSAccess                  Ordinal32                    - optional
--  hrFSBootable                TruthValue                   - optional
--  hrFSStorageIndex            Cardinal32                   - optional
--
--  OUTPUT Responses:
--  [See OUTPUT Responses from 'xcmSysAdminDeviceList']
--  STATUS      current
--  DESCRIPTION
--      "Create a host system device."
--  REFERENCE
--      "Section 4.2 'pdcreate' in POSIX IEEE 1387.4."
    ::= { xcmSysAdminOperationTypes 1301 }

xcmSysAdminDeviceDelete OBJECT IDENTIFIER
--  SYNTAX      xcmSysAdminDeviceDelete (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  OUTPUT Responses:
--  [See OUTPUT Responses from 'xcmSysAdminDeviceList']
--  STATUS      current
--  DESCRIPTION
--      "Delete a host system device."
--  REFERENCE
--      "Section 4.3 'pddelete' in POSIX IEEE 1387.4."
    ::= { xcmSysAdminOperationTypes 1302 }

xcmSysAdminDeviceList OBJECT IDENTIFIER
--  SYNTAX      xcmSysAdminDeviceList (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  INPUT List Filters:
--  From ANY Device level table in the IETF Host Resources MIB
--  From ANY Device level table in the XCMI Host Resources Ext MIB
--  either simple filters OR filter expressions
--
--  OUTPUT Responses:
--  [Argument of 'xcmSysAdminRequestedNone']
--  From 'xcmSysAdminRequestTable' in the XCMI System Admin MIB
--  xcmSysAdminRequestErrorStatus   XcmGenSNMPv2ErrorStatus  - mandatory
--  [Argument of 'xcmSysAdminRequestedBrief' - DEFAULT]
--  From 'hrDeviceTable' in the IETF Host Resources MIB (RFC 2790)
--  hrDeviceIndex               Cardinal32                   - mandatory
--  hrDeviceStatus              Ordinal32                    - mandatory
--  From 'xcmHrDevInfoTable' in the XCMI Host Resources Ext MIB
--  xcmHrDevInfoRowStatus       RowStatus                    - mandatory
--  xcmHrDevInfoName            XcmFixedLocaleDisplayString  - mandatory
--  xcmHrDevInfoRealization     XcmHrDevInfoRealization      - mandatory
--  [Argument of 'xcmSysAdminRequestedVerbose', additions to 'Brief']
--  From 'hrDeviceTable' in the IETF Host Resources MIB (RFC 2790)
--  hrDeviceType                OBJECT IDENTIFIER            - mandatory
--  hrDeviceDescr               DisplayString                - mandatory
--  hrDeviceID                  ProductID                    - mandatory
--  From 'xcmHrDevInfoTable' in the XCMI Host Resources Ext MIB
--  xcmHrDevInfoXStatus         XcmHrDevInfoXStatus          - mandatory
--  xcmHrDevInfoConditions      XcmHrDevInfoConditions       - mandatory
--  xcmHrDevInfoXConditions     XcmHrDevInfoXConditions      - mandatory
--  xcmHrDevInfoNextDeviceIndex         Cardinal32           - mandatory
--  xcmHrDevInfoPreviousDeviceIndex     Cardinal32           - mandatory
--  xcmHrDevInfoPhysicalDeviceIndex     Cardinal32           - mandatory
--  [Argument of 'xcmSysAdminRequestedAll']
--                              <OR>
--  [Argument of 'xcmSysAdminRequestedAttributes']
--  From ANY Device level table in the IETF Host Resources MIB
--  hr...                       [syntax]                     - cond mand
--  From ANY Device level table in the XCMI Host Resources Ext MIB
--  xcmHrDev...                 [syntax]                     - cond mand
--  STATUS      current
--  DESCRIPTION
--      "List attributes of a host system device."
--  REFERENCE
--      "Section 4.7 'pdls' in POSIX IEEE 1387.4."
    ::= { xcmSysAdminOperationTypes 1303 }

xcmSysAdminDeviceSet OBJECT IDENTIFIER
--  SYNTAX      xcmSysAdminDeviceSet (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  INPUT Set Assignments:
--  From ANY Device level table in the IETF Host Resources MIB
--  From ANY Device level table in the XCMI Host Resources Ext MIB
--  either simple assignments OR assignment expressions
--
--  INPUT Set Filters:
--  From ANY Device level table in the IETF Host Resources MIB
--  From ANY Device level table in the XCMI Host Resources Ext MIB
--  either simple filters OR filter expressions
--
--  OUTPUT Responses:
--  [See OUTPUT Responses from 'xcmSysAdminDeviceList']
--  STATUS      current
--  DESCRIPTION
--      "Set attributes of a host system device."
--  REFERENCE
--      "Section 4.16 'pdset' in POSIX IEEE 1387.4."
    ::= { xcmSysAdminOperationTypes 1304 }

xcmSysAdminDeviceClean OBJECT IDENTIFIER
--  SYNTAX      xcmSysAdminDeviceClean (...)
--
--  See:        xcmSysAdminDeviceDelete (identical arguments)
--  STATUS      current
--  DESCRIPTION
--      "Remove all jobs from a host system device."
--  REFERENCE
--      "Section 4.1 'pdclean' in POSIX IEEE 1387.4."
    ::= { xcmSysAdminOperationTypes 1305 }

xcmSysAdminDeviceDisable OBJECT IDENTIFIER
--  SYNTAX      xcmSysAdminDeviceDisable (...)
--
--  See:        xcmSysAdminDeviceDelete (identical arguments)
--  STATUS      current
--  DESCRIPTION
--      "Stop acceptance of jobs by a host system device."
--  REFERENCE
--      "Section 4.4 'pddisable' in POSIX IEEE 1387.4."
    ::= { xcmSysAdminOperationTypes 1306 }

xcmSysAdminDeviceEnable OBJECT IDENTIFIER
--  SYNTAX      xcmSysAdminDeviceEnable (...)
--
--  See:        xcmSysAdminDeviceDelete (identical arguments)
--  STATUS      current
--  DESCRIPTION
--      "Allow acceptance of jobs by a host system device."
--  REFERENCE
--      "Section 4.5 'pdenable' in POSIX IEEE 1387.4."
    ::= { xcmSysAdminOperationTypes 1307 }

xcmSysAdminDevicePause OBJECT IDENTIFIER
--  SYNTAX      xcmSysAdminDevicePause (...)
--
--  See:        xcmSysAdminDeviceDelete (identical arguments)
--  STATUS      current
--  DESCRIPTION
--      "Pause a host system device."
--  REFERENCE
--      "Section 4.9 'pdpause' in POSIX IEEE 1387.4."
    ::= { xcmSysAdminOperationTypes 1308 }

xcmSysAdminDeviceResume OBJECT IDENTIFIER
--  SYNTAX      xcmSysAdminDeviceResume (...)
--
--  See:        xcmSysAdminDeviceDelete (identical arguments)
--  STATUS      current
--  DESCRIPTION
--      "Resume a paused host system device."
--  REFERENCE
--      "Section 4.14 'pdresume' in POSIX IEEE 1387.4."
    ::= { xcmSysAdminOperationTypes 1309 }

xcmSysAdminDeviceShutdown OBJECT IDENTIFIER
--  SYNTAX      xcmSysAdminDeviceShutdown (...)
--
--  See:        xcmSysAdminDeviceDelete (identical arguments)
--  STATUS      current
--  DESCRIPTION
--      "Shutdown a host system device."
--  REFERENCE
--      "Section 4.17 'pdshutdown' in POSIX IEEE 1387.4."
    ::= { xcmSysAdminOperationTypes 1310 }

xcmSysAdminDeviceQueueList OBJECT IDENTIFIER
--  SYNTAX      xcmSysAdminDeviceQueueList (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  OUTPUT Responses:
--  [See OUTPUT Responses from 'xcmSysAdminJobList']
--  STATUS      current
--  DESCRIPTION
--      "List job queue on a host system device."
--  REFERENCE
--      "Section 4.12 'pdq' in POSIX IEEE 1387.4."
    ::= { xcmSysAdminOperationTypes 1311 }

--
--  XCMI - Device level operations (host system devices)
--

xcmSysAdminXCMIDeviceOperations OBJECT IDENTIFIER
--  STATUS      current
--  DESCRIPTION
--      "XCMI - Device level operations"
--  REFERENCE
--      "Section 4 'Printing Utilities' in POSIX IEEE 1387.4."
    ::= { xcmSysAdminOperationTypes 2300 }

xcmSysAdminDeviceManage OBJECT IDENTIFIER
--  SYNTAX      xcmSysAdminDeviceManage (...)
--
--  For future extensions
--  STATUS      current
--  DESCRIPTION
--      "XCMI - Manage a host system device."
--  REFERENCE
--      "Section 4 'Printing Utilities' in POSIX IEEE 1387.4."
    ::= { xcmSysAdminOperationTypes 2301 }

xcmSysAdminDeviceRestart OBJECT IDENTIFIER
--  SYNTAX      xcmSysAdminDeviceRestart (...)
--
--  See:        xcmSysAdminDeviceDelete (identical arguments)
--  STATUS      current
--  DESCRIPTION
--      "XCMI - Restart a host system device."
--  REFERENCE
--      "Section 4.17 'pdshutdown' in POSIX IEEE 1387.4."
    ::= { xcmSysAdminOperationTypes 2302 }

xcmSysAdminDeviceInstall OBJECT IDENTIFIER
--  SYNTAX      xcmSysAdminDeviceInstall (...)
--
--  See:        xcmSysAdminDeviceCreate (identical arguments)
--
--  Note:       May involve file transfer, in addition to explicit
--              host system device attributes.
--  STATUS      current
--  DESCRIPTION
--      "XCMI - Install a host system device."
    ::= { xcmSysAdminOperationTypes 2321 }

xcmSysAdminDeviceUpgrade OBJECT IDENTIFIER
--  SYNTAX      xcmSysAdminDeviceUpgrade (...)
--
--  See:        xcmSysAdminDeviceInstall (identical arguments)
--
--  Note:       May involve file transfer, in addition to explicit
--              host system device attributes.
--  STATUS      current
--  DESCRIPTION
--      "XCMI - Upgrade a host system device."
    ::= { xcmSysAdminOperationTypes 2322 }

xcmSysAdminDeviceBackup OBJECT IDENTIFIER
--  SYNTAX      xcmSysAdminDeviceBackup (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  INPUT Backup Filters:
--  From ANY Device level table in the IETF Host Resources MIB
--  From ANY Device level table in the XCMI Host Resources Ext MIB
--  either simple filters OR filter expressions
--
--  OUTPUT Responses:
--  [See OUTPUT Responses from 'xcmSysAdminDeviceList']
--
--  Note:       May involve file transfer, in addition to explicit
--              host system device attributes.
--  STATUS      current
--  DESCRIPTION
--      "XCMI - Backup a host system device."
    ::= { xcmSysAdminOperationTypes 2323 }

xcmSysAdminDeviceRestore OBJECT IDENTIFIER
--  SYNTAX      xcmSysAdminDeviceRestore (...)
--
--  See:        xcmSysAdminDeviceBackup (identical arguments)
--
--  Note:       May involve file transfer, in addition to explicit
--              host system device attributes.
--  STATUS      current
--  DESCRIPTION
--      "XCMI - Restore a host system device."
    ::= { xcmSysAdminOperationTypes 2324 }

xcmSysAdminDeviceConfigure OBJECT IDENTIFIER
--  SYNTAX      xcmSysAdminDeviceConfigure (...)
--
--  See:        xcmSysAdminDeviceSet (identical arguments)
--
--  Note:       May involve file transfer, in addition to explicit
--              host system device attributes.
--  STATUS      current
--  DESCRIPTION
--      "XCMI - Configure a host system device."
    ::= { xcmSysAdminOperationTypes 2325 }

xcmSysAdminDeviceDiagnose OBJECT IDENTIFIER
--  SYNTAX      xcmSysAdminDeviceDiagnose (...)
--
--  See:        xcmSysAdminDeviceBackup (identical arguments)
--
--  Note:       May involve file transfer, in addition to explicit
--              host system device attributes.
--  STATUS      current
--  DESCRIPTION
--      "XCMI - Diagnose a host system device."
    ::= { xcmSysAdminOperationTypes 2326 }

xcmSysAdminDeviceResetCounters OBJECT IDENTIFIER
--  SYNTAX      xcmSysAdminDeviceResetCounters (...)
--
--  See:        xcmSysAdminDeviceDelete (identical arguments)
--  STATUS      current
--  DESCRIPTION
--      "XCMI - Reset counters on a host system device."
    ::= { xcmSysAdminOperationTypes 2331 }

xcmSysAdminDeviceResetWarm OBJECT IDENTIFIER
--  SYNTAX      xcmSysAdminDeviceResetWarm (...)
--
--  See:        xcmSysAdminDeviceDelete (identical arguments)
--  STATUS      current
--  DESCRIPTION
--      "XCMI - Reset warm (w/out power cycle) a host system device."
    ::= { xcmSysAdminOperationTypes 2332 }

xcmSysAdminDeviceResetCold OBJECT IDENTIFIER
--  SYNTAX      xcmSysAdminDeviceResetCold (...)
--
--  See:        xcmSysAdminDeviceDelete (identical arguments)
--  STATUS      current
--  DESCRIPTION
--      "XCMI - Reset cold (w/ power cycle) a host system device."
    ::= { xcmSysAdminOperationTypes 2333 }

xcmSysAdminDeviceResetFactory OBJECT IDENTIFIER
--  SYNTAX      xcmSysAdminDeviceResetFactory (...)
--
--  See:        xcmSysAdminDeviceDelete (identical arguments)
--  STATUS      current
--  DESCRIPTION
--      "XCMI - Reset to factory defaults a host system device."
    ::= { xcmSysAdminOperationTypes 2334 }

--
--  POSIX - Job level operations (host system jobs)
--

xcmSysAdminJobOperations OBJECT IDENTIFIER
--  STATUS      current
--  DESCRIPTION
--      "POSIX - Job level operations (host system jobs)"
--  REFERENCE
--      "Section 4 'Printing Utilities' in POSIX IEEE 1387.4."
    ::= { xcmSysAdminOperationTypes 1400 }

xcmSysAdminJobCreate OBJECT IDENTIFIER
--  SYNTAX      xcmSysAdminJobCreate (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--  From 'xcmJobGenBasicTable' in the XCMI Job Monitoring MIB
--  xcmJobClientId              XcmGlobalUniqueID            - mandatory
--  xcmJobServiceType           XcmJMJobServiceTypeOID       - mandatory
--  xcmJobName                  OCTET STRING                 - optional
--  xcmJobOwner                 OCTET STRING                 - optional
--  xcmJobSubmittedLocaleIndex  Cardinal32                   - optional
--  From 'xcmJobGenExtTable' in the XCMI Job Monitoring MIB
--  xcmJobOriginator            OCTET STRING                 - optional
--  xcmJobSubmittingApplication OCTET STRING                 - optional
--  xcmJobComment               OCTET STRING                 - optional
--  xcmJobCopies                Ordinal32                    - optional
--  xcmJobOutputBinIndex        Integer32                    - optional
--  xcmJobAuthorizationUserName OCTET STRING                 - optional
--  From 'xcmJobGenSpoolingBasicTable' in the XCMI Job Monitoring MIB
--  xcmJobNumberOfJobResultSets Ordinal32                    - optional
--  xcmJobPriority              INTEGER(0..100)              - optional
--  From 'xcmJobGenSpoolingExtTable' in the XCMI Job Monitoring MIB
--  xcmJobProcessAfter          DateAndTime                  - optional
--  xcmJobDeadlineTime          DateAndTime                  - optional
--  xcmJobDiscardTime           DateAndTime                  - optional
--  xcmJobRetentionPeriod       Cardinal32                   - optional
--  xcmJobMessageToOperator     OCTET STRING                 - optional
--  From 'xcmJobGenAccountingBasicTable' in the XCMI Job Monitoring MIB
--  xcmJobAccountingUserName    OCTET STRING                 - optional
--  xcmJobAccountingInformation OCTET STRING                 - optional
--
--  INPUT Document Arguments:
--  From 'xcmDocGenBasicTable' in the XCMI Job Monitoring MIB
--  xcmDocSequenceNumber        Ordinal32                    - optional
--  xcmDocName                  OCTET STRING                 - optional
--  xcmDocFileName              OCTET STRING                 - optional
--  xcmDocFileNameType          XcmJMDocFileNameType         - optional
--  xcmDocType                  XcmJMDocType                 - optional
--  xcmDocFormat                XcmPrtInterpreterLangFamily  - optional
--  xcmDocFormatVariants        OCTET STRING                 - optional
--  xcmDocFormatVersion         OCTET STRING                 - optional
--  From 'xcmDocPrintExtTable' in the XCMI Job Monitoring MIB
--  xcmDocPrintDefaultMediumName    OCTET STRING             - optional
--  xcmDocPrintDefaultInputIndex    Ordinal16                - optional
--  xcmDocPrintFinishing            OCTET STRING             - optional
--  xcmDocPrintOutputMethod         XcmJMDocOutputMethod     - optional
--  xcmDocPrintNumberUp             OCTET STRING             - optional
--  xcmDocPrintSides                INTEGER(1..2)            - optional
--  xcmDocPrintCopyCount            Cardinal32               - optional
--
--  OUTPUT Responses:
--  [See OUTPUT Responses from 'xcmSysAdminJobList']
--  STATUS      current
--  DESCRIPTION
--      "Create a host system job."
--  REFERENCE
--      "Section 4.10 'pdpr' in POSIX IEEE 1387.4."
    ::= { xcmSysAdminOperationTypes 1401 }

xcmSysAdminJobDelete OBJECT IDENTIFIER
--  SYNTAX      xcmSysAdminJobDelete (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  From 'xcmJobGenBasicTable' in the XCMI Job Monitoring MIB
--  xcmJobIdentifierOnSystem    OCTET STRING                 - choice
--                              <OR>
--  From 'xcmJobGenBasicTable' in the XCMI Job Monitoring MIB
--  xcmJobClientId              XcmGlobalUniqueID            - choice
--
--  OUTPUT Responses:
--  [See OUTPUT Responses from 'xcmSysAdminJobList']
--  STATUS      current
--  DESCRIPTION
--      "Delete a host system job."
--  REFERENCE
--      "Section 4.3 'pddelete' in POSIX IEEE 1387.4."
    ::= { xcmSysAdminOperationTypes 1402 }

xcmSysAdminJobList OBJECT IDENTIFIER
--  SYNTAX      xcmSysAdminJobList (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  From 'xcmJobGenBasicTable' in the XCMI Job Monitoring MIB
--  xcmJobIdentifierOnSystem    OCTET STRING                 - choice
--                              <OR>
--  From 'xcmJobGenBasicTable' in the XCMI Job Monitoring MIB
--  xcmJobClientId              XcmGlobalUniqueID            - choice
--
--  INPUT List Filters:
--  From ANY Job level table in the XCMI Job Monitoring MIB
--  either simple filters OR filter expressions
--
--  OUTPUT Responses:
--  [Argument of 'xcmSysAdminRequestedNone']
--  From 'xcmSysAdminRequestTable' in the XCMI System Admin MIB
--  xcmSysAdminRequestErrorStatus   XcmGenSNMPv2ErrorStatus  - mandatory
--  [Argument of 'xcmSysAdminRequestedBrief' - DEFAULT]
--  From 'hrDeviceTable' in the IETF Host Resources MIB (RFC 2790)
--  hrDeviceIndex               Ordinal32                    - mandatory
--  From 'xcmJobGenBasicTable' in the XCMI Job Monitoring MIB
--  xcmJobIdentifierOnSystem    OCTET STRING                 - mandatory
--  xcmJobClientId              XcmGlobalUniqueID            - mandatory
--  xcmJobName                  OCTET STRING                 - mandatory
--  xcmJobCurrentState          XcmJMJobState                - mandatory
--  From 'xcmDevicesAssignedTable' in the XCMI Job Monitoring MIB
--  xcmDevicesAssignedHrDeviceIndex     Cardinal32           - mandatory
--  xcmDeviceStateOfDevicesAssigned     XcmHrDevInfoXStatus  - mandatory
--  xcmJobIdentifierDownstream          OCTET STRING         - mandatory
--  From 'xcmJobGenExtTable' in the XCMI Job Monitoring MIB
--  xcmJobServiceNameRequested  OCTET STRING                 - cond mand
--  From 'xcmJobGenSpoolingBasicTable' in the XCMI Job Monitoring MIB
--  xcmJobInteveningJobs        Integer32                    - cond mand
--  [Argument of 'xcmSysAdminRequestedVerbose', additions to 'Brief']
--  From 'xcmJobGenBasicTable' in the XCMI Job Monitoring MIB
--  xcmJobOwner                 OCTET STRING                 - mandatory
--  xcmJobStateReasons          XcmJMJobStateReasons         - mandatory
--  xcmJobXStateReasons         XcmJMJobXStateReasons        - mandatory
--  xcmJobX2StateReasons        XcmJMJobX2StateReasons       - mandatory
--  From 'xcmJobGenSpoolingBasicTable' in the XCMI Job Monitoring MIB
--  xcmJobTotalOctetsHigh       Cardinal64High               - cond mand
--  xcmJobTotalOctetsLow        Cardinal64Low                - cond mand
--  [Argument of 'xcmSysAdminRequestedAll']
--                              <OR>
--  [Argument of 'xcmSysAdminRequestedAttributes']
--  From ANY Job level table in the XCMI Job Monitoring MIB
--  xcm...                      [syntax]                     - cond mand
--  STATUS      current
--  DESCRIPTION
--      "List attributes of a host system job."
--  REFERENCE
--      "Section 4.7 'pdls' in POSIX IEEE 1387.4."
    ::= { xcmSysAdminOperationTypes 1403 }

xcmSysAdminJobSet OBJECT IDENTIFIER
--  SYNTAX      xcmSysAdminJobSet (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  From 'xcmJobGenBasicTable' in the XCMI Job Monitoring MIB
--  xcmJobIdentifierOnSystem    OCTET STRING                 - choice
--                              <OR>
--  From 'xcmJobGenBasicTable' in the XCMI Job Monitoring MIB
--  xcmJobClientId              XcmGlobalUniqueID            - choice
--
--  INPUT Set Arguments:
--  From ANY Job level table in the XCMI Job Monitoring MIB
--  either simple assignments OR assignment expressions
--
--  INPUT Set Filters:
--  From ANY Job level table in the XCMI Job Monitoring MIB
--  either simple filters OR filter expressions
--
--  OUTPUT Responses:
--  [See OUTPUT Responses from 'xcmSysAdminJobList']
--  STATUS      current
--  DESCRIPTION
--      "Set attributes of a host system job."
--  REFERENCE
--      "Section 4.16 'pdset' in POSIX IEEE 1387.4."
    ::= { xcmSysAdminOperationTypes 1404 }

xcmSysAdminJobPause OBJECT IDENTIFIER
--  SYNTAX      xcmSysAdminJobPause (...)
--
--  See:        xcmSysAdminJobDelete (identical arguments)
--  STATUS      current
--  DESCRIPTION
--      "Pause a host system job."
--  REFERENCE
--      "Section 4.9 'pdpause' in POSIX IEEE 1387.4."
    ::= { xcmSysAdminOperationTypes 1408 }

xcmSysAdminJobResume OBJECT IDENTIFIER
--  SYNTAX      xcmSysAdminJobResume (...)
--
--  See:        xcmSysAdminJobDelete (identical arguments)
--  STATUS      current
--  DESCRIPTION
--      "Resume a paused host system job."
--  REFERENCE
--      "Section 4.14 'pdresume' in POSIX IEEE 1387.4."
    ::= { xcmSysAdminOperationTypes 1409 }

xcmSysAdminJobInterrupt OBJECT IDENTIFIER
--  SYNTAX      xcmSysAdminJobInterrupt (...)
--
--  INPUT General Arguments:
--  From 'hrDeviceTable' in the IETF Host Resources MIB (RFC 2790)
--  hrDeviceIndex               Ordinal32                    - mandatory
--  From 'xcmJobGenBasicTable' in the XCMI Job Monitoring MIB
--  xcmJobIdentifierOnSystem (to start) OCTET STRING         - mandatory
--  xcmJobIdentifierOnSystem (to stop)  OCTET STRING         - optional
--
--  OUTPUT Responses:
--  [See OUTPUT Responses from 'xcmSysAdminJobList']
--  STATUS      current
--  DESCRIPTION
--      "Interrupt a host system job with another job."
--  REFERENCE
--      "Section 4.6 'pdinterrupt' in POSIX IEEE 1387.4."
    ::= { xcmSysAdminOperationTypes 1411 }

xcmSysAdminJobModify OBJECT IDENTIFIER
--  SYNTAX      xcmSysAdminJobModify (...)
--
--  See:        xcmSysAdminJobSet (identical arguments)
--  STATUS      current
--  DESCRIPTION
--      "Modify a host system job."
--  REFERENCE
--      "Section 4.8 'pdmod' in POSIX IEEE 1387.4."
    ::= { xcmSysAdminOperationTypes 1412 }

xcmSysAdminJobPromote OBJECT IDENTIFIER
--  SYNTAX      xcmSysAdminJobPromote (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  From 'xcmJobGenBasicTable' in the XCMI Job Monitoring MIB
--  xcmJobIdentifierOnSystem    OCTET STRING                 - choice
--                              <OR>
--  From 'xcmJobGenBasicTable' in the XCMI Job Monitoring MIB
--  xcmJobClientId              XcmGlobalUniqueID            - choice
--
--  INPUT Promote Arguments:
--  From 'xcmJobGenSpoolingBasicTable' in the XCMI Job Monitoring MIB
--  xcmJobPriority              INTEGER(0..100),             - optional
--  xcmJobInterveningJobs       Integer32                    - optional
--
--  OUTPUT Responses:
--  [See OUTPUT Responses from 'xcmSysAdminJobList']
--  From 'xcmJobGenSpoolingBasicTable' in the XCMI Job Monitoring MIB
--  xcmJobPriority              INTEGER(0..100),             - cond mand
--  xcmJobInterveningJobs       Integer32                    - cond mand
--  STATUS      current
--  DESCRIPTION
--      "Promote a host system job to process next on a device."
--  REFERENCE
--      "Section 4.11 'pdpromote' in POSIX IEEE 1387.4."
    ::= { xcmSysAdminOperationTypes 1413 }

xcmSysAdminJobRemove OBJECT IDENTIFIER
--  SYNTAX      xcmSysAdminJobRemove (...)
--
--  See:        xcmSysAdminJobDelete (identical arguments)
--  STATUS      current
--  DESCRIPTION
--      "Remove (cancel) a job from a host system device."
--  REFERENCE
--      "Section 4.15 'pdrm' in POSIX IEEE 1387.4."
    ::= { xcmSysAdminOperationTypes 1414 }

xcmSysAdminJobResubmit OBJECT IDENTIFIER
--  SYNTAX      xcmSysAdminJobResubmit (...)
--
--  INPUT General Arguments:
--  From 'hrDeviceTable' in the IETF Host Resources MIB (RFC 2790)
--  hrDeviceIndex (old)         Ordinal32                    - choice
--                              <OR>
--  From 'xcmHrDevInfoTable' in the XCMI Host Resources Ext MIB
--  xcmHrDevInfoName (old)      XcmFixedLocaleDisplayString  - choice
--
--  From 'xcmJobGenBasicTable' in the XCMI Job Monitoring MIB
--  xcmJobIdentifierOnSystem    OCTET STRING                 - choice
--                              <OR>
--  From 'xcmJobGenBasicTable' in the XCMI Job Monitoring MIB
--  xcmJobClientId              XcmGlobalUniqueID            - choice
--
--  From 'hrDeviceTable' in the IETF Host Resources MIB (RFC 2790)
--  hrDeviceIndex (new)         Ordinal32                    - choice
--                              <OR>
--  From 'xcmHrDevInfoTable' in the XCMI Host Resources Ext MIB
--  xcmHrDevInfoName (new)      XcmFixedLocaleDisplayString  - choice
--
--  OUTPUT Responses:
--  [See OUTPUT Responses from 'xcmSysAdminJobList']
--  STATUS      current
--  DESCRIPTION
--      "Resubmit a job to [the same or] another host system device."
--  REFERENCE
--      "Section 4.13 'pdresubmit' in POSIX IEEE 1387.4."
    ::= { xcmSysAdminOperationTypes 1415 }

--
--  XCMI - Job level operations (host system jobs)
--

xcmSysAdminXCMIJobOperations OBJECT IDENTIFIER
--  STATUS      current
--  DESCRIPTION
--      "XCMI - Job level operations (host system jobs)"
--  REFERENCE
--      "Section 4 'Printing Utilities' in POSIX IEEE 1387.4."
    ::= { xcmSysAdminOperationTypes 2400 }

xcmSysAdminJobManage OBJECT IDENTIFIER
--  SYNTAX      xcmSysAdminJobManage (...)
--
--  For future extensions
--  STATUS      current
--  DESCRIPTION
--      "XCMI - Manage a host system job."
--  REFERENCE
--      "Section 4 'Printing Utilities' in POSIX IEEE 1387.4."
    ::= { xcmSysAdminOperationTypes 2401 }

--
--  POSIX - Document level operations (host system documents)
--

xcmSysAdminDocOperations OBJECT IDENTIFIER
--  STATUS      current
--  DESCRIPTION
--      "POSIX - Document level operations"
--  REFERENCE
--      "Section 4 'Printing Utilities' in POSIX IEEE 1387.4."
    ::= { xcmSysAdminOperationTypes 1500 }

xcmSysAdminDocDelete OBJECT IDENTIFIER
--  SYNTAX      xcmSysAdminDocDelete (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  From 'xcmJobGenBasicTable' in the XCMI Job Monitoring MIB
--  xcmJobIdentifierOnSystem    OCTET STRING                 - choice
--                              <OR>
--  From 'xcmJobGenBasicTable' in the XCMI Job Monitoring MIB
--  xcmJobClientId              XcmGlobalUniqueID            - choice
--
--  INPUT Document Arguments:
--  From 'xcmDocGenBasicTable' in the XCMI Job Monitoring MIB
--  xcmDocSequenceNumber        Ordinal32                    - mandatory
--
--  OUTPUT Responses:
--  [See OUTPUT Responses from 'xcmSysAdminDocList']
--  STATUS      current
--  DESCRIPTION
--      "Delete a host system document."
--  REFERENCE
--      "Section 4.3 'pddelete' in POSIX IEEE 1387.4."
    ::= { xcmSysAdminOperationTypes 1502 }

xcmSysAdminDocList OBJECT IDENTIFIER
--  SYNTAX      xcmSysAdminDocList (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  From 'xcmJobGenBasicTable' in the XCMI Job Monitoring MIB
--  xcmJobIdentifierOnSystem    OCTET STRING                 - choice
--                              <OR>
--  From 'xcmJobGenBasicTable' in the XCMI Job Monitoring MIB
--  xcmJobClientId              XcmGlobalUniqueID            - choice
--
--  INPUT Document Arguments:
--  From 'xcmDocGenBasicTable' in the XCMI Job Monitoring MIB
--  xcmDocSequenceNumber        Ordinal32                    - mandatory
--
--  INPUT List Filters:
--  From ANY Document level table in the XCMI Job Monitoring MIB
--  either simple filters OR filter expressions
--
--  OUTPUT Responses:
--  [Argument of 'xcmSysAdminRequestedNone']
--  From 'xcmSysAdminRequestTable' in the XCMI System Admin MIB
--  xcmSysAdminRequestErrorStatus   XcmGenSNMPv2ErrorStatus  - mandatory
--  [Argument of 'xcmSysAdminRequestedBrief' - DEFAULT]
--  From 'xcmDocGenBasicTable' in the XCMI Job Monitoring MIB
--  xcmDocSequenceNumber        Ordinal32                    - mandatory
--  xcmDocName                  OCTET STRING                 - mandatory
--  xcmDocFormat                XcmPrtInterpreterLangFamily  - mandatory
--  xcmDocState                 XcmJMDocState                - mandatory
--  [Argument of 'xcmSysAdminRequestedVerbose', additions to 'Brief']
--  From 'xcmDocGenBasicTable' in the XCMI Job Monitoring MIB
--  xcmDocType                  XcmJMDocType                 - mandatory
--  xcmDocOctetCount            Cardinal32                   - mandatory
--  From 'xcmDocPrintExtTable' in the XCMI Job Monitoring MIB
--  xcmDocPrintSides            INTEGER(1..2)                - cond mand
--  xcmDocPrintCopyCount        Cardinal32                   - cond mand
--  [Argument of 'xcmSysAdminRequestedAll']
--                              <OR>
--  [Argument of 'xcmSysAdminRequestedAttributes']
--  From ANY Document level table in the XCMI Job Monitoring MIB
--  xcm...                      [syntax]                     - cond mand
--  STATUS      current
--  DESCRIPTION
--      "List attributes of a host system document."
--  REFERENCE
--      "Section 4.7 'pdls' in POSIX IEEE 1387.4."
    ::= { xcmSysAdminOperationTypes 1503 }

xcmSysAdminDocSet OBJECT IDENTIFIER
--  SYNTAX      xcmSysAdminDocSet (...)
--
--  INPUT General Arguments:
--  From 'hrDeviceTable' in the IETF Host Resources MIB (RFC 2790)
--  hrDeviceIndex               Ordinal32                    - choice
--                              <OR>
--  From 'xcmHrDevInfoTable' in the XCMI Host Resources Ext MIB
--  xcmHrDevInfoName            XcmFixedLocaleDisplayString  - choice
--
--  From 'xcmJobGenBasicTable' in the XCMI Job Monitoring MIB
--  xcmJobIdentifierOnSystem    OCTET STRING                 - choice
--                              <OR>
--  From 'xcmJobGenBasicTable' in the XCMI Job Monitoring MIB
--  xcmJobClientId              XcmGlobalUniqueID            - choice
--
--  INPUT Document Arguments:
--  From 'xcmDocGenBasicTable' in the XCMI Job Monitoring MIB
--  xcmDocSequenceNumber        Ordinal32                    - mandatory
--
--  INPUT Set Arguments:
--  From ANY Document level table in the XCMI Job Monitoring MIB
--  either simple assignments OR assignment expressions
--
--  INPUT Set Filters:
--  From ANY Document level table in the XCMI Job Monitoring MIB
--  either simple filters OR filter expressions
--
--  OUTPUT Responses:
--  [See OUTPUT Responses from 'xcmSysAdminDocList']
--  STATUS      current
--  DESCRIPTION
--      "Set attributes of a host system document."
--  REFERENCE
--      "Section 4.16 'pdset' in POSIX IEEE 1387.4."
    ::= { xcmSysAdminOperationTypes 1504 }

xcmSysAdminDocModify OBJECT IDENTIFIER
--  SYNTAX      xcmSysAdminDocModify (...)
--
--  See:        xcmSysAdminDocSet (identical arguments)
--  STATUS      current
--  DESCRIPTION
--      "Modify a host system document."
--  REFERENCE
--      "Section 4.8 'pdmod' in POSIX IEEE 1387.4."
    ::= { xcmSysAdminOperationTypes 1512 }

xcmSysAdminDocRemove OBJECT IDENTIFIER
--  SYNTAX      xcmSysAdminDocRemove (...)
--
--  See:        xcmSysAdminDocDelete (identical arguments)
--  STATUS      current
--  DESCRIPTION
--      "Remove a host system document."
--  REFERENCE
--      "Section 4.15 'pdrm' in POSIX IEEE 1387.4."
    ::= { xcmSysAdminOperationTypes 1514 }

--
--  XCMI - Document level operations (host system documents)
--

xcmSysAdminXCMIDocOperations OBJECT IDENTIFIER
--  STATUS      current
--  DESCRIPTION
--      "XCMI - Document level operations"
--  REFERENCE
--      "Section 4 'Printing Utilities' in POSIX IEEE 1387.4."
    ::= { xcmSysAdminOperationTypes 2500 }

xcmSysAdminDocManage OBJECT IDENTIFIER
--  SYNTAX      xcmSysAdminDocManage (...)
--
--  For future extensions
--  STATUS      current
--  DESCRIPTION
--      "XCMI - Manage a host system document."
--  REFERENCE
--      "Section 4 'Printing Utilities' in POSIX IEEE 1387.4."
    ::= { xcmSysAdminOperationTypes 2501 }

--.ts 'REGISTRY of XCMI/POSIX Common Argument Types'
--          REGISTRY of XCMI/POSIX Common Argument Types
--          (used in 'xcmSysAdminArgumentTypeOID' object
--          in the companion XCMI System Admin MIB).

xcmSysAdminArgumentTypes OBJECT IDENTIFIER
--  STATUS      current
--  DESCRIPTION
--      "The root of all XCMI/POSIX 'common' argument types defined in
--      the System Admin TC."
--  REFERENCE
--      "Section 3.1.6 'Common Attributes' in POSIX IEEE 1387.4."
    ::= { xcmSysAdminTC 3 }

xcmSysAdminAttributeFilename OBJECT IDENTIFIER
--  STATUS      current
--  DESCRIPTION
--      "The XCMI/POSIX 'common' argument type used in the
--      'xcmSysAdminArgumentTypeOID' object to indicate that
--      'xcmSysAdminArgumentString' contains the name of a file,
--      which contains POSIX 1387.4 attribute/value string pairs to be
--      inserted at the current point in the request argument list.
--
--      Usage:  The service provider shall ALWAYS read the specified
--      file and INSERT the arguments (NOT overwrite other arguments)."
--  REFERENCE
--      "Section 3.1.6.1 'attributes' in POSIX IEEE 1387.4."
    ::= { xcmSysAdminArgumentTypes 1 }

xcmSysAdminObjectClass OBJECT IDENTIFIER
--  STATUS      current
--  DESCRIPTION
--      "The XCMI/POSIX 'common' argument type used in the
--      'xcmSysAdminArgumentTypeOID' object to indicate that
--      'xcmSysAdminArgumentOID' contains one of the following
--      standard DPA (ISO 10175) or XCMI extended object classes.
--
--      Note1:  The final arc of all of the standard DPA system object
--      classes defined below is equal to 10 plus the final arc (after
--      'id-oc') in the original ISO DPA system object classes.
--
--      Note2:  The object class 'xcmSaOcDevice' below is the XCMI
--      generalization of the DPA object class 'printer', and is useful
--      with the XCMI System Admin MIB 'xcmSysAdminDevice...' suite of
--      request operations."
--  REFERENCE
--      "Section 3.1.6.2 'class' in POSIX IEEE 1387.4.
--      Section 9.1.6.1 'Object-class' and Annex A, 'id-oc-...'
--              in DPA (ISO/IEC 10175-1 / Final Text, March 1996).
--      'hrDeviceType' in IETF HR MIB (RFC 2790)."
    ::= { xcmSysAdminArgumentTypes 2 }

--          Short tag for one-line object class definitions
xcmSaOc                         OBJECT IDENTIFIER
    ::= { xcmSysAdminObjectClass 1 }

--          Definitions for XCMI extended object classes
--          (extensions to standard DPA object classes)
xcmSaOcOther                    OBJECT IDENTIFIER ::= { xcmSaOc 1 }
xcmSaOcUnknown                  OBJECT IDENTIFIER ::= { xcmSaOc 2 }
xcmSaOcDevice                   OBJECT IDENTIFIER ::= { xcmSaOc 3 }

--          Definitions for DPA standard object classes
--          (final arc of DPA object class 'id-oc-...' + 10)
xcmSaOcGeneric                  OBJECT IDENTIFIER ::= { xcmSaOc 10 }
xcmSaOcJob                      OBJECT IDENTIFIER ::= { xcmSaOc 11 }
xcmSaOcPrinter                  OBJECT IDENTIFIER ::= { xcmSaOc 12 }
xcmSaOcServer                   OBJECT IDENTIFIER ::= { xcmSaOc 13 }
xcmSaOcMedium                   OBJECT IDENTIFIER ::= { xcmSaOc 14 }
xcmSaOcFont                     OBJECT IDENTIFIER ::= { xcmSaOc 15 }
xcmSaOcTransferMethod           OBJECT IDENTIFIER ::= { xcmSaOc 18 }
xcmSaOcDeliveryMethod           OBJECT IDENTIFIER ::= { xcmSaOc 19 }
xcmSaOcAuxiliarySheet           OBJECT IDENTIFIER ::= { xcmSaOc 20 }
xcmSaOcFinishing                OBJECT IDENTIFIER ::= { xcmSaOc 21 }
xcmSaOcOutput                   OBJECT IDENTIFIER ::= { xcmSaOc 22 }
xcmSaOcImposition               OBJECT IDENTIFIER ::= { xcmSaOc 23 }
xcmSaOcScheduler                OBJECT IDENTIFIER ::= { xcmSaOc 24 }
xcmSaOcDocument                 OBJECT IDENTIFIER ::= { xcmSaOc 25 }
xcmSaOcResource                 OBJECT IDENTIFIER ::= { xcmSaOc 26 }
xcmSaOcInitialValueJob          OBJECT IDENTIFIER ::= { xcmSaOc 27 }
xcmSaOcInitialValueDocument     OBJECT IDENTIFIER ::= { xcmSaOc 28 }
xcmSaOcResourceContext          OBJECT IDENTIFIER ::= { xcmSaOc 29 }
xcmSaOcAuxiliarySheetPackage    OBJECT IDENTIFIER ::= { xcmSaOc 30 }

xcmSysAdminObjectMessage OBJECT IDENTIFIER
--  STATUS      current
--  DESCRIPTION
--      "The XCMI/POSIX 'common' argument type used in the
--      'xcmSysAdminArgumentTypeOID' object to indicate that
--      'xcmSysAdminArgumentString' contains a message to attach to the
--      object specified in this request."
--  REFERENCE
--      "Section 3.1.6.4 'message' in POSIX IEEE 1387.4."
    ::= { xcmSysAdminArgumentTypes 3 }

xcmSysAdminRequestedAttributes OBJECT IDENTIFIER
--  STATUS      current
--  DESCRIPTION
--      "The XCMI/POSIX 'common' argument type used in the
--      'xcmSysAdminArgumentTypeOID' object to indicate that
--      'xcmSysAdminArgumentOID' contains:
--
--      1)  'xcmSysAdminRequestedAll',                  - unordered list
--      2)  'xcmSysAdminRequestedBrief',                - ordered list
--      3)  'xcmSysAdminRequestedNone',                 - no output list
--      4)  'xcmSysAdminRequestedVerbose',              - ordered list
--      5)  Any valid attribute for the object of this operation."
--  REFERENCE
--      "Section 3.1.6.5 'requested-attributes' in IEEE 1387.4."
    ::= { xcmSysAdminArgumentTypes 4 }

xcmSysAdminRequestedAll OBJECT IDENTIFIER
--  STATUS      current
--  DESCRIPTION
--      "The service provider shall return the standard complete
--      set of object attributes in its response to this system admin
--      request operation (unordered list, implementation defined)."
    ::= { xcmSysAdminRequestedAttributes 1 }

xcmSysAdminRequestedBrief OBJECT IDENTIFIER
--  STATUS      current
--  DESCRIPTION
--      "The service provider shall return the standard brief (concise)
--      set of object attributes in its response to this system admin
--      request operation (ordered list, specified by XCMI/POSIX)."
    ::= { xcmSysAdminRequestedAttributes 2 }

xcmSysAdminRequestedNone OBJECT IDENTIFIER
--  STATUS      current
--  DESCRIPTION
--      "The service provider shall return NO members of the standard
--      set of object attributes in its response to this system admin
--      request operation (empty list)."
    ::= { xcmSysAdminRequestedAttributes 3 }

xcmSysAdminRequestedVerbose OBJECT IDENTIFIER
--  STATUS      current
--  DESCRIPTION
--      "The service provider shall return the standard verbose
--      set of object attributes in its response to this system admin
--      request operation (ordered list, specified by XCMI/POSIX)."
    ::= { xcmSysAdminRequestedAttributes 4 }

xcmSysAdminRequestedScope OBJECT IDENTIFIER
--  STATUS      current
--  DESCRIPTION
--      "The XCMI/POSIX 'common' argument type used in the
--      'xcmSysAdminArgumentTypeOID' object to indicate that
--      'xcmSysAdminArgumentInteger' contains the 'scope' (or 'level')
--      of desired response for the request operation, as follows:
--
--      1)  '0' - return attributes from the 'parent' object only/
--      2)  '1..n' - return attributes from the 'parent' object and ALSO
--          the 'contained' objects down to the specified 'level'."
--  REFERENCE
--      "Section 8.2.4.1 'List-object-attributes-argument'
--              in DPA (ISO/IEC 10175-1 / Final Text, March 1996)."
    ::= { xcmSysAdminArgumentTypes 5 }

--.ts 'REGISTRY of XCMI System Admin Parameter Types'
--          REGISTRY of XCMI System Admin Parameter Types
--          (used in 'xcmSysAdmin[Argument|Filter]TypeOID' objects
--          in the companion XCMI System Admin MIB).

xcmSysAdminParameterTypes OBJECT IDENTIFIER
--  STATUS      current
--  DESCRIPTION
--      "The root of all additional 'special' parameter types defined in
--      the System Admin TC."
    ::= { xcmSysAdminTC 4 }

xcmSysAdminParameterConstant OBJECT IDENTIFIER
--  STATUS      current
--  DESCRIPTION
--      "The 'special' parameter type used in the
--      'xcmSysAdmin[Argument|Filter]TypeOID' objects to indicate
--      that 'xcmSysAdmin[Argument|Filter][Syntax|Integer|String|OID]'
--      contain a 'constant' and NOT a named 'parameter'
--      specified in 'xcmSysAdmin[Argument|Filter]TypeOID'.
--
--      Usage:  For use in 'expressions' composed of multiple entries in
--      the 'xcmSysAdminArgumentTable' or the 'xcmSysAdminFilterTable'."
    ::= { xcmSysAdminParameterTypes 1 }

xcmSysAdminParameterOperation OBJECT IDENTIFIER
--  STATUS      current
--  DESCRIPTION
--      "The 'special' parameter type used in the
--      'xcmSysAdmin[Argument|Filter]TypeOID' objects to indicate
--      that 'xcmSysAdmin[Argument|Filter][Syntax|Integer|String|OID]'
--      are 'empty' and that
--      'xcmSysAdmin[Argument|Filter]Operation' contains an 'operation'.
--
--      Usage:  For use in 'expressions' composed of multiple entries in
--      the 'xcmSysAdminArgumentTable' or the 'xcmSysAdminFilterTable'."
    ::= { xcmSysAdminParameterTypes 2 }

--
--          The System Admin TC
--
--          Textual Conventions

--.ts 'XcmSysAdminGroupSupport'
XcmSysAdminGroupSupport ::= 
--  STATUS      current
--  DESCRIPTION
--      "The terse conformance statement of ALL mandatory, conditionally
--      mandatory, and optional System Admin MIB object groups which are
--      supported by this management agent implementation (ie, version)
--      on this host system, specified in a bit-mask.
--
--      The current set of values (which may be extended in the future)
--      is given below:
--
--            1 : sysAdminGeneralGroup        -  Mandatory
--            2 : sysAdminEventGroup          -  Conditionally Mandatory
--            4 : sysAdminRequestGroup        -  Mandatory
--            8 : sysAdminArgumentGroup       -  Mandatory
--           16 : sysAdminFilterGroup         -  Conditionally Mandatory
--           32 : sysAdminResponseGroup       -  Mandatory
--
--      Usage:  Conforming management agents shall ALWAYS accurately
--      report their support for System Admin MIB object groups."
    INTEGER (0..2147483647)  -- biggest int = 2**31-1

--.ts 'XcmSysAdminRequestData'
XcmSysAdminRequestData ::= 
--  STATUS      current
--  DESCRIPTION
--      "The system admin request data (if any) associated with
--      this conceptual row in the 'xcmSysAdminRequestTable'."
--  REFERENCE
--      "See:   Security Config, Account, and User groups in
--              XCMI Security MIB.
--      See:    Section 6.6 'Security in DPA' (pages 38 to 39) of
--              DPA (ISO/IEC 10175-1 / Final Text, March 1996)."
    OCTET STRING (SIZE (0..255))

--.ts 'XcmSysAdminRequestErrorString'
XcmSysAdminRequestErrorString ::= 
--  STATUS      current
--  DESCRIPTION
--      "The system admin request error string associated with
--      this conceptual row in the 'xcmSysAdminRequestTable'."
--  REFERENCE
--      "See:   'xcmSysAdminRequestError[Status|Argument|Filter]'."
    OCTET STRING (SIZE (0..255))

--.ts 'XcmSysAdminParameterOperation'
XcmSysAdminParameterOperation ::= 
--  STATUS      current
--  DESCRIPTION
--      "A system admin parameter operation,
--      used by system administrators and end users to specify
--      the correct operation for this system admin parameter.
--
--      Usage:  Assignments (for writes of parameters) shall ALWAYS be
--      performed with the 'assign...' and 'modify...' operators, and
--      be of the '<parameter> <assignOperator> <expression>' form.
--
--      Usage:  Expressions (for writes and filters) shall always be
--      be formed from the 'numeric...', 'logical...', 'ordering...',
--      'string...' , and 'punctuation...' operators.  Expressions shall
--      ALWAYS be specified in 'natural language' order, eg,
--      '(a + b) / (c - 1)'.
--
--      Usage:  Precedence shall ALWAYS be fully specified by the use of
--      parentheses (ie, conforming implementations need NOT support any
--      precedence evaluation for operators)."
--  REFERENCE
--      "See:   Section 6.4.5 'Filters' (pages 30 to 32) of
--              DPA (ISO/IEC 10175-1 / Final Text, March 1996).
--      See:    Section 5.6 'Filters' (pages 229 to 233) of
--              POSIX Sys Admin (IEEE 1387.4 / Draft 8, October 1994)."
    INTEGER  -- left brace delay
--      none(0),                        -  zero enums illegal in SMIv1
        {
        other(1),                       -- Other operation
        unknown(2),                     -- Unknown operation
        --  Assignment operations (for 'sets' of parameters)
        assign(10),                     -- '='   Becomes
        assignAdd(11),                  -- '+='
        assignSubtract(12),             -- '-='
        assignMultiply(13),             -- '*='
        assignDivide(14),               -- '/='
        assignModulus(15),              -- '%='
        assignLeftShift(16),            -- '<<'
        assignRightShift(17),           -- '>>'
        assignAND(21),                  -- '&=' Bitwise AND
        assignOR(22),                   -- '|=' Bitwise OR
        assignXOR(23),                  -- '^=' Bitwise XOR
        assignNOT(24),                  -- '~=' Bitwise Complement
        --  Modify operations ('xcmSysAdmin[Job|Doc]Modify' requests)
        modifyReplace(31),              -- Replace with new value(s)
        modifyAddValues(32),            -- Add new value(s)
        modifyRemoveValues(33),         -- Remove old value(s)
        modifySetToDefault(34),         -- Set to default value(s)
        --  Numeric operations (for expressions, see also Assignment)
        numericAdd(41),                 -- '+'
        numericSubtract(42),            -- '-'
        numericMultiply(43),            -- '*'
        numericDivide(44),              -- '/'
        numericModulus(45),             -- '%'
        numericExponent(46),            -- '**'
        numericAND(51),                 -- '&'  Bitwise AND
        numericOR(52),                  -- '|'  Bitwise OR
        numericXOR(53),                 -- '^'  Bitwise XOR
        numericNOT(54),                 -- '~'  Bitwise Complement
        --  Logical operations (for expressions)
        logicalAND(61),                 -- '&&' Logical AND
        logicalOR(62),                  -- '||' Logical Inclusive OR
        logicalXOR(63),                 -- '^^' Logical Exclusive OR
        logicalNOT(64),                 -- '!'  Logical NOT
        logicalPresent(65),             -- '*'  Logical Present
        logicalSelect(66),              --      Logical Select
        --  Ordering operations (for integers, strings, and OIDs)
        orderingEQ(71),                 -- '==' Equal
        orderingNE(72),                 -- '!=' Not equal
        orderingLT(73),                 -- '<'  Less than
        orderingGT(74),                 -- '>'  Greater than
        orderingLE(75),                 -- '<=' Less than or equal
        orderingGE(76),                 -- '>=' Greater than or equal
        --  Substring operations (for strings only)
        stringMatchExact(81),           -- Exact characters and length
        stringMatchCaseInsensitive(82), -- Ignore case
        stringMatchSameLetter(83),      -- Ignore accents, case, etc
        stringMatchApproximate(84),     -- Implementation defined
        stringMatchInitial(85),         -- '=*'  Initial substring
        stringMatchAny(86),             -- '*=*' Any substring
        stringMatchFinal(87),           -- '*='  Final substring
        --  Punctuation operations (for expressions)
        punctuationLeftParenthesis(91), -- '('
        punctuationRightParenthesis(92),-- ')'
        punctuationLeftBrace(93),       -- '['
        punctuationRightBrace(94),      -- ']'
        punctuationLeftBracket(95),     -- '{'
        punctuationRightBracket(96),    -- '}'
        punctuationPeriod(97),          -- '.'
        punctuationComma(98),           -- ','
        punctuationQuery(99),           -- '?'
        punctuationColon(100),          -- ':'
        punctuationSemiColon(101),      -- '/'
        punctuationSingleQuote(102),    -- '\''
        punctuationDoubleQuote(103)     -- '\"'
    }

--
--          The System Admin TC Dummy Group (DO NOT USE)
--
--          DO NOT USE - Present to suppress compiler warnings ONLY!
--
--          Note:  The following objects have 'odd' use of case in their
--          names (ie, 'xCm...'), in order to make obvious their related
--          textual conventions

xCmSysAdminDummy    OBJECT IDENTIFIER ::= { xcmSysAdminTC 999 }

xCmSysAdminGroupSupport OBJECT-TYPE
    SYNTAX      XcmSysAdminGroupSupport
    ACCESS      read-only
    STATUS      mandatory
    DESCRIPTION "Dummy - DO NOT USE"
    ::= { xCmSysAdminDummy 1 }

xCmSysAdminRequestData OBJECT-TYPE
    SYNTAX      XcmSysAdminRequestData
    ACCESS      read-only
    STATUS      mandatory
    DESCRIPTION "Dummy - DO NOT USE"
    ::= { xCmSysAdminDummy 2 }

xCmSysAdminRequestErrorString OBJECT-TYPE
    SYNTAX      XcmSysAdminRequestErrorString
    ACCESS      read-only
    STATUS      mandatory
    DESCRIPTION "Dummy - DO NOT USE"
    ::= { xCmSysAdminDummy 3 }

xCmSysAdminParameterOperation OBJECT-TYPE
    SYNTAX      XcmSysAdminParameterOperation
    ACCESS      read-only
    STATUS      mandatory
    DESCRIPTION "Dummy - DO NOT USE"
    ::= { xCmSysAdminDummy 4 }

END
