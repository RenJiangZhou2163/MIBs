Finisher-MIB DEFINITIONS ::= BEGIN
--  Module: Compilable IETF Finisher MIB - XCMI Version 5.01
--  Editor: Ira McDonald
--  File:   finisher.mv1 (SMIv1 version)
--  Date:   28 November 2001

--
--  Change Log for this corrected compilable version
--
--  - Changed SYNTAX of 'finDeviceAssociatedMediaPaths' and
--    'finDeviceAssociatedOutputs' (both bit-masks of indices)
--    to 'OCTET STRING (SIZE (0..255))' from 'OCTET STRING'
--    (to correct compiler warnings)
--  - Changed LAST-UPDATED and REVISIONS clauses in MODULE-COMPLIANCE
--    macro to use 2-digit years instead of 4-digit years
--    (for compatibility with many compilers)
--  - Added dummy objects for all textual conventions
--    (to correct compiler warnings)

IMPORTS
--  MODULE-IDENTITY, OBJECT-TYPE, Integer32,
--  experimental                                    FROM SNMPv2-SMI
--  TEXTUAL-CONVENTION                               FROM SNMPv2-TC
--  MODULE-COMPLIANCE, OBJECT-GROUP                FROM SNMPv2-CONF
--  hrDeviceIndex                           FROM HOST-RESOURCES-MIB
    hrDeviceIndex
        FROM    HOST-RESOURCES-MIB
    PrtMarkerSuppliesTypeTC, PrtSubUnitStatusTC,
    LocalizedDescriptionStringTC, PrtInputTypeTC,
    PrtMarkerSuppliesSupplyUnitTC, PrtMediaUnitTC,
    PrtCapacityUnitTC, PrtMarkerSuppliesClassTC,
    PresentOnOff, prtMIBConformance               
       FROM     Printer-MIB
    
    printmib,
    PrtMarkerSuppliesTypeTC,
    PrtSubUnitStatusTC,
    LocalizedDescriptionStringTC,
    PrtInputTypeTC,
    PrtMarkerSuppliesSupplyUnitTC,
    PrtMediaUnitTC,
    PrtCapacityUnitTC,
    PrtMarkerSuppliesClassTC,
    PresentOnOff,
    prtMIBConformance
        FROM    Printer-MIB
    experimental
        FROM    RFC1155-SMI
    OBJECT-TYPE
        FROM    RFC-1212
    ;

finisherMIB OBJECT IDENTIFIER
--  LAST-UPDATED "200106290000Z" - out-of-date to file date
--  LAST-UPDATED "0110010000Z" -  1 October 2001
--  ORGANIZATION "IETF Printer MIB Working Group"
--  CONTACT-INFO
--      "Ron Bergman
--
--
--       Dataproducts Corp.
--       1757 Tapo Canyon Road
--       Simi Valley, CA 91063-3394
--       rbergma@dpc.com
--
--      Send comments to the printmib WG using the Finisher MIB
--      Project (FIN) Mailing List:  fin@pwg.org
--
--      For further information, access the PWG web page under 'FIN':
--            http://www.pwg.org/
--
--      Implementers of this specification are encouraged to join the
--      fin mailing list in order to participate in discussions on any
--      clarifications needed and registration proposals being reviewed
--      in order to achieve consensus."
--  DESCRIPTION
--      "The MIB module for management of printer finisher units.
--       The Finisher MIB is an extension of the Printer MIB."
--  REVISION "200106290000Z" - out-of-date to file date
--  REVISION "0110010000Z" -  1 October 2001
--  DESCRIPTION
--      "The original version of this MIB."
    ::= { experimental 115 }

-- Textual conventions for this MIB module

FinDeviceTypeTC ::= 
-- This is a type 2 enumeration.
--  STATUS       current
--  DESCRIPTION
--    "The defined finishing device subunit process
--     enumerations."
    INTEGER  -- left brace delay
        {
         other(1),
         unknown(2),
         stitcher(3),
         folder(4),
         binder(5),
         trimmer(6),
         dieCutter(7),
         puncher(8),
         perforater(9),
         slitter(10),
         separationCutter(11),
         imprinter(12),
         wrapper(13),
         bander(14),
         makeEnvelope(15),
         stacker(16),
         sheetRotator(17),
         inserter(18)


        }

FinAttributeTypeTC ::= 
-- This is a type 3 enumeration.
--  STATUS     current
--  DESCRIPTION
--      "This textual convention defines the set of enums for use in
--       the finDeviceAttributeTable.  See section 5.7 for the complete
--       specification of each attribute."
    INTEGER  -- left brace delay
        {
         other(1),
         deviceName(3),
         deviceVendorName(4),
         deviceModel(5),
         deviceVersion(6),
         deviceSerialNumber(7),
         maximumSheets(8),
         finProcessOffsetUnits(9),
         finReferenceEdge(10),
         finAxisOffset(11),
         finJogEdge(12),
         finHeadLocation(13),
         finOperationRestrictions(14),
         finNumberOfPositions(15),
         namedConfiguration(16),
         finMediaTypeRestriction(17),
         finPrinterInputTraySupported(18),
         finPreviousFinishingOperation(19),
         finNextFinishingOperation(20),
         stitchingType(30),
         stitchingDirection(31),
         foldingType(40),
         bindingType(50),
         punchHoleType(80),
         punchHoleSizeLongDim(81),
         punchHoleSizeShortDim(82),
         punchPattern(83),
         slittingType(100),
         wrappingType(130),
         stackOutputType(160),
         stackOffset(161),
         stackRotation(162)
        }

FinEdgeTC ::= 
-- This is a type 2 enumeration.
--  STATUS       current
--  DESCRIPTION
--    "Specifies an edge for a Finishing Process."
    INTEGER  -- left brace delay
        {
         topEdge(3),


         bottomEdge(4),
         leftEdge(5),
         rightEdge(6)
        }

FinStitchingTypeTC ::= 
-- This is a type 2 enumeration.
--  STATUS       current
--  DESCRIPTION
--    "The defined stitching type enumerations.  For the edgeStitch and
--     stapleDual enums, the finReferenceEdge attribute is recommended
--     to define the edge to which the operation applies."
    INTEGER  -- left brace delay
        {
         other(1),         -- More information in other attributes
         unknown(2),
         stapleTopLeft(4),
         stapleBottomLeft(5),
         stapleTopRight(6),
         stapleBottomRight(7),
         saddleStitch(8),
         edgeStitch(9),
         stapleDual(10)
        }

StitchingDirTypeTC ::= 
-- This is a type 2 enumeration.
--  STATUS       current
--  DESCRIPTION
--    "Defines the direction, relative to the top sheet in the output
--     subunit, that the stitching operation was performed.  For a
--     topDown(3) process, the staple will be clinched on the bottom
--     of the stack.  This parameter can be used to determine what
--     order the pages of a booklet are to be printed such that the
--     staple clinch will be on the inside of the resulting booklet."
    INTEGER  -- left brace delay
        {
         unknown(2),
         topDown(3),
         bottomUp(4)
        }

StitchingAngleTypeTC ::= 
-- This is a type 2 enumeration.
--  STATUS       current
--  DESCRIPTION
--    "This enumeration provides a description of the angular
--     orientation of each stitch in a single or multiple stitching
--     operation, relative to the 'X' axis.  As with all finishing
--     operations, the 'X' axis is always relative to the portrait
--     orientation of the document regardless of the orientation
--     of the printed image.  This enum is primarily applicable to
--     corner stitching operations."
--
--
    INTEGER  -- left brace delay
        {
         unknown(2),
         horizontal(3),
         vertical(4),
         slanted(5)
        }

FinFoldingTypeTC ::= 
--This is a type 2 enumeration.
-- STATUS       current
-- DESCRIPTION
--   "The defined folding device process enumerations."
    INTEGER  -- left brace delay
        {
         other(1),        -- More information in other attributes
         unknown(2),
         zFold(3),
         halfFold(4),
         letterFold(5)
        }

FinBindingTypeTC ::= 
-- This is a type 2 enumeration.
--  STATUS       current
--  DESCRIPTION
--    "The defined binding type enumerations."
    INTEGER  -- left brace delay
        {
         other(1),          -- More information in other attributes
         unknown(2),
         tape(4),
         plastic(5),
         velo(6),
         perfect(7),
         spiral(8),
         adhesive(9),
         comb(10),
         padding(11)
        }

FinPunchHoleTypeTC ::= 
--This is a type 2 enumeration.
-- STATUS       current
-- DESCRIPTION
--   "The defined hole type punch process enumerations."
    INTEGER  -- left brace delay
        {
         other(1),        -- More information in other attributes
         unknown(2),
         round(3),
         oblong(4),
         square(5),
         rectangular(6),
         star(7)


        }

FinPunchPatternTC ::= 
--This is a type 2 enumeration.
-- STATUS       current
-- DESCRIPTION
--   "The defined hole pattern punch process enumerations."
    INTEGER  -- left brace delay
        {
         other(1),           --Pattern to be defined in other attributes
         unknown(2),
         twoHoleUSTop(4),    --Letter/legal, 8.5 inch edge
         threeHoleUS(5),     --Letter/ledger, 11 inch edge
         twoHoleDIN(6),      --A4/A3, 297 mm edge
         fourHoleDIN(7),     --A4/A3, 297 mm edge
         twentyTwoHoleUS(8), --Letter/ledger, 11 inch edge
         nineteenHoleUS(9),  --Letter/ledger, 11 inch edge
         twoHoleMetric(10),  --B5/B4, 257 mm edge
         swedish4Hole(11),   --A4/A3, 297 mm edge
         twoHoleUSSide(12),  --Letter/ledger, 11 inch edge
         fiveHoleUS(13),     --Letter/ledger, 11 inch edge
         sevenHoleUS(14),    --Letter/ledger, 11 inch edge
         mixed7H4S(15),      --A4/A3, 297 mm edge
         norweg6Hole(16),    --A4/A3, 297 mm edge
         metric26Hole(17),   --B5/B4, 257 mm edge
         metric30Hole(18)    --A4/A3, 297 mm edge
        }

FinSlittingTypeTC ::= 
-- This is a type 2 enumeration.
--  STATUS       current
--  DESCRIPTION
--    "The defined slitting type enumerations."
    INTEGER  -- left brace delay
        {
         other(1),         -- More information in other attributes
         unknown(2),
         slitAndSeparate(4),
         slitAndMerge(5)
        }

FinWrappingTypeTC ::= 
--This is a type 2 enumeration.
-- STATUS       current
-- DESCRIPTION
--   "The defined wrapping device process enumerations."
    INTEGER  -- left brace delay
        {
         other(1),        -- More information in other attributes
         unknown(2),
         shrinkWrap(4),
         paperWrap(5)
        }


FinStackOutputTypeTC ::= 
--This is a type 2 enumeration.
-- STATUS       current
-- DESCRIPTION
--   "The defined stack output type enumerations."
    INTEGER  -- left brace delay
        {
         other(1),        -- More information in other attributes
         unknown(2),
         straight(4),     -- No offset, one on top of another
         offset(5),
         crissCross(6)    -- Rotated
        }

-- Finisher Device Group (Mandatory)
--
-- A printer may support zero or more finishing subunits.  A
-- finishing device subunit may be associated with one or more
-- output subunits and one or more media path subunits.

finDevice  OBJECT IDENTIFIER  ::=  { printmib 30 }

finDeviceTable OBJECT-TYPE
    SYNTAX      SEQUENCE OF FinDeviceEntry
    ACCESS      not-accessible
    STATUS      mandatory
    DESCRIPTION
      "This table defines the finishing device subunits,
       including information regarding possible configuration
       options and the status for each finisher device subunit."
    ::= { finDevice 1 }

finDeviceEntry OBJECT-TYPE
    SYNTAX      FinDeviceEntry
    ACCESS      not-accessible
    STATUS      mandatory
    DESCRIPTION
      "There is an entry in the finishing device table for each
       possible finisher process.  Each individual finisher process is
       implemented by a finishing device represented in this table."
    INDEX  { hrDeviceIndex, finDeviceIndex }
    ::= { finDeviceTable 1 }

FinDeviceEntry ::= SEQUENCE {
        finDeviceIndex                  INTEGER, 
        finDeviceType                   FinDeviceTypeTC, 
        finDevicePresentOnOff           PresentOnOff, 
        finDeviceCapacityUnit           PrtCapacityUnitTC, 
        finDeviceMaxCapacity            INTEGER, 
        finDeviceCurrentCapacity        INTEGER, 
        finDeviceAssociatedMediaPaths   OCTET STRING, 


        finDeviceAssociatedOutputs      OCTET STRING, 
        finDeviceStatus                 PrtSubUnitStatusTC, 
        finDeviceDescription            LocalizedDescriptionStringTC 
        }                               

finDeviceIndex OBJECT-TYPE
--  SYNTAX      Integer32 (1..65535)
    SYNTAX      INTEGER (1..65535)
    ACCESS      read-only
    STATUS      mandatory
    DESCRIPTION
      "A unique value used to identify a finisher process.
       Although these values may change due to a major
       reconfiguration of the printer system (e.g. the addition
       of new finishing processes), the values are normally
       expected to remain stable across successive power cycles."
    ::= { finDeviceEntry 1 }

finDeviceType OBJECT-TYPE
    SYNTAX      FinDeviceTypeTC
    ACCESS      read-only
    STATUS      mandatory
    DESCRIPTION
      "Defines the type of finishing process associated with this
       table row entry."
    ::= { finDeviceEntry 2 }

finDevicePresentOnOff OBJECT-TYPE
    SYNTAX      PresentOnOff
    ACCESS      read-write
    STATUS      mandatory
    DESCRIPTION
      "Indicates if this finishing device subunit is available
       and whether the device subunit is enabled."
--  DEFVAL      { notPresent }
    ::= { finDeviceEntry 3 }

finDeviceCapacityUnit OBJECT-TYPE
    SYNTAX      PrtCapacityUnitTC
    ACCESS      read-only
    STATUS      mandatory
    DESCRIPTION
      "The unit of measure for specifying the capacity of this
       finisher device subunit."
    ::= { finDeviceEntry 4 }

finDeviceMaxCapacity OBJECT-TYPE
--  SYNTAX      Integer32 (-2..2147483647)
    SYNTAX      INTEGER (-2..2147483647)
    ACCESS      read-write
    STATUS      mandatory
    DESCRIPTION
      "The maximum capacity of this finisher device subunit in


       finDeviceCapacityUnits.  If the device can reliably sense
       this value, the value is sensed by the finisher device
       and is read-only: otherwise the value may be written by a
       management or control console application.  The value (-1)
       means other and specifically indicates that the device
       places no restrictions on this parameter.  The value (-2)
       means unknown."
--  DEFVAL      { -2 }      -  unknown
    ::= { finDeviceEntry 5 }

finDeviceCurrentCapacity OBJECT-TYPE
--  SYNTAX      Integer32 (-2..2147483647)
    SYNTAX      INTEGER (-2..2147483647)
    ACCESS      read-write
    STATUS      mandatory
    DESCRIPTION
      "The current capacity of this finisher device subunit in
       finDeviceCapacityUnits.  If the device can reliably sense
       this value, the value is sensed by the finisher and is
       read-only: otherwise the value may be written by a
       management or control console application.  The value (-1)
       means other and specifically indicates that the device
       places no restrictions on this parameter.  The value (-2)
       means unknown."
--  DEFVAL      { -2 }      -  unknown
    ::= { finDeviceEntry 6 }

finDeviceAssociatedMediaPaths OBJECT-TYPE
--  SYNTAX      OCTET STRING
    SYNTAX      OCTET STRING (SIZE (0..255))
    ACCESS      read-only
    STATUS      mandatory
    DESCRIPTION
      "Indicates the media paths which can supply media for this
       finisher device.  The value of this object is a bit map in an
       octet string with each position representing the value of a
       prtMediaPathIndex.  For a media path that can be a source
       for this finisher device subunit, the bit position equal
       to one less than the value of prtMediaPathIndex will be set.
       The bits are numbered starting with the most significant bit of
       the first byte being bit 0, the least significant bit of the
       first byte being bit 7, the most significant of the second byte
       being bit 8, and so on."
    ::= { finDeviceEntry 7 }

finDeviceAssociatedOutputs OBJECT-TYPE
--  SYNTAX      OCTET STRING
    SYNTAX      OCTET STRING (SIZE (0..255))
    ACCESS      read-only
    STATUS      mandatory
    DESCRIPTION
      "Indicates the printer output subunits this finisher device
       subunit services.  The value of this object is a bit map in an
       octet string with each position representing the value of a


       prtOutputIndex.  For an output subunit that is serviced
       by this finisher device subunit, the bit position equal to
       to one less than the value of prtOutputIndex will be set.
       The bits are numbered starting with the most significant bit of
       the first byte being bit 0, the least significant bit of the
       first byte being bit 7, the most significant of the second byte
       being bit 8, and so on."
    ::= { finDeviceEntry 8 }

finDeviceStatus OBJECT-TYPE
    SYNTAX      PrtSubUnitStatusTC
    ACCESS      read-only
    STATUS      mandatory
    DESCRIPTION
      "Indicates the current status of this finisher device
       subunit."
--  DEFVAL      { 5 }      -  unknown
    ::= { finDeviceEntry 9 }

finDeviceDescription OBJECT-TYPE
    SYNTAX      LocalizedDescriptionStringTC
    ACCESS      read-only
    STATUS      mandatory
    DESCRIPTION
      "A free form text description of this device subunit in the
       localization specified by prtGeneralCurrentLocalization."
    ::= { finDeviceEntry 10 }

-- Finisher Supply Group (Mandatory)
--
-- A finisher device, but not all finisher devices, may have one or more
-- supplies associated with it.  For example a finisher may use both
-- binding tape and stitching wire supplies. A finisher may also have
-- more than one source for a given type of supply e.g. multiple supply
-- sources of ink for imprinters.

finSupply  OBJECT IDENTIFIER  ::=  { printmib 31 }

finSupplyTable OBJECT-TYPE
    SYNTAX      SEQUENCE OF FinSupplyEntry
    ACCESS      not-accessible
    STATUS      mandatory
    DESCRIPTION
      "Each unique source of supply is an entry in the finisher
       supply table. Each supply entry has its own
       characteristics associated with it such as colorant and
       current supply level."
    ::= { finSupply 1 }

finSupplyEntry OBJECT-TYPE


    SYNTAX      FinSupplyEntry
    ACCESS      not-accessible
    STATUS      mandatory
    DESCRIPTION
      "A list of finisher devices, with their associated
       supplies and supplies characteristics."
    INDEX  { hrDeviceIndex, finSupplyIndex }
    ::= { finSupplyTable 1 }

FinSupplyEntry ::= SEQUENCE {
        finSupplyIndex                  INTEGER, 
        finSupplyDeviceIndex            INTEGER, 
        finSupplyClass                  PrtMarkerSuppliesClassTC, 
        finSupplyType                   PrtMarkerSuppliesTypeTC, 
        finSupplyDescription            LocalizedDescriptionStringTC, 
        finSupplyUnit                   PrtMarkerSuppliesSupplyUnitTC, 
        finSupplyMaxCapacity            INTEGER, 
        finSupplyCurrentLevel           INTEGER, 
        finSupplyColorName              OCTET STRING 
        }                               

finSupplyIndex OBJECT-TYPE
--  SYNTAX      Integer32 (1..65535)
    SYNTAX      INTEGER (1..65535)
    ACCESS      read-only
    STATUS      mandatory
    DESCRIPTION
      "A unique value used by a finisher to identify this supply
       container/receptacle.  Although these values may change
       due to a major reconfiguration of the finisher (e.g. the
       addition of new supply sources to the finisher), values
       are normally expected to remain stable across successive
       power cycles."
    ::= { finSupplyEntry 1 }

finSupplyDeviceIndex OBJECT-TYPE
--  SYNTAX      Integer32 (0..65535)
    SYNTAX      INTEGER (0..65535)
    ACCESS      read-only
    STATUS      mandatory
    DESCRIPTION
      "The value of finDeviceIndex corresponding to the finishing
       device subunit with which this finisher supply is associated."
    ::= { finSupplyEntry 2 }

finSupplyClass OBJECT-TYPE
    SYNTAX      PrtMarkerSuppliesClassTC
    ACCESS      read-only
    STATUS      mandatory
    DESCRIPTION
      "This value indicates whether this supply entity
       represents a supply that is consumed or a container that
       is filled."


    ::= { finSupplyEntry 3 }

finSupplyType OBJECT-TYPE
    SYNTAX      PrtMarkerSuppliesTypeTC
    ACCESS      read-only
    STATUS      mandatory
    DESCRIPTION
      "The type of this supply."
    ::= { finSupplyEntry 4 }

finSupplyDescription OBJECT-TYPE
    SYNTAX      LocalizedDescriptionStringTC
    ACCESS      read-only
    STATUS      mandatory
    DESCRIPTION
      "The description of this supply/receptacle in text useful
       for operators and management applications and in the
       localization specified by prtGeneralCurrentLocalization."
    ::= { finSupplyEntry 5 }

finSupplyUnit OBJECT-TYPE
    SYNTAX      PrtMarkerSuppliesSupplyUnitTC
    ACCESS      read-only
    STATUS      mandatory
    DESCRIPTION
      "Unit of measure of this finisher supply container or
       receptacle."
    ::= { finSupplyEntry 6 }

finSupplyMaxCapacity OBJECT-TYPE
--  SYNTAX      Integer32 (-2..2147483647)
    SYNTAX      INTEGER (-2..2147483647)
    ACCESS      read-write
    STATUS      mandatory
    DESCRIPTION
      "The maximum capacity of this supply container/receptacle
       expressed in Supply Units.  If this supply container/
       receptacle can reliably sense this value, the value is
       sensed  and is read-only/ otherwise the value may be
       written by a control panel or management application.  The
       value (-1) means other and places no restrictions on this
       parameter.  The value (-2) means unknown."
--  DEFVAL      { -2 }      -  unknown
    ::= { finSupplyEntry 7 }

finSupplyCurrentLevel OBJECT-TYPE
--  SYNTAX      Integer32
    SYNTAX      INTEGER
    ACCESS      read-write
    STATUS      mandatory
    DESCRIPTION
      "The current level if this supply is a container/ the
       remaining space if this supply is a receptacle. If this


       supply container/receptacle can reliably sense this value,
       the value is sensed and is read-only/ otherwise the value
       may be written by a control panel or management
       application.  The value (-1) means other and places no
       restrictions on this parameter. The value (-2) means
       unknown.  A value of (-3) means that the printer knows there
       is some supply or remaining space."
--  DEFVAL      { -2 }      -  unknown
    ::= { finSupplyEntry 8 }

--             Capacity Attribute Relationships
--
--                 MEDIA INPUT MEASUREMENT
--
--     _______ |                   |
--      |      |                   |
--      |      |                   |                   |
--      |      |_ _ _ _ _ _ _ _ _ _| ________________  |direction
--      |      |                   |      |            v
-- MaxCapacity |                   |      |
--      |      | Sheets remaining  | CurrentLevel
--      |      |                   |      |
--      v      |                   |      v
--     _______ +___________________+ _______

finSupplyColorName OBJECT-TYPE
    SYNTAX      OCTET STRING (SIZE(0..63))
    ACCESS      read-only
    STATUS      mandatory
    DESCRIPTION
      "The name of the color of this colorant using standardized
       string names from ISO 10175 (DPA) and ISO 10180 (SPDL)
       which are: other, unknown, white, red, green, blue, cyan,
       magenta, yellow and black.  Implementors may add
       additional string values.  The naming conventions in ISO
       9070 are recommended in order to avoid potential name
       clashes."
    ::= { finSupplyEntry 9 }

-- Finisher Supply, Media Input Group (Conditionally Mandatory)
--
-- A finisher device may have one or more associated supply media
-- inputs.  Each entry in this table defines an input for a
-- supply media type such as inserts, covers, etc.
--
-- This group is mandatory only if the printer system contains a
-- finisher device that requires a media supply used exclusively by a
-- finishing process.  Examples are inserts or covers that are not


-- supplied by an input subunit that provides media to the marker.

finSupplyMediaInput  OBJECT IDENTIFIER  ::=  { printmib 32 }

finSupplyMediaInputTable OBJECT-TYPE
    SYNTAX      SEQUENCE OF FinSupplyMediaInputEntry
    ACCESS      not-accessible
    STATUS      mandatory
    DESCRIPTION
      "The input subunits associated with a finisher supply media
       are each represented by an entry in this table."
::= { finSupplyMediaInput 1 }

finSupplyMediaInputEntry OBJECT-TYPE
    SYNTAX      FinSupplyMediaInputEntry
    ACCESS      not-accessible
    STATUS      mandatory
    DESCRIPTION
      "A list of finisher supply media input subunit features and
       characteristics."
    INDEX  { hrDeviceIndex, finSupplyMediaInputIndex }
    ::= { finSupplyMediaInputTable 1 }

FinSupplyMediaInputEntry ::= SEQUENCE {
        finSupplyMediaInputIndex        INTEGER, 
        finSupplyMediaInputDeviceIndex  INTEGER, 
        finSupplyMediaInputSupplyIndex  INTEGER, 
        finSupplyMediaInputType         PrtInputTypeTC, 
        finSupplyMediaInputDimUnit      PrtMediaUnitTC, 
        finSupplyMediaInputMediaDimFeedDir INTEGER, 
        finSupplyMediaInputMediaDimXFeedDir INTEGER, 
        finSupplyMediaInputStatus       PrtSubUnitStatusTC, 
        finSupplyMediaInputMediaName    OCTET STRING, 
        finSupplyMediaInputName         OCTET STRING, 
        finSupplyMediaInputDescription  LocalizedDescriptionStringTC, 
        finSupplyMediaInputSecurity     PresentOnOff, 
        finSupplyMediaInputMediaWeight  INTEGER, 
        finSupplyMediaInputMediaThickness INTEGER, 
        finSupplyMediaInputMediaType    OCTET STRING 
        }                               

finSupplyMediaInputIndex OBJECT-TYPE
--  SYNTAX      Integer32 (1..65535)
    SYNTAX      INTEGER (1..65535)
    ACCESS      read-only
    STATUS      mandatory
    DESCRIPTION
      "A unique value used by a finisher to identify this supply
       media input subunit.  Although these values may change
       due to a major reconfiguration of the finisher (e.g. the
       addition of new supply media input sources to the
       finisher), values are normally expected to remain stable


       across successive power cycles."
    ::= { finSupplyMediaInputEntry 1 }

finSupplyMediaInputDeviceIndex OBJECT-TYPE
--  SYNTAX      Integer32 (0..65535)
    SYNTAX      INTEGER (0..65535)
    ACCESS      read-only
    STATUS      mandatory
    DESCRIPTION
      "The value of finDeviceIndex corresponding to the finishing
       device subunit with which this finisher media supply is
       associated."
    ::= { finSupplyMediaInputEntry 2 }

finSupplyMediaInputSupplyIndex OBJECT-TYPE
--  SYNTAX      Integer32 (0..65535)
    SYNTAX      INTEGER (0..65535)
    ACCESS      read-only
    STATUS      mandatory
    DESCRIPTION
      "The value of finSupplyIndex corresponding to the finishing
       supply subunit with which this finisher media supply is
       associated."
    ::= { finSupplyMediaInputEntry 3 }

finSupplyMediaInputType OBJECT-TYPE
    SYNTAX      PrtInputTypeTC
    ACCESS      read-only
    STATUS      mandatory
    DESCRIPTION
      "The type of technology (discriminated primarily according
       to the feeder mechanism type) employed by the input
       subunit."
    ::= { finSupplyMediaInputEntry 4 }

finSupplyMediaInputDimUnit OBJECT-TYPE
    SYNTAX      PrtMediaUnitTC
    ACCESS      read-only
    STATUS      mandatory
    DESCRIPTION
      "The unit of measure for specifying dimensional values for
       this input device."
    ::= { finSupplyMediaInputEntry 5 }

finSupplyMediaInputMediaDimFeedDir OBJECT-TYPE
--  SYNTAX      Integer32 (-2..2147483647)
    SYNTAX      INTEGER (-2..2147483647)
    ACCESS      read-write
    STATUS      mandatory
    DESCRIPTION
      "This object provides the value of the dimension in the
       feed direction of the media that is placed or will be
       placed in this input device.  Feed dimension measurements
       are taken parallel to the feed direction of the device and


       measured in finSupplyMediaInputDimUnits.  If this input
       device can reliably sense this value, the value is sensed
       and is read-only access. Otherwise the value is read-write
       access and may be written by management or control panel
       applications. The value (-1) means other and specifically
       indicates that this device places no restrictions on this
       parameter. The value (-2) indicates unknown. "
    ::= { finSupplyMediaInputEntry 6 }

finSupplyMediaInputMediaDimXFeedDir OBJECT-TYPE
--  SYNTAX      Integer32 (-2..2147483647)
    SYNTAX      INTEGER (-2..2147483647)
    ACCESS      read-write
    STATUS      mandatory
    DESCRIPTION
      "This object provides the value of the dimension across the
       feed direction of the media that is placed or will be
       placed in this input device.  The cross feed direction is
       ninety degrees relative to the feed direction on this
       device and measured in finSupplyMediaInputDimUnits.  If
       this input device can reliably sense this value, the value
       is sensed and is read-only access. Otherwise the value is
       read-write access and may be written by management or
       control panel applications. The value (-1) means other and
       specifically indicates that this device places no
       restrictions on this parameter. The value (-2) indicates
       unknown. "
    ::= { finSupplyMediaInputEntry 7 }

finSupplyMediaInputStatus OBJECT-TYPE
    SYNTAX      PrtSubUnitStatusTC
    ACCESS      read-only
    STATUS      mandatory
    DESCRIPTION
      "This value indicates the current status of this input
       device."
--  DEFVAL      { 5 }      -  unknown
    ::= { finSupplyMediaInputEntry 8 }

finSupplyMediaInputMediaName OBJECT-TYPE
    SYNTAX      OCTET STRING (SIZE(0..63))
    ACCESS      read-write
    STATUS      mandatory
    DESCRIPTION
      "The name of the current media contained in this input
       device. Examples are Engineering Manual Cover, Section A Tab
       Divider or any ISO standard names."
    ::= { finSupplyMediaInputEntry 9 }

finSupplyMediaInputName OBJECT-TYPE
    SYNTAX      OCTET STRING (SIZE(0..63))
    ACCESS      read-write


    STATUS      mandatory
    DESCRIPTION
      "The name assigned to this input subunit."
    ::= { finSupplyMediaInputEntry 10 }

finSupplyMediaInputDescription OBJECT-TYPE
    SYNTAX      LocalizedDescriptionStringTC
    ACCESS      read-only
    STATUS      mandatory
    DESCRIPTION
      "A free form text description of this input subunit in the
       localization specified by prtGeneralCurrentLocalization."
    ::= { finSupplyMediaInputEntry 11 }

finSupplyMediaInputSecurity OBJECT-TYPE
    SYNTAX      PresentOnOff
    ACCESS      read-write
    STATUS      mandatory
    DESCRIPTION
      "Indicates if this subunit has some security associated
       with it."
    ::= { finSupplyMediaInputEntry 12 }

finSupplyMediaInputMediaWeight OBJECT-TYPE
--  SYNTAX      Integer32
    SYNTAX      INTEGER
    ACCESS      read-write
    STATUS      mandatory
    DESCRIPTION
      "The weight of the media associated with this Input device
       in grams per meter squared.  The value (-1) means other
       and specifically indicates that the device places no
       restriction on this parameter.  The value (-2) means
       unknown.  This object can be used to calculate the weight
       of individual pages processed by the document finisher.
       This value, when multiplied by the number of pages in a
       finished set, can be used to calculate the weight of a set
       before it is inserted into a mailing envelope."
    ::= { finSupplyMediaInputEntry 13 }

finSupplyMediaInputMediaThickness OBJECT-TYPE
--  SYNTAX      Integer32 (-2..2147483647)
    SYNTAX      INTEGER (-2..2147483647)
    ACCESS      read-write
    STATUS      mandatory
    DESCRIPTION
      "This object identifies the thickness of the input media
       processed by this document input subunit measured in
       micrometers.  This value may be used by devices (or
       operators) to set up proper machine tolerances for the
       feeder operation.  The value (-2) indicates that the media
       thickness is unknown or not used in the setup for this
       input subunit."


    ::= { finSupplyMediaInputEntry 14 }

finSupplyMediaInputMediaType OBJECT-TYPE
    SYNTAX      OCTET STRING (SIZE(0..63))
    ACCESS      read-write
    STATUS      mandatory
    DESCRIPTION
      "The name of the type of medium associated with this input
       subunit.  Valid values are standardized strings from ISO 10175
       (DPA) and ISO 10180 (SPDL) which are: stationary, transparency,
       envelope, envelope-plain, envelope window, continuous-long,
       continuous-short, tab-stock, labels, multi-layer."
    ::= { finSupplyMediaInputEntry 15 }

-- Finisher Device Attribute Group (Mandatory)
--
-- A finisher device subunit may have one or more parameters that
-- cannot be specified by any other objects in the MIB.  The
-- Device Attribute group facilitates the definition of these
-- parameters.  The objects which define the attributes are
-- read-write, to allow both Set and Get operations.
--
-- At least one table entry must exist for each finisher device defined
-- by the MIB.  If no other entry is possible for a finisher device, the
-- deviceName(3) attribute MUST be returned.

finDeviceAttribute  OBJECT IDENTIFIER  ::=  { printmib 33 }

finDeviceAttributeTable OBJECT-TYPE
    SYNTAX      SEQUENCE OF FinDeviceAttributeEntry
    ACCESS      not-accessible
    STATUS      mandatory
    DESCRIPTION
      "The attribute table defines special parameters that are
       applicable only to a minority of the finisher devices.
       An attribute table entry is used, rather than unique
       objects, to minimize the number of MIB objects and to
       allow for expansion without the addition of MIB objects.
       Each finisher device is represented by a separate row
       in the device subunit attribute table."
::= { finDeviceAttribute 1 }

finDeviceAttributeEntry OBJECT-TYPE
    SYNTAX      FinDeviceAttributeEntry
    ACCESS      not-accessible
    STATUS      mandatory
    DESCRIPTION
      "Each entry defines a finisher function parameter that
       cannot be represented by an object in the finisher
       device subunit table."


    INDEX  { hrDeviceIndex, finDeviceIndex,
             finDeviceAttributeTypeIndex,
             finDeviceAttributeInstanceIndex }
::= { finDeviceAttributeTable 1 }

FinDeviceAttributeEntry ::= SEQUENCE {
        finDeviceAttributeTypeIndex     FinAttributeTypeTC, 
        finDeviceAttributeInstanceIndex INTEGER, 
        finDeviceAttributeValueAsInteger INTEGER, 
        finDeviceAttributeValueAsOctets OCTET STRING 
        }                               

finDeviceAttributeTypeIndex OBJECT-TYPE
    SYNTAX      FinAttributeTypeTC
    ACCESS      read-only
    STATUS      mandatory
    DESCRIPTION
      "Defines the attribute type represented by this row."
    ::= { finDeviceAttributeEntry 1 }

finDeviceAttributeInstanceIndex OBJECT-TYPE
--  SYNTAX      Integer32 (1..65535)
    SYNTAX      INTEGER (1..65535)
    ACCESS      read-only
    STATUS      mandatory
    DESCRIPTION
      "An index that allows the discrimination of an attribute
       instance when the same attribute occurs multiple times for
       a specific instance of a finisher function.  The value of
       this index shall be 1 if only a single instance of the
       attribute occurs for the specific finisher function.
       Additional values shall be assigned in a contiguous manner."
    ::= { finDeviceAttributeEntry 2 }

finDeviceAttributeValueAsInteger OBJECT-TYPE
--  SYNTAX      Integer32 (-2..2147483647)
    SYNTAX      INTEGER (-2..2147483647)
    ACCESS      read-write
    STATUS      mandatory
    DESCRIPTION
      "Defines the integer value of the attribute.  The value of
       the attribute is represented as an integer if the
       finAttributeTypeTC description for the attribute has the
       tag 'INTEGER:'.

       Depending upon the attribute enum definition, this object
       may be either an integer, a counter, an index, or an enum.
       Attributes for which the concept of an integer value is
       not meaningful SHALL return a value of -1 for this
       attribute."
--  DEFVAL      { -2 }      -  unknown
    ::= { finDeviceAttributeEntry 3 }


finDeviceAttributeValueAsOctets OBJECT-TYPE
    SYNTAX      OCTET STRING (SIZE(0..63))
    ACCESS      read-write
    STATUS      mandatory
    DESCRIPTION
      "Contains the octet string value of the attribute.  The
       value of the attribute is represented as a string if the
       finAttributeTypeTC description for the attribute has the
       tag 'OCTETS:'.

       Depending upon the attribute enum definition, this object
       may be either a coded character set string (text) or a
       binary octet string.  Attributes for which the concept of
       an octet string value is not meaningful SHALL contain a
       zero length string."
--  DEFVAL      { ''H }      -  empty string
    ::= { finDeviceAttributeEntry 4 }

--          The Dummy Group (DO NOT USE)
--
--          DO NOT USE - Present to suppress compiler warnings ONLY!

finDummy          OBJECT IDENTIFIER  ::= { finisherMIB 999 }

finDummyDeviceType OBJECT-TYPE
    SYNTAX      FinDeviceTypeTC
    ACCESS      read-only
    STATUS      mandatory
    DESCRIPTION "Dummy - DO NOT USE"
    ::= { finDummy 1 }

finDummyAttributeType OBJECT-TYPE
    SYNTAX      FinAttributeTypeTC
    ACCESS      read-only
    STATUS      mandatory
    DESCRIPTION "Dummy - DO NOT USE"
    ::= { finDummy 2 }

finDummyEdge OBJECT-TYPE
    SYNTAX      FinEdgeTC
    ACCESS      read-only
    STATUS      mandatory
    DESCRIPTION "Dummy - DO NOT USE"
    ::= { finDummy 3 }

finDummyStitchingType OBJECT-TYPE
    SYNTAX      FinStitchingTypeTC
    ACCESS      read-only
    STATUS      mandatory
    DESCRIPTION "Dummy - DO NOT USE"
    ::= { finDummy 4 }

finDummyStitchingDirType OBJECT-TYPE
    SYNTAX      StitchingDirTypeTC
    ACCESS      read-only
    STATUS      mandatory
    DESCRIPTION "Dummy - DO NOT USE"
    ::= { finDummy 5 }

finDummyStitchingAngleType OBJECT-TYPE
    SYNTAX      StitchingAngleTypeTC
    ACCESS      read-only
    STATUS      mandatory
    DESCRIPTION "Dummy - DO NOT USE"
    ::= { finDummy 6 }

finDummyFoldingType OBJECT-TYPE
    SYNTAX      FinFoldingTypeTC
    ACCESS      read-only
    STATUS      mandatory
    DESCRIPTION "Dummy - DO NOT USE"
    ::= { finDummy 7 }

finDummyBindingType OBJECT-TYPE
    SYNTAX      FinBindingTypeTC
    ACCESS      read-only
    STATUS      mandatory
    DESCRIPTION "Dummy - DO NOT USE"
    ::= { finDummy 8 }

finDummyPunchHoleType OBJECT-TYPE
    SYNTAX      FinPunchHoleTypeTC
    ACCESS      read-only
    STATUS      mandatory
    DESCRIPTION "Dummy - DO NOT USE"
    ::= { finDummy 9 }

finDummyPunchPattern OBJECT-TYPE
    SYNTAX      FinPunchPatternTC
    ACCESS      read-only
    STATUS      mandatory
    DESCRIPTION "Dummy - DO NOT USE"
    ::= { finDummy 10 }

finDummySlittingType OBJECT-TYPE
    SYNTAX      FinSlittingTypeTC
    ACCESS      read-only
    STATUS      mandatory
    DESCRIPTION "Dummy - DO NOT USE"
    ::= { finDummy 11 }

finDummyWrappingType OBJECT-TYPE
    SYNTAX      FinWrappingTypeTC
    ACCESS      read-only
    STATUS      mandatory
    DESCRIPTION "Dummy - DO NOT USE"
    ::= { finDummy 12 }

finDummyStackOutputType OBJECT-TYPE
    SYNTAX      FinStackOutputTypeTC
    ACCESS      read-only
    STATUS      mandatory
    DESCRIPTION "Dummy - DO NOT USE"
    ::= { finDummy 13 }

-- Conformance Information

-- compliance statements

END
