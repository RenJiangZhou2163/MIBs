-- *****************************************************************
-- QTECH-FLASH-MIB.mib:  Qtech Flash MIB file
--
-- October 2009, linshuangfeng
--
-- Copyright (c) 2009 by Qtech Networks Co.,Ltd.
-- All rights reserved.
-- 
-- *****************************************************************
--

QTECH-FLASH-MIB DEFINITIONS ::= BEGIN

IMPORTS
        MODULE-IDENTITY,
        OBJECT-TYPE,
        Unsigned32
                FROM SNMPv2-SMI
        DisplayString
                FROM SNMPv2-TC
        MODULE-COMPLIANCE,
        OBJECT-GROUP
                FROM SNMPv2-CONF
        qtechMgmt
                FROM QTECH-SMI;

qtechFlashMIB MODULE-IDENTITY
        LAST-UPDATED "200910090000Z"
        ORGANIZATION "Qtech Networks Co.,Ltd."
        CONTACT-INFO
                " 
                Tel: 4008-111-000 

                E-mail: service@qtech.com.cn"
        DESCRIPTION
                "This module defines qtech system mibs."
        REVISION      "200910090000Z"
        DESCRIPTION
                "Initial version of this MIB module."
        ::= { qtechMgmt 47}


qtechFlashMIBObjects OBJECT IDENTIFIER ::= { qtechFlashMIB 1 }

    
rujieFlashDeviceTable OBJECT-TYPE
  SYNTAX      SEQUENCE OF RujieFlashDeviceEntry
  MAX-ACCESS  not-accessible
  STATUS      current
  DESCRIPTION
    "A table of flash device entries. Each of the
     objects provides the flash device information."
  ::= { qtechFlashMIBObjects 1 }

rujieFlashDeviceEntry OBJECT-TYPE
  SYNTAX      RujieFlashDeviceEntry
  MAX-ACCESS  not-accessible
  STATUS      current
  DESCRIPTION
    "An entry in the flash device table."
  INDEX { qtechFlashDeviceIndex }
  ::= { rujieFlashDeviceTable 1 }

RujieFlashDeviceEntry ::=
  SEQUENCE {
    qtechFlashDeviceIndex  Unsigned32,
    qtechFlashDeviceName   DisplayString,
    qtechFlashDeviceSize   Unsigned32,
    qtechFlashDeviceUsed   Unsigned32,
    qtechFlashDeviceFree   Unsigned32
  }
    
qtechFlashDeviceIndex OBJECT-TYPE
    SYNTAX        Unsigned32
    MAX-ACCESS    read-only
    STATUS        current
    DESCRIPTION
        "An index that uniquely represents a flash device."
    ::= { rujieFlashDeviceEntry 1 }

qtechFlashDeviceName OBJECT-TYPE
    SYNTAX        DisplayString
    MAX-ACCESS    read-only
    STATUS        current
    DESCRIPTION
        "A textual name assigned to the flash device."
    ::= { rujieFlashDeviceEntry 2 }
    
qtechFlashDeviceSize OBJECT-TYPE
    SYNTAX        Unsigned32
    MAX-ACCESS    read-only
    STATUS        current
    DESCRIPTION
        "This is the total size of the flash device."
    ::= { rujieFlashDeviceEntry 3 }

qtechFlashDeviceUsed OBJECT-TYPE
    SYNTAX        Unsigned32
    MAX-ACCESS    read-only
    STATUS        current
    DESCRIPTION
        "This is the used size of the flash device."
    ::= { rujieFlashDeviceEntry 4 }

qtechFlashDeviceFree OBJECT-TYPE
    SYNTAX        Unsigned32
    MAX-ACCESS    read-only
    STATUS        current
    DESCRIPTION
        "This is the free size of the flash device."
    ::= { rujieFlashDeviceEntry 5 }
        
qtechBootromDeviceTable OBJECT-TYPE
  SYNTAX      SEQUENCE OF QtechBootromDeviceEntry
  MAX-ACCESS  not-accessible
  STATUS      current
  DESCRIPTION
    "A table of bootrom device entries. Each of the
     objects provides the bootrom device information."
  ::= { qtechFlashMIBObjects 2 }

qtechBootromDeviceEntry OBJECT-TYPE
  SYNTAX      QtechBootromDeviceEntry
  MAX-ACCESS  not-accessible
  STATUS      current
  DESCRIPTION
    "An entry in the bootrom device table."
  INDEX { qtechBootromDeviceIndex }
  ::= { qtechBootromDeviceTable 1 }

QtechBootromDeviceEntry ::=
  SEQUENCE {
    qtechBootromDeviceIndex  Unsigned32,
    qtechBootromDeviceName   DisplayString,
    qtechBootromDeviceSize   Unsigned32
  }
    
qtechBootromDeviceIndex OBJECT-TYPE
    SYNTAX        Unsigned32
    MAX-ACCESS    read-only
    STATUS        current
    DESCRIPTION
        "An index that uniquely represents a bootrom device."
    ::= { qtechBootromDeviceEntry 1 }

qtechBootromDeviceName OBJECT-TYPE
    SYNTAX        DisplayString
    MAX-ACCESS    read-only
    STATUS        current
    DESCRIPTION
        "A textual name assigned to the bootrom device."
    ::= { qtechBootromDeviceEntry 2 }  
    
qtechBootromDeviceSize OBJECT-TYPE
    SYNTAX        Unsigned32
    MAX-ACCESS    read-only
    STATUS        current
    DESCRIPTION
        "This is the total size of the bootrom device."
    ::= { qtechBootromDeviceEntry 3 }
    
qtechFlashMIBConformance OBJECT IDENTIFIER ::= { qtechFlashMIB 2 }
qtechFlashMIBCompliances OBJECT IDENTIFIER ::= { qtechFlashMIBConformance 1 }
qtechFlashMIBGroups      OBJECT IDENTIFIER ::= { qtechFlashMIBConformance 2 }


-- compliance statements

qtechFlashMIBCompliance MODULE-COMPLIANCE
        STATUS  current
        DESCRIPTION
                "The compliance statement for entities which implement
                the Qtech Flash MIB"
        MODULE  -- this module
                MANDATORY-GROUPS { qtechFlashMIBGroup
                 }
        ::= { qtechFlashMIBCompliances 1 }
                
-- units of conformance

qtechFlashMIBGroup OBJECT-GROUP
        OBJECTS {
          qtechFlashDeviceIndex,
          qtechFlashDeviceName,
          qtechFlashDeviceSize,
          qtechFlashDeviceUsed,
          qtechFlashDeviceFree
        }
        STATUS  current
        DESCRIPTION
                "A collection of objects providing flash information to a Qtech agent."
        ::= { qtechFlashMIBGroups 1 } 
  
qtechBootromDeviceMIBGroup OBJECT-GROUP
        OBJECTS {
          qtechBootromDeviceIndex,
          qtechBootromDeviceName,
          qtechBootromDeviceSize
        }
        STATUS  current
        DESCRIPTION
                "A collection of objects providing bootrom device information to a Qtech agent."
        ::= { qtechFlashMIBGroups 2 } 
  
END
