-- *****************************************************************
-- QTECH-PFXV6-MIB.mib:  Qtech PFXv6 MIB file
--
--  2015.01.13, huangguohua@qtech.com.cn
--
-- Copyright (c) 2002 by Qtech Networks Co.,Ltd.
-- All rights reserved.
-- 
-- *****************************************************************
--

QTECH-PFXV6-MIB DEFINITIONS ::= BEGIN

IMPORTS
        MODULE-IDENTITY,
        OBJECT-TYPE,
        IpAddress,
        Integer32,
        Counter32
                FROM SNMPv2-SMI
        RowStatus,
        DisplayString,
        PhysAddress
                FROM SNMPv2-TC
        MODULE-COMPLIANCE,
        OBJECT-GROUP
                FROM SNMPv2-CONF
        IfIndex
                FROM QTECH-TC        
        qtechMgmt
                FROM QTECH-SMI;

qtechPFXv6MIB MODULE-IDENTITY
        LAST-UPDATED "201501130000Z"
        ORGANIZATION "Qtech Networks Co.,Ltd."
        CONTACT-INFO
                " 
                Tel: 4008-111-000 

                E-mail: service@qtech.com.cn"
        DESCRIPTION
                "This module defines qtech pfxv6 mibs."
        REVISION      "201501130000Z"
        DESCRIPTION
                "Initial version of this MIB module."
        ::= { qtechMgmt 134}

qtechPFXv6MIBObjects OBJECT IDENTIFIER ::= { qtechPFXv6MIB 1 }


 -- IPv6 local pool table
   
 qtechPFXv6Table OBJECT-TYPE
     SYNTAX  SEQUENCE OF QtechPFXv6Entry
     MAX-ACCESS  not-accessible
     STATUS  current
     DESCRIPTION
             "The IPv6 local pool statistics."
     ::= { qtechPFXv6MIBObjects 1 }

 qtechPFXv6Entry OBJECT-TYPE
     SYNTAX  QtechPFXv6Entry
     MAX-ACCESS  not-accessible
     STATUS  current
     DESCRIPTION
             "Each pool entry statistics."
     INDEX   { qtechPFXv6Name }
     ::= { qtechPFXv6Table 1 }

 QtechPFXv6Entry ::=
     SEQUENCE {
         qtechPFXv6Name
             DisplayString,
         qtechPFXv6Total
             Integer32,
         qtechPFXv6Rejects
             Integer32,
         qtechPFXv6Accepts
             Integer32,
         qtechPFXv6Frees
             Integer32,
         qtechPFXv6Userate
             INTEGER
     }
		
 qtechPFXv6Name OBJECT-TYPE
     SYNTAX  DisplayString (SIZE (0..32))
     MAX-ACCESS  read-only
     STATUS  current
     DESCRIPTION
             "The pool name."
     ::= { qtechPFXv6Entry 1 }

 qtechPFXv6Total OBJECT-TYPE
     SYNTAX  Integer32
     MAX-ACCESS  read-only
     STATUS  current
     DESCRIPTION
             "The total prefix number of pool."
     ::= { qtechPFXv6Entry 2 }
	 
 qtechPFXv6Rejects OBJECT-TYPE
     SYNTAX  Integer32
     MAX-ACCESS  read-only
     STATUS  current
     DESCRIPTION
             "Rejects number of pool."
     ::= { qtechPFXv6Entry 3 }

 qtechPFXv6Accepts OBJECT-TYPE
     SYNTAX  Integer32
     MAX-ACCESS  read-only
     STATUS  current
     DESCRIPTION
             "Accepts number of pool."
     ::= { qtechPFXv6Entry 4 }
	 
 qtechPFXv6Frees OBJECT-TYPE
     SYNTAX  Integer32
     MAX-ACCESS  read-only
     STATUS  current
     DESCRIPTION
             "Frees number of pool."
     ::= { qtechPFXv6Entry 5 }
	 
 qtechPFXv6Userate OBJECT-TYPE
     SYNTAX  INTEGER (0..100)
     MAX-ACCESS  read-only
     STATUS  current
     DESCRIPTION
             "Use rate of pool."
     ::= { qtechPFXv6Entry 6 }
	    
                
 --  Interface configure pool for SLAAC 
   
 qtechPFXv6IfTable OBJECT-TYPE
     SYNTAX  SEQUENCE OF QtechPFXv6IfEntry
     MAX-ACCESS  not-accessible
     STATUS  current
     DESCRIPTION
             "Interface configure pool for SLAAC."
     ::= { qtechPFXv6MIBObjects 2 }

 qtechPFXv6IfEntry OBJECT-TYPE
     SYNTAX  QtechPFXv6IfEntry
     MAX-ACCESS  not-accessible
     STATUS  current
     DESCRIPTION
             "Each pool entry statistics"
     INDEX   { qtechPFXv6IfIfIndex}
     ::= { qtechPFXv6IfTable 1 }

 QtechPFXv6IfEntry ::=
     SEQUENCE {
         qtechPFXv6IfIfIndex
             IfIndex,
         qtechPFXv6IfName
             DisplayString,
         qtechPFXv6IfTotal
             Integer32,
         qtechPFXv6IfRejects
             Integer32,
         qtechPFXv6IfAccepts
             Integer32,
         qtechPFXv6IfFrees
             Integer32,
         qtechPFXv6IfUserate
             INTEGER
     }

 qtechPFXv6IfIfIndex OBJECT-TYPE
     SYNTAX  IfIndex
     MAX-ACCESS  read-only
     STATUS  current
     DESCRIPTION
             "The interface on which this entry's equivalence
             is effective.  The interface identified by a
             particular value of this index is the same
             interface as identified by the same value of
             ifIndex."
     ::= { qtechPFXv6IfEntry 1 }
                  
 qtechPFXv6IfName OBJECT-TYPE
     SYNTAX  DisplayString (SIZE (0..32))
     MAX-ACCESS  read-only
     STATUS  current
     DESCRIPTION
             "The pool name."
     ::= { qtechPFXv6IfEntry 2 }

 qtechPFXv6IfTotal OBJECT-TYPE
     SYNTAX  Integer32
     MAX-ACCESS  read-only
     STATUS  current
     DESCRIPTION
             "The total prefix number of pool."
     ::= { qtechPFXv6IfEntry 3 }
	 
 qtechPFXv6IfRejects OBJECT-TYPE
     SYNTAX  Integer32
     MAX-ACCESS  read-only
     STATUS  current
     DESCRIPTION
             "Rejects number of pool."
     ::= { qtechPFXv6IfEntry 4 }

 qtechPFXv6IfAccepts OBJECT-TYPE
     SYNTAX  Integer32
     MAX-ACCESS  read-only
     STATUS  current
     DESCRIPTION
             "Accepts number of pool."
     ::= { qtechPFXv6IfEntry 5 }
	 
 qtechPFXv6IfFrees OBJECT-TYPE
     SYNTAX  Integer32
     MAX-ACCESS  read-only
     STATUS  current
     DESCRIPTION
             "Frees number of pool."
     ::= { qtechPFXv6IfEntry 6 }

 qtechPFXv6IfUserate OBJECT-TYPE
     SYNTAX  INTEGER (0..100)
     MAX-ACCESS  read-only
     STATUS  current
     DESCRIPTION
             "Use rate of pool."
     ::= { qtechPFXv6IfEntry 7 }
	 
 --  Counter for PFXv6

 qtechSlaacRequestNumber OBJECT-TYPE
        SYNTAX Counter32
        MAX-ACCESS read-only
        STATUS current
        DESCRIPTION
            "Number of SLAAC request this system have"
       ::= { qtechPFXv6MIBObjects 3 }        

 qtechSlaacRequestSuccessNumber OBJECT-TYPE
        SYNTAX Counter32
        MAX-ACCESS read-only
        STATUS current
        DESCRIPTION
            "Success Number of SLAAC request this system have"
        ::= { qtechPFXv6MIBObjects 4 }        
         
qtechPFXv6MIBConformance OBJECT IDENTIFIER ::= { qtechPFXv6MIB 2 }
qtechPFXv6MIBCompliances OBJECT IDENTIFIER ::= { qtechPFXv6MIBConformance 1 }
qtechPFXv6MIBGroups      OBJECT IDENTIFIER ::= { qtechPFXv6MIBConformance 2 }


-- compliance statements

qtechPFXv6MIBCompliance MODULE-COMPLIANCE
        STATUS  current
        DESCRIPTION
                "The compliance statement for entities which implement
                the Qtech PFXv6 MIB"
        MODULE  -- this module
                MANDATORY-GROUPS { qtechPFXv6MIBGroup
                 }        
        ::= { qtechPFXv6MIBCompliances 1 }
                
-- units of conformance

qtechPFXv6MIBGroup OBJECT-GROUP
        OBJECTS {
         qtechPFXv6Name,
         qtechPFXv6Total,
         qtechPFXv6Rejects,
         qtechPFXv6Accepts,
         qtechPFXv6Frees,
		 qtechPFXv6Userate,
         qtechPFXv6IfIfIndex,
         qtechPFXv6IfName,
         qtechPFXv6IfTotal,
         qtechPFXv6IfRejects,
         qtechPFXv6IfAccepts,
         qtechPFXv6IfFrees,
		 qtechPFXv6IfUserate,
         qtechSlaacRequestNumber,
         qtechSlaacRequestSuccessNumber
        }
        STATUS  current
        DESCRIPTION
                "A collection of objects providing pfxv6 management and
                opertion to a Qtech agent."
        ::= { qtechPFXv6MIBGroups 1 } 
  
END
