-- *****************************************************************
-- QTECH-MPLS-SIGNAL-MIB.mib:  Qtech MPLS Signal MIB file
--
-- MAY 2011, Liujinhui
--
-- Copyright (c) 2011 by Qtech Networks Co.,Ltd.
-- All rights reserved.
-- 
-- *****************************************************************
--

QTECH-MPLS-SIGNAL-MIB DEFINITIONS ::= BEGIN


IMPORTS
        MODULE-IDENTITY,
        OBJECT-TYPE,
        TimeTicks,
        IpAddress,
        Unsigned32,
        Gauge32,
        Counter32
                FROM SNMPv2-SMI
        TruthValue,
        DisplayString,
        RowStatus
                FROM SNMPv2-TC
        TimeStamp
                FROM SNMPv2-TC          -- [RFC2579]
        InetAddressPrefixLength,
        InetAddressType,
        InetAddress,
        InetPortNumber
             FROM INET-ADDRESS-MIB      --  [RFC3291]                
        MODULE-COMPLIANCE,
        OBJECT-GROUP
                FROM SNMPv2-CONF
        ConfigStatus
                FROM QTECH-TC    
        EnabledStatus 
                FROM P-BRIDGE-MIB                
        AreaID,
        Status,
        PositiveInteger,
        DesignatedRouterPriority,
        RouterID,
        HelloRange 
                FROM OSPF-MIB
        qtechMgmt
                FROM QTECH-SMI;

qtechMplsSignalMIB MODULE-IDENTITY
        LAST-UPDATED "201105150000Z"
        ORGANIZATION "Qtech Networks Co.,Ltd."
        CONTACT-INFO
                " 
                Tel: 4008-111-000 

                E-mail: service@qtech.com.cn"
        DESCRIPTION
                "This module defines qtech mpls signal mibs."
        REVISION      "201105150000Z"
        DESCRIPTION
                "Initial version of this MIB module."
        ::= { qtechMgmt 98}

qtechMplsSignalMIBObjects OBJECT IDENTIFIER ::= { qtechMplsSignalMIB 1 }
--****************************************************************

qtechMplsSignalObjects       OBJECT IDENTIFIER ::= { qtechMplsSignalMIBObjects 1 }
qtechMplsSignalConformance   OBJECT IDENTIFIER ::= { qtechMplsSignalMIBObjects 2 }

--****************************************************************
-- MPLS Signale Objects
--****************************************************************

qtechMplsSignalmplsGernalMibObjects  OBJECT IDENTIFIER ::= { qtechMplsSignalObjects 1 }     
qtechMplsSignalConfigMibObjects      OBJECT IDENTIFIER ::= { qtechMplsSignalObjects 2 } 

qtechMplsVersion OBJECT-TYPE
    SYNTAX  Unsigned32
    MAX-ACCESS read-only
    STATUS current
    DESCRIPTION
           "Current mpls version used."
     ::={ qtechMplsSignalmplsGernalMibObjects 1 }
qtechMPLSSignal    OBJECT-TYPE
    SYNTAX  INTEGER {
                     ldp(1),
                     rsvp-te(2),
                     cr-ldp(3),
                     other(4)
                       }
    MAX-ACCESS read-only
    STATUS current
    DESCRIPTION
           "MPLS signal we support."
     ::={ qtechMplsSignalmplsGernalMibObjects 2 }
qtechMPLSTESignal     OBJECT-TYPE
    SYNTAX      TruthValue     
    MAX-ACCESS read-only
    STATUS current
    DESCRIPTION   
          "Enable TE or not."
    ::={ qtechMplsSignalmplsGernalMibObjects 3 }     
                        
qtechMPLSConfigLspNum  OBJECT-TYPE
    SYNTAX  Unsigned32
    MAX-ACCESS read-only
    STATUS current
    DESCRIPTION
           "The number of static LSP configuration."
     ::={ qtechMplsSignalConfigMibObjects 1 }   
        
qtechMPLSActiveLspNum  OBJECT-TYPE
    SYNTAX  Unsigned32
    MAX-ACCESS read-only
    STATUS current
    DESCRIPTION
           "Total number of active LSP."
     ::={ qtechMplsSignalConfigMibObjects 2 }   
              
qtechMPLSAdministrativeGroupTable OBJECT-TYPE
    SYNTAX SEQUENCE OF QtechMPLSAdministrativeGroupEntry
    MAX-ACCESS not-accessible
    STATUS current
    DESCRIPTION
        "Information describing the configured  parame-ters  
         and cumulative statistics of the LSP Administrative Group."
    ::= { qtechMplsSignalObjects 3} 
          
qtechMPLSAdministrativeGroupEntry OBJECT-TYPE
    SYNTAX QtechMPLSAdministrativeGroupEntry
    MAX-ACCESS not-accessible
    STATUS current
    DESCRIPTION
            "The entry of qtechMPLSAdministrativeGroupTable."
    INDEX { qtechMPLSFecIndex }
    ::= { qtechMPLSAdministrativeGroupTable 1 }     

QtechMPLSAdministrativeGroupEntry ::= 
    SEQUENCE {
      qtechMPLSFecIndex                INTEGER,
      qtechMPLSLSPName                 DisplayString,
      qtechMPLSLSPStates               INTEGER,
      qtechMPLSLSPForwardBytes         INTEGER,
      qtechMPLSLSPForwardPackets       INTEGER,
      qtechMPLSLSPActiveTime           TimeStamp,
      qtechMPLSLSPCreationTime         TimeStamp,
      qtechMPLSLSPPrimaryCreationTime  TimeStamp,
      qtechMPLSLSPSwitchTimes          INTEGER,
      qtechMPLSLSPLatestSwitchTime     TimeStamp,
      qtechMPLSLSPPathchangeTime       TimeStamp,
      qtechMPLSLSPConfigChangeTime     TimeStamp,
      qtechMPLSLSPBackupPath           DisplayString,
      qtechMPLSLSPOperationPath        INTEGER,
      qtechMPLSLSPIngress              InetAddressType,
      qtechMPLSLSPDestination          InetAddressType,
      qtechMPLSLSPAdministrativeGroupName DisplayString
    }

qtechMPLSFecIndex OBJECT-TYPE
    SYNTAX  INTEGER
    MAX-ACCESS not-accessible
    STATUS current
    DESCRIPTION
           "The index which uniquely identifies this entry."
     ::={ qtechMPLSAdministrativeGroupEntry 1 } 
     
qtechMPLSLSPName       OBJECT-TYPE
    SYNTAX  DisplayString
    MAX-ACCESS read-only
    STATUS current
    DESCRIPTION
           "LSP name."
     ::={ qtechMPLSAdministrativeGroupEntry 2 }  
qtechMPLSLSPStates          OBJECT-TYPE
    SYNTAX                 INTEGER {
                                    active(1),
                                    inactive(2)
                                   }
    MAX-ACCESS read-only
    STATUS current
    DESCRIPTION
      "LSP states"
      ::= { qtechMPLSAdministrativeGroupEntry 3 }
qtechMPLSLSPForwardBytes       OBJECT-TYPE
    SYNTAX  INTEGER
    MAX-ACCESS read-only
    STATUS current
    DESCRIPTION
           "Forwarding bytes by LSP,where 0 means does not support."
     ::={ qtechMPLSAdministrativeGroupEntry 4 }  
     
qtechMPLSLSPForwardPackets       OBJECT-TYPE
    SYNTAX  INTEGER
    MAX-ACCESS read-only
    STATUS current
    DESCRIPTION
           "Forwarding packets by LSP,where 0 means does not support"
     ::={ qtechMPLSAdministrativeGroupEntry 5 }  
     
qtechMPLSLSPActiveTime      OBJECT-TYPE  
    SYNTAX  TimeStamp
    MAX-ACCESS read-only
    STATUS current
    DESCRIPTION
           "Total LSP Active time."
     ::={ qtechMPLSAdministrativeGroupEntry 6 }  
      
qtechMPLSLSPCreationTime      OBJECT-TYPE  
    SYNTAX  TimeStamp
    MAX-ACCESS read-only
    STATUS current
    DESCRIPTION
           "LSP creation time."
     ::={ qtechMPLSAdministrativeGroupEntry 7 }    
     
qtechMPLSLSPPrimaryCreationTime      OBJECT-TYPE  
    SYNTAX  TimeStamp
    MAX-ACCESS read-only
    STATUS current
    DESCRIPTION
           "Primary LSP creation time."
     ::={ qtechMPLSAdministrativeGroupEntry 8 } 
      
qtechMPLSLSPSwitchTimes    OBJECT-TYPE
    SYNTAX  INTEGER
    MAX-ACCESS read-only
    STATUS current
    DESCRIPTION
           "Total primary-standby switching times."
     ::={ qtechMPLSAdministrativeGroupEntry 9 }
       
qtechMPLSLSPLatestSwitchTime      OBJECT-TYPE   
    SYNTAX  TimeStamp
    MAX-ACCESS read-only
    STATUS current
    DESCRIPTION
           "The latest switching time"
     ::={ qtechMPLSAdministrativeGroupEntry 10 }   
       
qtechMPLSLSPPathchangeTime      OBJECT-TYPE   
    SYNTAX  TimeStamp
    MAX-ACCESS read-only
    STATUS current
    DESCRIPTION
           "The latest LSP change time."
     ::={ qtechMPLSAdministrativeGroupEntry 11 }  
     
qtechMPLSLSPConfigChangeTime      OBJECT-TYPE   
    SYNTAX  TimeStamp
    MAX-ACCESS read-only
    STATUS current
    DESCRIPTION
           "The Latest LSP configuration change time."
     ::={ qtechMPLSAdministrativeGroupEntry 12 }   
     
qtechMPLSLSPBackupPath      OBJECT-TYPE   
    SYNTAX  DisplayString
    MAX-ACCESS read-only
    STATUS current
    DESCRIPTION
           "Backup path name."
     ::={ qtechMPLSAdministrativeGroupEntry 13 }   
     
qtechMPLSLSPOperationPath      OBJECT-TYPE   
    SYNTAX  INTEGER {
                    primary(1),
                    backup(2),
                    none(3)
                    }
    MAX-ACCESS read-only
    STATUS current
    DESCRIPTION
           "Operational path which is used"
     ::={ qtechMPLSAdministrativeGroupEntry 14 }
     
qtechMPLSLSPIngress        OBJECT-TYPE   
    SYNTAX  InetAddressType
    MAX-ACCESS read-only
    STATUS current
    DESCRIPTION
           "LSP ingress."
     ::={ qtechMPLSAdministrativeGroupEntry 15 }   
     
qtechMPLSLSPDestination        OBJECT-TYPE   
    SYNTAX  InetAddressType
    MAX-ACCESS read-only
    STATUS current
    DESCRIPTION
           "LSP egress."
     ::={ qtechMPLSAdministrativeGroupEntry 16 }  

qtechMPLSLSPAdministrativeGroupName     OBJECT-TYPE
    SYNTAX  DisplayString
    MAX-ACCESS read-only
    STATUS current
    DESCRIPTION
           "LSP Administrative Group name."
     ::={ qtechMPLSAdministrativeGroupEntry 17 }                             
END
