-- *****************************************************************
-- QTECH-GATEWAY-SMI.mib: Qtech GATEWAY SMI File
-- 
-- May. 2010, panshiyong
--
-- Copyright (c) 2010 by Qtech Networks Co.,Ltd.
-- All rights reserved.
-- 
-- *****************************************************************
--

QTECH-GATEWAY-SMI DEFINITIONS ::= BEGIN

IMPORTS
        MODULE-IDENTITY,
        OBJECT-IDENTITY
                FROM SNMPv2-SMI
        products
                FROM QTECH-SMI;
                
gateway          OBJECT IDENTIFIER ::= { products 5 }

gatewayMib MODULE-IDENTITY
        LAST-UPDATED "201005250000Z"
        ORGANIZATION "Qtech Networks Co.,Ltd."
        CONTACT-INFO
                " 
                Tel: 4008-111-000 

                E-mail: service@qtech.com.cn"
        DESCRIPTION
                "The Structure of Management Information for the
                 Qtech enterprise."
        REVISION      "201005250000Z"
        DESCRIPTION
                "Initial version of this MIB module."
        ::= { gateway 1 }        

qtechGatewayProducts OBJECT-IDENTITY
        STATUS  current
        DESCRIPTION
                "qtechGatewayProducts is the root OBJECT IDENTIFIER from
                 which sysObjectID values are assigned for gateway.  Actual
                 values are defined in QTECH-PRODUCTS-MIB."
        ::= { gatewayMib 1 }
        
END
