-- *******************************************************************
-- QTECH-WLAN-FIT-AP-IN-MIB.mib : Qtech MIB
-- May 2010, ruanyucheng
--
-- Copyright (c) 2010 by Qtech Networks Co.,Ltd.
-- All rights reserved.
-- *******************************************************************
QTECH-WLAN-FIT-AP-IN-MIB DEFINITIONS ::= BEGIN
    IMPORTS
        MODULE-IDENTITY,
        OBJECT-TYPE,
        Integer32,
        Counter32,
        IpAddress,
        TimeTicks,
        Unsigned32
            FROM SNMPv2-SMI
        TruthValue,
        DisplayString,
        MacAddress,
        RowStatus
            FROM SNMPv2-TC
        Gauge
            FROM RFC1155-SMI
        MODULE-COMPLIANCE,
        NOTIFICATION-GROUP,
        OBJECT-GROUP
            FROM SNMPv2-CONF
        qtechStaMacAddr,    
        qtechApApName,
        qtechApCfgRadioId,    
        qtechApMacAddr,
        qtechApgWlanId
            FROM QTECH-AC-MGMT-MIB
        ifIndex
            FROM RFC1213-MIB
        qtechMgmt
            FROM QTECH-SMI;
--*******************************************
--* module definition
--*******************************************
qtechFitApMibModule MODULE-IDENTITY
    LAST-UPDATED    "201002260000Z"
    ORGANIZATION
        "Qtech Networks Co.,Ltd."
    CONTACT-INFO
        "Tel: 4008-111-000
           E-mail: service@qtech.com.cn "

    DESCRIPTION
       "
       Wlan software private MIB for Qtech SNC according to the China
       Mobile standard. This is device manage MIB.
       "
    REVISION      "201002280000Z"
    DESCRIPTION
       "Initial version of this MIB module."

    ::= { qtechMgmt  83 }

qtechAlarmTrapsObjects       OBJECT IDENTIFIER  ::= { qtechFitApMibModule 10 }
qtechAlarmTraps              OBJECT IDENTIFIER  ::= { qtechFitApMibModule 0 }
--**************************************************
--* apQtechTrapObjects begins * 
--**************************************************
qtechWIDSIllegalAlarmTrap NOTIFICATION-TYPE
    OBJECTS {
        qtechWIDSSuspiciousType,
        qtechWIDSSuspiciousDeviceMac,
        qtechWIDSSuspiciousDeviceExtensionInfo
    }
    STATUS  current
    DESCRIPTION
            " This trap will be sent at once when detecting an suspicious AP."
    ::= { qtechAlarmTraps 1 }  
    
qtechTelMtWorkModeChgTrap    NOTIFICATION-TYPE
    OBJECTS {
        qtechAPCurrentPMMode,
        qtechChgWorkModeAPMac
    }
    STATUS  current
    DESCRIPTION
            " This trap will be sent when the ap monitor workMode Change."
    ::= { qtechAlarmTraps 2 }    

    
qtechAttackAlarm   NOTIFICATION-TYPE
		OBJECTS {
        qtechAttackType,
        qtechAttackCilentIP,
        qtechAttackCilentExternInfo
    }
    STATUS  current
    DESCRIPTION
            " This trap will be sent when Attack has Appeared ."
    ::= { qtechAlarmTraps 4 }         
----------------------------------------------------
----------------------------------------------------
qtechWIDSSuspiciousType  OBJECT-TYPE
    SYNTAX      DisplayString  (SIZE(1..40))
    MAX-ACCESS  read-write
    STATUS      current
    DESCRIPTION
        " Suspicious ap type , eg: nonlicet AP   or disturb AP."
    ::= { qtechAlarmTrapsObjects 1 }

qtechWIDSSuspiciousDeviceMac OBJECT-TYPE
    SYNTAX      MacAddress
    MAX-ACCESS  read-write
    STATUS      current
    DESCRIPTION
        " The macaddress of the suspicious device."
    ::= { qtechAlarmTrapsObjects 2 }

qtechWIDSSuspiciousDeviceExtensionInfo OBJECT-TYPE
    SYNTAX      DisplayString  (SIZE(1..40))
    MAX-ACCESS  read-write
    STATUS      current
    DESCRIPTION
        " The information left for the future extension."
    ::= { qtechAlarmTrapsObjects 3 }  
    
qtechAPCurrentPMMode     OBJECT-TYPE
    SYNTAX      DisplayString  (SIZE(1..40))
    MAX-ACCESS  read-write
    STATUS      current
    DESCRIPTION
        " The information for the current ap monitor workMode ."
    ::= { qtechAlarmTrapsObjects 4 }        
    
qtechChgWorkModeAPMac  OBJECT-TYPE
    SYNTAX      MacAddress
    MAX-ACCESS  read-write
    STATUS      current
    DESCRIPTION
        " The macaddress of the ap device."
    ::= { qtechAlarmTrapsObjects 7 }  
    
qtechAttackType  OBJECT-TYPE
    SYNTAX      DisplayString  (SIZE(1..40))
    MAX-ACCESS  read-write
    STATUS      current
    DESCRIPTION
        " The attack type string ."
    ::= { qtechAlarmTrapsObjects 8 } 
    
qtechAttackCilentIP OBJECT-TYPE
    SYNTAX      IpAddress
    MAX-ACCESS  read-write
    STATUS      current
    DESCRIPTION
            " The ipaddress of the attack client."
    ::= { qtechAlarmTrapsObjects 9 }
    
qtechAttackCilentExternInfo  OBJECT-TYPE
    SYNTAX      DisplayString  (SIZE(1..40))
    MAX-ACCESS  read-write
    STATUS      current
    DESCRIPTION
        " The attack extern info string ."
    ::= { qtechAlarmTrapsObjects 10 }   
   
--**************************************************
--* apQtechTrapObjects ends * 
--**************************************************
qtechSystemInfoConfigObjects     OBJECT IDENTIFIER  ::= { qtechFitApMibModule 1 }
qtechDomain   OBJECT-TYPE
    SYNTAX DisplayString
    MAX-ACCESS read-only
    STATUS current
    DESCRIPTION
        "The Product Domain."
    ::= { qtechSystemInfoConfigObjects 1 }
    
qtechPhySeparatedEnable   OBJECT-TYPE
    SYNTAX INTEGER {
          off(0),
          on(1)
    }
    MAX-ACCESS read-write
    STATUS current
    DESCRIPTION
        "virtual phy separated enable config ,0:off 1:on."
    ::= { qtechSystemInfoConfigObjects 2 }      
    
qtechForfendDosAttackEnable   OBJECT-TYPE
    SYNTAX INTEGER {
          off(0),
          on(1)
    }
    MAX-ACCESS read-write
    STATUS current
    DESCRIPTION
        "Forfend DOS Attack config ,0:off 1:on."
    ::= { qtechSystemInfoConfigObjects 3 } 
    
qtechAcTrafficLoadBalancing OBJECT-TYPE
    SYNTAX TruthValue 
    MAX-ACCESS read-write
    STATUS current
    DESCRIPTION         
        " AC Traffic Load Balancing enable. "
    ::= { qtechSystemInfoConfigObjects 4 }  
    
qtechAcTrafficLoadBalanceThreshold    OBJECT-TYPE
    SYNTAX Integer32 
    MAX-ACCESS read-write
    STATUS current
    DESCRIPTION         
        " AC Traffic Load Balancing Threshold value . "
    ::= { qtechSystemInfoConfigObjects 5 }  
    
qtechAcTrafficOtherAPThresholdValue   OBJECT-TYPE
    SYNTAX Integer32 
    MAX-ACCESS read-write
    STATUS current
    DESCRIPTION         
        " other AP Traffic Threshold value . "
    ::= { qtechSystemInfoConfigObjects 6 }    

qtechAcAPWIDSScanningMode   OBJECT-TYPE
    SYNTAX INTEGER 
    MAX-ACCESS read-write
    STATUS current
    DESCRIPTION         
        " config AP WIDS scanning mode , 
        0: all channel scanning  1: auto select channel scanning . "
    ::= { qtechSystemInfoConfigObjects 7 }  
    
qtechAcAPLegitimateMode    OBJECT-TYPE
    SYNTAX INTEGER 
    MAX-ACCESS read-only
    STATUS current
    DESCRIPTION         
        " config AP Legitimate Mode value 
         0:legal ap 1: Illegal ap 2: Disturb AP . "
    ::= { qtechSystemInfoConfigObjects 8 }    
    
qtechAcAPTreatMode     OBJECT-TYPE
    SYNTAX INTEGER 
    MAX-ACCESS read-only
    STATUS current
    DESCRIPTION         
        " config Illegal AP Process mode 0:DOS attrack  1: disturb AP. "
    ::= { qtechSystemInfoConfigObjects 9 }  
    
qtechAcAssociationFailureTotalTimes  OBJECT-TYPE
    SYNTAX      Counter32
    MAX-ACCESS  read-only
    STATUS      current
    DESCRIPTION
        " The total times the association fails on AC."
    ::= { qtechSystemInfoConfigObjects 10 }
    
qtechAcAirIfRxTotalDataFrams  OBJECT-TYPE
    SYNTAX      Counter32
    MAX-ACCESS  read-only
    STATUS      current
    DESCRIPTION
        " The air interface total Rx Data Farms on AC."
    ::= { qtechSystemInfoConfigObjects 11 }   

qtechAcAirIfTxTotalDataFrams  OBJECT-TYPE
    SYNTAX      Counter32
    MAX-ACCESS  read-only
    STATUS      current
    DESCRIPTION
        " The air interface total Tx Data Farms on AC."
    ::= { qtechSystemInfoConfigObjects 12 }  
    
qtechAcAirIfTxTotalLostFrams  OBJECT-TYPE
    SYNTAX      Counter32
    MAX-ACCESS  read-only
    STATUS      current
    DESCRIPTION
        " The air interface total Tx Losted Data Farms on AC."
    ::= { qtechSystemInfoConfigObjects 13 } 
    
qtechAcAirIfTxAssociateFrams   OBJECT-TYPE
    SYNTAX      Counter32
    MAX-ACCESS  read-only
    STATUS      current
    DESCRIPTION
        " The air interface total Tx Associate  Farms on AC."
    ::= { qtechSystemInfoConfigObjects 14 } 
    
qtechAcAirIfRxAssociateFrams   OBJECT-TYPE
    SYNTAX      Counter32
    MAX-ACCESS  read-only
    STATUS      current
    DESCRIPTION
        " The air interface total Rx Associate  Farms on AC."
    ::= { qtechSystemInfoConfigObjects 15 } 
 
qtechAcAirIfBeaconTotalFrams  OBJECT-TYPE
    SYNTAX      Counter32
    MAX-ACCESS  read-only
    STATUS      current
    DESCRIPTION
        " The air interface total Beacon Farms on AC."
    ::= { qtechSystemInfoConfigObjects 16 } 
    
qtechAcAirIfRxTotalDataBytes   OBJECT-TYPE
    SYNTAX      Counter32
    MAX-ACCESS  read-only
    STATUS      current
    DESCRIPTION
        " The air interface total Rx right Data Bytes on AC."
    ::= { qtechSystemInfoConfigObjects 17 }   
    
qtechAcAirIfTxTotalDataBytes   OBJECT-TYPE
    SYNTAX      Counter32
    MAX-ACCESS  read-only
    STATUS      current
    DESCRIPTION
        " The air interface total Tx right Data Bytes on AC."
    ::= { qtechSystemInfoConfigObjects 18 } 
    
qtechAcAirRxFlux   OBJECT-TYPE
    SYNTAX      INTEGER
    MAX-ACCESS  read-only
    STATUS      current
    DESCRIPTION
        " The air interface Uplink Flux  on AC."
    ::= { qtechSystemInfoConfigObjects 19 }               
    
qtechAcAirTxFlux   OBJECT-TYPE
    SYNTAX      INTEGER
    MAX-ACCESS  read-only
    STATUS      current
    DESCRIPTION
        " The air interface Downlink Flux  on AC."
    ::= { qtechSystemInfoConfigObjects 20 }  
        
    
--*******************************************
--   apAPInfoConfigTable starts
--******************************************* 
qtechInfoConfigObjects  OBJECT IDENTIFIER  ::= { qtechFitApMibModule 2 } 
qtechInfoConfigTable  OBJECT-TYPE
    SYNTAX SEQUENCE OF QtechApInfoConfigTableEntry
    MAX-ACCESS not-accessible
    STATUS current
    DESCRIPTION
      "ap configuration Info table."
    ::={ qtechInfoConfigObjects 1 } 
    
qtechInfoConfigTableEntry    OBJECT-TYPE
    SYNTAX  QtechApInfoConfigTableEntry
    MAX-ACCESS  not-accessible
    STATUS  current
    DESCRIPTION
        "ap configuration Info table."
    INDEX   { qtechApMacAddr }
    ::= { qtechInfoConfigTable 1 }    
    
QtechApInfoConfigTableEntry  ::=
    SEQUENCE {
        qtechAcAPWIDSWorkMode              INTEGER
    }  
    
qtechAcAPWIDSWorkMode  OBJECT-TYPE
    SYNTAX INTEGER 
    MAX-ACCESS read-write
    STATUS current
    DESCRIPTION         
        " config AP WIDS work mode, 0: WIDS disabled  1:only support monitor 
        2:support AP monotor and access . "
    ::= { qtechInfoConfigTableEntry 1 }       
--*******************************************
--   apAPInfoConfigTable ends
--*******************************************          

qtechStationConfigObjects        OBJECT IDENTIFIER  ::= { qtechFitApMibModule 4 } 
--**************************************************
--* apapAC Station CONFIG starts * 
--**************************************************
qtechConfigStaInfoTable OBJECT-TYPE
    SYNTAX SEQUENCE OF QtechApConfigStaInfoTableEntry
    MAX-ACCESS not-accessible
    STATUS current
    DESCRIPTION
      "AC Config Station."
    ::={ qtechStationConfigObjects 1 }

qtechConfigStaInfoTableEntry OBJECT-TYPE
    SYNTAX  QtechApConfigStaInfoTableEntry
    MAX-ACCESS  not-accessible
    STATUS  current
    DESCRIPTION
        "AC Config AP Bandwith max."
    INDEX   { qtechStaMacAddr }
    ::= { qtechConfigStaInfoTable 1 }
    
QtechApConfigStaInfoTableEntry ::=
    SEQUENCE {
    		qtechACconfigAPBandwith         Integer32
    }  

qtechACconfigAPBandwith   OBJECT-TYPE
    SYNTAX Integer32
    MAX-ACCESS read-write
    STATUS current
    DESCRIPTION
        "AC Config AP Bandwith max."
    ::= { qtechConfigStaInfoTableEntry 1 }  
--**************************************************
--* apapAC Station CONFIG ends * 
--**************************************************    

--apWlanIdSecurityCfgObjects        OBJECT IDENTIFIER  ::= { qtechFitApMibModule 5 } 

--**************************************************
--* apapAC WlanIdSecurity CONFIG starts * 
--**************************************************  
--apSecurityCfgTable OBJECT-TYPE
--    SYNTAX SEQUENCE OF ApSecurityCfgTableEntry
--    MAX-ACCESS not-accessible
--    STATUS current
--    DESCRIPTION
--      "AP security  config."
--    ::={ apWlanIdSecurityCfgObjects 1 }

--apSecurityCfgTableEntry OBJECT-TYPE
--    SYNTAX  ApSecurityCfgTableEntry
--    MAX-ACCESS  not-accessible
--    STATUS  current
--    DESCRIPTION
--        "AP security  config."
--    INDEX   { qtechgWlanId }
--    ::= { apSecurityCfgTable 1 }
    
--ApSecurityCfgTableEntry ::=
--    SEQUENCE {
--    		apsecurityMode                        INTEGER,       in china mobile node ApSSIDConfigTableEntry 
--    		apAuthenMode                          INTEGER,       in china mobile node apSSIDConfigTableEntry
--    		apSecurityCiphers                     INTEGER,       in china mobile node apSSIDConfigTableEntry
--    		apWEPCipherKeyIndex                   INTEGER,       in china mobile node apSecurityConfigTableEntry
--        apWEPCipherKeyValue                   DisplayString, in china mobile node apSecurityConfigTableEntry
--        apWEPCipherKeyCharType                INTEGER,       in china mobile node apSecurityConfigTableEntry
--        apPSKCipherKeyValue                   DisplayString, in china mobile node apSecurityConfigTableEntry
--        apPSKCipherKeyCharType                INTEGER,       in china mobile node apSecurityConfigTableEntry
--        apWAPIASIPAddress                     IpAddress,     in china mobile node apSecurityConfigTableEntry
--        apWAPIIsInstalledCer                  TruthValue,    in china mobile node apSecurityConfigTableEntry
--        apWAPIConfigVersion                   Integer32,     in china mobile node apWAPIExternInfoConfigTableEntry
--        apWAPIControlledAuthControl           TruthValue,    in china mobile node apWAPIExternInfoConfigTableEntry
--        apWAPIControlledPortControl           INTEGER,       in china mobile node apWAPIExternInfoConfigTableEntry
--        apWAPIOptionImplemented               TruthValue,    in china mobile node apWAPIExternInfoConfigTableEntry
--        apWAPIPreauthenticationImplemented    TruthValue,
--        apWAPIEnabled                         TruthValue,
--        apWAPIPreauthEnabled                  TruthValue,
--        apWAPIUnicastKeysSupported            Unsigned32,
--        apWAPIUnicastRekeyMethod              INTEGER,
--        apWAPIUnicastRekeyTime                Unsigned32,
--        apWAPIUnicastRekeyPackets             Unsigned32,
--        apWAPIMulticastCipher                 OCTET STRING,
--        apWAPIMulticastRekeyMethod            INTEGER,
--        apWAPIMulticastRekeyTime              Unsigned32,
--        apWAPIMulticastRekeyPackets  	        Unsigned32,
--        apWAPIMulticastRekeyStrict  	        TruthValue,
--        apWAPIPSKValue 	                      OCTET STRING,
--        apWAPICertificateUpdateCount 	        Unsigned32,
--        apWAPIUnicastUpdateCount  	          Unsigned32,
--        apWAPIMulticastCipherSize 	          Unsigned32,
--        apWAPIBKReauthThreshold 	            Unsigned32,
--        apWAPISATimeout 	                    Unsigned32,
--        apWAPIAuthSuiteSelected 	            OCTET STRING,
--        apWAPIUnicastCipherSelected 	        OCTET STRING,
--        apWAPIMulticastCipherSelected 	      OCTET STRING,
--        apWAPIBKIDUsed 	                      OCTET STRING,
--        apWAPIAuthSuiteRequested 	            OCTET STRING,
--        apWAPIUnicastCipherRequested 	        OCTET STRING,
--        apWAPIMulticastCipherRequested 	      OCTET STRING,
--        apWAPIUnicastCipher                   OCTET STRING,
--        apWAPIUnicastCipherEnabled            TruthValue,
--        apWAPIUnicastCipherSize               Unsigned32,
--        apWAPIAuthenticationSuite             OCTET STRING,
--        apWAPIAuthenticationSuiteEnabled      TruthValue      in china mobile node apWAPIExternInfoConfigTableEntry
--    }  
        
--**************************************************
--* apapAC Security CONFIG ends * 
--**************************************************  
--**************************************************
--* apapAirIfInfoStatisticsTable starts * 
--************************************************** 
qtechAirIfStatisticsObjects     OBJECT IDENTIFIER  ::= { qtechFitApMibModule 6 }
qtechAirIfInfoStatisticsTable OBJECT-TYPE
    SYNTAX SEQUENCE OF QtechApAirIfInfoStatisticsTableEntry
    MAX-ACCESS not-accessible
    STATUS current
    DESCRIPTION
      "get air interface parameters statistics."
    ::={ qtechAirIfStatisticsObjects 1 }
  
qtechAirIfInfoStatisticsTableEntry OBJECT-TYPE
    SYNTAX  QtechApAirIfInfoStatisticsTableEntry
    MAX-ACCESS  not-accessible
    STATUS  current
    DESCRIPTION
        "get  AP Associa Fail times "
    INDEX   { qtechApgWlanId,qtechApMacAddr }
    ::= { qtechAirIfInfoStatisticsTable 1 }

QtechApAirIfInfoStatisticsTableEntry ::=
    SEQUENCE {
       qtechRxTotalDataFrams     Counter32,
       qtechTxTotalDataFrams     Counter32,
       qtechTxLostDataFrams      Counter32,   
       qtechTxAssociateFrams     Counter32,
       qtechRxAssociateFrams     Counter32,
       qtechBeaconFrams          Counter32,
       qtechRxTotalDataBytes     Counter32,
       qtechTxTotalDataBytes     Counter32,
       qtechRESUtilization       INTEGER
    }
    
qtechRxTotalDataFrams  OBJECT-TYPE
    SYNTAX Counter32
    MAX-ACCESS read-only
    STATUS current
    DESCRIPTION
        "ap total Rx Data Frams."
    ::= { qtechAirIfInfoStatisticsTableEntry 1 }  
    
qtechTxTotalDataFrams   OBJECT-TYPE
    SYNTAX Counter32
    MAX-ACCESS read-only
    STATUS current
    DESCRIPTION
        "ap total Tx Data Frams."
    ::= { qtechAirIfInfoStatisticsTableEntry 2 }  
    
qtechTxLostDataFrams   OBJECT-TYPE
    SYNTAX Counter32
    MAX-ACCESS read-only
    STATUS current
    DESCRIPTION
        "ap total Tx Lost Data Frams."
    ::= { qtechAirIfInfoStatisticsTableEntry 3 }   
    
qtechTxAssociateFrams  OBJECT-TYPE
    SYNTAX Counter32
    MAX-ACCESS read-only
    STATUS current
    DESCRIPTION
        "ap total Tx Associate Frams."
    ::= { qtechAirIfInfoStatisticsTableEntry 4 } 
    
qtechRxAssociateFrams   OBJECT-TYPE
    SYNTAX Counter32
    MAX-ACCESS read-only
    STATUS current
    DESCRIPTION
        "ap total Rx Associate Frams."
    ::= { qtechAirIfInfoStatisticsTableEntry 5 }    
    
qtechBeaconFrams    OBJECT-TYPE
    SYNTAX Counter32
    MAX-ACCESS read-only
    STATUS current
    DESCRIPTION
        "ap Beacon Total Frams."
    ::= { qtechAirIfInfoStatisticsTableEntry 6 }  
    
qtechRxTotalDataBytes   OBJECT-TYPE
    SYNTAX Counter32
    MAX-ACCESS read-only
    STATUS current
    DESCRIPTION
        "ap total Rx Data Bytes."
    ::= { qtechAirIfInfoStatisticsTableEntry 7 }  
    
qtechTxTotalDataBytes   OBJECT-TYPE
    SYNTAX Counter32
    MAX-ACCESS read-only
    STATUS current
    DESCRIPTION
        "ap total Tx Data Bytes."
    ::= { qtechAirIfInfoStatisticsTableEntry 8 }    
    
qtechRESUtilization   OBJECT-TYPE
    SYNTAX INTEGER
    MAX-ACCESS read-only
    STATUS current
    DESCRIPTION
        "ap Resource Utilization."
    ::= { qtechAirIfInfoStatisticsTableEntry 9 }
---------------------------------------------------------
---------------------------------------------------------    
--**************************************************
--* apAirIfInfoStatisticsTable starts * 
--************************************************** 
qtechAirIfTxResendDataTable OBJECT-TYPE
    SYNTAX SEQUENCE OF QtechApAirIfTxResendDataTableEntry
    MAX-ACCESS not-accessible
    STATUS current
    DESCRIPTION
      "get air interface Resend Data frames."
    ::={ qtechAirIfStatisticsObjects 2 }
    
qtechAirIfTxResendDataTableEntry OBJECT-TYPE
    SYNTAX  QtechApAirIfTxResendDataTableEntry
    MAX-ACCESS  not-accessible
    STATUS  current
    DESCRIPTION
        "get air interface Resend Data frames"
    INDEX   { qtechStaMacAddr }
    ::= { qtechAirIfTxResendDataTable 1 }

QtechApAirIfTxResendDataTableEntry ::=
    SEQUENCE {
          qtechStaResendDataFrams  Counter32
    }   
   
qtechStaResendDataFrams    OBJECT-TYPE
    SYNTAX Counter32
    MAX-ACCESS read-only
    STATUS current
    DESCRIPTION
        "station total Resend Data Frams."
    ::= { qtechAirIfTxResendDataTableEntry 1 }
    
            
--**************************************************
--* apapAirIfInfoStatisticsTable ends * 
--************************************************** 

--**************************************************
--* apTermServiceStatistics starts * 
--************************************************** 

qtechTermServiceStatistics              OBJECT IDENTIFIER  ::= { qtechFitApMibModule 7 }
qtechTermServiceStatisticsWithSSID      OBJECT IDENTIFIER  ::= { qtechTermServiceStatistics 1 } 
qtechTermServiceStatisticsWithAP        OBJECT IDENTIFIER  ::= { qtechTermServiceStatistics 2 } 
qtechTermServiceSTatisticsWithStation   OBJECT IDENTIFIER  ::= { qtechTermServiceStatistics 3 } 

qtechTermServiceStaticWithSSIDTable  OBJECT-TYPE
    SYNTAX SEQUENCE OF QtechApTermServiceStaticWithSSIDTableEntry
    MAX-ACCESS not-accessible
    STATUS current
    DESCRIPTION
      "get Term Service Statistics With SSID."
    ::={ qtechTermServiceStatisticsWithSSID 1 }
  
qtechTermServiceStaticWithSSIDTableEntry OBJECT-TYPE
    SYNTAX  QtechApTermServiceStaticWithSSIDTableEntry
    MAX-ACCESS  not-accessible
    STATUS  current
    DESCRIPTION
        "get Term Service Statistics With SSID"
    INDEX   { qtechApgWlanId }
    ::= { qtechTermServiceStaticWithSSIDTable 1 }

QtechApTermServiceStaticWithSSIDTableEntry ::=
    SEQUENCE { 
           qtechTotalUserNum                                INTEGER,  
           qtechCurrentUserNum                              INTEGER,  
           qtechStaReqAccessTimes                           INTEGER,
           qtechRspStaAccessReqTimes                        INTEGER,
           qtechStaAccessSucessTimes                        INTEGER,
           qtechIneffiLinkVerifyFailTime                    INTEGER,
           qtechTimeoutLinkVerifyFailTime                   INTEGER,
           qtechInefficiencyLinkVerifyFailTime              INTEGER,
           qtechOtherReasonLinkVerifyFailTime               INTEGER,
           qtechIneffiAssociationFailTime                   INTEGER,
           qtechTimeoutAssociationFailTime                  INTEGER,
           qtechInefficiencyAssociationFailTime             INTEGER,
           qtechOtherReasonAssociationFailTime              INTEGER,
           qtechTotalReassociationAtmptTimes                INTEGER,
           qtechTotalReassociationSuccessTimes              INTEGER,
           qtechIneffiReassociationFailTime                 INTEGER,
           qtechTimeoutReassociationFailTime                INTEGER,
           qtechInefficiencyReassociationFailTime           INTEGER,
           qtechOtherReasonReassociationFailTime            INTEGER,
           qtechTotalIdentificationAtmptTimes               INTEGER,
           qtechTotalIdentificationSuccessTimes             INTEGER,
           qtechPwdErrorIdentifyFailTime                    INTEGER,
           qtechIneffiIdentificationFailTime                INTEGER,
           qtechTimeoutIdentificationFailTime               INTEGER,
           qtechInefficiencyIdentificationFailTime          INTEGER,
           qtechOtherReasonIdentificationFailTime           INTEGER,
           qtechTotalRemoveLinkVerifyFailTimes              INTEGER,
           qtechLeaveAPCoverageRemoveLinkVerifyFailTimes    INTEGER,
           qtechInefficiencyRemoveLinkVerifyFailTime        INTEGER,
           qtechLinkVerifyFailRemoveLinkVerifyFailTime      INTEGER,
           qtechOtherReasonRemoveLinkVerifyFailTime         INTEGER,
           qtechTotalRemoveLinkAssociationTimes             INTEGER,
           qtechLeaveAPCoverageRemoveAssociationFailTimes   INTEGER,
           qtechInefficiencyRemoveAssociationFailTime       INTEGER,
           qtechAssociationFailRemoveAssociationFailTime    INTEGER,
           qtechOtherReasonRemoveAssociationFailTime        INTEGER         
    }

qtechTotalUserNum OBJECT-TYPE
    SYNTAX INTEGER
    MAX-ACCESS read-only
    STATUS current
    DESCRIPTION
        "Total user number that have connected to the AP."
    ::= { qtechTermServiceStaticWithSSIDTableEntry 1}
    
qtechCurrentUserNum   OBJECT-TYPE
    SYNTAX INTEGER
    MAX-ACCESS read-only
    STATUS current
    DESCRIPTION
        "Total current user number that have connected to the AP."
    ::= { qtechTermServiceStaticWithSSIDTableEntry 2}  
    
qtechStaReqAccessTimes OBJECT-TYPE
    SYNTAX INTEGER
    MAX-ACCESS read-only
    STATUS current
    DESCRIPTION
        "station request to access to AP times."
    ::= { qtechTermServiceStaticWithSSIDTableEntry 3}    

qtechRspStaAccessReqTimes  OBJECT-TYPE
    SYNTAX INTEGER
    MAX-ACCESS read-only
    STATUS current
    DESCRIPTION
        "ap response station access request times."
    ::= { qtechTermServiceStaticWithSSIDTableEntry 4}    
    
qtechStaAccessSucessTimes  OBJECT-TYPE
    SYNTAX INTEGER
    MAX-ACCESS read-only
    STATUS current
    DESCRIPTION
        "sta success to connet to ap times."
    ::= { qtechTermServiceStaticWithSSIDTableEntry 5}      

qtechIneffiLinkVerifyFailTime OBJECT-TYPE
    SYNTAX INTEGER
    MAX-ACCESS read-only
    STATUS current
    DESCRIPTION
        "Total link verify failure times due to algorithm or transform SN discrepancy."
    ::= { qtechTermServiceStaticWithSSIDTableEntry 6}

qtechTimeoutLinkVerifyFailTime OBJECT-TYPE
    SYNTAX INTEGER
    MAX-ACCESS read-only
    STATUS current
    DESCRIPTION
        "Total link verify failure times due to timeout."
    ::= { qtechTermServiceStaticWithSSIDTableEntry 7}
    
qtechInefficiencyLinkVerifyFailTime OBJECT-TYPE
    SYNTAX INTEGER
    MAX-ACCESS read-only
    STATUS current
    DESCRIPTION
        "Total link verify failure times due to inefficiency."
    ::= { qtechTermServiceStaticWithSSIDTableEntry 8}
    
qtechOtherReasonLinkVerifyFailTime OBJECT-TYPE
    SYNTAX INTEGER
    MAX-ACCESS read-only
    STATUS current
    DESCRIPTION
        "Total link verify failure times due to other reason."
    ::= { qtechTermServiceStaticWithSSIDTableEntry 9}
    
qtechIneffiAssociationFailTime OBJECT-TYPE
    SYNTAX INTEGER
    MAX-ACCESS read-only
    STATUS current
    DESCRIPTION
        "Total Association failure times due to algorithm or transform SN discrepancy."
    ::= { qtechTermServiceStaticWithSSIDTableEntry 10}

qtechTimeoutAssociationFailTime OBJECT-TYPE
    SYNTAX INTEGER
    MAX-ACCESS read-only
    STATUS current
    DESCRIPTION
        "Total Association failure times due to timeout."
    ::= { qtechTermServiceStaticWithSSIDTableEntry 11}
    
qtechInefficiencyAssociationFailTime OBJECT-TYPE
    SYNTAX INTEGER
    MAX-ACCESS read-only
    STATUS current
    DESCRIPTION
        "Total Association failure times due to inefficiency."
    ::= { qtechTermServiceStaticWithSSIDTableEntry 12}
    
qtechOtherReasonAssociationFailTime OBJECT-TYPE
    SYNTAX INTEGER
    MAX-ACCESS read-only
    STATUS current
    DESCRIPTION
        "Total Association failure times due to other reason."
    ::= { qtechTermServiceStaticWithSSIDTableEntry 13}
    
qtechTotalReassociationAtmptTimes OBJECT-TYPE
    SYNTAX INTEGER
    MAX-ACCESS read-only
    STATUS current
    DESCRIPTION
        "Total re-association attempt times."
    ::= { qtechTermServiceStaticWithSSIDTableEntry 14}
    
qtechTotalReassociationSuccessTimes OBJECT-TYPE
    SYNTAX INTEGER
    MAX-ACCESS read-only
    STATUS current
    DESCRIPTION
        "Total re-association success times."
    ::= { qtechTermServiceStaticWithSSIDTableEntry 15}

qtechIneffiReassociationFailTime OBJECT-TYPE
    SYNTAX INTEGER
    MAX-ACCESS read-only
    STATUS current
    DESCRIPTION
        "Total Reassociation failure times due to algorithm or transform SN discrepancy."
    ::= { qtechTermServiceStaticWithSSIDTableEntry 16}

qtechTimeoutReassociationFailTime OBJECT-TYPE
    SYNTAX INTEGER
    MAX-ACCESS read-only
    STATUS current
    DESCRIPTION
        "Total Reassociation failure times due to timeout."
    ::= { qtechTermServiceStaticWithSSIDTableEntry 17}
    
qtechInefficiencyReassociationFailTime OBJECT-TYPE
    SYNTAX INTEGER
    MAX-ACCESS read-only
    STATUS current
    DESCRIPTION
        "Total Reassociation failure times due to inefficiency."
    ::= { qtechTermServiceStaticWithSSIDTableEntry 18}
    
qtechOtherReasonReassociationFailTime OBJECT-TYPE
    SYNTAX INTEGER
    MAX-ACCESS read-only
    STATUS current
    DESCRIPTION
        "Total Reassociation failure times due to other reason."
    ::= { qtechTermServiceStaticWithSSIDTableEntry 19}
    
qtechTotalIdentificationAtmptTimes OBJECT-TYPE
    SYNTAX INTEGER
    MAX-ACCESS read-only
    STATUS current
    DESCRIPTION
        "Total Identification attempt times."
    ::= { qtechTermServiceStaticWithSSIDTableEntry 20}
    
qtechTotalIdentificationSuccessTimes OBJECT-TYPE
    SYNTAX INTEGER
    MAX-ACCESS read-only
    STATUS current
    DESCRIPTION
        "Total Identification success times."
    ::= { qtechTermServiceStaticWithSSIDTableEntry 21}
    
qtechPwdErrorIdentifyFailTime OBJECT-TYPE
    SYNTAX INTEGER
    MAX-ACCESS read-only
    STATUS current
    DESCRIPTION
        "Total identification failure times due to password error."
    ::= { qtechTermServiceStaticWithSSIDTableEntry 22}    

qtechIneffiIdentificationFailTime OBJECT-TYPE
    SYNTAX INTEGER
    MAX-ACCESS read-only
    STATUS current
    DESCRIPTION
        "Total Identification failure times due to algorithm or transform SN discrepancy."
    ::= { qtechTermServiceStaticWithSSIDTableEntry 23}

qtechTimeoutIdentificationFailTime OBJECT-TYPE
    SYNTAX INTEGER
    MAX-ACCESS read-only
    STATUS current
    DESCRIPTION
        "Total Identification failure times due to timeout."
    ::= { qtechTermServiceStaticWithSSIDTableEntry 24}
    
qtechInefficiencyIdentificationFailTime OBJECT-TYPE
    SYNTAX INTEGER
    MAX-ACCESS read-only
    STATUS current
    DESCRIPTION
        "Total Identification failure times due to inefficiency."
    ::= { qtechTermServiceStaticWithSSIDTableEntry 25}
    
qtechOtherReasonIdentificationFailTime OBJECT-TYPE
    SYNTAX INTEGER
    MAX-ACCESS read-only
    STATUS current
    DESCRIPTION
        "Total Identification failure times due to other reason."
    ::= { qtechTermServiceStaticWithSSIDTableEntry 26}
    
qtechTotalRemoveLinkVerifyFailTimes OBJECT-TYPE
    SYNTAX INTEGER
    MAX-ACCESS read-only
    STATUS current
    DESCRIPTION
        "Total failure times of removing link verification."
    ::= { qtechTermServiceStaticWithSSIDTableEntry 27} 
    
qtechLeaveAPCoverageRemoveLinkVerifyFailTimes OBJECT-TYPE
    SYNTAX INTEGER
    MAX-ACCESS read-only
    STATUS current
    DESCRIPTION
        "Total failure times due to leaving AP coverage area."
    ::= { qtechTermServiceStaticWithSSIDTableEntry 28}   
    
qtechInefficiencyRemoveLinkVerifyFailTime OBJECT-TYPE
    SYNTAX INTEGER
    MAX-ACCESS read-only
    STATUS current
    DESCRIPTION
        "Total remove link failure times due to inefficiency."
    ::= { qtechTermServiceStaticWithSSIDTableEntry 29}  
    
qtechLinkVerifyFailRemoveLinkVerifyFailTime OBJECT-TYPE
    SYNTAX INTEGER
    MAX-ACCESS read-only
    STATUS current
    DESCRIPTION
        "Total remove link failure times due to link verify failure."
    ::= { qtechTermServiceStaticWithSSIDTableEntry 30}      

qtechOtherReasonRemoveLinkVerifyFailTime OBJECT-TYPE
    SYNTAX INTEGER
    MAX-ACCESS read-only
    STATUS current
    DESCRIPTION
        "Total remove link failure times due to other reason."
    ::= { qtechTermServiceStaticWithSSIDTableEntry 31} 

qtechTotalRemoveLinkAssociationTimes OBJECT-TYPE
    SYNTAX INTEGER
    MAX-ACCESS read-only
    STATUS current
    DESCRIPTION
        "Total failure times of removing association."
    ::= { qtechTermServiceStaticWithSSIDTableEntry 32}  
    
qtechLeaveAPCoverageRemoveAssociationFailTimes OBJECT-TYPE
    SYNTAX INTEGER
    MAX-ACCESS read-only
    STATUS current
    DESCRIPTION
        "Total remove association failure times due to leaving AP coverage area."
    ::= { qtechTermServiceStaticWithSSIDTableEntry 33}   
    
qtechInefficiencyRemoveAssociationFailTime OBJECT-TYPE
    SYNTAX INTEGER
    MAX-ACCESS read-only
    STATUS current
    DESCRIPTION
        "Total remove association failure times due to inefficiency."
    ::= { qtechTermServiceStaticWithSSIDTableEntry 34}  
    
qtechAssociationFailRemoveAssociationFailTime OBJECT-TYPE
    SYNTAX INTEGER
    MAX-ACCESS read-only
    STATUS current
    DESCRIPTION
        "Total remove association failure times due to link verify failure."
    ::= { qtechTermServiceStaticWithSSIDTableEntry 35}      

qtechOtherReasonRemoveAssociationFailTime OBJECT-TYPE
    SYNTAX INTEGER
    MAX-ACCESS read-only
    STATUS current
    DESCRIPTION
        "Total remove association failure times due to other reason."
    ::= { qtechTermServiceStaticWithSSIDTableEntry 36}
--*************************************************   
--*************************************************
qtechTermServiceStationWithStationTable OBJECT-TYPE
    SYNTAX SEQUENCE OF QtechTermServiceStationWithStationTableEntry
    MAX-ACCESS not-accessible
    STATUS current
    DESCRIPTION
        "Statistic of user MAC address by SSID."
    ::= { qtechTermServiceSTatisticsWithStation 1	 }

qtechTermServiceStationWithStationTableEntry OBJECT-TYPE
    SYNTAX QtechTermServiceStationWithStationTableEntry
    MAX-ACCESS not-accessible
    STATUS current
    DESCRIPTION
        "The entry of apTermServiceStationWithStationTable."
    INDEX
    { qtechApgWlanId,qtechStaMacAddr}
    ::= { qtechTermServiceStationWithStationTable 1 }

QtechTermServiceStationWithStationTableEntry ::=
    SEQUENCE {
        qtechStaAssociateTime         Counter32,
        qtechRxStaDataFrams           Counter32,
        qtechRXStaErrorFrams          Counter32,
        qtechTxStaDataFrams           Counter32,
        qtechReSendDataFrams          Counter32,
        qtechStaRxAvgSpeed            INTEGER,
        qtechStaTxAvgSpeed            INTEGER,
        qtechStaThroughput            INTEGER,
        qtechStaSignalStrength        INTEGER,
        qtechStaSignalNoise           INTEGER
    } 
  
   
qtechStaAssociateTime  OBJECT-TYPE
    SYNTAX Counter32
    MAX-ACCESS read-only
    STATUS current
    DESCRIPTION
        "station Associate to ap time ,unit is minute."
    ::= { qtechTermServiceStationWithStationTableEntry 2}   
    
qtechRxStaDataFrams   OBJECT-TYPE
    SYNTAX Counter32
    MAX-ACCESS read-only
    STATUS current
    DESCRIPTION
        "ap Rx station Data Frames ."
    ::= { qtechTermServiceStationWithStationTableEntry 3}   
    
qtechRXStaErrorFrams   OBJECT-TYPE
    SYNTAX Counter32
    MAX-ACCESS read-only
    STATUS current
    DESCRIPTION
        "ap Rx station Error Frames ."
    ::= { qtechTermServiceStationWithStationTableEntry 4} 
    
qtechTxStaDataFrams    OBJECT-TYPE
    SYNTAX Counter32
    MAX-ACCESS read-only
    STATUS current
    DESCRIPTION
        "ap Tx station Data Frames ."
    ::= { qtechTermServiceStationWithStationTableEntry 5}     
    
qtechReSendDataFrams    OBJECT-TYPE
    SYNTAX Counter32
    MAX-ACCESS read-only
    STATUS current
    DESCRIPTION
        "ap Resend station Data Frames ."
    ::= { qtechTermServiceStationWithStationTableEntry 6}    
    
qtechStaRxAvgSpeed OBJECT-TYPE
    SYNTAX INTEGER
    MAX-ACCESS read-only
    STATUS current
    DESCRIPTION
        "ap Send  to station average DATA speed ."
    ::= { qtechTermServiceStationWithStationTableEntry 7}  
    
qtechStaTxAvgSpeed   OBJECT-TYPE
    SYNTAX INTEGER
    MAX-ACCESS read-only
    STATUS current
    DESCRIPTION
        "ap Send  from station average DATA speed ."
    ::= { qtechTermServiceStationWithStationTableEntry 8}  
    
qtechStaThroughput  OBJECT-TYPE
    SYNTAX INTEGER
    MAX-ACCESS read-only
    STATUS current
    DESCRIPTION
        "station Throughput ."
    ::= { qtechTermServiceStationWithStationTableEntry 9}  
    
qtechStaSignalStrength  OBJECT-TYPE
    SYNTAX INTEGER
    MAX-ACCESS read-only
    STATUS current
    DESCRIPTION
        "ap receive station signal strength ."
    ::= { qtechTermServiceStationWithStationTableEntry 10}   
    
qtechStaSignalNoise  OBJECT-TYPE
    SYNTAX INTEGER
    MAX-ACCESS read-only
    STATUS current
    DESCRIPTION
        "ap receive station signal noise ."
    ::= { qtechTermServiceStationWithStationTableEntry 11}                    
--*************************************************

---------------------------------------------------
---------------------------------------------------
qtechTermServiceStaticWithAPTable  OBJECT-TYPE
    SYNTAX SEQUENCE OF QtechTermServiceStaticWithAPTableEntry
    MAX-ACCESS not-accessible
    STATUS current
    DESCRIPTION
      "get Term Service Statistics With AP."
    ::={ qtechTermServiceStatisticsWithAP 1 }
  
qtechTermServiceStaticWithAPTableEntry OBJECT-TYPE
    SYNTAX  QtechTermServiceStaticWithAPTableEntry
    MAX-ACCESS  not-accessible
    STATUS  current
    DESCRIPTION
        "get Term Service Statistics With AP"
    INDEX   { qtechApMacAddr }
    ::= { qtechTermServiceStaticWithAPTable 1 }

QtechTermServiceStaticWithAPTableEntry ::=
    SEQUENCE {     
          qtechUserAccumulateTime     Counter32,
          qtechAssociaFailTimes       Counter32
          
    }
qtechUserAccumulateTime OBJECT-TYPE
    SYNTAX Counter32
    MAX-ACCESS read-only
    STATUS current
    DESCRIPTION
        "Total accumulation time of all users that have connected to the AP."
    ::= { qtechTermServiceStaticWithAPTableEntry 1}
    
qtechAssociaFailTimes   OBJECT-TYPE
    SYNTAX Counter32
    MAX-ACCESS read-only
    STATUS current
    DESCRIPTION
        "Total Associate Fail times for the AP."
    ::= { qtechTermServiceStaticWithAPTableEntry 2}  
--**************************************************
--* apTermServiceStatistics ends * 
--**************************************************

qtechDOT11WIDSParamObjects     OBJECT IDENTIFIER  ::= { qtechFitApMibModule 8 }
--**************************************************
--* apDot11WIDSInfoTable begins
--**************************************************
qtechDot11WIDSInfoTable OBJECT-TYPE
    SYNTAX SEQUENCE OF QtechDot11WIDSInfoEntry
    MAX-ACCESS not-accessible
    STATUS current
    DESCRIPTION
      "The table used to acac the configuration information of ac/ac."
    ::={ qtechDOT11WIDSParamObjects 1 }

qtechDot11WIDSInfoEntry OBJECT-TYPE
    SYNTAX QtechDot11WIDSInfoEntry
    MAX-ACCESS not-accessible
    STATUS current
    DESCRIPTION
      "The entry of the table used to acac the configuration information of ac/ac."
    INDEX { qtechDot11WIDSLocalIndex }
    ::={ qtechDot11WIDSInfoTable 1 }

QtechDot11WIDSInfoEntry ::=
    SEQUENCE {
        qtechDot11WIDSLocalIndex                       INTEGER,
        qtechDot11WIDSpermittedSSID                    DisplayString,
        qtechDot11WIDSpermitBSSID                      MacAddress,
        qtechDot11WIDSDeviceOUI                        DisplayString,
        qtechDot11WIDSSuspiciousAPBSS                  MacAddress,
        qtechDot11WIDSSuspiciousAPCount                INTEGER,
        qtechDot11WIDSMomentFirstTimeDetectedSusAP     TimeTicks,
        qtechDot11WIDSMomentLastTimeDetectedSusAP      TimeTicks,
        qtechDot11WIDSSuspiciousAPSSID                 DisplayString,
        qtechDot11WIDSSuspiciousAPMaxSignalStrength    INTEGER,
        qtechDot11WIDSSuspiciousAPUsingChannel         INTEGER,
        qtechDot11WIDSSuspiciousAPFrameEncrption       INTEGER,
        qtechDot11WIDSSuspiciousAPNeedsDealingTag      TruthValue,
        qtechDot11WIDSSuspiciousAPIgnoredTag           TruthValue,
        qtechDot11WIDSSuspiciousSTAMAC                 MacAddress,
        qtechDot11WIDSAPCountDetectingSuspiciousSTA    INTEGER,
        qtechDot11WIDSMomentFirstTimeDetectedSusSTA    TimeTicks,
        qtechDot11WIDSMomentLastTimeDetectedSusSTA     TimeTicks,
        qtechDot11WIDSBSSIDSuspiciousSTAAccessing      MacAddress,
        qtechDot11WIDSSuspiciousSTAMaxSignalStrength   INTEGER,
        qtechDot11WIDSSuspiciousSTAUsingChannel        INTEGER,
        qtechDot11WIDSSuspiciousSTAWorksInAdhocMode    TruthValue,
        qtechDot11WIDSSuspiciousSTANeedsDealingTag     TruthValue,
        qtechDot11WIDSSuspiciousSTAIgnoredTag          TruthValue,
        qtechDot11WIDSFloodAttackDetectSwitch          TruthValue,
        qtechDot11WIDSSpoofAttackDetectSwitch          TruthValue,
        qtechDot11WIDSWeakIVDetectSwitch               TruthValue,
        qtechDot11WIDSClearIllegalEquipmentHistroyTag  TruthValue,
        qtechDot11WIDSClearAttackDetectionHistroyTag   TruthValue,
        qtechDot11WIDSClearAttackDetectionStaticsTag   TruthValue
    }
    
qtechDot11WIDSLocalIndex  OBJECT-TYPE
    SYNTAX  INTEGER
    MAX-ACCESS  not-accessible
    STATUS      current
    DESCRIPTION
        " The dot11 wids local index num ."
    ::= { qtechDot11WIDSInfoEntry 1 }

qtechDot11WIDSpermittedSSID OBJECT-TYPE
    SYNTAX  DisplayString
    MAX-ACCESS  read-only
    STATUS      current
    DESCRIPTION
        " The ssid permitted to access the service."
    ::= { qtechDot11WIDSInfoEntry 2 }

qtechDot11WIDSpermitBSSID OBJECT-TYPE
    SYNTAX  MacAddress
    MAX-ACCESS  read-only
    STATUS      current
    DESCRIPTION
        " The bssid permitted to access the service."
    ::= { qtechDot11WIDSInfoEntry 3 }

qtechDot11WIDSDeviceOUI OBJECT-TYPE
    SYNTAX  DisplayString
    MAX-ACCESS  read-only
    STATUS      current
    DESCRIPTION
        " The OUI whose device is permitted to provide the service."
    ::= { qtechDot11WIDSInfoEntry 4 }

qtechDot11WIDSSuspiciousAPBSS OBJECT-TYPE
    SYNTAX  MacAddress
    MAX-ACCESS  read-only
    STATUS      current
    DESCRIPTION
        " The BSS MAC of the Suspicious AP."
    ::= { qtechDot11WIDSInfoEntry 5 }

qtechDot11WIDSSuspiciousAPCount OBJECT-TYPE
    SYNTAX  INTEGER
    MAX-ACCESS  read-only
    STATUS      current
    DESCRIPTION
        " The count of the Suspicious AP."
    ::= { qtechDot11WIDSInfoEntry 6 }

qtechDot11WIDSMomentFirstTimeDetectedSusAP OBJECT-TYPE
    SYNTAX  TimeTicks
    MAX-ACCESS  read-only
    STATUS      current
    DESCRIPTION
        " The moment when the AP is detected as the Suspicious AP at the first time."
    ::= { qtechDot11WIDSInfoEntry 7 }

qtechDot11WIDSMomentLastTimeDetectedSusAP OBJECT-TYPE
    SYNTAX  TimeTicks
    MAX-ACCESS  read-only
    STATUS      current
    DESCRIPTION
        " The moment when the AP is detected as the Suspicious AP at the last time."
    ::= { qtechDot11WIDSInfoEntry 8 }

qtechDot11WIDSSuspiciousAPSSID OBJECT-TYPE
    SYNTAX  DisplayString
    MAX-ACCESS  read-only
    STATUS      current
    DESCRIPTION
        " The SSID of the Suspicious AP."
    ::= { qtechDot11WIDSInfoEntry 9 }

qtechDot11WIDSSuspiciousAPMaxSignalStrength OBJECT-TYPE
    SYNTAX  INTEGER
    MAX-ACCESS  read-only
    STATUS      current
    DESCRIPTION
        " The max signal strength of the Suspicious AP."
    ::= { qtechDot11WIDSInfoEntry 10 }

qtechDot11WIDSSuspiciousAPUsingChannel OBJECT-TYPE
    SYNTAX  INTEGER
    MAX-ACCESS  read-only
    STATUS      current
    DESCRIPTION
        " The channel the Suspicious AP is in."
    ::= { qtechDot11WIDSInfoEntry 11 }

qtechDot11WIDSSuspiciousAPFrameEncrption OBJECT-TYPE
    SYNTAX  INTEGER
    MAX-ACCESS  read-only
    STATUS      current
    DESCRIPTION
        " The frame encrption of the Suspicious AP."
    ::= { qtechDot11WIDSInfoEntry 12 }

qtechDot11WIDSSuspiciousAPNeedsDealingTag OBJECT-TYPE
    SYNTAX  TruthValue
    MAX-ACCESS  read-only
    STATUS      current
    DESCRIPTION
        " The tag telling whether it needs to deal the Suspicious AP."
    ::= { qtechDot11WIDSInfoEntry 13 }

qtechDot11WIDSSuspiciousAPIgnoredTag OBJECT-TYPE
    SYNTAX  TruthValue
    MAX-ACCESS  read-only
    STATUS      current
    DESCRIPTION
        " The tag telling whether to ignore the Suspicious AP."
    ::= { qtechDot11WIDSInfoEntry 14 }

qtechDot11WIDSSuspiciousSTAMAC OBJECT-TYPE
    SYNTAX  MacAddress
    MAX-ACCESS  read-only
    STATUS      current
    DESCRIPTION
        " The MAC of the the Suspicious STA."
    ::= { qtechDot11WIDSInfoEntry 15 }

qtechDot11WIDSAPCountDetectingSuspiciousSTA OBJECT-TYPE
    SYNTAX  INTEGER
    MAX-ACCESS  read-only
    STATUS      current
    DESCRIPTION
        " The AP count which is detecting the Suspicious STA."
    ::= { qtechDot11WIDSInfoEntry 16 }

qtechDot11WIDSMomentFirstTimeDetectedSusSTA OBJECT-TYPE
    SYNTAX  TimeTicks
    MAX-ACCESS  read-only
    STATUS      current
    DESCRIPTION
        " The moment when the STA is detected as the Suspicious STA at the first time."
    ::= { qtechDot11WIDSInfoEntry 17 }

qtechDot11WIDSMomentLastTimeDetectedSusSTA OBJECT-TYPE
    SYNTAX  TimeTicks
    MAX-ACCESS  read-only
    STATUS      current
    DESCRIPTION
        " The moment when the AP is detected as the Suspicious AP at the last time."
    ::= { qtechDot11WIDSInfoEntry 18 }

qtechDot11WIDSBSSIDSuspiciousSTAAccessing OBJECT-TYPE
    SYNTAX  MacAddress
    MAX-ACCESS  read-only
    STATUS      current
    DESCRIPTION
        " The BSSID which the the Suspicious STA is trying to access."
    ::= { qtechDot11WIDSInfoEntry 19 }

qtechDot11WIDSSuspiciousSTAMaxSignalStrength OBJECT-TYPE
    SYNTAX  INTEGER
    MAX-ACCESS  read-only
    STATUS      current
    DESCRIPTION
        " The max signal strength of the Suspicious STA."
    ::= { qtechDot11WIDSInfoEntry 20 }

qtechDot11WIDSSuspiciousSTAUsingChannel OBJECT-TYPE
    SYNTAX  INTEGER
    MAX-ACCESS  read-only
    STATUS      current
    DESCRIPTION
        " The channel the Suspicious sta is in."
    ::= { qtechDot11WIDSInfoEntry 21 }

qtechDot11WIDSSuspiciousSTAWorksInAdhocMode OBJECT-TYPE
    SYNTAX  TruthValue
    MAX-ACCESS  read-only
    STATUS      current
    DESCRIPTION
        " The tag whether the Suspicious STA is working in the Ad hoc mode."
    ::= { qtechDot11WIDSInfoEntry 22 }


qtechDot11WIDSSuspiciousSTANeedsDealingTag OBJECT-TYPE
    SYNTAX  TruthValue
    MAX-ACCESS  read-only
    STATUS      current
    DESCRIPTION
        " The tag telling whether it needs to deal the Suspicious STA."
    ::= { qtechDot11WIDSInfoEntry 23 }

qtechDot11WIDSSuspiciousSTAIgnoredTag OBJECT-TYPE
    SYNTAX  TruthValue
    MAX-ACCESS  read-write
    STATUS      current
    DESCRIPTION
        " The tag telling whether to ignore the Suspicious STA."
    ::= { qtechDot11WIDSInfoEntry 24 }

qtechDot11WIDSFloodAttackDetectSwitch OBJECT-TYPE
    SYNTAX  TruthValue
    MAX-ACCESS  read-write
    STATUS      current
    DESCRIPTION
        " This tag tells whether to enable flooding attack detecting."
    ::= { qtechDot11WIDSInfoEntry 25 }

qtechDot11WIDSSpoofAttackDetectSwitch OBJECT-TYPE
    SYNTAX  TruthValue
    MAX-ACCESS  read-write
    STATUS      current
    DESCRIPTION
        " This tag tells whether to enable spoof attack detecting."
    ::= { qtechDot11WIDSInfoEntry 26 }

qtechDot11WIDSWeakIVDetectSwitch OBJECT-TYPE
    SYNTAX  TruthValue
    MAX-ACCESS  read-write
    STATUS      current
    DESCRIPTION
        "This tag tells whether to enable weak IV detecting."
    ::= { qtechDot11WIDSInfoEntry 27 }

qtechDot11WIDSClearIllegalEquipmentHistroyTag OBJECT-TYPE
    SYNTAX  TruthValue
    MAX-ACCESS  read-write
    STATUS      current
    DESCRIPTION
        " This tag tells whether to clear the illegal equipment history."
    ::= { qtechDot11WIDSInfoEntry 28 }

qtechDot11WIDSClearAttackDetectionHistroyTag OBJECT-TYPE
    SYNTAX  TruthValue
    MAX-ACCESS  read-write
    STATUS      current
    DESCRIPTION
        " This tag tells whether to clear the attack detection history."
    ::= { qtechDot11WIDSInfoEntry 29 }

qtechDot11WIDSClearAttackDetectionStaticsTag OBJECT-TYPE
    SYNTAX  TruthValue
    MAX-ACCESS  read-write
    STATUS      current
    DESCRIPTION
        " This tag tells whether to clear the attack detection statics."
    ::= { qtechDot11WIDSInfoEntry 30 }

--**************************************************
--* apDot11WIDSInfoTable ends
--**************************************************
--**************************************************
--* apDot11LawlessApInfoTable   starts
--**************************************************
qtechDot11LawlessApInfoTable OBJECT-TYPE
    SYNTAX SEQUENCE OF QtechDot11LawlessApInfoTableEntry
    MAX-ACCESS not-accessible
    STATUS current
    DESCRIPTION
      "The table used to display Lawless AP info t"
    ::={ qtechDOT11WIDSParamObjects 2 }

qtechDot11LawlessApInfoTableEntry OBJECT-TYPE
    SYNTAX QtechDot11LawlessApInfoTableEntry
    MAX-ACCESS not-accessible
    STATUS current
    DESCRIPTION
      "The table used to display Lawless AP info "
    INDEX { qtechLawlessAPIndex }
    ::={ qtechDot11LawlessApInfoTable 1 }

QtechDot11LawlessApInfoTableEntry ::=
    SEQUENCE {
          qtechLawlessAPIndex               INTEGER,   
          qtechLawlessAPSignalStrength      Integer32,
          qtechLawlessAPSignalSNR           Integer32,
          qtechLawlessAPChannelNum          INTEGER,
          qtechLawlessAPSSIDName            DisplayString,   
          qtechLawlessAPMacaddr             MacAddress,
          qtechLawlessAPTreatMode           INTEGER
                        
    }
    
qtechLawlessAPIndex     OBJECT-TYPE
    SYNTAX  INTEGER
    MAX-ACCESS  not-accessible
    STATUS      current
    DESCRIPTION
        " This is Lawless AP local Index number ."
    ::= { qtechDot11LawlessApInfoTableEntry 1 }
    
qtechLawlessAPSignalStrength    OBJECT-TYPE
    SYNTAX  Integer32
    MAX-ACCESS  read-only
    STATUS      current
    DESCRIPTION
        " This is Lawless AP signal Strength ."
    ::= { qtechDot11LawlessApInfoTableEntry 2 } 
    
qtechLawlessAPSignalSNR   OBJECT-TYPE
    SYNTAX  Integer32
    MAX-ACCESS  read-only
    STATUS      current
    DESCRIPTION
        " This is Lawless AP signal SNR ."
    ::= { qtechDot11LawlessApInfoTableEntry 3 }   
    
qtechLawlessAPChannelNum    OBJECT-TYPE
    SYNTAX  INTEGER
    MAX-ACCESS  read-only
    STATUS      current
    DESCRIPTION
        " This is Lawless AP Channel Number ."
    ::= { qtechDot11LawlessApInfoTableEntry 4 }   
    
qtechLawlessAPSSIDName  OBJECT-TYPE
    SYNTAX  DisplayString
    MAX-ACCESS  read-only
    STATUS      current
    DESCRIPTION
        " This is Lawless AP SSID Name display ."
    ::= { qtechDot11LawlessApInfoTableEntry 5 }  
    
qtechLawlessAPMacaddr  OBJECT-TYPE
    SYNTAX  MacAddress
    MAX-ACCESS  read-only
    STATUS      current
    DESCRIPTION
        " This is Lawless AP BSSID <MAC_ADDRESS> ."
    ::= { qtechDot11LawlessApInfoTableEntry 6 }     

qtechLawlessAPTreatMode   OBJECT-TYPE
    SYNTAX  INTEGER 
    MAX-ACCESS  read-only
    STATUS      current
    DESCRIPTION
        " This is Lawless AP Treat mode detail 1: DosAttack state
          2: disturb User connect to lawless AP ."
    ::= { qtechDot11LawlessApInfoTableEntry 7 }     
         
--**************************************************
--* apLawlessApInfoTable   ends
--**************************************************

--**************************************************
--* apDot11UndefinedApInfoTable   starts
--**************************************************
qtechDot11UndefinedApInfoTable OBJECT-TYPE
    SYNTAX SEQUENCE OF QtechDot11UndefinedApInfoTableEntry
    MAX-ACCESS not-accessible
    STATUS current
    DESCRIPTION
      "The table used to display Undefined AP info t"
    ::={ qtechDOT11WIDSParamObjects 3 }

qtechDot11UndefinedApInfoTableEntry OBJECT-TYPE
    SYNTAX QtechDot11UndefinedApInfoTableEntry
    MAX-ACCESS not-accessible
    STATUS current
    DESCRIPTION
      "The table used to display Undefined AP info "
    INDEX { qtechUndefinedAPIndex }
    ::={ qtechDot11UndefinedApInfoTable 1 }

QtechDot11UndefinedApInfoTableEntry ::=
    SEQUENCE {
          qtechUndefinedAPIndex               INTEGER,   
          qtechUndefinedAPSignalStrength      Integer32,
          qtechUndefinedAPSignalSNR           Integer32,
          qtechUndefinedAPChannelNum          INTEGER,
          qtechUndefinedAPSSIDName            DisplayString,   
          qtechUndefinedAPMacaddr             MacAddress,
          qtechUndefinedAPTreatMode           INTEGER
                        
    }
    
qtechUndefinedAPIndex     OBJECT-TYPE
    SYNTAX  INTEGER
    MAX-ACCESS  not-accessible
    STATUS      current
    DESCRIPTION
        " This is Undefined AP local Index number ."
    ::= { qtechDot11UndefinedApInfoTableEntry 1 }
    
qtechUndefinedAPSignalStrength    OBJECT-TYPE
    SYNTAX  Integer32
    MAX-ACCESS  read-only
    STATUS      current
    DESCRIPTION
        " This is Undefined AP signal Strength ."
    ::= { qtechDot11UndefinedApInfoTableEntry 2 } 
    
qtechUndefinedAPSignalSNR   OBJECT-TYPE
    SYNTAX  Integer32
    MAX-ACCESS  read-only
    STATUS      current
    DESCRIPTION
        " This is Undefined AP signal SNR ."
    ::= { qtechDot11UndefinedApInfoTableEntry 3 }   
    
qtechUndefinedAPChannelNum    OBJECT-TYPE
    SYNTAX  INTEGER
    MAX-ACCESS  read-only
    STATUS      current
    DESCRIPTION
        " This is Undefined AP Channel Number ."
    ::= { qtechDot11UndefinedApInfoTableEntry 4 }   
    
qtechUndefinedAPSSIDName  OBJECT-TYPE
    SYNTAX  DisplayString
    MAX-ACCESS  read-only
    STATUS      current
    DESCRIPTION
        " This is Undefined AP SSID Name display ."
    ::= { qtechDot11UndefinedApInfoTableEntry 5 }  
    
qtechUndefinedAPMacaddr  OBJECT-TYPE
    SYNTAX  MacAddress
    MAX-ACCESS  read-only
    STATUS      current
    DESCRIPTION
        " This is Undefined AP BSSID <MAC_ADDRESS> ."
    ::= { qtechDot11UndefinedApInfoTableEntry 6 }     

qtechUndefinedAPTreatMode   OBJECT-TYPE
    SYNTAX  INTEGER 
    MAX-ACCESS  read-only
    STATUS      current
    DESCRIPTION
        " This is Undefined AP Treat mode detail 1: DosAttack state
          2: disturb User connect to lawless AP ."
    ::= { qtechDot11UndefinedApInfoTableEntry 7 }     
         
--**************************************************
--* qtechUndefinedApInfoTable   ends
--**************************************************

--**************************************************
--* apDot11LegalityApInfoTable   starts
--**************************************************
qtechDot11LegalityApInfoTable OBJECT-TYPE
    SYNTAX SEQUENCE OF QtechDot11LegalityApInfoTableEntry
    MAX-ACCESS not-accessible
    STATUS current
    DESCRIPTION
      "The table used to display Legality AP info t"
    ::={ qtechDOT11WIDSParamObjects 4 }

qtechDot11LegalityApInfoTableEntry OBJECT-TYPE
    SYNTAX QtechDot11LegalityApInfoTableEntry
    MAX-ACCESS not-accessible
    STATUS current
    DESCRIPTION
      "The table used to display Legality AP info "
    INDEX { qtechLegalityAPIndex }
    ::={ qtechDot11LegalityApInfoTable 1 }

QtechDot11LegalityApInfoTableEntry ::=
    SEQUENCE {
          qtechLegalityAPIndex               INTEGER,   
          qtechLegalityAPSignalStrength      Integer32,
          qtechLegalityAPSignalSNR           Integer32,
          qtechLegalityAPChannelNum          INTEGER,
          qtechLegalityAPSSIDName            DisplayString,   
          qtechLegalityAPMacaddr             MacAddress,
          qtechLegalityAPTreatMode           INTEGER
                        
    }
    
qtechLegalityAPIndex     OBJECT-TYPE
    SYNTAX  INTEGER
    MAX-ACCESS  not-accessible
    STATUS      current
    DESCRIPTION
        " This is Legality AP local Index number ."
    ::= { qtechDot11LegalityApInfoTableEntry 1 }
    
qtechLegalityAPSignalStrength    OBJECT-TYPE
    SYNTAX  Integer32
    MAX-ACCESS  read-only
    STATUS      current
    DESCRIPTION
        " This is Legality AP signal Strength ."
    ::= { qtechDot11LegalityApInfoTableEntry 2 } 
    
qtechLegalityAPSignalSNR   OBJECT-TYPE
    SYNTAX  Integer32
    MAX-ACCESS  read-only
    STATUS      current
    DESCRIPTION
        " This is Legality AP signal SNR ."
    ::= { qtechDot11LegalityApInfoTableEntry 3 }   
    
qtechLegalityAPChannelNum    OBJECT-TYPE
    SYNTAX  INTEGER
    MAX-ACCESS  read-only
    STATUS      current
    DESCRIPTION
        " This is Legality AP Channel Number ."
    ::= { qtechDot11LegalityApInfoTableEntry 4 }   
    
qtechLegalityAPSSIDName  OBJECT-TYPE
    SYNTAX  DisplayString
    MAX-ACCESS  read-only
    STATUS      current
    DESCRIPTION
        " This is Legality AP SSID Name display ."
    ::= { qtechDot11LegalityApInfoTableEntry 5 }  
    
qtechLegalityAPMacaddr  OBJECT-TYPE
    SYNTAX  MacAddress
    MAX-ACCESS  read-only
    STATUS      current
    DESCRIPTION
        " This is Legality AP BSSID <MAC_ADDRESS> ."
    ::= { qtechDot11LegalityApInfoTableEntry 6 }     

qtechLegalityAPTreatMode   OBJECT-TYPE
    SYNTAX  INTEGER 
    MAX-ACCESS  read-only
    STATUS      current
    DESCRIPTION
        " This is Legality AP Treat mode detail 1: DosAttack state
          2: disturb User connect to lawless AP ."
    ::= { qtechDot11LegalityApInfoTableEntry 7 }     
         
--**************************************************
--* qtechLegalityApInfoTable   ends
--**************************************************

--**********************************************
--*  apSSIDListCreateTable starts
--**********************************************
--apSSIDConfigObjects              OBJECT IDENTIFIER  ::= { qtechFitApMibModule 9 }   please see china mobile node ApSSIDListCreateTableEntry
--apSSIDListCreateTable OBJECT-TYPE
--    SYNTAX SEQUENCE OF ApSSIDListCreateTableEntry
--    MAX-ACCESS not-accessible
--    STATUS current
--    DESCRIPTION
--      "The SSID list manegment for ap."
--    ::={ apSSIDConfigObjects 1 }

--apSSIDListCreateTableEntry OBJECT-TYPE
--    SYNTAX  ApSSIDListCreateTableEntry
--    MAX-ACCESS  not-accessible
--    STATUS  current
--    DESCRIPTION
--        "The SSID list manegment for ap"
--    INDEX   {qtechgWlanId} 
--    ::= { apSSIDListCreateTable 1 }
    
--ApSSIDListCreateTableEntry ::=
--    SEQUENCE {
--         apListBSSIDAddr   MacAddress,
--         apSSIDRadioNum    INTEGER,
--         apSSIDApMACaddr   MacAddress
--    }
--**********************************************
--*apSSIDListCreateTable ends
--**********************************************
END
