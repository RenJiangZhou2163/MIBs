-- *****************************************************************
-- QTECH-SMI.mib: QTECH-SMI
--                Qtech Enterprise Structure of Management Information
--
-- March 2002, Wuzg
-- 
-- Copyright (c) 2002 by Qtech Networks Co.,Ltd.
-- All rights reserved.
-- 
-- *****************************************************************
--

QTECH-SMI DEFINITIONS ::= BEGIN

IMPORTS
        MODULE-IDENTITY,
        OBJECT-IDENTITY,
        enterprises
                FROM SNMPv2-SMI;

-- Qtech Snmpagent Enterprise Specific Objects
   qtech          OBJECT IDENTIFIER ::= { enterprises 27514 }

   products        OBJECT IDENTIFIER ::= { qtech 1 }

   switch          OBJECT IDENTIFIER ::= { products 1 }
   
switchMib MODULE-IDENTITY
        LAST-UPDATED "200203190000Z"
        ORGANIZATION "Qtech Networks Co.,Ltd."
        CONTACT-INFO
                " 
                Tel: 4008-111-000 

                E-mail: service@qtech.com.cn"
        DESCRIPTION
                "The Structure of Management Information for the
                 Qtech enterprise."
        REVISION      "200203190000Z"
        DESCRIPTION
                "Initial version of this MIB module."
        ::= { switch 10 }        

qtechSwitchProducts OBJECT-IDENTITY
        STATUS  current
        DESCRIPTION
                "qtechSwitchProducts is the root OBJECT IDENTIFIER from
                which sysObjectID values are assigned for switch.  Actual
                values are defined in QTECH-PRODUCTS-MIB."
        ::= { switchMib 1 }

qtechMgmt OBJECT-IDENTITY
        STATUS  current
        DESCRIPTION
                "qtechMgmt is the main subtree for those functional mib."
        ::= { switchMib 2 }

qtechAgentCapability OBJECT-IDENTITY
        STATUS  current
        DESCRIPTION
                "qtechAgentCapability provides a root object identifier
                from which AGENT-CAPABILITIES values may be assigned."
        ::= { switchMib 3 }

qtechModules OBJECT-IDENTITY
        STATUS  current
        DESCRIPTION
                "qtechModules provides a root object identifier
                from which MODULE-IDENTITY values may be assigned."
        ::= { switchMib 4 }
        
qtechExperiment OBJECT-IDENTITY
        STATUS  current
        DESCRIPTION
                "qtechExperiment provides a root object identifier
                from which experimental mibs may be temporarily
                based.  mibs are typicially based here if they
                fall in one of two categories
                1) are IETF work-in-process mibs which have not
                been assigned a permanent object identifier by
                the IANA.
                2) are qtech work-in-process which has not been
                assigned a permanent object identifier by the
                qtech assigned number authority, typicially because
                the mib is not ready for deployment.

                NOTE WELL:  support for mibs in the qtechExperiment
                subtree will be deleted when a permanent object
                identifier assignment is made."
        ::= { switchMib 5 }
 
END
