-- *******************************************************************
-- QTECH-WLAN-FAT-AP-IN-MIB.mib : Qtech MIB
-- February 2010, ruanyucheng
--
-- Copyright (c) 2010 by Qtech Networks Co.,Ltd.
-- All rights reserved.
-- *******************************************************************
QTECH-WLAN-FAT-AP-IN-MIB DEFINITIONS ::= BEGIN
    IMPORTS
        MODULE-IDENTITY,
        OBJECT-TYPE,
        Integer32,
        IpAddress,
        Unsigned32,
        TimeTicks
            FROM SNMPv2-SMI
        TruthValue,
        DisplayString,
        MacAddress,
        RowStatus
            FROM SNMPv2-TC
        Gauge
            FROM RFC1155-SMI
        MODULE-COMPLIANCE,
        NOTIFICATION-GROUP,
        OBJECT-GROUP
            FROM SNMPv2-CONF
        qtechApgWlanId
            FROM QTECH-AC-MGMT-MIB
        ifIndex
            FROM RFC1213-MIB
        qtechMgmt
            FROM QTECH-SMI;
--*******************************************
--* module definition
--*******************************************
qtechStandardmibmodule MODULE-IDENTITY
    LAST-UPDATED    "201002260000Z"
    ORGANIZATION
        "Qtech Networks Co.,Ltd."
    CONTACT-INFO
        "Tel: 4008-111-000
           E-mail: service@qtech.com.cn "

    DESCRIPTION
       "
       Wlan software private MIB for Qtech SNC according to the China
       Mobile standard. This is device manage MIB.
       "
    REVISION      "201002280000Z"
    DESCRIPTION
       "Initial version of this MIB module."

    ::= { qtechMgmt  82 }
    
    
                                                                                      
qtechStandardTraps               OBJECT IDENTIFIER  ::= { qtechStandardmibmodule 0 }
qtechConfigInfoObjects           OBJECT IDENTIFIER  ::= { qtechStandardmibmodule 1 }
qtechPerformanceStatObjects      OBJECT IDENTIFIER  ::= { qtechStandardmibmodule 2 }

qtechSysInfoConfig               OBJECT IDENTIFIER  ::= { qtechConfigInfoObjects 1 }
qtechRadioInfoConfig             OBJECT IDENTIFIER  ::= { qtechConfigInfoObjects 2 }
qtechWapiConfig                  OBJECT IDENTIFIER  ::= { qtechConfigInfoObjects 3 }
qtechAdminInfoConfig             OBJECT IDENTIFIER  ::= { qtechConfigInfoObjects 4 }
qtechPollTimeConfig              OBJECT IDENTIFIER  ::= { qtechConfigInfoObjects 5 }

qtechAirIfServiceStat            OBJECT IDENTIFIER  ::= { qtechPerformanceStatObjects 1 }
qtechTermServiceStat             OBJECT IDENTIFIER  ::= { qtechPerformanceStatObjects 2 }


--**************************************************
--* Traps begin here
--**************************************************

qtechRadioPortTrap NOTIFICATION-TYPE
    STATUS  current
    DESCRIPTION
            " Radio port trap."
    ::= { qtechStandardTraps 1 }
    
--**************************************************
--* Traps end here
--**************************************************

--**************************************************
--* qtechSysInfoConfig begins here
--**************************************************
     
qtechDomain OBJECT-TYPE
    SYNTAX DisplayString
    MAX-ACCESS read-only
    STATUS current
    DESCRIPTION
        "The domain of the AP."
    ::= { qtechSysInfoConfig 1}  
    
qtechLayer2Isolate OBJECT-TYPE
    SYNTAX INTEGER
    MAX-ACCESS read-write
    STATUS current
    DESCRIPTION
        "Is layer 2 isolation opened."
    ::= { qtechSysInfoConfig 2} 
    
qtechDosAttackProtect OBJECT-TYPE
    SYNTAX INTEGER
    MAX-ACCESS read-write
    STATUS current
    DESCRIPTION
        "Is DOS attack protected."
    ::= { qtechSysInfoConfig 3} 
    
--**************************************************
--* qtechVlanConfigTable begins
--**************************************************
qtechVlanConfigTable OBJECT-TYPE
    SYNTAX SEQUENCE OF QtechVlanConfigEntry
    MAX-ACCESS not-accessible
    STATUS current
    DESCRIPTION
        "Configuration of vlan"
    ::= { qtechSysInfoConfig 4 }

qtechVlanConfigEntry OBJECT-TYPE
    SYNTAX QtechVlanConfigEntry
    MAX-ACCESS not-accessible
    STATUS current
    DESCRIPTION
        "The entry of apVlanConfigTable."
    INDEX
    { qtechWlanId}
    ::= { qtechVlanConfigTable 1 }

QtechVlanConfigEntry ::=
    SEQUENCE {
        qtechVlanId                        INTEGER,
        qtechSSID													DisplayString
        } 
  
qtechVlanId OBJECT-TYPE               
    SYNTAX INTEGER               
    MAX-ACCESS read-create             
    STATUS current               
    DESCRIPTION               
        "Vlan ID."               
    ::= { qtechVlanConfigEntry 1 } 
    
qtechSSID OBJECT-TYPE               
    SYNTAX DisplayString               
    MAX-ACCESS read-create             
    STATUS current               
    DESCRIPTION               
        "SSID."               
    ::= { qtechVlanConfigEntry 2 } 


--**************************************************
--* qtechVlanConfigTable ends
--************************************************** 


--**************************************************
--* qtechSysInfoConfig ends here
--**************************************************

--**************************************************
--* qtechRadioInfoConfig begins here
--**************************************************


--**************************************************
--* qtechRadioConfigTable begins
--**************************************************
qtechRadioConfigTable OBJECT-TYPE
    SYNTAX SEQUENCE OF QtechRadioConfigEntry
    MAX-ACCESS not-accessible
    STATUS current
    DESCRIPTION
        "Configuration of Radio"
    ::= { qtechRadioInfoConfig 1 }

qtechRadioConfigEntry OBJECT-TYPE
    SYNTAX QtechRadioConfigEntry
    MAX-ACCESS not-accessible
    STATUS current
    DESCRIPTION
        "The entry of apRadioConfigTable."
    INDEX
    { ifIndex }
    ::= { qtechRadioConfigTable 1 }

QtechRadioConfigEntry ::=
    SEQUENCE {
	qtechSSIDNum  		 INTEGER,
	qtechRadioSecurityMch   INTEGER ,      
	qtechRadioSecurityParam DisplayString,          
	qtechRadioQos           INTEGER,
	qtechRtsCtsThreshold    INTEGER,        
        qtechMaxUserPermit 	 INTEGER,	            
	qtechUserNumOnLine      INTEGER,
	qtechAirInterfaceType 	 INTEGER,            
        qtechChannelMode        INTEGER,
    	qtechCurrentChannel	 INTEGER,
    	qtechSNR	 	 INTEGER,
    	qtechHoppingTimes	 INTEGER,
        qtechHopDetectItvTime 	 INTEGER,
        qtechPowerMgr     	 INTEGER,
    	qtechTxPower		 INTEGER
        } 
qtechSSIDNum OBJECT-TYPE               
    SYNTAX INTEGER               
    MAX-ACCESS read-only              
    STATUS current               
    DESCRIPTION               
        "SSID number."               
    ::= { qtechRadioConfigEntry 1 }
    
qtechRadioSecurityMch OBJECT-TYPE               
    SYNTAX INTEGER               
    MAX-ACCESS read-write              
    STATUS current               
    DESCRIPTION               
        "Radio security mechanism of the AP."               
    ::= { qtechRadioConfigEntry 2 }

qtechRadioSecurityParam OBJECT-TYPE               
    SYNTAX DisplayString               
    MAX-ACCESS read-write              
    STATUS current               
    DESCRIPTION               
        "Radio security parameter of the AP."               
    ::= { qtechRadioConfigEntry 3 }

qtechRadioQos OBJECT-TYPE               
    SYNTAX INTEGER               
    MAX-ACCESS read-write              
    STATUS current               
    DESCRIPTION               
        "Whether to activate VMM."               
    ::= { qtechRadioConfigEntry 4 }
    
qtechRtsCtsThreshold OBJECT-TYPE               
    SYNTAX INTEGER               
    MAX-ACCESS read-write              
    STATUS current               
    DESCRIPTION               
        "RTS/CTS threshold"               
    ::= { qtechRadioConfigEntry 5 }
    
qtechMaxUserPermit OBJECT-TYPE               
    SYNTAX INTEGER               
    MAX-ACCESS read-write              
    STATUS current               
    DESCRIPTION               
        "Max user number permited"               
    ::= { qtechRadioConfigEntry 6 }

qtechUserNumOnLine OBJECT-TYPE               
    SYNTAX INTEGER               
    MAX-ACCESS read-only              
    STATUS current               
    DESCRIPTION               
        "User number on line"               
    ::= { qtechRadioConfigEntry 7 }
    
qtechAirInterfaceType OBJECT-TYPE               
    SYNTAX INTEGER               
    MAX-ACCESS read-write              
    STATUS current               
    DESCRIPTION               
        "Air interface type"               
    ::= { qtechRadioConfigEntry 8 }
    
qtechChannelMode OBJECT-TYPE               
    SYNTAX INTEGER               
    MAX-ACCESS read-write              
    STATUS current               
    DESCRIPTION               
        "Channel mode of the AP."               
    ::= { qtechRadioConfigEntry 9 }
    
qtechCurrentChannel OBJECT-TYPE               
    SYNTAX INTEGER               
    MAX-ACCESS read-write              
    STATUS current               
    DESCRIPTION               
        "Current channel."               
    ::= { qtechRadioConfigEntry 10 }
    
qtechSNR OBJECT-TYPE               
    SYNTAX INTEGER               
    MAX-ACCESS read-only              
    STATUS current               
    DESCRIPTION               
        "Signal noise ratio."               
    ::= { qtechRadioConfigEntry 11 }

qtechHoppingTimes OBJECT-TYPE               
    SYNTAX INTEGER               
    MAX-ACCESS read-only              
    STATUS current               
    DESCRIPTION               
        "Frequency hopping times"               
    ::= { qtechRadioConfigEntry 12 }

qtechHopDetectItvTime OBJECT-TYPE               
    SYNTAX INTEGER               
    MAX-ACCESS read-write              
    STATUS current               
    DESCRIPTION               
        "Inteval time of hopping detection"               
    ::= { qtechRadioConfigEntry 13 }
    
qtechPowerMgr OBJECT-TYPE               
    SYNTAX INTEGER               
    MAX-ACCESS read-write              
    STATUS current               
    DESCRIPTION               
        "Power management of the AP"               
    ::= { qtechRadioConfigEntry 14 }
    
qtechTxPower OBJECT-TYPE               
    SYNTAX INTEGER               
    MAX-ACCESS read-only              
    STATUS current               
    DESCRIPTION               
        "Current transmit power of the AP"               
    ::= { qtechRadioConfigEntry 15 }  


--**************************************************
--* qtechRadioConfigTable ends
--************************************************** 

 
--**************************************************
--* qtechRadioInfoConfig ends here
--**************************************************


--**************************************************
--* qtechWapiConfig begins here
--**************************************************


--**************************************************
--* qtechWapiConfigTable begins
--**************************************************

qtechWapiConfigTable OBJECT-TYPE
    SYNTAX SEQUENCE OF QtechWapiConfigEntry
    MAX-ACCESS not-accessible
    STATUS current
    DESCRIPTION
        "The table describe the wapi cofiguration the AP."
    ::= { qtechWapiConfig 1	 }

qtechWapiConfigEntry OBJECT-TYPE
    SYNTAX QtechWapiConfigEntry
    MAX-ACCESS not-accessible
    STATUS current
    DESCRIPTION
        "The entry of qtechWapiConfigTable."
    INDEX
    { qtechWlanId }
    ::= { qtechWapiConfigTable 1 }


QtechWapiConfigEntry ::=
    SEQUENCE {
        qtechWlanId								INTEGER,
        qtechTrustASCfg            INTEGER,
        qtechCertType              INTEGER,
        qtechCertState							INTEGER,
        qtechCertSetup             INTEGER
    } 

qtechWlanId OBJECT-TYPE               
    SYNTAX INTEGER               
    MAX-ACCESS read-only               
    STATUS current               
    DESCRIPTION               
        "Index of the table."               
    ::= { qtechWapiConfigEntry 1 } 
  
qtechTrustASCfg OBJECT-TYPE               
    SYNTAX INTEGER               
    MAX-ACCESS read-write               
    STATUS current               
    DESCRIPTION               
        "AS config trust by AP."               
    ::= { qtechWapiConfigEntry 2 } 

qtechCertType OBJECT-TYPE               
    SYNTAX INTEGER               
    MAX-ACCESS read-only               
    STATUS current               
    DESCRIPTION               
        "Certificate type."               
    ::= { qtechWapiConfigEntry 3 } 
    
qtechCertState OBJECT-TYPE               
    SYNTAX INTEGER               
    MAX-ACCESS read-only               
    STATUS current               
    DESCRIPTION               
        "Certificate state."               
    ::= { qtechWapiConfigEntry 4 } 

qtechCertSetup OBJECT-TYPE               
    SYNTAX INTEGER               
    MAX-ACCESS read-write               
    STATUS current               
    DESCRIPTION               
        "Certificate setup."               
    ::= { qtechWapiConfigEntry 5 } 

--**************************************************
--* qtechWapiConfigTable ends
--**************************************************

--**************************************************
--* qtechWapiConfig ends here
--**************************************************


--**************************************************
--*qtechAdminInfoConfig
--**************************************************
qtechAdminName OBJECT-TYPE 
    SYNTAX DisplayString  (SIZE(1..32))
    MAX-ACCESS read-write
    STATUS current
				DESCRIPTION
           "The name of the administrator."
		::= { qtechAdminInfoConfig 1 }
				
qtechAdminPwd OBJECT-TYPE
    SYNTAX DisplayString  (SIZE(1..32))
    MAX-ACCESS read-write
    STATUS current
				DESCRIPTION
           "The password of the administrator."
		::= { qtechAdminInfoConfig 2 }


--**************************************************
--*qtechPollTimeConfig
--**************************************************
qtechPollTimeOfLast OBJECT-TYPE
    SYNTAX TimeTicks
    MAX-ACCESS read-only
    STATUS current
				DESCRIPTION
           "The last time of administrator 
            poll the devices."
		::= { qtechPollTimeConfig 1 }


--**************************************************
--* qtechAirIfServiceStat begins here
--**************************************************
qtechUplinkTotalDataFrameNum OBJECT-TYPE
    SYNTAX INTEGER
    MAX-ACCESS read-only
    STATUS current
    DESCRIPTION
        "Total uplink data frame number of channel during AP running time."
    ::= { qtechAirIfServiceStat 1} 

qtechDownlinkTotalDataFrameNum OBJECT-TYPE
    SYNTAX INTEGER
    MAX-ACCESS read-only
    STATUS current
    DESCRIPTION
        "Total downlink data frame number of channel during AP running time."
    ::= { qtechAirIfServiceStat 2} 

qtechDownlinkTotalLostDataFrameNum OBJECT-TYPE
    SYNTAX INTEGER
    MAX-ACCESS read-only
    STATUS current
    DESCRIPTION
        "Total downlink lost data frame number of channel during AP running time."
    ::= { qtechAirIfServiceStat 3} 
    
          
                
qtechTotalSignalFrameNum OBJECT-TYPE                
    SYNTAX INTEGER
    MAX-ACCESS read-only
    STATUS current
    DESCRIPTION
        "Total signal frame number of the AP."
    ::= { qtechAirIfServiceStat 4}
    
qtechCorrectPkgByteRxByMAC OBJECT-TYPE
    SYNTAX INTEGER
    MAX-ACCESS read-only
    STATUS current
    DESCRIPTION
        "Total correct package byte number receive by MAC layer."
    ::= { qtechAirIfServiceStat 5}
    
qtechPkgByteTxByMAC OBJECT-TYPE
    SYNTAX INTEGER
    MAX-ACCESS read-only
    STATUS current
    DESCRIPTION
        "Total package byte number  transmit by MAC layer."
    ::= { qtechAirIfServiceStat 6}
    
qtechUplinkPortFlow OBJECT-TYPE
    SYNTAX INTEGER
    MAX-ACCESS read-only
    STATUS current
    DESCRIPTION
        "Radio uplink port flow of the AP."
    ::= { qtechAirIfServiceStat 7}    
    
    
qtechDownlinkPortFlow OBJECT-TYPE
    SYNTAX INTEGER
    MAX-ACCESS read-only
    STATUS current
    DESCRIPTION
        "Radio downlink port flow of the AP."
    ::= { qtechAirIfServiceStat 8}
    
    
--**************************************************
--* qtechAirIfServiceStat ends here
--**************************************************


--**************************************************
--* qtechTermServiceStat begins here
--**************************************************

qtechTotalUserNum OBJECT-TYPE
    SYNTAX INTEGER
    MAX-ACCESS read-only
    STATUS current
    DESCRIPTION
        "Total user number that have connected to the AP."
    ::= { qtechTermServiceStat 1}


qtechUserAccumulateTime OBJECT-TYPE
    SYNTAX INTEGER
    MAX-ACCESS read-only
    STATUS current
    DESCRIPTION
        "Total accumulation time of all users that have connected to the AP."
    ::= { qtechTermServiceStat 2}
    

    
--**************************************************
--* qtechTermServiceStatSSIDTable begins
--**************************************************

qtechTermServiceStatSSIDTable OBJECT-TYPE
    SYNTAX SEQUENCE OF QtechTermServiceStatSSIDEntry
    MAX-ACCESS not-accessible
    STATUS current
    DESCRIPTION
        "Statistic of air terminal service by SSID."
    ::= { qtechTermServiceStat 34	 }

qtechTermServiceStatSSIDEntry OBJECT-TYPE
    SYNTAX QtechTermServiceStatSSIDEntry
    MAX-ACCESS not-accessible
    STATUS current
    DESCRIPTION
        "The entry of apTermServiceStatSSIDTable."
    INDEX
    { qtechWlanId }
    ::= { qtechTermServiceStatSSIDTable 1 }

QtechTermServiceStatSSIDEntry ::=
    SEQUENCE {
        qtechCorrectPkgByteRxByMACBySSID                       INTEGER,
        qtechPkgByteTxByMACBySSID    						              INTEGER,
        qtechAirIfResUsageRatio									              INTEGER,        
        qtechTotalAssociationUserNum                           INTEGER,
        qtechOnlineUserNum												              INTEGER,
        qtechUserReqAccessTimes									              INTEGER,
        qtechResponseReqAccessTimes							              INTEGER,
        qtechSuccessAccessTimes									              INTEGER,
				qtechIneffiLinkVerifyFailTime													INTEGER,
				qtechTimeoutLinkVerifyFailTime	                        INTEGER,
				qtechInefficiencyLinkVerifyFailTime                    INTEGER,
				qtechOtherReasonLinkVerifyFailTime                     INTEGER,
				qtechIneffiAssociationFailTime                         INTEGER,
				qtechTimeoutAssociationFailTime                        INTEGER,
				qtechInefficiencyAssociationFailTime                   INTEGER,
				qtechOtherReasonAssociationFailTime                    INTEGER,
				qtechTotalReassociationAtmptTimes                      INTEGER,
				qtechTotalReassociationSuccessTimes                    INTEGER,
				qtechIneffiReassociationFailTime                       INTEGER,
				qtechTimeoutReassociationFailTime                      INTEGER,
				qtechInefficiencyReassociationFailTime                 INTEGER,
				qtechOtherReasonReassociationFailTime                  INTEGER,
				qtechTotalIdentificationAtmptTimes                     INTEGER,
				qtechTotalIdentificationSuccessTimes                   INTEGER,
				qtechPwdErrorIdentifyFailTime                          INTEGER,
				qtechIneffiIdentificationFailTime                      INTEGER,
				qtechTimeoutIdentificationFailTime                     INTEGER,
				qtechInefficiencyIdentificationFailTime                INTEGER,
				qtechOtherReasonIdentificationFailTime                 INTEGER,
				qtechTotalRemoveLinkVerifyFailTimes                    INTEGER,
				qtechLeaveAPCoverageRemoveLinkVerifyFailTimes          INTEGER,
				qtechInefficiencyRemoveLinkVerifyFailTime              INTEGER,
				qtechLinkVerifyFailRemoveLinkVerifyFailTime            INTEGER,
				qtechOtherReasonRemoveLinkVerifyFailTime               INTEGER,
				qtechTotalRemoveLinkAssociationTimes                   INTEGER,
				qtechLeaveAPCoverageRemoveAssociationFailTimes         INTEGER,
				qtechInefficiencyRemoveAssociationFailTime             INTEGER,
				qtechAssociationFailRemoveAssociationFailTime          INTEGER,
				qtechOtherReasonRemoveAssociationFailTime              INTEGER
    } 
    
qtechCorrectPkgByteRxByMACBySSID OBJECT-TYPE
    SYNTAX INTEGER
    MAX-ACCESS read-only
    STATUS current
    DESCRIPTION
        "Total correct package byte number receive by MAC layer."
    ::= { qtechTermServiceStatSSIDEntry 1}
    
qtechPkgByteTxByMACBySSID OBJECT-TYPE
    SYNTAX INTEGER
    MAX-ACCESS read-only
    STATUS current
    DESCRIPTION
        "Total package byte number  transmit by MAC layer."
    ::= { qtechTermServiceStatSSIDEntry 2}
    
qtechAirIfResUsageRatio OBJECT-TYPE
    SYNTAX INTEGER
    MAX-ACCESS read-only
    STATUS current
    DESCRIPTION
        "Resource usage ratio of AP air interface."
    ::= { qtechTermServiceStatSSIDEntry 3}
  
qtechTotalAssociationUserNum OBJECT-TYPE
    SYNTAX INTEGER
    MAX-ACCESS read-only
    STATUS current
    DESCRIPTION
        "Total number of users associated to the AP."
    ::= { qtechTermServiceStatSSIDEntry 4}
    
qtechOnlineUserNum OBJECT-TYPE
    SYNTAX INTEGER
    MAX-ACCESS read-only
    STATUS current
    DESCRIPTION
        "Number of users online."
    ::= { qtechTermServiceStatSSIDEntry 5}
    
qtechUserReqAccessTimes OBJECT-TYPE
    SYNTAX INTEGER
    MAX-ACCESS read-only
    STATUS current
    DESCRIPTION
        "Times of request initiate by the user."
    ::= { qtechTermServiceStatSSIDEntry 6}
    
qtechResponseReqAccessTimes OBJECT-TYPE
    SYNTAX INTEGER
    MAX-ACCESS read-only
    STATUS current
    DESCRIPTION
        "Times of correct response to user access request."
    ::= { qtechTermServiceStatSSIDEntry 7}
    
qtechSuccessAccessTimes OBJECT-TYPE
    SYNTAX INTEGER
    MAX-ACCESS read-only
    STATUS current
    DESCRIPTION
        "Times of succeed access to the AP."
    ::= { qtechTermServiceStatSSIDEntry 8}
    
qtechIneffiLinkVerifyFailTime OBJECT-TYPE
    SYNTAX INTEGER
    MAX-ACCESS read-only
    STATUS current
    DESCRIPTION
        "Total link verify failure times due to algorithm or transform SN discrepancy."
    ::= { qtechTermServiceStatSSIDEntry 9}

qtechTimeoutLinkVerifyFailTime OBJECT-TYPE
    SYNTAX INTEGER
    MAX-ACCESS read-only
    STATUS current
    DESCRIPTION
        "Total link verify failure times due to timeout."
    ::= { qtechTermServiceStatSSIDEntry 10}
    
qtechInefficiencyLinkVerifyFailTime OBJECT-TYPE
    SYNTAX INTEGER
    MAX-ACCESS read-only
    STATUS current
    DESCRIPTION
        "Total link verify failure times due to inefficiency."
    ::= { qtechTermServiceStatSSIDEntry 11}
    
qtechOtherReasonLinkVerifyFailTime OBJECT-TYPE
    SYNTAX INTEGER
    MAX-ACCESS read-only
    STATUS current
    DESCRIPTION
        "Total link verify failure times due to other reason."
    ::= { qtechTermServiceStatSSIDEntry 12}
    
qtechIneffiAssociationFailTime OBJECT-TYPE
    SYNTAX INTEGER
    MAX-ACCESS read-only
    STATUS current
    DESCRIPTION
        "Total Association failure times due to algorithm or transform SN discrepancy."
    ::= { qtechTermServiceStatSSIDEntry 13}

qtechTimeoutAssociationFailTime OBJECT-TYPE
    SYNTAX INTEGER
    MAX-ACCESS read-only
    STATUS current
    DESCRIPTION
        "Total Association failure times due to timeout."
    ::= { qtechTermServiceStatSSIDEntry 14}
    
qtechInefficiencyAssociationFailTime OBJECT-TYPE
    SYNTAX INTEGER
    MAX-ACCESS read-only
    STATUS current
    DESCRIPTION
        "Total Association failure times due to inefficiency."
    ::= { qtechTermServiceStatSSIDEntry 15}
    
qtechOtherReasonAssociationFailTime OBJECT-TYPE
    SYNTAX INTEGER
    MAX-ACCESS read-only
    STATUS current
    DESCRIPTION
        "Total Association failure times due to other reason."
    ::= { qtechTermServiceStatSSIDEntry 16}
    
qtechTotalReassociationAtmptTimes OBJECT-TYPE
    SYNTAX INTEGER
    MAX-ACCESS read-only
    STATUS current
    DESCRIPTION
        "Total re-association attempt times."
    ::= { qtechTermServiceStatSSIDEntry 17}
    
qtechTotalReassociationSuccessTimes OBJECT-TYPE
    SYNTAX INTEGER
    MAX-ACCESS read-only
    STATUS current
    DESCRIPTION
        "Total re-association success times."
    ::= { qtechTermServiceStatSSIDEntry 18}

qtechIneffiReassociationFailTime OBJECT-TYPE
    SYNTAX INTEGER
    MAX-ACCESS read-only
    STATUS current
    DESCRIPTION
        "Total Reassociation failure times due to algorithm or transform SN discrepancy."
    ::= { qtechTermServiceStatSSIDEntry 19}

qtechTimeoutReassociationFailTime OBJECT-TYPE
    SYNTAX INTEGER
    MAX-ACCESS read-only
    STATUS current
    DESCRIPTION
        "Total Reassociation failure times due to timeout."
    ::= { qtechTermServiceStatSSIDEntry 20}
    
qtechInefficiencyReassociationFailTime OBJECT-TYPE
    SYNTAX INTEGER
    MAX-ACCESS read-only
    STATUS current
    DESCRIPTION
        "Total Reassociation failure times due to inefficiency."
    ::= { qtechTermServiceStatSSIDEntry 21}
    
qtechOtherReasonReassociationFailTime OBJECT-TYPE
    SYNTAX INTEGER
    MAX-ACCESS read-only
    STATUS current
    DESCRIPTION
        "Total Reassociation failure times due to other reason."
    ::= { qtechTermServiceStatSSIDEntry 22}
    
qtechTotalIdentificationAtmptTimes OBJECT-TYPE
    SYNTAX INTEGER
    MAX-ACCESS read-only
    STATUS current
    DESCRIPTION
        "Total Identification attempt times."
    ::= { qtechTermServiceStatSSIDEntry 23}
    
qtechTotalIdentificationSuccessTimes OBJECT-TYPE
    SYNTAX INTEGER
    MAX-ACCESS read-only
    STATUS current
    DESCRIPTION
        "Total Identification success times."
    ::= { qtechTermServiceStatSSIDEntry 24}
    
qtechPwdErrorIdentifyFailTime OBJECT-TYPE
    SYNTAX INTEGER
    MAX-ACCESS read-only
    STATUS current
    DESCRIPTION
        "Total identification failure times due to password error."
    ::= { qtechTermServiceStatSSIDEntry 25}    

qtechIneffiIdentificationFailTime OBJECT-TYPE
    SYNTAX INTEGER
    MAX-ACCESS read-only
    STATUS current
    DESCRIPTION
        "Total Identification failure times due to algorithm or transform SN discrepancy."
    ::= { qtechTermServiceStatSSIDEntry 26}

qtechTimeoutIdentificationFailTime OBJECT-TYPE
    SYNTAX INTEGER
    MAX-ACCESS read-only
    STATUS current
    DESCRIPTION
        "Total Identification failure times due to timeout."
    ::= { qtechTermServiceStatSSIDEntry 27}
    
qtechInefficiencyIdentificationFailTime OBJECT-TYPE
    SYNTAX INTEGER
    MAX-ACCESS read-only
    STATUS current
    DESCRIPTION
        "Total Identification failure times due to inefficiency."
    ::= { qtechTermServiceStatSSIDEntry 28}
    
qtechOtherReasonIdentificationFailTime OBJECT-TYPE
    SYNTAX INTEGER
    MAX-ACCESS read-only
    STATUS current
    DESCRIPTION
        "Total Identification failure times due to other reason."
    ::= { qtechTermServiceStatSSIDEntry 29}
    
qtechTotalRemoveLinkVerifyFailTimes OBJECT-TYPE
    SYNTAX INTEGER
    MAX-ACCESS read-only
    STATUS current
    DESCRIPTION
        "Total failure times of removing link verification."
    ::= { qtechTermServiceStatSSIDEntry 30} 
    
qtechLeaveAPCoverageRemoveLinkVerifyFailTimes OBJECT-TYPE
    SYNTAX INTEGER
    MAX-ACCESS read-only
    STATUS current
    DESCRIPTION
        "Total failure times due to leaving AP coverage area."
    ::= { qtechTermServiceStatSSIDEntry 31}   
    
qtechInefficiencyRemoveLinkVerifyFailTime OBJECT-TYPE
    SYNTAX INTEGER
    MAX-ACCESS read-only
    STATUS current
    DESCRIPTION
        "Total remove link failure times due to inefficiency."
    ::= { qtechTermServiceStatSSIDEntry 32}  
    
qtechLinkVerifyFailRemoveLinkVerifyFailTime OBJECT-TYPE
    SYNTAX INTEGER
    MAX-ACCESS read-only
    STATUS current
    DESCRIPTION
        "Total remove link failure times due to link verify failure."
    ::= { qtechTermServiceStatSSIDEntry 33}      

qtechOtherReasonRemoveLinkVerifyFailTime OBJECT-TYPE
    SYNTAX INTEGER
    MAX-ACCESS read-only
    STATUS current
    DESCRIPTION
        "Total remove link failure times due to other reason."
    ::= { qtechTermServiceStatSSIDEntry 34} 

qtechTotalRemoveLinkAssociationTimes OBJECT-TYPE
    SYNTAX INTEGER
    MAX-ACCESS read-only
    STATUS current
    DESCRIPTION
        "Total failure times of removing association."
    ::= { qtechTermServiceStatSSIDEntry 35}  
    
qtechLeaveAPCoverageRemoveAssociationFailTimes OBJECT-TYPE
    SYNTAX INTEGER
    MAX-ACCESS read-only
    STATUS current
    DESCRIPTION
        "Total remove association failure times due to leaving AP coverage area."
    ::= { qtechTermServiceStatSSIDEntry 36}   
    
qtechInefficiencyRemoveAssociationFailTime OBJECT-TYPE
    SYNTAX INTEGER
    MAX-ACCESS read-only
    STATUS current
    DESCRIPTION
        "Total remove association failure times due to inefficiency."
    ::= { qtechTermServiceStatSSIDEntry 37}  
    
qtechAssociationFailRemoveAssociationFailTime OBJECT-TYPE
    SYNTAX INTEGER
    MAX-ACCESS read-only
    STATUS current
    DESCRIPTION
        "Total remove association failure times due to link verify failure."
    ::= { qtechTermServiceStatSSIDEntry 38}      

qtechOtherReasonRemoveAssociationFailTime OBJECT-TYPE
    SYNTAX INTEGER
    MAX-ACCESS read-only
    STATUS current
    DESCRIPTION
        "Total remove association failure times due to other reason."
    ::= { qtechTermServiceStatSSIDEntry 39}
    

--**************************************************
--* qtechTermServiceStatSSIDTable ends
--**************************************************  
    

--**************************************************
--* qtechUserMacAddrTable begins
--**************************************************

qtechUserMacAddrTable OBJECT-TYPE
    SYNTAX SEQUENCE OF QtechUserMacAddrEntry
    MAX-ACCESS not-accessible
    STATUS current
    DESCRIPTION
        "Statistic of user MAC address by SSID."
    ::= { qtechTermServiceStat 35	 }

qtechUserMacAddrEntry OBJECT-TYPE
    SYNTAX QtechUserMacAddrEntry
    MAX-ACCESS not-accessible
    STATUS current
    DESCRIPTION
        "The entry of qtechUserMacAddrTable."
    INDEX
    { qtechWlanId,qtechTerminalIndex}
    ::= { qtechUserMacAddrTable 1 }

QtechUserMacAddrEntry ::=
    SEQUENCE {
        qtechTerminalIndex            INTEGER,
        qtechUserMacAdddr             MacAddress
    } 
qtechTerminalIndex OBJECT-TYPE
    SYNTAX INTEGER
    MAX-ACCESS read-only
    STATUS current
    DESCRIPTION
        "The index of the terminal."
    ::= { qtechUserMacAddrEntry 1}
      
qtechUserMacAdddr OBJECT-TYPE
    SYNTAX MacAddress
    MAX-ACCESS read-only
    STATUS current
    DESCRIPTION
        "User MAC address."
    ::= { qtechUserMacAddrEntry 2}
    
    

--**************************************************
--* qtechUserMacAddrTable ends
--**************************************************     
    
--**************************************************
--* qtechTermServiceStatTable begins
--**************************************************

qtechTermServiceStatTable OBJECT-TYPE
    SYNTAX SEQUENCE OF QtechTermServiceStatEntry
    MAX-ACCESS not-accessible
    STATUS current
    DESCRIPTION
        "Statistic of terminal service by terminal."
    ::= { qtechTermServiceStat 36	 }

qtechTermServiceStatEntry OBJECT-TYPE
    SYNTAX QtechTermServiceStatEntry
    MAX-ACCESS not-accessible
    STATUS current
    DESCRIPTION
        "The entry of qtechTermServiceStatTable."
    INDEX
    { qtechTerminalIndex}
    ::= { qtechTermServiceStatTable 1 }

QtechTermServiceStatEntry ::=
    SEQUENCE {
        qtechTotalReTxFramNum				 INTEGER,
        qtechUserOnLineTime					 INTEGER,
        qtechRevDataFrameNum					 INTEGER,
        qtechRevErrorDataFrameNum		 INTEGER,
        qtechSendDataFrameNum				 INTEGER,
        qtechSendSuccessDataFrameNum	 INTEGER,
        qtechSendReTxDataFrameNum	 	 INTEGER,        
        qtechAvgSendRate							 INTEGER,
        qtechAvgReceiveRate					 INTEGER,
        qtechTotalDataThroughput			 INTEGER,
        qtechSignalStrength					 INTEGER,
        qtechNoise										 INTEGER
    } 
qtechTotalReTxFramNum OBJECT-TYPE
    SYNTAX INTEGER
    MAX-ACCESS read-only
    STATUS current
    DESCRIPTION
        "The total re-transmit data frame number of each user."
    ::= { qtechTermServiceStatEntry 1}
      
    
qtechUserOnLineTime OBJECT-TYPE
    SYNTAX INTEGER
    MAX-ACCESS read-only
    STATUS current
    DESCRIPTION
        "User on-line time."
    ::= { qtechTermServiceStatEntry 2}
    
qtechRevDataFrameNum OBJECT-TYPE
    SYNTAX INTEGER
    MAX-ACCESS read-only
    STATUS current
    DESCRIPTION
        "Number of data frame receive by AP from user."
    ::= { qtechTermServiceStatEntry 3}
    
qtechRevErrorDataFrameNum OBJECT-TYPE
    SYNTAX INTEGER
    MAX-ACCESS read-only
    STATUS current
    DESCRIPTION
        "Number of error data frame receive by AP from user."
    ::= { qtechTermServiceStatEntry 4}
    
qtechSendDataFrameNum OBJECT-TYPE
    SYNTAX INTEGER
    MAX-ACCESS read-only
    STATUS current
    DESCRIPTION
        "Number of data frame sent by AP to user."
    ::= { qtechTermServiceStatEntry 5}
    
qtechSendSuccessDataFrameNum OBJECT-TYPE
    SYNTAX INTEGER
    MAX-ACCESS read-only
    STATUS current
    DESCRIPTION
        "Number of data frame sent by AP to user successfully."
    ::= { qtechTermServiceStatEntry 6}
    
qtechSendReTxDataFrameNum OBJECT-TYPE
    SYNTAX INTEGER
    MAX-ACCESS read-only
    STATUS current
    DESCRIPTION
        "Number of retransmit data frame sent by AP to user successfully."
    ::= { qtechTermServiceStatEntry 7}

     
qtechAvgSendRate OBJECT-TYPE
    SYNTAX INTEGER
    MAX-ACCESS read-only
    STATUS current
    DESCRIPTION
        "Avearage rate of data that is sent from the AP to users"
    ::= { qtechTermServiceStatEntry 8}
    
qtechAvgReceiveRate OBJECT-TYPE
    SYNTAX INTEGER
    MAX-ACCESS read-only
    STATUS current
    DESCRIPTION
        "Avearage rate of data that is received by users from the AP"
    ::= { qtechTermServiceStatEntry 9}    
    
qtechTotalDataThroughput OBJECT-TYPE
    SYNTAX INTEGER
    MAX-ACCESS read-only
    STATUS current
    DESCRIPTION
        "Total data throughout of the user."
    ::= { qtechTermServiceStatEntry 10} 
    
qtechSignalStrength OBJECT-TYPE
    SYNTAX INTEGER
    MAX-ACCESS read-only
    STATUS current
    DESCRIPTION
        "Signal strength receive by the AP."
    ::= { qtechTermServiceStatEntry 11} 
    
qtechNoise OBJECT-TYPE
    SYNTAX INTEGER
    MAX-ACCESS read-only
    STATUS current
    DESCRIPTION
        "Noise when AP receive information from user."
    ::= { qtechTermServiceStatEntry 12}

--**************************************************
--* qtechTermServiceStatTable ends
--**************************************************  
  
    
--**************************************************
--* qtechTermServiceStat ends here
--**************************************************


END
