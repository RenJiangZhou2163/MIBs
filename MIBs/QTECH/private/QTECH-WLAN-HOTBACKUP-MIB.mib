-- *****************************************************************
-- QTECH-WLAN-HOTBACKUP-MIB.mib:  Qtech WLAN HOT-BACKUP MIB file
--
-- July 2012, jiangweifeng
-- 
-- Copyright (c) 2012 by Qtech Networks Co.,Ltd.
-- All rights reserved.
-- *****************************************************************


QTECH-WLAN-HOTBACKUP-MIB DEFINITIONS ::= BEGIN

IMPORTS
    MODULE-IDENTITY, 
    OBJECT-TYPE,
    Integer32,
    IpAddress
        FROM SNMPv2-SMI
    qtechMgmt
        FROM QTECH-SMI
    InetAddress,
    InetAddressType
        FROM INET-ADDRESS-MIB;

qtechWlanHotbackupMIB MODULE-IDENTITY
    LAST-UPDATED "201207310000Z"
    ORGANIZATION "Qtech Networks Co.,Ltd."
    CONTACT-INFO
            " 
            Tel: 4008-111-000 
                
            E-mail: service@qtech.com.cn"
    DESCRIPTION
            "This MIB is intended to get the wlan hot-backup 
            information on AC. AC may establish hot-backup relationship 
            with several ACs(called peers)."
    REVISION  "201207310000Z"
    DESCRIPTION
            "Initial version of this mib."
    ::= { qtechMgmt 115 }

qtechWlanHotbackupMIBObjects OBJECT IDENTIFIER 
    ::= { qtechWlanHotbackupMIB 1 }

qtechWlanHotbackupNotificationsMIBObjects OBJECT IDENTIFIER
    ::= { qtechWlanHotbackupMIB 2 }

qtechWlanHotbackupNtfObjects OBJECT IDENTIFIER
    ::= { qtechWlanHotbackupNotificationsMIBObjects 1 }

qtechWlanHotbackupNotifications OBJECT IDENTIFIER
    ::= { qtechWlanHotbackupNotificationsMIBObjects 2 }

--*******************************************************************
--qtechWlanHotbackupPeerTable:  list of wlan hot-backup peer
--*******************************************************************
qtechWlanHotbackupPeerTable  OBJECT-TYPE
     SYNTAX      SEQUENCE OF QtechWlanHotbackupPeerEntry
     MAX-ACCESS  not-accessible
     STATUS      current
     DESCRIPTION
                 "A table listing the peers establishing hot-backup 
                 relationship with this AC."
     ::= { qtechWlanHotbackupMIBObjects 1 }

qtechWlanHotbackupPeerEntry OBJECT-TYPE
     SYNTAX      QtechWlanHotbackupPeerEntry
     MAX-ACCESS  not-accessible
     STATUS      current
     DESCRIPTION
                 "Wlan hot-backup peer entry."
     INDEX       { qtechWlanHotbackupIpAddress }
     ::= { qtechWlanHotbackupPeerTable  1 }

QtechWlanHotbackupPeerEntry ::= SEQUENCE {
         qtechWlanHotbackupIpAddress        IpAddress,
         qtechWlanHotbackupIsEnabled        INTEGER,
         qtechWlanHotbackupState            INTEGER
         }

qtechWlanHotbackupIpAddress OBJECT-TYPE
     SYNTAX      IpAddress
     MAX-ACCESS  not-accessible
     STATUS      current
     DESCRIPTION
                 "Wlan hot-backup peer's IP address."
     ::= { qtechWlanHotbackupPeerEntry 1 }

qtechWlanHotbackupIsEnabled OBJECT-TYPE
     SYNTAX      INTEGER {
                     disable(0),
                     enable(1)
                 }
     MAX-ACCESS  read-only
     STATUS      current
     DESCRIPTION
                 "Wlan hot-backup enable state with this peer."
     ::= { qtechWlanHotbackupPeerEntry 2 }

qtechWlanHotbackupState OBJECT-TYPE
     SYNTAX      INTEGER {
                     hb-disable(1),
                     probe(2),
                     hdsk(3),
                     tcp-connect(4),
                     sulking(5),
                     channel-up(6)
                 }
     MAX-ACCESS  read-only
     STATUS      current
     DESCRIPTION
                 "Wlan hot-backup state with this peer."
     ::= { qtechWlanHotbackupPeerEntry 3 }

--*******************************************************************
--qtechWlanHotbackupContextTable:  list of wlan hot-backup context
--*******************************************************************
qtechWlanHotbackupContextTable OBJECT-TYPE
    SYNTAX      SEQUENCE OF QtechWlanHotbackupContextEntry
    MAX-ACCESS  not-accessible
    STATUS      current
    DESCRIPTION
        "The table descrips information about AC context info."
    ::= { qtechWlanHotbackupMIBObjects 2 }

qtechWlanHotbackupContextEntry OBJECT-TYPE
    SYNTAX      QtechWlanHotbackupContextEntry
    MAX-ACCESS  not-accessible
    STATUS      current
    DESCRIPTION
        "Each entry contains information about AC context info."
    INDEX { qtechWlanHotbackupCtxIpAddress, qtechWlanHotbackupContextId }
    ::= { qtechWlanHotbackupContextTable 1 }

QtechWlanHotbackupContextEntry ::=
    SEQUENCE {
		qtechWlanHotbackupCtxIpAddress IpAddress,
        qtechWlanHotbackupContextId  INTEGER,
        qtechWlanHotbackupContextState INTEGER
    }

qtechWlanHotbackupCtxIpAddress OBJECT-TYPE
     SYNTAX      IpAddress
     MAX-ACCESS  read-only
     STATUS      current
     DESCRIPTION
                 "Wlan hot-backup peer's IP address."
     ::= { qtechWlanHotbackupContextEntry 1 }
	
qtechWlanHotbackupContextId OBJECT-TYPE
    SYNTAX      INTEGER
    MAX-ACCESS  read-only
    STATUS      current
    DESCRIPTION
        "Each entry contains context id."
    ::= { qtechWlanHotbackupContextEntry 2 }

qtechWlanHotbackupContextState OBJECT-TYPE
    SYNTAX      INTEGER {
                    disable(0),
                    unknown(1),
                    single-active(2),
                    single-standby(3),
                    pair-active(4),
                    pair-standby(5)
                }
    MAX-ACCESS  read-only
    STATUS      current
    DESCRIPTION
         "Each entry contains context state."
    ::= { qtechWlanHotbackupContextEntry 3 }

-- ****************************************
--
--               Notify nodes
--
-- ****************************************
qtechNotifyPeerIpType OBJECT-TYPE
    SYNTAX      InetAddressType
    MAX-ACCESS  accessible-for-notify
    STATUS      current
    DESCRIPTION
        "Represents the peer ip type."
    ::= { qtechWlanHotbackupNtfObjects 1 }
    
qtechNotifyPeerIp OBJECT-TYPE
    SYNTAX      InetAddress
    MAX-ACCESS  accessible-for-notify
    STATUS      current
    DESCRIPTION
        "Represents the peer ip."
    ::= { qtechWlanHotbackupNtfObjects 2 }

qtechNotifyCtxId OBJECT-TYPE
    SYNTAX      INTEGER(0..65535)
    MAX-ACCESS  accessible-for-notify
    STATUS      current
    DESCRIPTION
        "Represents the context id."
    ::= { qtechWlanHotbackupNtfObjects 3 }
    
qtechNotifyOldState OBJECT-TYPE
    SYNTAX      INTEGER {
                    disable(0),
                    unknown(1),
                    single-active(2),
                    single-standby(3),
                    pair-active(4),
                    pair-standby(5)
                }
    MAX-ACCESS  accessible-for-notify
    STATUS      current
    DESCRIPTION
        "Represents the old state."
    ::= { qtechWlanHotbackupNtfObjects 4 }
    
qtechNotifyNewState OBJECT-TYPE
    SYNTAX      INTEGER {
                    disable(0),
                    unknown(1),
                    single-active(2),
                    single-standby(3),
                    pair-active(4),
                    pair-standby(5)
                }
    MAX-ACCESS  accessible-for-notify
    STATUS      current
    DESCRIPTION
        "Represents the new state."
    ::= { qtechWlanHotbackupNtfObjects 5 }
    
qtechNotifyWlanHBChange NOTIFICATION-TYPE
    OBJECTS     {
                  qtechNotifyPeerIpType,
                  qtechNotifyPeerIp,
                  qtechNotifyCtxId,
                  qtechNotifyOldState,
                  qtechNotifyNewState
                }
    STATUS      current
    DESCRIPTION
        "This notification is sent by the AC hotbackup change state."
    ::= { qtechWlanHotbackupNotifications 1 }
    
END
