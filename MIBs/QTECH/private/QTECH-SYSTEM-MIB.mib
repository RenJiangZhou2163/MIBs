-- *****************************************************************
-- QTECH-SYSTEM-MIB.mib:  Qtech System MIB file
--
-- March 2002, Wuzg
--
-- Copyright (c) 2002 by Qtech Networks Co.,Ltd.
-- All rights reserved.
-- 
-- *****************************************************************
--

QTECH-SYSTEM-MIB DEFINITIONS ::= BEGIN

IMPORTS
        MODULE-IDENTITY,
        OBJECT-TYPE,
        NOTIFICATION-TYPE,
        Integer32,
        TimeTicks,
        Unsigned32
                FROM SNMPv2-SMI
        DisplayString,
        MacAddress
                FROM SNMPv2-TC
        Gauge
                FROM RFC1155-SMI
        MODULE-COMPLIANCE,
        OBJECT-GROUP
                FROM SNMPv2-CONF
        qtechApMacAddr   
                FROM QTECH-AC-MGMT-MIB
        qtechMemoryPoolCurrentUtilization
                FROM QTECH-MEMORY-MIB
        qtechCPUUtilization1Min,
        Percent
                FROM QTECH-PROCESS-MIB
        qtechMgmt
                FROM QTECH-SMI;

qtechSystemMIB MODULE-IDENTITY
        LAST-UPDATED "200203200000Z"
        ORGANIZATION "Qtech Networks Co.,Ltd."
        CONTACT-INFO
                " 
                Tel: 4008-111-000 

                E-mail: service@qtech.com.cn"
        DESCRIPTION
                "This module defines qtech system mibs."
        REVISION      "200203200000Z"
        DESCRIPTION
                "Initial version of this MIB module."
        ::= { qtechMgmt 1}

qtechSystemMIBObjects OBJECT IDENTIFIER ::= { qtechSystemMIB 1 }

qtechSystemHwVersion OBJECT-TYPE
        SYNTAX DisplayString(SIZE (1..32))
        MAX-ACCESS read-only
        STATUS current
        DESCRIPTION
          "Return the string of the Revision number of hardware resides
          on the FastSwitch."
        ::= { qtechSystemMIBObjects 1 }

qtechSystemSwVersion OBJECT-TYPE
        SYNTAX DisplayString(SIZE (1..32))
        MAX-ACCESS read-only
        STATUS current
        DESCRIPTION
          "Return the string of the Revision number of software resides
          on the FastSwitch."
        ::= { qtechSystemMIBObjects 2 }
        
qtechSystemBootVersion OBJECT-TYPE
        SYNTAX DisplayString(SIZE (1..32))
        MAX-ACCESS read-only
        STATUS current
        DESCRIPTION
          "Return the string of the Revision number of BOOT software resides
          on the FastSwitch."
        ::= { qtechSystemMIBObjects 3 }
        
qtechSystemSysCtrlVersion OBJECT-TYPE
        SYNTAX DisplayString(SIZE (1..32))
        MAX-ACCESS read-only
        STATUS current
        DESCRIPTION
          "Return the string of the Revision number of CTRL software resides
          on the FastSwitch."
        ::= { qtechSystemMIBObjects 4 }       

qtechSystemParametersSave OBJECT-TYPE
        SYNTAX Integer32
        MAX-ACCESS read-write
        STATUS current
        DESCRIPTION
            "Save all parameters changed in configuration by setting 
            this object to any value but 0, set its value to 0 will
            cause no action of agent, otherwise all changes of 
            prarameters will be saved for retrive when system is 
            reset, if parameter is changed but not saved all changes
            will come to their original value when system down and up
            again, when query always return value 0."
        ::= { qtechSystemMIBObjects 5 }

qtechSystemOutBandRate OBJECT-TYPE
   	  SYNTAX  INTEGER {
                baud9600  (1),
                baud19200 (2),
                baud38400 (3),
                baud57600 (4),
                baud115200 (5)
             }
        MAX-ACCESS read-write
        STATUS current
        DESCRIPTION
   	    "Determine the console(OutBand) baud rate :
             9600 - 1,19200 - 2, 38300 - 3, 57600 - 4, 115200 - 5, 
             when the console baud rate is other value will return value 0."
   	::=  { qtechSystemMIBObjects 6 }
        
qtechSystemReset OBJECT-TYPE
        SYNTAX INTEGER {
            normal(0),
            restart(1)
        } 
        MAX-ACCESS read-write
        STATUS current
        DESCRIPTION
            "This Object allow perform soft reset of system by setting its
            value to none zero. if a soft resetis performed, after this 
            having completed a warm start trap will send to declare the state
            and when queried will always return 0."
        ::= { qtechSystemMIBObjects 7 }

qtechSwitchLayer OBJECT-TYPE
   	  SYNTAX  INTEGER {
                layer2 (1), -- Layer 2 Switch
                layer3 (2), -- Layer 3 Switch
                router(3)  -- Router
             }
        MAX-ACCESS read-only
        STATUS current
        DESCRIPTION
   		"Which layer's device the switch in system "
   	     ::=  { qtechSystemMIBObjects 8 }

qtechSystemHwPower OBJECT-TYPE
        SYNTAX INTEGER{
        	rpsNoLink(1),
        	rpsLinkAndNoPower(2),
        	rpsLinkAndReadyForPower(3),
        	rpsLinkAndPower(4)
        }
        MAX-ACCESS read-only
        STATUS current
        DESCRIPTION
          "The state of power."
        ::= { qtechSystemMIBObjects 9 }

qtechSystemHwFan OBJECT-TYPE
        SYNTAX INTEGER{
        	work(1),
        	stop(2)
        }
        MAX-ACCESS read-only
        STATUS current
        DESCRIPTION
          "The state of fan."
        ::= { qtechSystemMIBObjects 10 }

--The qtechSystemOutBandTimeout is obsoleted after 2007.9
qtechSystemOutBandTimeout OBJECT-TYPE
        SYNTAX     Integer32(0..3600)
        UNITS      "seconds"
        MAX-ACCESS read-write
        STATUS obsolete
        DESCRIPTION
          "The timeout of console.0 indicate that timeout function is disabled."
        ::= { qtechSystemMIBObjects 11 }

--The qtechSystemTelnetTimeout is obsoleted after 2007.9
qtechSystemTelnetTimeout OBJECT-TYPE
        SYNTAX     Integer32(0..3600)
        UNITS      "seconds"
        MAX-ACCESS read-write
        STATUS obsolete
        DESCRIPTION
          "The timeout of telnet.0 indicate that timeout function is disabled."
        ::= { qtechSystemMIBObjects 12 }
      
qtechSystemMainFile OBJECT-TYPE
        SYNTAX DisplayString(SIZE (1..255))
        MAX-ACCESS read-only
        STATUS current
        DESCRIPTION
          "Return the string of the name of main file on the FastSwitch."
        ::= { qtechSystemMIBObjects 13 }
        
qtechSystemCurrentPower OBJECT-TYPE
        SYNTAX Integer32
        MAX-ACCESS read-only
        STATUS current
        DESCRIPTION
          "Return the current power of the FastSwitch."
        ::= { qtechSystemMIBObjects 14 }

qtechSystemRemainPower OBJECT-TYPE
        SYNTAX Integer32
        MAX-ACCESS read-only
        STATUS current
        DESCRIPTION
          "Return the remain power of the FastSwitch."
        ::= { qtechSystemMIBObjects 15 }

qtechSystemTemperature OBJECT-TYPE
        SYNTAX Integer32
        MAX-ACCESS read-only
        STATUS current
        DESCRIPTION
          "Return the temperature of the FastSwitch."
        ::= { qtechSystemMIBObjects 16 }

qtechSystemElectricalSourceNum OBJECT-TYPE
        SYNTAX Integer32
        MAX-ACCESS read-only
        STATUS current
        DESCRIPTION
          "Return the electrical source number of the FastSwitch."
        ::= { qtechSystemMIBObjects 17 }

qtechSystemElectricalSourceIsNormalTable OBJECT-TYPE
  SYNTAX      SEQUENCE OF QtechSystemElectricalSourceIsNormalEntry
  MAX-ACCESS  not-accessible
  STATUS      current
  DESCRIPTION
    "A table of electrical source entries. Each object displays 
     whether different electrical sources are normal or not."
  ::= { qtechSystemMIBObjects 18 }

qtechSystemElectricalSourceIsNormalEntry OBJECT-TYPE
  SYNTAX      QtechSystemElectricalSourceIsNormalEntry
  MAX-ACCESS  not-accessible
  STATUS      current
  DESCRIPTION
    "An entry displays whether different electrical sources are normal or not."
  INDEX { qtechSystemElectricalSourceIsNormalIndex }
  ::= { qtechSystemElectricalSourceIsNormalTable 1 }

QtechSystemElectricalSourceIsNormalEntry ::=
  SEQUENCE {
    qtechSystemElectricalSourceIsNormalIndex  Integer32,
    qtechSystemElectricalSourceIsNormal  INTEGER,
    qtechSystemElectricalSourceName   DisplayString
  }
    
qtechSystemElectricalSourceIsNormalIndex OBJECT-TYPE
    SYNTAX        Integer32
    MAX-ACCESS    read-only
    STATUS        current
    DESCRIPTION
        "An index that uniquely represents a electrical source."
    ::= { qtechSystemElectricalSourceIsNormalEntry 1 }

qtechSystemElectricalSourceIsNormal OBJECT-TYPE
   	SYNTAX  INTEGER {
                noexist (1),          --no exist
                existnopower (2),     -- exist no power
                existreadypower (3),  --exist ready power
                normal (4),           --normal
                powerbutabnormal (5), --power but abnormal
                unknow (6)            --unknow
             }
    MAX-ACCESS    read-only
    STATUS        current
    DESCRIPTION
        "This object displays whether an electrical source is normal or not."
    ::= { qtechSystemElectricalSourceIsNormalEntry 2 }
    
qtechSystemElectricalSourceName OBJECT-TYPE
    SYNTAX        DisplayString
    MAX-ACCESS    read-only
    STATUS        current
    DESCRIPTION
        "The name of electrical source"
    ::= { qtechSystemElectricalSourceIsNormalEntry 3 }  
    
qtechSystemCurrentVoltage OBJECT-TYPE
        SYNTAX Integer32
        MAX-ACCESS read-only
        STATUS current
        DESCRIPTION
          "Return the current voltage of the FastSwitch."
        ::= { qtechSystemMIBObjects 19 }
        
qtechSystemFanNUM OBJECT-TYPE
        SYNTAX Integer32
        MAX-ACCESS read-only
        STATUS current
        DESCRIPTION
          "Return the number of fan on the FastSwitch."
        ::= { qtechSystemMIBObjects 20 }  
        
qtechSystemFanIsNormalTable OBJECT-TYPE
  SYNTAX      SEQUENCE OF QtechSystemFanIsNormalEntry
  MAX-ACCESS  not-accessible
  STATUS      current
  DESCRIPTION
    "A table of fan entries. Each object displays 
     whether different fans are normal or not."
  ::= { qtechSystemMIBObjects 21 }

qtechSystemFanIsNormalEntry OBJECT-TYPE
  SYNTAX      QtechSystemFanIsNormalEntry
  MAX-ACCESS  not-accessible
  STATUS      current
  DESCRIPTION
    "An entry displays whether different fans are normal or not."
  INDEX { qtechSystemFanIsNormalIndex }
  ::= { qtechSystemFanIsNormalTable 1 }

QtechSystemFanIsNormalEntry ::=
  SEQUENCE {
    qtechSystemFanIsNormalIndex  Integer32,
    qtechSystemFanIsNormal  INTEGER,
    qtechSystemFanName   DisplayString,
    qtechSystemFanSpeed  Integer32
  }
    
qtechSystemFanIsNormalIndex OBJECT-TYPE
    SYNTAX        Integer32
    MAX-ACCESS    read-only
    STATUS        current
    DESCRIPTION
        "An index that uniquely represents a fan."
    ::= { qtechSystemFanIsNormalEntry 1 }

qtechSystemFanIsNormal OBJECT-TYPE
   	SYNTAX  INTEGER {
                noexist (1),          --no exist
                existnopower (2),     -- exist no power
                existreadypower (3),  --exist ready power
                normal (4),           --normal
                powerbutabnormal (5), --power but abnormal
                unknow (6)            --unknow
             }
    MAX-ACCESS    read-only
    STATUS        current
    DESCRIPTION
        "This object displays whether an fan is normal or not."
    ::= { qtechSystemFanIsNormalEntry 2 }   
        
qtechSystemFanName OBJECT-TYPE
    SYNTAX        DisplayString
    MAX-ACCESS    read-only
    STATUS        current
    DESCRIPTION
        "The name of fan"
    ::= { qtechSystemFanIsNormalEntry 3 }     

qtechSystemFanSpeed OBJECT-TYPE
    SYNTAX        Integer32
    MAX-ACCESS    read-only
    STATUS        current
    DESCRIPTION
        "This object displays the fan's speed."
    ::= { qtechSystemFanIsNormalEntry 4 }   

qtechSystemReloadTimeRemain OBJECT-TYPE
        SYNTAX Integer32
        MAX-ACCESS read-only
        STATUS current
        DESCRIPTION
          "Return the remain time of reloading on the FastSwitch."
        ::= { qtechSystemMIBObjects 22 }      
        
qtechSystemTemperatureTable OBJECT-TYPE
  SYNTAX      SEQUENCE OF QtechSystemTemperatureEntry
  MAX-ACCESS  not-accessible
  STATUS      current
  DESCRIPTION
    "A table of temperature entries. Each object displays 
     the temperature information."
  ::= { qtechSystemMIBObjects 23 }

qtechSystemTemperatureEntry OBJECT-TYPE
  SYNTAX      QtechSystemTemperatureEntry
  MAX-ACCESS  not-accessible
  STATUS      current
  DESCRIPTION
    "An entry displays the temperature information."
  INDEX { qtechSystemTemperatureIndex }
  ::= { qtechSystemTemperatureTable 1 }

QtechSystemTemperatureEntry ::=
  SEQUENCE {
    qtechSystemTemperatureIndex    Integer32,
    qtechSystemTemperatureName     DisplayString,
    qtechSystemTemperatureCurrent  Integer32,
    qtechSystemTemperatureWarningVaule Integer32,
    qtechSystemTemperatureCritialVaule Integer32
  }
    
qtechSystemTemperatureIndex OBJECT-TYPE
    SYNTAX        Integer32
    MAX-ACCESS    read-only
    STATUS        current
    DESCRIPTION
        "An index that uniquely represents a device's temperature information."
    ::= { qtechSystemTemperatureEntry 1 }

qtechSystemTemperatureName OBJECT-TYPE
    SYNTAX        DisplayString
    MAX-ACCESS    read-only
    STATUS        current
    DESCRIPTION
        "A textual name assigned to a temperature chip"
    ::= { qtechSystemTemperatureEntry 2 }          
                    
qtechSystemTemperatureCurrent OBJECT-TYPE
    SYNTAX        Integer32
    MAX-ACCESS    read-only
    STATUS        current
    DESCRIPTION
        "Return the current temperature of the FastSwitch.The temperature display
         is not supported for the current temperature returns to 0."
    ::= { qtechSystemTemperatureEntry 3 }        
        
qtechSystemTemperatureWarningVaule OBJECT-TYPE
    SYNTAX        Integer32
    MAX-ACCESS    read-write
    STATUS        current
    DESCRIPTION
        "The first warning of temperature of the device CPU."
    ::= { qtechSystemTemperatureEntry 4 }       
        
qtechSystemTemperatureCritialVaule OBJECT-TYPE
    SYNTAX        Integer32
    MAX-ACCESS    read-write
    STATUS        current
    DESCRIPTION
        "The second warning of temperature of the device CPU."
    ::= { qtechSystemTemperatureEntry 5 }           
        
qtechSystemSerialno OBJECT-TYPE
        SYNTAX DisplayString 
        MAX-ACCESS read-only
        STATUS current
        DESCRIPTION
          "Return the string of the serial number resides
          on the FastSwitch."
        ::= { qtechSystemMIBObjects 24 }    
    
qtechSystemVersionTable OBJECT-TYPE
  SYNTAX      SEQUENCE OF QtechSystemVersionEntry
  MAX-ACCESS  not-accessible
  STATUS      current
  DESCRIPTION
    "A table of system version entries. Each object displays 
     the system version information."
  ::= { qtechSystemMIBObjects 25 }

qtechSystemVersionEntry OBJECT-TYPE
  SYNTAX      QtechSystemVersionEntry
  MAX-ACCESS  not-accessible
  STATUS      current
  DESCRIPTION
    "An entry displays the system version information."
  INDEX { qtechSystemVersionIndex }
  ::= { qtechSystemVersionTable 1 }

QtechSystemVersionEntry ::=
  SEQUENCE {
    qtechSystemVersionIndex    Unsigned32,
    qtechSystemVersionName     DisplayString,
    qtechSystemVersionSwBoot   DisplayString,
    qtechSystemVersionSwCtrl   DisplayString,
    qtechSystemVersionSwMain   DisplayString,
    qtechSystemVersionHw       DisplayString,
    qtechSystemVersionSerialno DisplayString
  }
    
qtechSystemVersionIndex OBJECT-TYPE
    SYNTAX        Unsigned32
    MAX-ACCESS    read-only
    STATUS        current
    DESCRIPTION
        "An index that uniquely represents a device's system version information."
    ::= { qtechSystemVersionEntry 1 }

qtechSystemVersionName OBJECT-TYPE
    SYNTAX        DisplayString
    MAX-ACCESS    read-only
    STATUS        current
    DESCRIPTION
        "A textual name assigned to a system version chip"
    ::= { qtechSystemVersionEntry 2 }          
                    
qtechSystemVersionSwBoot OBJECT-TYPE
    SYNTAX        DisplayString
    MAX-ACCESS    read-only
    STATUS        current
    DESCRIPTION
        "Return the software boot system version of the FastSwitch."
    ::= { qtechSystemVersionEntry 3 }        
        
qtechSystemVersionSwCtrl OBJECT-TYPE
    SYNTAX        DisplayString
    MAX-ACCESS    read-only
    STATUS        current
    DESCRIPTION
        "Return the software ctrl system version of the FastSwitch."
    ::= { qtechSystemVersionEntry 4 }       
        
qtechSystemVersionSwMain OBJECT-TYPE
    SYNTAX        DisplayString
    MAX-ACCESS    read-only
    STATUS        current
    DESCRIPTION
        "Return the software main system version of the FastSwitch."
    ::= { qtechSystemVersionEntry 5 }      
        
qtechSystemVersionHw OBJECT-TYPE
    SYNTAX        DisplayString
    MAX-ACCESS    read-only
    STATUS        current
    DESCRIPTION
        "Return the hardware system version of the FastSwitch."
    ::= { qtechSystemVersionEntry 6 }      
                
qtechSystemVersionSerialno OBJECT-TYPE
    SYNTAX        DisplayString
    MAX-ACCESS    read-only
    STATUS        current
    DESCRIPTION
        "Return the serial number of the FastSwitch."
    ::= { qtechSystemVersionEntry 7 }               

--System models added 2010-05
qtechSystemSysModel OBJECT-TYPE
    SYNTAX        DisplayString
    MAX-ACCESS    read-only
    STATUS        current
    DESCRIPTION
        "Return the SysModel of equipment."
    ::={ qtechSystemMIBObjects 26 }
    
qtechSystemUptime OBJECT-TYPE
    SYNTAX        INTEGER
    MAX-ACCESS    read-only
    STATUS        current
    DESCRIPTION
        "Return the SysUptime of equipment,unit is seconds."
    ::={ qtechSystemMIBObjects 27 }
    
--System Sample Time 2010-05
qtechSystemSampleTime OBJECT-TYPE
    SYNTAX        Integer32
    MAX-ACCESS    read-write
    STATUS        current
    DESCRIPTION
        "Sampling duration."
    ::={ qtechSystemMIBObjects 28 }
    
qtechSystemStatWindowTime OBJECT-TYPE
    SYNTAX        Integer32
    MAX-ACCESS    read-write
    STATUS        current
    DESCRIPTION
        "Stating duration."
    ::={ qtechSystemMIBObjects 29 }
    
qtechSystemManufacturer OBJECT-TYPE
    SYNTAX DisplayString 
    MAX-ACCESS read-only
    STATUS current
    DESCRIPTION
      "Return the string of the manufacturer."
    ::= { qtechSystemMIBObjects 30 }    
    
qtechSystemCurrentTime OBJECT-TYPE
    SYNTAX DisplayString 
    MAX-ACCESS read-write
    STATUS current
    DESCRIPTION
      "Return the current time of the system."
    ::= { qtechSystemMIBObjects 31 }    
    
qtechSystemWarnResendTime OBJECT-TYPE
    SYNTAX Integer32
    MAX-ACCESS read-write
    STATUS current
    DESCRIPTION
      "Return the resending time of warn trap of the system."
    ::= { qtechSystemMIBObjects 32 }    
    
qtechSystemSoftwareName OBJECT-TYPE
    SYNTAX DisplayString
    MAX-ACCESS read-only
    STATUS current
    DESCRIPTION
      "Return the software name of the system."
    ::= { qtechSystemMIBObjects 33 }    
    
qtechSystemSoftwareManufacturer OBJECT-TYPE
    SYNTAX DisplayString
    MAX-ACCESS read-only
    STATUS current
    DESCRIPTION
      "Return the software manufacturer of the system."
    ::= { qtechSystemMIBObjects 34 }    
    
qtechSystemCpuType OBJECT-TYPE
    SYNTAX DisplayString
    MAX-ACCESS read-only
    STATUS current
    DESCRIPTION
      "Return the cpu type infomation of the system."
    ::= { qtechSystemMIBObjects 35 }    
    
qtechSystemMemoryType OBJECT-TYPE
    SYNTAX DisplayString
    MAX-ACCESS read-only
    STATUS current
    DESCRIPTION
      "Return the memory type of the system."
    ::= { qtechSystemMIBObjects 36 }    
    
qtechSystemMemorySize OBJECT-TYPE
    SYNTAX Gauge
    MAX-ACCESS read-only
    STATUS current
    DESCRIPTION
      "Return the memory card storage of the system."
    ::= { qtechSystemMIBObjects 37 }    
    
qtechSystemFlashSize OBJECT-TYPE
    SYNTAX Gauge
    MAX-ACCESS read-only
    STATUS current
    DESCRIPTION
      "Return the flash size of the system."
    ::= { qtechSystemMIBObjects 38 }    
    
 --lank ap 2010-7    
qtechSystemLankApTable OBJECT-TYPE
  SYNTAX      SEQUENCE OF QtechSystemLankApEntry
  MAX-ACCESS  not-accessible
  STATUS      current
  DESCRIPTION
    "A table of lank ap system entries. Each object displays 
     the lank ap system information."
  ::= { qtechSystemMIBObjects 39 }

qtechSystemLankApEntry OBJECT-TYPE
  SYNTAX      QtechSystemLankApEntry
  MAX-ACCESS  not-accessible
  STATUS      current
  DESCRIPTION
    "An entry displays the lank ap system information."
  INDEX { qtechSystemLankApMacAddr }
  ::= { qtechSystemLankApTable 1 }

QtechSystemLankApEntry ::=
  SEQUENCE {
    qtechSystemLankApMacAddr              MacAddress,
    qtechSystemLankApStatWindowTime       Integer32,
    qtechSystemLankApSampleTime           Integer32,
    qtechSystemLankApReset                INTEGER,
    qtechSystemLankApSoftwareName         DisplayString,
    qtechSystemLankApSwVersion            DisplayString,
    qtechSystemLankApSoftwareManufacturer DisplayString,
    qtechSystemLankApCpuType              DisplayString,
    qtechSystemLankApMemoryType           DisplayString,
    qtechSystemLankApMemorySize           Gauge,
    qtechSystemLankAPFlashSize            Gauge,
    qtechSystemLankApManufacturer         DisplayString,
    qtechSystemLankApSerialno             DisplayString,
    qtechSystemLankApSysModel             DisplayString,
    qtechSystemLankApUptime               INTEGER,
    qtechSystemLankApAccurateUptime       TimeTicks,
    qtechSystemLankApHwVersion            DisplayString
  }
    
qtechSystemLankApMacAddr OBJECT-TYPE
    SYNTAX        MacAddress
    MAX-ACCESS    read-only
    STATUS        current
    DESCRIPTION
        "An index that uniquely represents lank ap system information."
    ::= { qtechSystemLankApEntry 1 }    
    
qtechSystemLankApStatWindowTime OBJECT-TYPE
    SYNTAX        Integer32
    MAX-ACCESS    read-write
    STATUS        current
    DESCRIPTION
        "Stating duration of lank ap."
    ::={ qtechSystemLankApEntry 2 }   

qtechSystemLankApSampleTime OBJECT-TYPE
    SYNTAX        Integer32
    MAX-ACCESS    read-write
    STATUS        current
    DESCRIPTION
        "Sampling duration of lank ap."
    ::={ qtechSystemLankApEntry 3 }    
    
qtechSystemLankApReset OBJECT-TYPE
    SYNTAX INTEGER {
        normal(0),
        restart(1)
    }
    MAX-ACCESS read-write
    STATUS current
    DESCRIPTION
        "This Object allow perform soft reset of lank ap system by setting 
         its value to none zero. if a soft resetis performed, after this 
         having completed a warm start trap will send to declare the state
         and when queried will always return 0."
    ::= { qtechSystemLankApEntry 4 }
        
qtechSystemLankApSoftwareName OBJECT-TYPE
    SYNTAX DisplayString
    MAX-ACCESS read-only
    STATUS current
    DESCRIPTION
      "Return the software name of the lank ap system."
    ::= { qtechSystemLankApEntry 5 }    

qtechSystemLankApSwVersion OBJECT-TYPE
    SYNTAX DisplayString(SIZE (1..32))
    MAX-ACCESS read-only
    STATUS current
    DESCRIPTION
        "Return the string of the Revision number of software resides
         on the lank ap FastSwitch."
    ::= { qtechSystemLankApEntry 6 }   
    
qtechSystemLankApSoftwareManufacturer OBJECT-TYPE
    SYNTAX DisplayString
    MAX-ACCESS read-only
    STATUS current
    DESCRIPTION
      "Return the software manufacturer of the lank ap system."
    ::= { qtechSystemLankApEntry 7 } 
  
qtechSystemLankApCpuType OBJECT-TYPE
    SYNTAX DisplayString
    MAX-ACCESS read-only
    STATUS current
    DESCRIPTION
      "Return the cpu type infomation of the lank ap system."
    ::= { qtechSystemLankApEntry 8 }  
   
qtechSystemLankApMemoryType OBJECT-TYPE
    SYNTAX DisplayString
    MAX-ACCESS read-only
    STATUS current
    DESCRIPTION
      "Return the memory type of the lank ap system."
    ::= { qtechSystemLankApEntry 9 }    
 
qtechSystemLankApMemorySize OBJECT-TYPE
    SYNTAX Gauge
    MAX-ACCESS read-only
    STATUS current
    DESCRIPTION
      "Return the memory card storage of the lank ap system."
    ::= { qtechSystemLankApEntry 10 }    

qtechSystemLankAPFlashSize OBJECT-TYPE
    SYNTAX Gauge
    MAX-ACCESS read-only
    STATUS current
    DESCRIPTION
      "Return the flash size of the lank ap system."
    ::= { qtechSystemLankApEntry 11 }   
    
qtechSystemLankApManufacturer OBJECT-TYPE
    SYNTAX DisplayString 
    MAX-ACCESS read-only
    STATUS current
    DESCRIPTION
      "Return the string of the manufacturer of lank ap."
    ::= { qtechSystemLankApEntry 12} 
    
qtechSystemLankApSerialno OBJECT-TYPE
        SYNTAX DisplayString 
        MAX-ACCESS read-only
        STATUS current
        DESCRIPTION
          "Return the string of the serial number resides
          on the lank ap FastSwitch."
        ::= { qtechSystemLankApEntry 13 }    
        
qtechSystemLankApSysModel OBJECT-TYPE
    SYNTAX        DisplayString
    MAX-ACCESS    read-only
    STATUS        current
    DESCRIPTION
        "Return the SysModel of lank ap equipment."
    ::={ qtechSystemLankApEntry 14 }
      
qtechSystemLankApUptime OBJECT-TYPE
    SYNTAX        INTEGER
    MAX-ACCESS    read-only
    STATUS        current
    DESCRIPTION
        "Return the SysUptime of lank ap equipment."
    ::={ qtechSystemLankApEntry 15 }
    
qtechSystemLankApAccurateUptime OBJECT-TYPE
    SYNTAX        TimeTicks
    MAX-ACCESS    read-only
    STATUS        current
    DESCRIPTION
        "Return the accurate system Uptime of ap equipment,unit is ticks"
    ::={ qtechSystemLankApEntry 16 }

qtechSystemLankApHwVersion OBJECT-TYPE
    SYNTAX DisplayString(SIZE (1..32))
    MAX-ACCESS read-only
    STATUS current
    DESCRIPTION
        "Return the string of the Revision number of hardware resides
         on the lank ap FastSwitch."
    ::= { qtechSystemLankApEntry 17 }   
    

qtechSystemBoardTemperatureTable OBJECT-TYPE
  SYNTAX      SEQUENCE OF QtechSystemBoardTemperatureEntry
  MAX-ACCESS  not-accessible
  STATUS      current
  DESCRIPTION
    "A table of board temperature entries. Each object displays 
     the board temperature information."
  ::= { qtechSystemMIBObjects 40 }

qtechSystemBoardTemperatureEntry OBJECT-TYPE
  SYNTAX      QtechSystemBoardTemperatureEntry
  MAX-ACCESS  not-accessible
  STATUS      current
  DESCRIPTION
    "An entry displays the board temperature information."
  INDEX { qtechSystemBoardTemperatureIndex }
  ::= { qtechSystemBoardTemperatureTable 1 }

QtechSystemBoardTemperatureEntry ::=
  SEQUENCE {
    qtechSystemBoardTemperatureIndex    Integer32,
    qtechSystemBoardTemperatureName     DisplayString,
    qtechSystemBoardTemperatureCurrent  Integer32
  }
    
qtechSystemBoardTemperatureIndex OBJECT-TYPE
    SYNTAX        Integer32
    MAX-ACCESS    read-only
    STATUS        current
    DESCRIPTION
        "An index that uniquely represents a device's board temperature information."
    ::= { qtechSystemBoardTemperatureEntry 1 }

qtechSystemBoardTemperatureName OBJECT-TYPE
    SYNTAX        DisplayString
    MAX-ACCESS    read-only
    STATUS        current
    DESCRIPTION
        "A textual name assigned to a board temperature chip"
    ::= { qtechSystemBoardTemperatureEntry 2 }          
                    
qtechSystemBoardTemperatureCurrent OBJECT-TYPE
    SYNTAX        Integer32
    MAX-ACCESS    read-only
    STATUS        current
    DESCRIPTION
        "Return the current board temperature of the FastSwitch.The temperature display
         is not supported for the current temperature returns to 0."
    ::= { qtechSystemBoardTemperatureEntry 3 }    

qtechSystemElectricalInformationTable OBJECT-TYPE
  SYNTAX      SEQUENCE OF QtechSystemElectricalInformationEntry
  MAX-ACCESS  not-accessible
  STATUS      current
  DESCRIPTION
    "A table of electrical entries. Each object displays the electrical information."
  ::= { qtechSystemMIBObjects 41 }

qtechSystemElectricalInformationEntry OBJECT-TYPE
  SYNTAX      QtechSystemElectricalInformationEntry
  MAX-ACCESS  not-accessible
  STATUS      current
  DESCRIPTION
    "An entry displays the electrical information."
  INDEX {qtechSystemElectricalInformationDeviceIndex, qtechSystemElectricalInformationIndex }
  ::= { qtechSystemElectricalInformationTable 1 }

QtechSystemElectricalInformationEntry ::=
  SEQUENCE {
    qtechSystemElectricalInformationDeviceIndex      Integer32,
    qtechSystemElectricalInformationIndex            Integer32,
    qtechSystemElectricalInformationStatus           INTEGER,
    qtechSystemElectricalInformationType             DisplayString,
    qtechSystemElectricalInformationAttribute        DisplayString,
    qtechSystemElectricalInformationSofeVersion      DisplayString,
    qtechSystemElectricalInformationHardwareVersion  DisplayString,
    qtechSystemElectricalInformationSerial           DisplayString,
    qtechSystemElectricalInformationProductionDate   DisplayString,
    qtechSystemElectricalInformationRatedPower       Integer32,
    qtechSystemElectricalInformationInVoltage        Integer32,
    qtechSystemElectricalInformationInCurrent        Integer32,
    qtechSystemElectricalInformationOutVoltage       Integer32,
    qtechSystemElectricalInformationOutCurrent       Integer32,
    qtechSystemElectricalInformationOutPower         Integer32,
    qtechSystemElectricalInformationTemperature      Integer32,
    qtechSystemElectricalInformationAirflowCoexist   DisplayString,
    qtechSystemElectricalInformationWarningStatus    DisplayString
  }

qtechSystemElectricalInformationDeviceIndex OBJECT-TYPE
    SYNTAX        Integer32
    MAX-ACCESS    read-only
    STATUS        current
    DESCRIPTION
        "An index that uniquely represents a device."
    ::= { qtechSystemElectricalInformationEntry 1 }

qtechSystemElectricalInformationIndex OBJECT-TYPE
    SYNTAX        Integer32
    MAX-ACCESS    read-only
    STATUS        current
    DESCRIPTION
        "An index that uniquely represents a electriacl."
    ::= { qtechSystemElectricalInformationEntry 2 }

qtechSystemElectricalInformationStatus OBJECT-TYPE
   	SYNTAX  INTEGER {
                noexist (1),          --no exist
                existnopower (2),     -- exist no power
                existreadypower (3),  --exist ready power
                normal (4),           --normal
                powerbutabnormal (5), --power but abnormal
                unknow (6)            --unknow
             }
    MAX-ACCESS    read-only
    STATUS        current
    DESCRIPTION
        "This object displays whether an electrical source is normal or not.
         If the electrical is no exist, the other of electrical information maybe 
         return nothing information and 0."
    ::= { qtechSystemElectricalInformationEntry 3 }

qtechSystemElectricalInformationType OBJECT-TYPE
    SYNTAX        DisplayString
    MAX-ACCESS    read-only
    STATUS        current
    DESCRIPTION
        "This object displays the type of the electrical. If the device is no support this information,
         This object will return nothing information."
    ::= { qtechSystemElectricalInformationEntry 4 }

qtechSystemElectricalInformationAttribute OBJECT-TYPE
    SYNTAX        DisplayString
    MAX-ACCESS    read-only
    STATUS        current
    DESCRIPTION
        "This object displays attribute of the electrical. If the device is no support
         this information, This object will return nothing information."
    ::= { qtechSystemElectricalInformationEntry 5 }

qtechSystemElectricalInformationSofeVersion OBJECT-TYPE
    SYNTAX        DisplayString
    MAX-ACCESS    read-only
    STATUS        current
    DESCRIPTION
        "This object displays the sofe version of the electrical. If the device is no support
         this information, This object will return nothing information."
    ::= { qtechSystemElectricalInformationEntry 6}

qtechSystemElectricalInformationHardwareVersion OBJECT-TYPE
    SYNTAX        DisplayString
    MAX-ACCESS    read-only
    STATUS        current
    DESCRIPTION
        "This object displays the hardware version of the electrical. If the device is no support
         this information, This object will return nothing information."
    ::= { qtechSystemElectricalInformationEntry 7 }

qtechSystemElectricalInformationSerial OBJECT-TYPE
    SYNTAX        DisplayString
    MAX-ACCESS    read-only
    STATUS        current
    DESCRIPTION
        "This object displays the serial of the electrical. If the device is no support
         this information, This object will return nothing information."
    ::= { qtechSystemElectricalInformationEntry 8 }

qtechSystemElectricalInformationProductionDate OBJECT-TYPE
    SYNTAX        DisplayString
    MAX-ACCESS    read-only
    STATUS        current
    DESCRIPTION
        "This object displays the productiron date of the electrical. If the device is no support
         this information, This object will return nothing information."
    ::= { qtechSystemElectricalInformationEntry 9 }

qtechSystemElectricalInformationRatedPower OBJECT-TYPE
    SYNTAX        Integer32
    MAX-ACCESS    read-only
    STATUS        current
    DESCRIPTION
        "This object displays the rated power(Unit: W) of the electrical. If the device is no support
         this information, This object will return 0."
    ::= { qtechSystemElectricalInformationEntry 10 }

qtechSystemElectricalInformationInVoltage OBJECT-TYPE
    SYNTAX        Integer32
    MAX-ACCESS    read-only
    STATUS        current
    DESCRIPTION
        "This object displays the input voltage(Unit: V) of the electrical. If the device is no support
         this information, This object will return 0."
    ::= { qtechSystemElectricalInformationEntry 11 }

qtechSystemElectricalInformationInCurrent OBJECT-TYPE
    SYNTAX        Integer32
    MAX-ACCESS    read-only
    STATUS        current
    DESCRIPTION
        "This object displays the input current(Unit: mA) of the electrical. If the device is no support
         this information, This object will return 0."
    ::= { qtechSystemElectricalInformationEntry 12 }

qtechSystemElectricalInformationOutVoltage OBJECT-TYPE
    SYNTAX        Integer32
    MAX-ACCESS    read-only
    STATUS        current
    DESCRIPTION
        "This object displays the output voltage(Unit: V) of the electrical. If the device is no support
         this information, This object will return 0."
    ::= { qtechSystemElectricalInformationEntry 13 }

qtechSystemElectricalInformationOutCurrent OBJECT-TYPE
    SYNTAX        Integer32
    MAX-ACCESS    read-only
    STATUS        current
    DESCRIPTION
        "This object displays the output current(Unit: mA) of the electrical. If the device is no support
         this information, This object will return 0."
    ::= { qtechSystemElectricalInformationEntry 14 }

qtechSystemElectricalInformationOutPower OBJECT-TYPE
    SYNTAX        Integer32
    MAX-ACCESS    read-only
    STATUS        current
    DESCRIPTION
        "This object displays the output power(Unit: W) of the electrical. If the device is no support
         this information, This object will return 0."
    ::= { qtechSystemElectricalInformationEntry 15 }

qtechSystemElectricalInformationTemperature OBJECT-TYPE
    SYNTAX        Integer32
    MAX-ACCESS    read-only
    STATUS        current
    DESCRIPTION
        "This object displays the temperature(Unit: C) of the electrical. If the device is no support
         this information, This object will return -255."
    ::= { qtechSystemElectricalInformationEntry 16 }

qtechSystemElectricalInformationAirflowCoexist OBJECT-TYPE
    SYNTAX        DisplayString
    MAX-ACCESS    read-only
    STATUS        current
    DESCRIPTION
        "This object displays the airflow coexist of the electrical. If the device is no support
         this information, This object will return nothing information."
    ::= { qtechSystemElectricalInformationEntry 17 }

qtechSystemElectricalInformationWarningStatus OBJECT-TYPE
    SYNTAX        DisplayString
    MAX-ACCESS    read-only
    STATUS        current
    DESCRIPTION
        "This object displays the warning status of the electrical. If the device is no support
         this information, This object will return nothing information."
    ::= { qtechSystemElectricalInformationEntry 18 }	

qtechSystemFanInformationTable OBJECT-TYPE
  SYNTAX      SEQUENCE OF QtechSystemFanInformationEntry
  MAX-ACCESS  not-accessible
  STATUS      current
  DESCRIPTION
    "A table of fan entries. Each object displays the fan information."
  ::= { qtechSystemMIBObjects 42 }

qtechSystemFanInformationEntry OBJECT-TYPE
  SYNTAX      QtechSystemFanInformationEntry
  MAX-ACCESS  not-accessible
  STATUS      current
  DESCRIPTION
    "An entry displays the fan information."
  INDEX { qtechSystemFanInformationDeviceIndex ,  qtechSystemFanInformationFanIndex}
  ::= {qtechSystemFanInformationTable 1 }

QtechSystemFanInformationEntry ::=
  SEQUENCE {
    qtechSystemFanInformationDeviceIndex      Integer32,
    qtechSystemFanInformationFanIndex         Integer32,
    qtechSystemFanInformationStatus           INTEGER,
    qtechSystemFanInformationType             DisplayString,
    qtechSystemFanInformationAttribute        DisplayString,
    qtechSystemFanInformationSofeVersion      DisplayString,
    qtechSystemFanInformationFirmwareVersion  DisplayString,
    qtechSystemFanInformationHardwareVersion  DisplayString,
    qtechSystemFanInformationSerial           DisplayString,
    qtechSystemFanInformationProductionDate   DisplayString,
    qtechSystemFanInformationTemperature      Integer32,
    qtechSystemFanInformationNumber           Integer32,
    qtechSystemFanInformationAirflowCoexist   DisplayString,
    qtechSystemFanInformationWarningStatus    DisplayString
  }

qtechSystemFanInformationDeviceIndex  OBJECT-TYPE
    SYNTAX        Integer32
    MAX-ACCESS    read-only
    STATUS        current
    DESCRIPTION
        "An index that uniquely represents a device."
    ::= { qtechSystemFanInformationEntry 1 }

qtechSystemFanInformationFanIndex OBJECT-TYPE
    SYNTAX        Integer32
    MAX-ACCESS    read-only
    STATUS        current
    DESCRIPTION
        "An index that uniquely represents a fan device."
    ::= { qtechSystemFanInformationEntry 2 }

qtechSystemFanInformationStatus OBJECT-TYPE
   	SYNTAX  INTEGER {
                noexist (1),          --no exist
                existnopower (2),     --exist no power
                existreadypower (3),  --exist ready power
                normal (4),           --normal
                powerbutabnormal (5), --power but abnormal
                unknow (6)            --unknow
             }
    MAX-ACCESS    read-only
    STATUS        current
    DESCRIPTION
        "This object displays whether an fan device source is exist or not.
         If the fan device is no exist, the other of fan information maybe 
         return nothing information and 0."
    ::= { qtechSystemFanInformationEntry 3 }

qtechSystemFanInformationType OBJECT-TYPE
    SYNTAX        DisplayString
    MAX-ACCESS    read-only
    STATUS        current
    DESCRIPTION
        "This object displays the type of the fan. If the device is no support this information,
         This object will return nothing information."
    ::= { qtechSystemFanInformationEntry 4 }

qtechSystemFanInformationAttribute OBJECT-TYPE
    SYNTAX        DisplayString
    MAX-ACCESS    read-only
    STATUS        current
    DESCRIPTION
        "This object displays attribute of the fan. If the device is no support
         this information, This object will return nothing information."
    ::= { qtechSystemFanInformationEntry 5 }

qtechSystemFanInformationSofeVersion OBJECT-TYPE
    SYNTAX        DisplayString
    MAX-ACCESS    read-only
    STATUS        current
    DESCRIPTION
        "This object displays the sofe version of the fan. If the device is no support
         this information, This object will return nothing information."
    ::= { qtechSystemFanInformationEntry 6}

qtechSystemFanInformationFirmwareVersion OBJECT-TYPE
    SYNTAX        DisplayString
    MAX-ACCESS    read-only
    STATUS        current
    DESCRIPTION
        "This object displays the firmware version of the fan. If the device is no support
         this information, This object will return nothing information."
    ::= { qtechSystemFanInformationEntry 7 }

qtechSystemFanInformationHardwareVersion OBJECT-TYPE
    SYNTAX        DisplayString
    MAX-ACCESS    read-only
    STATUS        current
    DESCRIPTION
        "This object displays the hardware version of the fan. If the device is no support
         this information, This object will return nothing information."
    ::= { qtechSystemFanInformationEntry 8 }

qtechSystemFanInformationSerial OBJECT-TYPE
    SYNTAX        DisplayString
    MAX-ACCESS    read-only
    STATUS        current
    DESCRIPTION
        "This object displays the serial of the fan. If the device is no support
         this information, This object will return nothing information."
    ::= { qtechSystemFanInformationEntry 9 }

qtechSystemFanInformationProductionDate OBJECT-TYPE
    SYNTAX        DisplayString
    MAX-ACCESS    read-only
    STATUS        current
    DESCRIPTION
        "This object displays the productiron date of the fan. If the device is no support
         this information, This object will return nothing information."
    ::= { qtechSystemFanInformationEntry 10 }

qtechSystemFanInformationTemperature OBJECT-TYPE
    SYNTAX        Integer32
    MAX-ACCESS    read-only
    STATUS        current
    DESCRIPTION
        "This object displays the temperature of the fan device. If the device is no support
         this information, This object will return -255."
    ::= { qtechSystemFanInformationEntry 11 }

qtechSystemFanInformationNumber OBJECT-TYPE
    SYNTAX        Integer32
    MAX-ACCESS    read-only
    STATUS        current
    DESCRIPTION
        "This object displays the number of the fan device. If the device is no support
         this information, This object will return 0."
    ::= { qtechSystemFanInformationEntry 12 }

qtechSystemFanInformationAirflowCoexist OBJECT-TYPE
    SYNTAX        DisplayString
    MAX-ACCESS    read-only
    STATUS        current
    DESCRIPTION
        "This object displays the airflow coexist of the fan device. If the device is no support
         this information, This object will return nothing information."
    ::= { qtechSystemFanInformationEntry 13 }

qtechSystemFanInformationWarningStatus OBJECT-TYPE
    SYNTAX        DisplayString
    MAX-ACCESS    read-only
    STATUS        current
    DESCRIPTION
        "This object displays the warning status of the fan device. If the device is no support
         this information, This object will return nothing information."
    ::= { qtechSystemFanInformationEntry 14 }

qtechSystemFanStatusTable OBJECT-TYPE
  SYNTAX      SEQUENCE OF QtechSystemFanStatusEntry
  MAX-ACCESS  not-accessible
  STATUS      current
  DESCRIPTION
    "A table of fan status entries. Each object displays the fan status information."
  ::= { qtechSystemMIBObjects 43 }

qtechSystemFanStatusEntry OBJECT-TYPE
  SYNTAX      QtechSystemFanStatusEntry
  MAX-ACCESS  not-accessible
  STATUS      current
  DESCRIPTION
    "An entry displays the fan status information."
  INDEX { qtechSystemFanStatusDeviceIndex,
          qtechSystemFanStatusFanIndex,
          qtechSystemFanStatusIndex }
  ::= {qtechSystemFanStatusTable 1 }

QtechSystemFanStatusEntry ::=
  SEQUENCE {
    qtechSystemFanStatusDeviceIndex      Integer32,
    qtechSystemFanStatusFanIndex         Integer32,
    qtechSystemFanStatusIndex            Integer32,
    qtechSystemFanStatus                 INTEGER,
    qtechSystemFanStatusLevel            Integer32,
    qtechSystemFanStatusSpeed            Integer32
  }

qtechSystemFanStatusDeviceIndex  OBJECT-TYPE
    SYNTAX        Integer32
    MAX-ACCESS    read-only
    STATUS        current
    DESCRIPTION
        "An index that uniquely represents a device."
    ::= { qtechSystemFanStatusEntry 1 }

qtechSystemFanStatusFanIndex OBJECT-TYPE
    SYNTAX        Integer32
    MAX-ACCESS    read-only
    STATUS        current
    DESCRIPTION
        "An index that uniquely represents a fan device."
    ::= { qtechSystemFanStatusEntry 2 }

qtechSystemFanStatusIndex OBJECT-TYPE
    SYNTAX        Integer32
    MAX-ACCESS    read-only
    STATUS        current
    DESCRIPTION
        "An index that uniquely represents a fan."
    ::= { qtechSystemFanStatusEntry 3 }

qtechSystemFanStatus OBJECT-TYPE
   	SYNTAX  INTEGER {
                noexist (1),          --no exist
                existnopower (2),     --exist no power
                existreadypower (3),  --exist ready power
                normal (4),           --normal
                powerbutabnormal (5), --power but abnormal
                unknow (6)            --unknow
             }
    MAX-ACCESS    read-only
    STATUS        current
    DESCRIPTION
        "This object displays whether an fan is normal or not."
    ::= { qtechSystemFanStatusEntry 4 }

qtechSystemFanStatusLevel OBJECT-TYPE
    SYNTAX        Integer32
    MAX-ACCESS    read-only
    STATUS        current
    DESCRIPTION
        "This object displays the level of the fan speed. If the device is no support this information,
         This object will return 0."
    ::= { qtechSystemFanStatusEntry 5 }

qtechSystemFanStatusSpeed OBJECT-TYPE
    SYNTAX        Integer32
    MAX-ACCESS    read-only
    STATUS        current
    DESCRIPTION
        "This object displays fan speed(rpm). If the device is no support
         this information, This object will return nothing information."
    ::= { qtechSystemFanStatusEntry 6 }

qtechSystemMultipleTemperatureTable OBJECT-TYPE
  SYNTAX      SEQUENCE OF QtechSystemMultipleTemperatureEntry
  MAX-ACCESS  not-accessible
  STATUS      current
  DESCRIPTION
    "A table of multiple temperature entries. Each object displays 
     the multiple temperature information."
  ::= { qtechSystemMIBObjects 44 }

qtechSystemMultipleTemperatureEntry OBJECT-TYPE
  SYNTAX      QtechSystemMultipleTemperatureEntry
  MAX-ACCESS  not-accessible
  STATUS      current
  DESCRIPTION
    "An entry displays the multiple temperature information."
  INDEX { qtechSystemMultipleTemperatureDeviceIndex,
          qtechSystemMultipleTemperatureSlotIndex, 
          qtechSystemMultipleTemperatureIndex }
  ::= { qtechSystemMultipleTemperatureTable 1 }

QtechSystemMultipleTemperatureEntry ::=
  SEQUENCE {
    qtechSystemMultipleTemperatureDeviceIndex  Integer32,
    qtechSystemMultipleTemperatureSlotIndex    Integer32,
    qtechSystemMultipleTemperatureIndex        Integer32,
    qtechSystemMultipleTemperatureName         DisplayString,
    qtechSystemMultipleTemperatureCurrent      Integer32,
    qtechSystemMultipleTemperatureWarning      Integer32,
    qtechSystemMultipleTemperatureCritical     Integer32
  }

qtechSystemMultipleTemperatureDeviceIndex OBJECT-TYPE
    SYNTAX        Integer32
    MAX-ACCESS    read-only
    STATUS        current
    DESCRIPTION
        "An index that uniquely represents a device."
    ::= { qtechSystemMultipleTemperatureEntry 1 }

qtechSystemMultipleTemperatureSlotIndex OBJECT-TYPE
    SYNTAX        Integer32
    MAX-ACCESS    read-only
    STATUS        current
    DESCRIPTION
        "An index that uniquely represents a slot device."
    ::= { qtechSystemMultipleTemperatureEntry 2 }

qtechSystemMultipleTemperatureIndex OBJECT-TYPE
    SYNTAX        Integer32
    MAX-ACCESS    read-only
    STATUS        current
    DESCRIPTION
        "An index that uniquely represents a device's multiple temperature information."
    ::= { qtechSystemMultipleTemperatureEntry 3 }

qtechSystemMultipleTemperatureName OBJECT-TYPE
    SYNTAX        DisplayString
    MAX-ACCESS    read-only
    STATUS        current
    DESCRIPTION
        "A textual name assigned to a multiple temperature chip"
    ::= { qtechSystemMultipleTemperatureEntry 4 }          
                    
qtechSystemMultipleTemperatureCurrent OBJECT-TYPE
    SYNTAX        Integer32
    MAX-ACCESS    read-only
    STATUS        current
    DESCRIPTION
        "Return the current multiple temperature of the FastSwitch.The temperature display
         is not supported for the current temperature returns to -255."
::= { qtechSystemMultipleTemperatureEntry 5 }

qtechSystemMultipleTemperatureWarning OBJECT-TYPE
    SYNTAX        Integer32
    MAX-ACCESS    read-write
    STATUS        current
    DESCRIPTION
        "Return the warning multiple temperature of the FastSwitch.The temperature display
         is not supported for the warning temperature returns to -255."
::= { qtechSystemMultipleTemperatureEntry 6 }

qtechSystemMultipleTemperatureCritical OBJECT-TYPE
    SYNTAX        Integer32
    MAX-ACCESS    read-write
    STATUS        current
    DESCRIPTION
        "Return the critical multiple temperature of the FastSwitch.The temperature display
         is not supported for the critical temperature returns to -255."
::= { qtechSystemMultipleTemperatureEntry 7 }
        
qtechSystemAccurateUptime OBJECT-TYPE
    SYNTAX        TimeTicks
    MAX-ACCESS    read-only
    STATUS        current
    DESCRIPTION
        "Return the accurate system Uptime of equipment,unit is ticks."
    ::={ qtechSystemMIBObjects 45 }     

qtechSystemPowerIndex OBJECT-TYPE
    SYNTAX Integer32
    MAX-ACCESS read-only
    STATUS current
    DESCRIPTION
        "Index of power"
    ::= { qtechSystemMIBObjects 46 }

qtechSystemSwitchID OBJECT-TYPE
    SYNTAX Integer32
    MAX-ACCESS read-only
    STATUS current
    DESCRIPTION
        "Switch id in VSU"
    ::= { qtechSystemMIBObjects 47 }

qtechSystemApDeviceDescriptionTable OBJECT-TYPE
  SYNTAX      SEQUENCE OF QtechSystemApDeviceDescriptionEntry
  MAX-ACCESS  not-accessible
  STATUS      current
  DESCRIPTION
    "A table of lank ap system entries. Each object displays 
     the lank ap system information."
  ::= { qtechSystemMIBObjects 48 }

qtechSystemApDeviceDescriptionEntry OBJECT-TYPE
  SYNTAX      QtechSystemApDeviceDescriptionEntry
  MAX-ACCESS  not-accessible
  STATUS      current
  DESCRIPTION
    "An entry displays the ap Device Description."
  INDEX { qtechSystemApDescMacAddr }
  ::= { qtechSystemApDeviceDescriptionTable 1 }

QtechSystemApDeviceDescriptionEntry ::=
  SEQUENCE {
    qtechSystemApDescMacAddr          MacAddress,
    qtechSystemApMemoryType           INTEGER,
    qtechSystemApMemorySize           Gauge,
    qtechSystemAPFlashType            INTEGER,
    qtechSystemAPFlashSize            Gauge,
    qtechSystemApNVRAMSize            Gauge,
    qtechSystemApCFSize               Gauge,
    qtechSystemApCPUType              DisplayString        
  }
    
qtechSystemApDescMacAddr OBJECT-TYPE
    SYNTAX        MacAddress
    MAX-ACCESS    read-only
    STATUS        current
    DESCRIPTION
        "An index that uniquely represents ap system information."
    ::= { qtechSystemApDeviceDescriptionEntry 1 } 

qtechSystemApMemoryType OBJECT-TYPE
    SYNTAX INTEGER {
        reserved(0),
        sdram(1),
        ddram(2)
    }
    MAX-ACCESS    read-only
    STATUS        current
    DESCRIPTION
        "Return the memory type of the lank ap system."
    ::= { qtechSystemApDeviceDescriptionEntry 2 } 

qtechSystemApMemorySize OBJECT-TYPE
    SYNTAX        Gauge
    MAX-ACCESS    read-only
    STATUS        current
    DESCRIPTION
        "Return the memory card storage of the lank ap system, unit is MB."
    ::= { qtechSystemApDeviceDescriptionEntry 3 } 

qtechSystemAPFlashType OBJECT-TYPE
    SYNTAX INTEGER {
        reserved(0),
        nor(1),
        non-nor(2)
    }
    MAX-ACCESS    read-only
    STATUS        current
    DESCRIPTION
        "An index that uniquely represents ap system information."
    ::= { qtechSystemApDeviceDescriptionEntry 4 } 

qtechSystemAPFlashSize OBJECT-TYPE
    SYNTAX        Gauge
    MAX-ACCESS    read-only
    STATUS        current
    DESCRIPTION
        "Return the flash size of the lank ap system, unit is MB."
    ::= { qtechSystemApDeviceDescriptionEntry 5 } 

qtechSystemApNVRAMSize OBJECT-TYPE
    SYNTAX        Gauge
    MAX-ACCESS    read-only
    STATUS        current
    DESCRIPTION
        "Return the NVRAM size of the lank ap system, unit is MB."
    ::= { qtechSystemApDeviceDescriptionEntry 6 } 

qtechSystemApCFSize OBJECT-TYPE
    SYNTAX        Gauge
    MAX-ACCESS    read-only
    STATUS        current
    DESCRIPTION
        "Return the CF size of the lank ap system, unit is MB."
    ::= { qtechSystemApDeviceDescriptionEntry 7 } 

qtechSystemApCPUType OBJECT-TYPE
    SYNTAX        DisplayString
    MAX-ACCESS    read-only
    STATUS        current
    DESCRIPTION
        "Return the cpu type of the lank ap system."
    ::= { qtechSystemApDeviceDescriptionEntry 8 } 

qtechSystemApDeviceStatisticsTable OBJECT-TYPE
  SYNTAX      SEQUENCE OF QtechSystemApDeviceStatisticsEntry
  MAX-ACCESS  not-accessible
  STATUS      current
  DESCRIPTION
    "A table of lank ap system entries. Each object displays 
     the lank ap system information."
  ::= { qtechSystemMIBObjects 49 }
  
qtechSystemApDeviceStatisticsEntry OBJECT-TYPE
  SYNTAX      QtechSystemApDeviceStatisticsEntry
  MAX-ACCESS  not-accessible
  STATUS      current
  DESCRIPTION
    "An entry displays the ap Device Statistics."
  INDEX { qtechSystemApStatMacAddr }
  ::= { qtechSystemApDeviceStatisticsTable 1 }

QtechSystemApDeviceStatisticsEntry ::=
  SEQUENCE {
    qtechSystemApStatMacAddr                   MacAddress,
    qtechSystemApInterfaceNum                  Integer32,
    qtechSystemApUptime                        TimeTicks,
    qtechSystemApCPUUtilizationCurrent         Percent,
    qtechSystemApCPUUtilizationAverage         Percent, 
    qtechSystemApMemoryPoolCurrentUtilization  Percent,
    qtechSystemApMemoryPoolAverageUtilization  Percent,
    qtechSystemApFlashFreeSize                 Unsigned32,
    qtechSystemAPDeviceTemperature             Integer32
  }
    
qtechSystemApStatMacAddr OBJECT-TYPE
    SYNTAX        MacAddress
    MAX-ACCESS    read-only
    STATUS        current
    DESCRIPTION
        "An index that uniquely represents ap system information."
    ::= { qtechSystemApDeviceStatisticsEntry 1 }    

qtechSystemApInterfaceNum OBJECT-TYPE
    SYNTAX        Integer32
    MAX-ACCESS    read-only
    STATUS        current
    DESCRIPTION
        "Return the interface number of the lank ap system."
    ::= { qtechSystemApDeviceStatisticsEntry 2 }  

qtechSystemApUptime OBJECT-TYPE
    SYNTAX        TimeTicks
    MAX-ACCESS    read-only
    STATUS        current
    DESCRIPTION
        "Return the SysUptime of lank ap equipment, unit is ticks."
    ::= { qtechSystemApDeviceStatisticsEntry 3 } 

qtechSystemApCPUUtilizationCurrent OBJECT-TYPE
    SYNTAX        Percent
    MAX-ACCESS    read-only
    STATUS        current
    DESCRIPTION
        "This is the collection of current lank ap cpu using rate."
    ::= { qtechSystemApDeviceStatisticsEntry 4 }

qtechSystemApCPUUtilizationAverage OBJECT-TYPE
    SYNTAX        Percent
    MAX-ACCESS    read-only
    STATUS        current
    DESCRIPTION
        "This is the average cpu using rate currently."
    ::= { qtechSystemApDeviceStatisticsEntry 5 }

qtechSystemApMemoryPoolCurrentUtilization OBJECT-TYPE
    SYNTAX        Percent
    MAX-ACCESS    read-only
    STATUS        current
    DESCRIPTION
        "This is the memory pool utilization currently."
    ::= { qtechSystemApDeviceStatisticsEntry 6 }

qtechSystemApMemoryPoolAverageUtilization OBJECT-TYPE
    SYNTAX        Percent
    MAX-ACCESS    read-only
    STATUS        current
    DESCRIPTION
        "This is the average memory pool utilization currently."
    ::= { qtechSystemApDeviceStatisticsEntry 7 } 

qtechSystemApFlashFreeSize OBJECT-TYPE
    SYNTAX        Unsigned32
    MAX-ACCESS    read-only
    STATUS        current
    DESCRIPTION
        "This is the free size of the flash device, unit is MB."
    ::= { qtechSystemApDeviceStatisticsEntry 8 }

qtechSystemAPDeviceTemperature OBJECT-TYPE
    SYNTAX        Integer32
    MAX-ACCESS    read-only
    STATUS        current
    DESCRIPTION
        "This is the temperature of the ap.But the ap is no support
         this information, so it will return 35 in perpetuity"
    ::= { qtechSystemApDeviceStatisticsEntry 9 }   
    
qtechSystemUptimeMsLow OBJECT-TYPE
  SYNTAX        Unsigned32
  MAX-ACCESS    read-only
  STATUS        current
  DESCRIPTION
    "Return the equipment SysUptime Low 32-bit,unit is tick."
  ::={ qtechSystemMIBObjects 50 }
  
qtechSystemUptimeMsHigh OBJECT-TYPE
  SYNTAX        Unsigned32
  MAX-ACCESS    read-only
  STATUS        current
  DESCRIPTION
    "Return the equipment SysUptime High 32-bit,unit is tick."
  ::={ qtechSystemMIBObjects 51 }      
 
qtechSystemFanSNTable OBJECT-TYPE
  SYNTAX      SEQUENCE OF QtechSystemFanSNEntry
  MAX-ACCESS  not-accessible
  STATUS      current
  DESCRIPTION
    "A table of fan's serial number"
  ::= { qtechSystemMIBObjects 52 }

qtechSystemFanSNEntry OBJECT-TYPE
  SYNTAX      QtechSystemFanSNEntry
  MAX-ACCESS  not-accessible
  STATUS      current
  DESCRIPTION
    "An entry displays fan SN."
  INDEX { qtechSystemFanPadIndex }
  ::= { qtechSystemFanSNTable 1 }

QtechSystemFanSNEntry ::=
  SEQUENCE {
    qtechSystemFanPadIndex          Integer32,
    qtechSystemFanPadName           DisplayString,
    qtechSystemFanPadSN             DisplayString
  }

qtechSystemFanPadIndex OBJECT-TYPE
    SYNTAX        Integer32
    MAX-ACCESS    read-only
    STATUS        current
    DESCRIPTION
        "Return the index of the fan pad."
    ::= { qtechSystemFanSNEntry 1 }  

qtechSystemFanPadName OBJECT-TYPE
    SYNTAX        DisplayString
    MAX-ACCESS    read-only
    STATUS        current
    DESCRIPTION
        "Return the name of the fan pad."
    ::= { qtechSystemFanSNEntry 2 } 

qtechSystemFanPadSN OBJECT-TYPE
    SYNTAX        DisplayString
    MAX-ACCESS    read-only
    STATUS        current
    DESCRIPTION
        "Return the SN of the fan pad."
    ::= { qtechSystemFanSNEntry 3 } 

qtechSystemDsfSNTable OBJECT-TYPE
  SYNTAX      SEQUENCE OF QtechSystemDsfSNEntry
  MAX-ACCESS  not-accessible
  STATUS      current
  DESCRIPTION
    "A table of dsf's serial number"
  ::= { qtechSystemMIBObjects 53 }

qtechSystemDsfSNEntry OBJECT-TYPE
  SYNTAX      QtechSystemDsfSNEntry
  MAX-ACCESS  not-accessible
  STATUS      current
  DESCRIPTION
    "An entry displays dsf SN."
  INDEX { qtechSystemDsfIndex }
  ::= { qtechSystemDsfSNTable 1 }

QtechSystemDsfSNEntry ::=
  SEQUENCE {
    qtechSystemDsfIndex          Integer32,  
    qtechSystemDsfName           DisplayString,
    qtechSystemDsfSN             DisplayString
  }

qtechSystemDsfIndex OBJECT-TYPE
    SYNTAX        Integer32
    MAX-ACCESS    read-only
    STATUS        current
    DESCRIPTION
        "Return the index of the dsf."
    ::= { qtechSystemDsfSNEntry 1 }  

qtechSystemDsfName OBJECT-TYPE
    SYNTAX        DisplayString
    MAX-ACCESS    read-only
    STATUS        current
    DESCRIPTION
        "Return the name of the dsf."
    ::= { qtechSystemDsfSNEntry 2 } 

qtechSystemDsfSN OBJECT-TYPE
    SYNTAX        DisplayString
    MAX-ACCESS    read-only
    STATUS        current
    DESCRIPTION
        "Return the SN of the dsf."
    ::= { qtechSystemDsfSNEntry 3 } 

qtechSystemPowerSNTable OBJECT-TYPE
  SYNTAX      SEQUENCE OF QtechSystemPowerSNEntry
  MAX-ACCESS  not-accessible
  STATUS      current
  DESCRIPTION
    "A table of power's serial number"
  ::= { qtechSystemMIBObjects 54 }

qtechSystemPowerSNEntry OBJECT-TYPE
  SYNTAX      QtechSystemPowerSNEntry
  MAX-ACCESS  not-accessible
  STATUS      current
  DESCRIPTION
    "An entry displays power SN."
  INDEX { qtechSystemPowerSNIndex }
  ::= { qtechSystemPowerSNTable 1 }

QtechSystemPowerSNEntry ::=
  SEQUENCE {
    qtechSystemPowerSNIndex          Integer32,
    qtechSystemPowerSNName           DisplayString,  
    qtechSystemPowerSN               DisplayString
  }

qtechSystemPowerSNIndex OBJECT-TYPE
    SYNTAX        Integer32
    MAX-ACCESS    read-only
    STATUS        current
    DESCRIPTION
        "Return the index of the power."
    ::= { qtechSystemPowerSNEntry 1 }  

qtechSystemPowerSNName OBJECT-TYPE
    SYNTAX        DisplayString
    MAX-ACCESS    read-only
    STATUS        current
    DESCRIPTION
        "Return the name of the power."
    ::= { qtechSystemPowerSNEntry 2 } 

qtechSystemPowerSN OBJECT-TYPE
    SYNTAX        DisplayString
    MAX-ACCESS    read-only
    STATUS        current
    DESCRIPTION
        "Return the SN of the power."
    ::= { qtechSystemPowerSNEntry 3 } 
 
 qtechSystemFanPad1SpeedTable OBJECT-TYPE
  SYNTAX      SEQUENCE OF QtechSystemFanPad1SpeedEntry
  MAX-ACCESS  not-accessible
  STATUS      current
  DESCRIPTION
    "A table of fan's speed on fan pad1."
  ::= { qtechSystemMIBObjects 55 }

qtechSystemFanPad1SpeedEntry OBJECT-TYPE
  SYNTAX      QtechSystemFanPad1SpeedEntry
  MAX-ACCESS  not-accessible
  STATUS      current
  DESCRIPTION
    "An entry displays fan's speed on same fan pad"
  INDEX { qtechSystemOamFanPad1Index }
  ::= { qtechSystemFanPad1SpeedTable 1 }

QtechSystemFanPad1SpeedEntry ::=
  SEQUENCE {
    qtechSystemOamFanPad1Index    Integer32,
    qtechSystemOamFanPad1Name	  DisplayString,
    qtechSystemFanPad1Speed1         Integer32,
    qtechSystemFanPad1Speed2         Integer32,
    qtechSystemFanPad1Speed3         Integer32,
    qtechSystemFanPad1Speed4         Integer32,
    qtechSystemFanPad1Speed5         Integer32,
    qtechSystemFanPad1Speed6         Integer32,
    qtechSystemFanPad1Speed7         Integer32,
    qtechSystemFanPad1Speed8         Integer32,    
    qtechSystemFanPad1Speed9         Integer32
  }

qtechSystemOamFanPad1Index OBJECT-TYPE
    SYNTAX        Integer32
    MAX-ACCESS    read-only
    STATUS        current
    DESCRIPTION
        "Return the index of the fan pad."
    ::= { qtechSystemFanPad1SpeedEntry 1 }

qtechSystemOamFanPad1Name OBJECT-TYPE
    SYNTAX        DisplayString
    MAX-ACCESS    read-only
    STATUS        current
    DESCRIPTION
        "Return the name of the fan pad."
    ::= { qtechSystemFanPad1SpeedEntry 2 }

qtechSystemFanPad1Speed1 OBJECT-TYPE
    SYNTAX        Integer32
    MAX-ACCESS    read-only
    STATUS        current
    DESCRIPTION
        "Return the speed of the fan1."
    ::= { qtechSystemFanPad1SpeedEntry 3 }

qtechSystemFanPad1Speed2 OBJECT-TYPE
    SYNTAX        Integer32
    MAX-ACCESS    read-only
    STATUS        current
    DESCRIPTION
        "Return the speed of the fan2."
    ::= { qtechSystemFanPad1SpeedEntry 4 }

qtechSystemFanPad1Speed3 OBJECT-TYPE
    SYNTAX        Integer32
    MAX-ACCESS    read-only
    STATUS        current
    DESCRIPTION
        "Return the speed of the fan3."
    ::= { qtechSystemFanPad1SpeedEntry 5 }

qtechSystemFanPad1Speed4 OBJECT-TYPE
    SYNTAX        Integer32
    MAX-ACCESS    read-only
    STATUS        current
    DESCRIPTION
        "Return the speed of the fan4."
    ::= { qtechSystemFanPad1SpeedEntry 6 }

qtechSystemFanPad1Speed5 OBJECT-TYPE
    SYNTAX        Integer32
    MAX-ACCESS    read-only
    STATUS        current
    DESCRIPTION
        "Return the speed of the fan5."
    ::= { qtechSystemFanPad1SpeedEntry 7 }

qtechSystemFanPad1Speed6 OBJECT-TYPE
    SYNTAX        Integer32
    MAX-ACCESS    read-only
    STATUS        current
    DESCRIPTION
        "Return the speed of the fan6."
    ::= { qtechSystemFanPad1SpeedEntry 8 }

qtechSystemFanPad1Speed7 OBJECT-TYPE
    SYNTAX        Integer32
    MAX-ACCESS    read-only
    STATUS        current
    DESCRIPTION
        "Return the speed of the fan7."
    ::= { qtechSystemFanPad1SpeedEntry 9 }

qtechSystemFanPad1Speed8 OBJECT-TYPE
    SYNTAX        Integer32
    MAX-ACCESS    read-only
    STATUS        current
    DESCRIPTION
        "Return the speed of the fan8."
    ::= { qtechSystemFanPad1SpeedEntry 10 }
   
qtechSystemFanPad1Speed9 OBJECT-TYPE
    SYNTAX        Integer32
    MAX-ACCESS    read-only
    STATUS        current
    DESCRIPTION
        "Return the speed of the fan9."
    ::= { qtechSystemFanPad1SpeedEntry 11 }

qtechSystemFanPad2SpeedTable OBJECT-TYPE
  SYNTAX      SEQUENCE OF QtechSystemFanPad2SpeedEntry
  MAX-ACCESS  not-accessible
  STATUS      current
  DESCRIPTION
    "A table of fan's speed on fan pad2."
  ::= { qtechSystemMIBObjects 56 }

qtechSystemFanPad2SpeedEntry OBJECT-TYPE
  SYNTAX      QtechSystemFanPad2SpeedEntry
  MAX-ACCESS  not-accessible
  STATUS      current
  DESCRIPTION
    "An entry displays fan's speed on same fan pad2"
  INDEX { qtechSystemOamFanPad2Index }
  ::= { qtechSystemFanPad2SpeedTable 1 }

QtechSystemFanPad2SpeedEntry ::=
  SEQUENCE {
    qtechSystemOamFanPad2Index    Integer32,
    qtechSystemOamFanPad2Name	  DisplayString,
    qtechSystemFanPad2Speed1         Integer32,
    qtechSystemFanPad2Speed2         Integer32,
    qtechSystemFanPad2Speed3         Integer32,
  }

qtechSystemOamFanPad2Index OBJECT-TYPE
    SYNTAX        Integer32
    MAX-ACCESS    read-only
    STATUS        current
    DESCRIPTION
        "Return the index of the fan pad2."
    ::= { qtechSystemFanPad2SpeedEntry 1 }

qtechSystemOamFanPad2Name OBJECT-TYPE
    SYNTAX        DisplayString
    MAX-ACCESS    read-only
    STATUS        current
    DESCRIPTION
        "Return the name of the fan pad."
    ::= { qtechSystemFanPad2SpeedEntry 2 }

qtechSystemFanPad2Speed1 OBJECT-TYPE
    SYNTAX        Integer32
    MAX-ACCESS    read-only
    STATUS        current
    DESCRIPTION
        "Return the speed of the fan1."
    ::= { qtechSystemFanPad2SpeedEntry 3 }

qtechSystemFanPad2Speed2 OBJECT-TYPE
    SYNTAX        Integer32
    MAX-ACCESS    read-only
    STATUS        current
    DESCRIPTION
        "Return the speed of the fan2."
    ::= { qtechSystemFanPad2SpeedEntry 4 }

qtechSystemFanPad2Speed3 OBJECT-TYPE
    SYNTAX        Integer32
    MAX-ACCESS    read-only
    STATUS        current
    DESCRIPTION
        "Return the speed of the fan3."
    ::= { qtechSystemFanPad2SpeedEntry 5 }

qtechSystemFanPad3SpeedTable OBJECT-TYPE
  SYNTAX      SEQUENCE OF QtechSystemFanPad3SpeedEntry
  MAX-ACCESS  not-accessible
  STATUS      current
  DESCRIPTION
    "A table of fan's speed on fan pad3."
  ::= { qtechSystemMIBObjects 57 }

qtechSystemFanPad3SpeedEntry OBJECT-TYPE
  SYNTAX      QtechSystemFanPad3SpeedEntry
  MAX-ACCESS  not-accessible
  STATUS      current
  DESCRIPTION
    "An entry displays fan's speed on same fan pad3"
  INDEX { qtechSystemOamFanPad3Index }
  ::= { qtechSystemFanPad3SpeedTable 1 }

QtechSystemFanPad3SpeedEntry ::=
  SEQUENCE {
    qtechSystemOamFanPad3Index    Integer32,
    qtechSystemOamFanPad3Name	  DisplayString,
    qtechSystemFanPad3Speed1         Integer32,
    qtechSystemFanPad3Speed2         Integer32,
    qtechSystemFanPad3Speed3         Integer32,
    qtechSystemFanPad3Speed4         Integer32,
    qtechSystemFanPad3Speed5         Integer32,
  }

qtechSystemOamFanPad3Index OBJECT-TYPE
    SYNTAX        Integer32
    MAX-ACCESS    read-only
    STATUS        current
    DESCRIPTION
        "Return the index of the fan pad3."
    ::= { qtechSystemFanPad3SpeedEntry 1 }

qtechSystemOamFanPad3Name OBJECT-TYPE
    SYNTAX        DisplayString
    MAX-ACCESS    read-only
    STATUS        current
    DESCRIPTION
        "Return the name of the fan pad."
    ::= { qtechSystemFanPad3SpeedEntry 2 }

qtechSystemFanPad3Speed1 OBJECT-TYPE
    SYNTAX        Integer32
    MAX-ACCESS    read-only
    STATUS        current
    DESCRIPTION
        "Return the speed of the fan1."
    ::= { qtechSystemFanPad3SpeedEntry 3 }

qtechSystemFanPad3Speed2 OBJECT-TYPE
    SYNTAX        Integer32
    MAX-ACCESS    read-only
    STATUS        current
    DESCRIPTION
        "Return the speed of the fan2."
    ::= { qtechSystemFanPad3SpeedEntry 4 }

qtechSystemFanPad3Speed3 OBJECT-TYPE
    SYNTAX        Integer32
    MAX-ACCESS    read-only
    STATUS        current
    DESCRIPTION
        "Return the speed of the fan3."
    ::= { qtechSystemFanPad3SpeedEntry 5 }

qtechSystemFanPad3Speed4 OBJECT-TYPE
    SYNTAX        Integer32
    MAX-ACCESS    read-only
    STATUS        current
    DESCRIPTION
        "Return the speed of the fan4."
    ::= { qtechSystemFanPad3SpeedEntry 6 }

qtechSystemFanPad3Speed5 OBJECT-TYPE
    SYNTAX        Integer32
    MAX-ACCESS    read-only
    STATUS        current
    DESCRIPTION
        "Return the speed of the fan5."
    ::= { qtechSystemFanPad3SpeedEntry 7 }
   
qtechSystemMIBTraps OBJECT IDENTIFIER ::= { qtechSystemMIB 2 }

qtechSystemHardChangeDesc OBJECT-TYPE
        SYNTAX DisplayString
        MAX-ACCESS accessible-for-notify
        STATUS current
        DESCRIPTION
          "The description of hard change"
        ::= { qtechSystemMIBTraps 1 }       
        
qtechSystemHardChangeDetected NOTIFICATION-TYPE
        OBJECTS   {qtechSystemHardChangeDesc}
        STATUS     current
        DESCRIPTION
                "System hardware has changed include number of devices or number of modules 
                 or the place or type of the module is change."
        ::= { qtechSystemMIBTraps 2 }
        
qtechSystemPowerStateChange NOTIFICATION-TYPE
        OBJECTS   {qtechSystemHwPower}
        STATUS     current
        DESCRIPTION
                "while the state of power changed, then this trap will be sent."
        ::= { qtechSystemMIBTraps 3 }
        
qtechSystemFanStateChange NOTIFICATION-TYPE
        OBJECTS   {qtechSystemHwFan}
        STATUS     current
        DESCRIPTION
                "while the state of fan changed, then this trap will be sent."
        ::= { qtechSystemMIBTraps 4 }                

--2010-05    
qtechSystemCPUusageTooHighTrap NOTIFICATION-TYPE
        OBJECTS   {qtechCPUUtilization1Min}
        STATUS     current
        DESCRIPTION
                "CPU usage Too High warning."
        ::= { qtechSystemMIBTraps 5 }
                      
--2010-05 
qtechSystemCPUusageTooHighRecovTrap NOTIFICATION-TYPE
        OBJECTS   {qtechCPUUtilization1Min}
        STATUS     current
        DESCRIPTION
                "clear the warning of CPU usage too high and report the current CPU usage."
        ::= { qtechSystemMIBTraps 6 }
        
--2010-05 
qtechSystemTmpTooHighTrap NOTIFICATION-TYPE
        OBJECTS   {qtechSystemTemperatureCurrent}
        STATUS     current
        DESCRIPTION
                "Temperature Too High warning."
        ::= { qtechSystemMIBTraps 7 }   
           
--Temperature Too High Recover Trap 2010-05 
qtechSystemTmpTooHighRecovTrap NOTIFICATION-TYPE
        OBJECTS   {qtechSystemTemperatureCurrent}
        STATUS     current
        DESCRIPTION
                "clear the warning of temperature too high and report the current temperature."
        ::= { qtechSystemMIBTraps 8 }
                
--Memory usage too high trap 2010-05 
qtechSystemMemusageTooHighTrap NOTIFICATION-TYPE
        OBJECTS   {qtechMemoryPoolCurrentUtilization}
        STATUS     current
        DESCRIPTION
                "Memory usage too high warning."
        ::= { qtechSystemMIBTraps 9 }   
        
--Memory usage too high recover trap 2010-05 
qtechSystemMemusageTooHighRecovTrap NOTIFICATION-TYPE
        OBJECTS   {qtechMemoryPoolCurrentUtilization}
        STATUS     current
        DESCRIPTION
                "clear the warning of Memory usage too high and report the current Memory usage."
        ::= { qtechSystemMIBTraps 10 }  
        
--lank ap 2010-7     
qtechSystemLankApCPUusageTooHighTrap NOTIFICATION-TYPE
        OBJECTS   {
           qtechApMacAddr,
           qtechCPUUtilization1Min
        }
        STATUS     current
        DESCRIPTION
                "lank ap CPU usage Too High warning."
        ::= { qtechSystemMIBTraps 11 }
                      
--lank ap 2010-7 
qtechSystemLankApCPUusageTooHighRecovTrap NOTIFICATION-TYPE
        OBJECTS   {
           qtechApMacAddr,
           qtechCPUUtilization1Min
        }
        STATUS     current
        DESCRIPTION
                "clear the warning of lank ap CPU usage too high and report the current CPU usage."
        ::= { qtechSystemMIBTraps 12 }
        
--lank ap 2010-7
qtechSystemLankApMemusageTooHighTrap NOTIFICATION-TYPE
        OBJECTS   {
           qtechApMacAddr,
           qtechMemoryPoolCurrentUtilization
        }
        STATUS     current
        DESCRIPTION
                "lank ap Memory usage too high warning."
        ::= { qtechSystemMIBTraps 13 }   
        
--lank ap 2010-7
qtechSystemLankApMemusageTooHighRecovTrap NOTIFICATION-TYPE
        OBJECTS   {
           qtechApMacAddr,
           qtechMemoryPoolCurrentUtilization
        }
        STATUS     current
        DESCRIPTION
                "clear the warning of lank ap Memory usage too high and report the current Memory usage."
        ::= { qtechSystemMIBTraps 14 }    

--System reset trap 2010-7
qtechSystemResetTrap NOTIFICATION-TYPE
        STATUS     current
        DESCRIPTION
                "send a trap while system reset"
        ::= { qtechSystemMIBTraps 15 }
        
--lank ap reset trap 2010-8
qtechSystemLankApResetTrap NOTIFICATION-TYPE
        OBJECTS   {qtechApMacAddr}
        STATUS     current
        DESCRIPTION
                "send a trap while lank ap system reset"
        ::= { qtechSystemMIBTraps 16 }
   
qtechSystemPowerOnTrap NOTIFICATION-TYPE
        OBJECTS   {qtechSystemPowerIndex}
        STATUS     current
        DESCRIPTION
                "send a trap while power on."
        ::= { qtechSystemMIBTraps 17 }
                      
qtechSystemPowerOffTrap NOTIFICATION-TYPE
        OBJECTS   {qtechSystemPowerIndex}
        STATUS     current
        DESCRIPTION
                "send a trap while power off."
        ::= { qtechSystemMIBTraps 18 }

qtechSystemPowerOnTrapInVSU NOTIFICATION-TYPE
        OBJECTS   { 
            qtechSystemSwitchID,
            qtechSystemPowerIndex
        }
        STATUS     current
        DESCRIPTION
                "send a trap while power on in VSU."
        ::= { qtechSystemMIBTraps 19 }
                      
qtechSystemPowerOffTrapInVSU NOTIFICATION-TYPE
        OBJECTS   {
            qtechSystemSwitchID,
            qtechSystemPowerIndex
        }
        STATUS     current
        DESCRIPTION
                "send a trap while power off in VSU."
        ::= { qtechSystemMIBTraps 20 }

qtechSystemTmpTableTooHighTrap NOTIFICATION-TYPE
        OBJECTS   {
            qtechSystemMultipleTemperatureSlotIndex
        }
        STATUS     current
        DESCRIPTION
                "Temperature Too High warning with the slot index."
        ::= { qtechSystemMIBTraps 21 }

qtechSystemTmpTableTooHighRecovTrap NOTIFICATION-TYPE
        OBJECTS   {
            qtechSystemMultipleTemperatureSlotIndex
        }
        STATUS     current
        DESCRIPTION
                "clear the warning of Temperature too high with the slot index."
        ::= { qtechSystemMIBTraps 22 }

qtechSystemTmpTableTooHighTrapVSU NOTIFICATION-TYPE
        OBJECTS   {
            qtechSystemMultipleTemperatureDeviceIndex,
            qtechSystemMultipleTemperatureSlotIndex
        }
        STATUS     current
        DESCRIPTION
                "Temperature Too High warning with the slot index in VSU."
        ::= { qtechSystemMIBTraps 23 }
 
qtechSystemTmpTableTooHighRecovTrapVSU NOTIFICATION-TYPE
        OBJECTS   {            
            qtechSystemMultipleTemperatureDeviceIndex,
            qtechSystemMultipleTemperatureSlotIndex
        }
        STATUS     current
        DESCRIPTION
                "clear the warning of Temperature too high with the slot index."
        ::= { qtechSystemMIBTraps 24 }

qtechSystemFanTableStateChange  NOTIFICATION-TYPE
        OBJECTS   {
            qtechSystemFanStatusFanIndex,
            qtechSystemFanStatusIndex,
            qtechSystemFanStatus
        }
        STATUS     current
        DESCRIPTION
                "while the state of fan changed, then this trap will be sent."
        ::= { qtechSystemMIBTraps 25 }                

qtechSystemFanTableStateChangeVSU NOTIFICATION-TYPE
        OBJECTS   {
            qtechSystemFanStatusDeviceIndex,  
            qtechSystemFanStatusFanIndex,
            qtechSystemFanStatusIndex,
            qtechSystemFanStatus
        }
        STATUS     current
        DESCRIPTION
                "In VSU, while the state of fan changed, then this trap will be sent."
        ::= { qtechSystemMIBTraps 26 }                
        
qtechSystemMIBConformance OBJECT IDENTIFIER ::= { qtechSystemMIB 3 }
qtechSystemMIBCompliances OBJECT IDENTIFIER ::= { qtechSystemMIBConformance 1 }
qtechSystemMIBGroups      OBJECT IDENTIFIER ::= { qtechSystemMIBConformance 2 }


-- compliance statements

qtechSystemMIBCompliance MODULE-COMPLIANCE
        STATUS  current
        DESCRIPTION
                "The compliance statement for entities which implement
                the Qtech System MIB"
        MODULE  -- this module
                MANDATORY-GROUPS { qtechSystemMIBGroup
                 }
        ::= { qtechSystemMIBCompliances 1 }
                
-- units of conformance

qtechSystemMIBGroup OBJECT-GROUP
        OBJECTS {
               qtechSystemHwVersion, 
               qtechSystemSwVersion,
               qtechSystemBootVersion,
               qtechSystemSysCtrlVersion,
               qtechSystemParametersSave,
               qtechSystemReset,
               qtechSystemOutBandRate,
               qtechSwitchLayer 
        }
        STATUS  current
        DESCRIPTION
                "A collection of objects providing system information and
                opertion to a Qtech agent."
        ::= { qtechSystemMIBGroups 1 } 
  
END
