-- *****************************************************************
-- QTECH-ANTI-ARPCHEAT-MIB.mib:  Qtech Anti Arpcheat MIB file
--
-- January 2007, LinYanMin
--
-- Copyright (c) 2007 by Qtech Networks Co.,Ltd.
-- All rights reserved.
-- 
-- *****************************************************************

QTECH-ANTI-ARPCHEAT-MIB DEFINITIONS ::= BEGIN

IMPORTS
        MODULE-IDENTITY,
        OBJECT-TYPE,
        Integer32,
        IpAddress
                FROM SNMPv2-SMI
        MacAddress
                FROM SNMPv2-TC
        MODULE-COMPLIANCE,
        OBJECT-GROUP
                FROM SNMPv2-CONF
        IfIndex
                FROM QTECH-TC 
        VlanId
                FROM Q-BRIDGE-MIB
        qtechMgmt
                FROM QTECH-SMI;
 
qtechAntiArpcheatMIB MODULE-IDENTITY
        LAST-UPDATED "200701290000Z"
        ORGANIZATION "Qtech Networks Co.,Ltd."
        CONTACT-INFO
                " 
                Tel: 4008-111-000 

                E-mail: service@qtech.com.cn"
        DESCRIPTION
                "This module defines qtech anti arpcheat mibs."
        REVISION      "200701290000Z"
        DESCRIPTION
                "Initial version of this MIB module."
        ::= { qtechMgmt 41}

qtechAntiArpcheatMIBObjects OBJECT IDENTIFIER ::= { qtechAntiArpcheatMIB 1 }

--
--  user management
--

qtechTrustedArpDelete OBJECT-TYPE
    SYNTAX Integer32
    MAX-ACCESS read-write
    STATUS      current    
    DESCRIPTION
            "Setting the variable value to zero refers to delete all the trusted ARP and L2 interface bindings. 
      Setting any variable values other than zero refers to no action taken."      
    ::= { qtechAntiArpcheatMIBObjects 1 }  


qtechTrustedArpTable OBJECT-TYPE
    SYNTAX  SEQUENCE OF QtechTrustedArpEntry
    MAX-ACCESS  not-accessible
    STATUS  current
    DESCRIPTION
            "It is used to set the trusted ARP and lists of trusted ARP and L2 interface bindings."
   ::= { qtechAntiArpcheatMIBObjects 2 }  

qtechTrustedArpEntry OBJECT-TYPE
    SYNTAX  QtechTrustedArpEntry
    MAX-ACCESS  not-accessible
    STATUS  current
    DESCRIPTION
            "Lists of the trusted ARP and L2 interface bindins."
    INDEX   { trustedArpIfIndex,
              trustedArpIp }
    
    ::= { qtechTrustedArpTable 1 }

QtechTrustedArpEntry ::=
    SEQUENCE {
            trustedArpIfIndex
                     IfIndex,
	          trustedArpIp
                     IpAddress,
            trustedArpMediaPhysAddress
                     MacAddress,
            trustedArpVlan
	                   VlanId,
            trustedArpOperationType
                     Integer32
    }

trustedArpIfIndex OBJECT-TYPE
    SYNTAX  IfIndex
    MAX-ACCESS  read-write
    STATUS  current
    DESCRIPTION
            "The interface that is correspondent with the trusted ARP."
    ::= { qtechTrustedArpEntry 1 }

trustedArpIp OBJECT-TYPE
     SYNTAX  IpAddress
     MAX-ACCESS  read-write
     STATUS  current
     DESCRIPTION
             "The IP address that is correspondent with the trusted ARP."
     ::= { qtechTrustedArpEntry 2 }

trustedArpMediaPhysAddress OBJECT-TYPE
     SYNTAX  MacAddress
     MAX-ACCESS  read-write
     STATUS  current
     DESCRIPTION
              "The MAC address that is correspondent with the trusted ARP."          
     ::= { qtechTrustedArpEntry 3 }	     

trustedArpVlan OBJECT-TYPE
        SYNTAX  VlanId
        MAX-ACCESS  read-write
        STATUS  current
        DESCRIPTION
              "The VLAN ID to which the interface that is correspondent with the trusted ARP belongs."
    ::= { qtechTrustedArpEntry 4 }    

trustedArpOperationType OBJECT-TYPE
    SYNTAX Integer32
    MAX-ACCESS read-write
    STATUS      current    
    DESCRIPTION
             "Setting the variable value to zero refers to delete the binding of trusted ARP and L2 interface. 
      Setting the variable value to 1 refers to add the binding of trusted ARP and L2 interface. Setting any 
      values other than 0 and 1 refers to no action taken." 
    ::= { qtechTrustedArpEntry 5 }  

-- compliance statements
         
qtechAntiArpcheatMIBConformance OBJECT IDENTIFIER ::= { qtechAntiArpcheatMIB 2 }
qtechAntiArpcheatMIBCompliances OBJECT IDENTIFIER ::= { qtechAntiArpcheatMIBConformance 1 }
qtechAntiArpcheatMIBGroups      OBJECT IDENTIFIER ::= { qtechAntiArpcheatMIBConformance 2 }

qtechAntiArpcheatMIBCompliance MODULE-COMPLIANCE
        STATUS  current
        DESCRIPTION
                "The compliance statement for entities which implement
                the Qtech Anti Arpcheat MIB"
        MODULE  -- this module
                MANDATORY-GROUPS { qtechAntiArpcheatMIBGroup
                 }
                       
        ::= { qtechAntiArpcheatMIBCompliances 1 }
                
-- units of conformance

qtechAntiArpcheatMIBGroup OBJECT-GROUP
        OBJECTS {
         qtechTrustedArpDelete,
	       trustedArpIfIndex,
	       trustedArpIp,
         trustedArpMediaPhysAddress,
         trustedArpVlan,
         trustedArpOperationType
        }
        STATUS  current
        DESCRIPTION
                "A collection of objects providing anti arpcheat management and
                opertion to a Qtech agent."
        ::= { qtechAntiArpcheatMIBGroups 1 } 

END
