-- *****************************************************************
-- QTECH-ETHERLIKE-MIB.mib:  Qtech etherlike MIB file
--
-- September 2009, xiongtu
--
-- Copyright (c) 2009 by Qtech Networks Co.,Ltd.
-- All rights reserved.
-- 
-- *****************************************************************
--

QTECH-ETHERLIKE-MIB DEFINITIONS ::= BEGIN

IMPORTS
        MODULE-IDENTITY,
        OBJECT-TYPE,
        Counter64
                FROM SNMPv2-SMI
        MODULE-COMPLIANCE,
        OBJECT-GROUP
                FROM SNMPv2-CONF
        IfIndex
                FROM QTECH-TC
        qtechMgmt
                FROM QTECH-SMI;

qtechEtherlikeMIB MODULE-IDENTITY
        LAST-UPDATED "200909170000Z"
        ORGANIZATION "Qtech Networks Co.,Ltd."
        CONTACT-INFO
                " 
                Tel: 4008-111-000

                E-mail: service@qtech.com.cn"
        DESCRIPTION
                "This module defines qtech etherlike mibs."
        REVISION      "200909170000Z"
        DESCRIPTION
                "Initial version of this MIB module."
        ::= { qtechMgmt 55}

qtechEtherlikeMIBObjects OBJECT IDENTIFIER ::= { qtechEtherlikeMIB 1 }


qtechEtherlikeTable OBJECT-TYPE
        SYNTAX SEQUENCE OF QtechEtherlikeEntry
        MAX-ACCESS not-accessible
        STATUS current
        DESCRIPTION
            "Access table of frames collision counter on interface." 
        ::= { qtechEtherlikeMIBObjects 1 }
    
qtechEtherlikeEntry OBJECT-TYPE
        SYNTAX QtechEtherlikeEntry
        MAX-ACCESS not-accessible
        STATUS current
        DESCRIPTION
            "Interfac frames collision counter access." 
        INDEX { qtechEtherlikeIfIndex }
        ::= { qtechEtherlikeTable 1 }

QtechEtherlikeEntry ::=
        SEQUENCE {
            qtechEtherlikeIfIndex IfIndex,
      	    qtechLocIfCollisions Counter64
        }

qtechEtherlikeIfIndex OBJECT-TYPE
        SYNTAX IfIndex
        MAX-ACCESS read-only
        STATUS current
        DESCRIPTION
            "Interface number"
        ::= { qtechEtherlikeEntry 1 }

qtechLocIfCollisions OBJECT-TYPE
        SYNTAX Counter64
        MAX-ACCESS read-only
        STATUS current
        DESCRIPTION
            "Interfac frames collision counter."
        ::= { qtechEtherlikeEntry 2 }

     
                                     
qtechEtherlikeMIBConformance OBJECT IDENTIFIER ::= { qtechEtherlikeMIB 3 }
qtechEtherlikeMIBCompliances OBJECT IDENTIFIER ::= { qtechEtherlikeMIBConformance 1 }
qtechEtherlikeMIBGroups      OBJECT IDENTIFIER ::= { qtechEtherlikeMIBConformance 2 }

-- compliance statements

qtechEtherlikeMIBCompliance MODULE-COMPLIANCE
        STATUS  current
        DESCRIPTION
                "The compliance statement for entities which implement
                the Qtech Interface MIB"
        MODULE  -- this module
                MANDATORY-GROUPS { qtechcollisionMIBGroups
                 }
        ::= { qtechEtherlikeMIBCompliances 1 }
                
-- units of conformance


qtechcollisionMIBGroups OBJECT-GROUP
        OBJECTS {
            qtechEtherlikeIfIndex,
      	    qtechLocIfCollisions
        }
        STATUS  current
        DESCRIPTION
                "Interfac frames collision counter collection." 
        ::= { qtechEtherlikeMIBGroups 1 }         
                        
                
END
