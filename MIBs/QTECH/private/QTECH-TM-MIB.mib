-- *****************************************************************
-- QTECH-TM-MIB.mib:  Qtech interface MIB file
--
-- Dec 2010, zhuzm
--
-- Copyright (c) 2002 by Qtech Networks Co.,Ltd.
-- All rights reserved.
-- 
-- *****************************************************************
--

QTECH-TM-MIB DEFINITIONS ::= BEGIN

IMPORTS
        MODULE-IDENTITY,
        OBJECT-TYPE,
        Integer32,
        TimeTicks
                FROM SNMPv2-SMI
        MODULE-COMPLIANCE,
        OBJECT-GROUP
                FROM SNMPv2-CONF
        IfIndex
                FROM QTECH-TC
        qtechMgmt
                FROM QTECH-SMI;

qtechTMMIB MODULE-IDENTITY
        LAST-UPDATED "201012130000Z"
        ORGANIZATION "Qtech Networks Co.,Ltd."
        CONTACT-INFO
                " 
                Tel: 4008-111-000 

                E-mail: service@qtech.com.cn"
        DESCRIPTION
                "This module defines qtech TM mibs."
        REVISION      "201012130000Z"
        DESCRIPTION
                "Initial version of this MIB module."
        ::= { qtechMgmt 91 }

qtechTMMIBObjects OBJECT IDENTIFIER ::= { qtechTMMIB 1 }

qtechTMQosDramMIBObjects OBJECT IDENTIFIER ::= { qtechTMMIBObjects 1 }
qtechTMQosDropMIBObjects OBJECT IDENTIFIER ::= { qtechTMMIBObjects 2 }
qtechTMQosQueMIBObjects  OBJECT IDENTIFIER ::= { qtechTMMIBObjects 3 }


qtechQosDramTable OBJECT-TYPE
        SYNTAX SEQUENCE OF QtechQosDramEntry
        MAX-ACCESS not-accessible
        STATUS current
        DESCRIPTION
            "This item is to show the Hardware Dram usage information.
             It indicates the BUFFER traffic consumed."
        ::= { qtechTMQosDramMIBObjects 1 }
    
qtechQosDramEntry OBJECT-TYPE
        SYNTAX QtechQosDramEntry
        MAX-ACCESS not-accessible
        STATUS current
        DESCRIPTION
            "This item is to show the Hardware Dram usage information.
             It indicates the BUFFER traffic consumed."
        INDEX { qtechQoSDramIndex }
        ::= { qtechQosDramTable 1 }

QtechQosDramEntry ::=
        SEQUENCE {
            qtechQoSDramIndex     Integer32,
            qtechQosDramTotal     Integer32,
            qtechQosDramCurUsed   Integer32
        }

qtechQoSDramIndex  OBJECT-TYPE
        SYNTAX Integer32
        MAX-ACCESS read-only
        STATUS current
        DESCRIPTION
            "This item specifies the Petra Chip"
        ::= { qtechQosDramEntry 1 }

qtechQosDramTotal OBJECT-TYPE
        SYNTAX Integer32
        MAX-ACCESS read-only
        STATUS current
        DESCRIPTION
            "This item shows Total Dram Size by MB, that's, the total BUFFER of
             the specified Petra Chip."
        ::= { qtechQosDramEntry 2 }
        	
qtechQosDramCurUsed OBJECT-TYPE
        SYNTAX Integer32
        MAX-ACCESS read-only
        STATUS current
        DESCRIPTION
            "This item shows the CURRENT used Dram Size by B, that's,
             the BUFFER consumed by traffic on the specified Petra Chip."
        ::= { qtechQosDramEntry 3 }
 

--- qtechTMQosDropMIBObjects
qtechQosDropTable OBJECT-TYPE
        SYNTAX SEQUENCE OF QtechQosDropEntry
        MAX-ACCESS not-accessible
        STATUS current
        DESCRIPTION
            "This item is to show the packet DROP Stat. information.
             It includes information about INGRESS drop packet Stat.,
             EGRESS drop packet Stat., etc."
        ::= { qtechTMQosDropMIBObjects 1 }
    
qtechQosDropEntry OBJECT-TYPE
        SYNTAX QtechQosDropEntry
        MAX-ACCESS not-accessible
        STATUS current
        DESCRIPTION
            "This item is to show the packet DROP Stat. information.
             It includes information about INGRESS drop packet Stat.,
             EGRESS drop packet Stat., etc."
        INDEX { qtechQoSDropIndex }
        ::= { qtechQosDropTable 1 }

QtechQosDropEntry ::=
        SEQUENCE {
            qtechQoSDropIndex            Integer32,
            qtechQoSTotalEnQue           Integer32,
            qtechQoSTotalDeQue           Integer32,
       	    qtechQoSEnQueDrop            Integer32,
       	    qtechQoSEnQueDropByBuf       Integer32,
       	    qtechQoSEnQueDropByBufDesc   Integer32,
       	    qtechQoSEnQueDropByOther     Integer32,
       	    qtechQoSDeQueDrop            Integer32,
       	    qtechQoSLastClearTime        TimeTicks
        }

qtechQoSDropIndex  OBJECT-TYPE
        SYNTAX Integer32
        MAX-ACCESS read-only
        STATUS current
        DESCRIPTION
            "This item specifies the Petra Chip"
        ::= { qtechQosDropEntry 1 }
        
qtechQoSTotalEnQue OBJECT-TYPE
        SYNTAX Integer32
        MAX-ACCESS read-only
        STATUS current
        DESCRIPTION
            "This item shows Total Enqueue Packet Stat. of the specified
             Petra Chip"
        ::= { qtechQosDropEntry 2 }
        	
qtechQoSTotalDeQue OBJECT-TYPE
        SYNTAX Integer32
        MAX-ACCESS read-only
        STATUS current
        DESCRIPTION
            "This item shows Total Dequeue Packet Stat. of the specified
             Petra Chip"
        ::= { qtechQosDropEntry 3 }

qtechQoSEnQueDrop OBJECT-TYPE
        SYNTAX Integer32
        MAX-ACCESS read-only
        STATUS current
        DESCRIPTION
            "This item shows Total Enqueue Drop Packet Stat. of the specified
             Petra Chip"
        ::= { qtechQosDropEntry 4 }
        
qtechQoSEnQueDropByBuf OBJECT-TYPE
        SYNTAX Integer32
        MAX-ACCESS read-only
        STATUS current
        DESCRIPTION
            "This item shows Total Enqueue Drop Packet Stat. of the specified
             Petra Chip, due to Buffer reason "
        ::= { qtechQosDropEntry 5 }
        	
qtechQoSEnQueDropByBufDesc OBJECT-TYPE
        SYNTAX Integer32
        MAX-ACCESS read-only
        STATUS current
        DESCRIPTION
            "This item shows Total Enqueue Drop Packet Stat. of the specified
             Petra Chip, due to Buffer Descriptor reason"
        ::= { qtechQosDropEntry 6 }
        	
qtechQoSEnQueDropByOther OBJECT-TYPE
        SYNTAX Integer32
        MAX-ACCESS read-only
        STATUS current
        DESCRIPTION
            "This item shows Total Enqueue Drop Packet Stat. of the specified
             Petra Chip, due to other reason"
        ::= { qtechQosDropEntry 7 }
        
qtechQoSDeQueDrop OBJECT-TYPE
        SYNTAX Integer32
        MAX-ACCESS read-only
        STATUS current
        DESCRIPTION
            "This item shows Total Dequeue Drop Packet Stat. of the specified
             Petra Chip"
        ::= { qtechQosDropEntry 8 }

qtechQoSLastClearTime OBJECT-TYPE
        SYNTAX TimeTicks
        MAX-ACCESS read-only
        STATUS current
        DESCRIPTION
            "This item shows the last clear time."
        ::= { qtechQosDropEntry 9 }


--- qtechTMQosQueMIBObjects
qtechQosQueTable OBJECT-TYPE
        SYNTAX SEQUENCE OF QtechQosQueEntry
        MAX-ACCESS not-accessible
        STATUS current
        DESCRIPTION
            "This item is to show the buffer historic information of
             the specified interface.
             It includes information about the CURRENT buffer consumed by KB,
               the MAXINUM buffer allocated by B,
               the Peak Value of BUFFER consumed in the past by B,
               the rate of BUFFER consumed by percentage, etc."
        ::= { qtechTMQosQueMIBObjects 1 }
    
qtechQosQueEntry OBJECT-TYPE
        SYNTAX QtechQosQueEntry
        MAX-ACCESS not-accessible
        STATUS current
        DESCRIPTION
            "This item is to show the buffer historic information of
             the specified interface.
             It includes information about the CURRENT buffer consumed by KB,
               the MAXINUM buffer allocated by B,
               the Peak Value of BUFFER consumed in the past by B,
               the rate of BUFFER consumed by percentage, etc."
        INDEX { qtechQoSIfIndex,
                qtechQoSIfChipIndex,
                qtechQoSIfChipQueIndex
              }
        ::= { qtechQosQueTable 1 }
  
QtechQosQueEntry ::=
        SEQUENCE {
            qtechQoSIfIndex          IfIndex,
            qtechQoSIfChipIndex      INTEGER,
            qtechQoSIfChipQueIndex   INTEGER,
            qtechQoSIfChipMax        Integer32,
            qtechQoSIfChipCur        Integer32,
            qtechQoSIfChipPeak       Integer32,
            qtechQoSIfChipRate       Integer32,
            qtechQoSIfChipTime       TimeTicks
        } 

qtechQoSIfIndex OBJECT-TYPE
        SYNTAX IfIndex
        MAX-ACCESS read-only
        STATUS current
        DESCRIPTION
            "This item indicates the Interface Index."
        ::= { qtechQosQueEntry 1 }
        	
qtechQoSIfChipIndex OBJECT-TYPE
        SYNTAX INTEGER {
        	chip-0(0),
        	chip-1(1)
        }
        MAX-ACCESS read-only
        STATUS current
        DESCRIPTION
            "This item specifies the Petra Chip."
        ::= { qtechQosQueEntry 2 }
        	
qtechQoSIfChipQueIndex OBJECT-TYPE
        SYNTAX INTEGER {
                queue-1(1),
        	queue-2(2),
        	queue-3(3),
        	queue-4(4),
        	queue-5(5),
        	queue-6(6),
        	queue-7(7),
        	queue-8(8)
        }
        MAX-ACCESS read-only
        STATUS current
        DESCRIPTION
            "This item specifies the queue index of the specified Petra Chip."
        ::= { qtechQosQueEntry 3 }

qtechQoSIfChipMax OBJECT-TYPE
        SYNTAX Integer32
        MAX-ACCESS read-only
        STATUS current
        DESCRIPTION
            "This item specifies the MAXINUM buffer allocated on the specified
             Petra Chip, by KByte."
        ::= { qtechQosQueEntry 4 }
           
qtechQoSIfChipCur OBJECT-TYPE
        SYNTAX Integer32
        MAX-ACCESS read-only
        STATUS current
        DESCRIPTION
            "This item specifies the CURRENT buffer consumed on the specified
             Petra Chip, by Byte."
        ::= { qtechQosQueEntry 5 }

qtechQoSIfChipPeak OBJECT-TYPE
        SYNTAX Integer32
        MAX-ACCESS read-only
        STATUS current
        DESCRIPTION
            "This item specifies the Peak Value of BUFFER consumed in the past
             on the specified Petra Chip, by Byte."
        ::= { qtechQosQueEntry 6 }
        	
qtechQoSIfChipRate OBJECT-TYPE
        SYNTAX Integer32
        MAX-ACCESS read-only
        STATUS current
        DESCRIPTION
            "This item specifies the rate of BUFFER consumed on the specified
             Petra Chip since last clear operation,  by percentage."
        ::= { qtechQosQueEntry 7 }        	
        	
qtechQoSIfChipTime OBJECT-TYPE
        SYNTAX TimeTicks
        MAX-ACCESS read-only
        STATUS current
        DESCRIPTION
            "This item shows the last clear time."
        ::= { qtechQosQueEntry 8 }    
        
--**********************************************************************
-- about conformance info 
--**********************************************************************
qtechTMMIBConformance OBJECT IDENTIFIER ::= { qtechTMMIB 2 }
qtechTMMIBCompliances OBJECT IDENTIFIER ::= { qtechTMMIBConformance 1 }
qtechTMMIBGroups      OBJECT IDENTIFIER ::= { qtechTMMIBConformance 2 }

-- compliance statements
qtechTMMIBCompliance MODULE-COMPLIANCE
			STATUS  current
    	DESCRIPTION
        	"The compliance statement for entities which implement
         	the QtechTMMIB"
    	MODULE  
    	MANDATORY-GROUPS { 
        	qtechTMMIBGroup
    	}
    	::= { qtechTMMIBCompliances 1 }

-- units of conformance
qtechTMMIBGroup OBJECT-GROUP
        OBJECTS {
            qtechQoSDramIndex,
            qtechQosDramTotal,
            qtechQosDramCurUsed,
            
            qtechQoSDropIndex,
            qtechQoSTotalEnQue,
            qtechQoSTotalDeQue,
       	    qtechQoSEnQueDrop,
       	    qtechQoSEnQueDropByBuf,
       	    qtechQoSEnQueDropByBufDesc,
       	    qtechQoSEnQueDropByOther,
       	    qtechQoSDeQueDrop,
       	    qtechQoSLastClearTime,
       	    
       	    qtechQoSIfIndex,
            qtechQoSIfChipIndex,
            qtechQoSIfChipQueIndex,
            qtechQoSIfChipMax,
            qtechQoSIfChipCur,
            qtechQoSIfChipPeak,
            qtechQoSIfChipRate,
            qtechQoSIfChipTime
        }
        STATUS current
        DESCRIPTION
              "A collection of objects to show information about the Hardware
               Dram usage,the packet DROP State, and the buffer historic
               information of the specified interface."
        ::= { qtechTMMIBGroups 1 }

END
