------------------------------------------------------------------------------
--
--  File         : mpDot1agCfmMib.mib
--  Description  : 
--  Version      :  
--  Date         : Sept 5, 2008
--  Copyright    : 2008 by maipu (sichuan) communication technology co.,ltd.
--			All rights reserved.
--
-- $Id:
-- 
------------------------------------------------------------------------------

------------------------------------------------------------------------------
MPDOT1AGCFMMIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;


mpDot1agCfmMib      	MODULE-IDENTITY
                    		LAST-UPDATED 	"0809051557Z"
                    		ORGANIZATION 	"Maipu (Sichuan) Communication Technology Co. LTD."
                    		CONTACT-INFO
                    			""
                    		DESCRIPTION
                      			"The external private MIB for 802.1ag CFM"
                    		::= { mpSwOamMib  2 }


mpDot1agCfmPortTable	OBJECT-TYPE
                    		SYNTAX  SEQUENCE OF   MpDot1agCfmPortEntry
                    		MAX-ACCESS  not-accessible
                    		STATUS  current
                    		DESCRIPTION
                    			"The table of 802.1ag CFM ports, the ports are configured as MIP or MEP."
                    		::= { mpDot1agCfmMib 1 }

mpDot1agCfmPortEntry	OBJECT-TYPE
                    		SYNTAX  MpDot1agCfmPortEntry
                    		MAX-ACCESS  not-accessible
                    		STATUS  current
                    		DESCRIPTION
                    			"The table of 802.1ag CFM ports, the ports are configured as MIP or MEP."
                    		INDEX  { ifIndex }
                    		::= { mpDot1agCfmPortTable 1 }

MpDot1agCfmPortEntry	::= SEQUENCE {
                    			mpDot1agCfmPortType    INTEGER,
                    			mpDot1agCfmPortStatus   RowStatus
                    	             }


mpDot1agCfmPortType 	OBJECT-TYPE
                    		SYNTAX  INTEGER {
                    			         mep(1),
                    			          mip(2)
                    			        }
                    		MAX-ACCESS  read-only
                    		STATUS  current
                    		DESCRIPTION
                    			"The type of port CFM function, 
                    			mep(1): at least one mep is configured on the port;
                    			mip(2): none mep is configure on the port."
                    		::= { mpDot1agCfmPortEntry 1 }

mpDot1agCfmPortStatus	OBJECT-TYPE
                    		SYNTAX  RowStatus
                    		MAX-ACCESS  read-create
                    		STATUS  current
                    		DESCRIPTION
                    			"The rowstatus of the table"
                    		::= { mpDot1agCfmPortEntry 2 }



END
------------------------------------------------------------------------------
-- ============================================================================
-- $Log: mpDot1agCfmMib.mib,v $
-- Revision 1.1.2.1  2008/09/09 01:06:42  yangtian
-- VRSP-7622
-- CFM增加私有MIB
--
--
--
-- ============================================================================
