DEFINITIONS ::= BEGIN

mpSwDHCPPSnooping  OBJECT IDENTIFIER ::= {mpSwitchTech 8}

dhcpspEnable  OBJECT-TYPE
    SYNTAX  INTEGER {
            enable(1),
            disable(2)
            }
    ACCESS  read-write
    STATUS  5
    DESCRIPTION
            "DHCP Snooping使能"
    ::= {mpSwDHCPPSnooping 1}

dhcpspInforEnable  OBJECT-TYPE
    SYNTAX  INTEGER {
            enable(1),
            disable(2)
            }
    ACCESS  read-write
    STATUS  5
    DESCRIPTION
            "Option 82选项使能"
    ::= {mpSwDHCPPSnooping 2}

dhcpspInforPolicy  OBJECT-TYPE
    SYNTAX  INTEGER {
            replace(1),
            drop(2),
            keep(3)
            }
    ACCESS  read-write
    STATUS  5
    DESCRIPTION
            "转发策略配置"
    ::= {mpSwDHCPPSnooping 3}

dhcpspInforFormat  OBJECT-TYPE
    SYNTAX  INTEGER {
            default(1),
            usrcfg(2)
            }
    ACCESS  read-write
    STATUS  5
    DESCRIPTION
            "DHCP报文OPTION 82选项填充方式配置"
    ::= {mpSwDHCPPSnooping 4}

debugKey  OBJECT-TYPE
    SYNTAX  INTEGER(0..255)
    ACCESS  read-write
    STATUS  5
    DESCRIPTION
            "DEBUG开关"
    ::= {mpSwDHCPPSnooping 5}

dataTimeOut  OBJECT-TYPE
    SYNTAX  INTEGER
    ACCESS  read-write
    STATUS  5
    DESCRIPTION
            "超时时间"
    ::= {mpSwDHCPPSnooping 6}

dhcpspInforRremoteId  OBJECT-TYPE
    SYNTAX  DisplayString(SIZE(0..63))
    ACCESS  read-write
    STATUS  5
    DESCRIPTION
            "远端ID配置"
    ::= {mpSwDHCPPSnooping 7}

dhcpspSaveType  OBJECT-TYPE
    SYNTAX  INTEGER {
            AUTO-FLASH(1),
            MANUAL-FLASH(2),
            AUTO-FTP(3),
            MANUAL-FTP(4),
            AUTO-TFTP(5),
            MANUAL-TFTP(6)
            }
    ACCESS  read-write
    STATUS  5
    DESCRIPTION
            "保存方式"
    ::= {mpSwDHCPPSnooping 8}

dhcpspSaveHost  OBJECT-TYPE
    SYNTAX  IpAddress
    ACCESS  read-write
    STATUS  5
    DESCRIPTION
            "远程备份主机IP"
    ::= {mpSwDHCPPSnooping 9}

dhcpspSaveUser  OBJECT-TYPE
    SYNTAX  DisplayString(SIZE(1..32))
    ACCESS  read-write
    STATUS  5
    DESCRIPTION
            "FTP连接用户名称"
    ::= {mpSwDHCPPSnooping 10}

dhcpspSavePassword  OBJECT-TYPE
    SYNTAX  DisplayString(SIZE(1..32))
    ACCESS  read-write
    STATUS  5
    DESCRIPTION
            "FTP连接用户密码"
    ::= {mpSwDHCPPSnooping 11}

dhcpspSaveFileName  OBJECT-TYPE
    SYNTAX  DisplayString(SIZE(1..32))
    ACCESS  read-write
    STATUS  5
    DESCRIPTION
            "备份文件名称"
    ::= {mpSwDHCPPSnooping 12}

dhcpspSaveDelay  OBJECT-TYPE
    SYNTAX  INTEGER (10..32768)
    ACCESS  read-write
    STATUS  5
    DESCRIPTION
            "保存延时写入"
    ::= {mpSwDHCPPSnooping 13}

dhcpspSavePool  OBJECT-TYPE
    SYNTAX  INTEGER（10..60）
    ACCESS  read-write
    STATUS  5
    DESCRIPTION
            "保存轮询周期"
    ::= {mpSwDHCPPSnooping 14}

dhcpspRelayIp  OBJECT-TYPE
    SYNTAX  IpAddress
    ACCESS  read-write
    STATUS  5
    DESCRIPTION
            "本机接口IP"
    ::= {mpSwDHCPPSnooping 15}

dhcpspPortTable  OBJECT-TYPE
    SYNTAX  SEQUENCE OF dhcpspPortEntry
    ACCESS  not-accessible
    STATUS  5
    DESCRIPTION
            "dhcp snooping 端口属性表."
    ::= {mpSwDHCPPSnooping 20}

dhcpspPortEntry  OBJECT-TYPE
    SYNTAX  dhcpspPortEntry
    ACCESS  not-accessible
    STATUS  5
    DESCRIPTION
            "端口信息表项."
    INDEX   {dhcpspPortId}
    ::= {dhcpspPortTable 1}

dhcpspPortId  OBJECT-TYPE
    SYNTAX  INTEGER
    ACCESS  read-only
    STATUS  5
    DESCRIPTION
            "端口ID"
    ::= {dhcpspPortEntry 1}

dhcpspPortRateLimit  OBJECT-TYPE
    SYNTAX  INTEGER(1..4096)
    ACCESS  read-write
    STATUS  5
    DESCRIPTION
            "端口速率限制"
    ::= {dhcpspPortEntry 2}

dhcpspPortTrust  OBJECT-TYPE
    SYNTAX  INTEGER {
            trust(1),
            untrust(2)
            }
    ACCESS  read-write
    STATUS  5
    DESCRIPTION
            "端口速率限制"
    ::= {dhcpspPortEntry 3}

dhcpspPortName  OBJECT-TYPE
    SYNTAX  DisplayString(SIZE(0..40))
    ACCESS  read-only
    STATUS  5
    DESCRIPTION
            "端口名"
    ::= {dhcpspPortEntry 4}

dhcpspInforCircuitId  OBJECT-TYPE
    SYNTAX  DisplayString(SIZE(0..63))
    ACCESS  read-write
    STATUS  5
    DESCRIPTION
            "端口电路ID"
    ::= {dhcpspPortEntry 5}

dhcpspBindDataTable  OBJECT-TYPE
    SYNTAX  SEQUENCE OF dhcpspBindDataEntry
    ACCESS  not-accessible
    STATUS  5
    DESCRIPTION
            "dhcp snooping 动态绑定表."
    ::= {mpSwDHCPPSnooping 22}

dhcpspBindDataEntry  OBJECT-TYPE
    SYNTAX  dhcpspBindDataEntry
    ACCESS  not-accessible
    STATUS  5
    DESCRIPTION
            "动态绑定表项."
    INDEX   {dhcpspDataMacAddr,dhcpspDataPort,dhcpspDataVlan,dhcpspDataIpAddr}
    ::= {dhcpspBindDataTable 1}

dhcpspDataIpAddr  OBJECT-TYPE
    SYNTAX  IpAddress
    ACCESS  read-only
    STATUS  5
    DESCRIPTION
            "IP地址"
    ::= {dhcpspBindDataEntry 1}

dhcpspDataPort  OBJECT-TYPE
    SYNTAX  INTEGER
    ACCESS  read-only
    STATUS  5
    DESCRIPTION
            "端口号"
    ::= {dhcpspBindDataEntry 2}

dhcpspDataVlan  OBJECT-TYPE
    SYNTAX  INTEGER（1..4094）
    ACCESS  read-only
    STATUS  5
    DESCRIPTION
            "VLAN 号"
    ::= {dhcpspBindDataEntry 3}

dhcpspDataLeaseTime  OBJECT-TYPE
    SYNTAX  INTEGER
    ACCESS  read-only
    STATUS  5
    DESCRIPTION
            "租约时间"
    ::= {dhcpspBindDataEntry 4}

dhcpspDataLeaseTimeBak  OBJECT-TYPE
    SYNTAX  INTEGER
    ACCESS  read-only
    STATUS  5
    DESCRIPTION
            "租约时间"
    ::= {dhcpspBindDataEntry 5}

dhcpspDataXid  OBJECT-TYPE
    SYNTAX  Gauge
    ACCESS  read-only
    STATUS  5
    DESCRIPTION
            "事务ID"
    ::= {dhcpspBindDataEntry 6}

dhcpspDataFlag  OBJECT-TYPE
    SYNTAX  INTEGER {
            valid(1),
            invalid(2)
            }
    ACCESS  read-only
    STATUS  5
    DESCRIPTION
            "有效标记"
    ::= {dhcpspBindDataEntry 7}

dhcpspDataIpsgFlag  OBJECT-TYPE
    SYNTAX  INTEGER {
            valid(1),
            invalid(2)
            }
    ACCESS  read-only
    STATUS  5
    DESCRIPTION
            "ipsg写标记"
    ::= {dhcpspBindDataEntry 8}

dhcpspDataMacAddr  OBJECT-TYPE
    SYNTAX  PhysAddress
    ACCESS  read-only
    STATUS  5
    DESCRIPTION
            "mac 地址"
    ::= {dhcpspBindDataEntry 9}

dhcpspBindDataRowStatus  OBJECT-TYPE
    SYNTAX  RowStatus
    ACCESS  read-only
    STATUS  5
    DESCRIPTION
            ""
    ::= {dhcpspBindDataEntry 21}
END
