------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPAAAMIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;



mpAAAMib            	MODULE-IDENTITY
                    		LAST-UPDATED 	"0812291627Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { mpMgmt  27 }

------------------------------------------------------------------------------
-- Textual Conventions
------------------------------------------------------------------------------
EnabledStatus ::= TEXTUAL-CONVENTION
    STATUS      current
    DESCRIPTION
        "A simple status value for the object."
    SYNTAX      INTEGER {
	enabled(1), disabled(2) }

------------------------------------------------------------------------------



------------------------------------------------------------------------------
aaaConf             	OBJECT IDENTIFIER ::= { mpAAAMib 1 }


------------------------------------------------------------------------------
aaaGlobal           	OBJECT IDENTIFIER ::= { aaaConf 1 }

aaaNewModel         	OBJECT-TYPE
                    		SYNTAX  EnabledStatus
                    		MAX-ACCESS  read-write
                    		STATUS  current
                    		DESCRIPTION
                    			"AAA开关"
                    		::= { aaaGlobal 1 }

aaaAcctSurNullName  	OBJECT-TYPE
                    		SYNTAX  EnabledStatus
                    		MAX-ACCESS  read-write
                    		STATUS  current
                    		DESCRIPTION
                    			"是否计费用户名为空的用户"
                    		::= { aaaGlobal 2 }

aaaAcctUpdate       	OBJECT-TYPE
                    		SYNTAX  INTEGER {
                    			         disable(0),
                    			          newInfo(1),
                    			          periodic(2)
                    			        }
                    		MAX-ACCESS  read-write
                    		STATUS  current
                    		DESCRIPTION
                    			"计费是否更新
                    			 0——不定时更新
                    			 1——当有新的计费消息时更新
                    			 2——周期性定时更新"
                    		::= { aaaGlobal 3 }

aaaAcctPeriInter    	OBJECT-TYPE
                    		SYNTAX  Unsigned32(1..2147483647)
                    		MAX-ACCESS  read-write
                    		STATUS  current
                    		DESCRIPTION
                    			"周期性定时更新间隔"
                    		::= { aaaGlobal 4 }

aaaAuthBanner       	OBJECT-TYPE
                    		SYNTAX  DisplayString(SIZE(0..220))
                    		MAX-ACCESS  read-write
                    		STATUS  current
                    		DESCRIPTION
                    			"认证登陆提示语"
                    		::= { aaaGlobal 5 }

aaaAuthFailMsg      	OBJECT-TYPE
                    		SYNTAX  DisplayString(SIZE(0..220))
                    		MAX-ACCESS  read-write
                    		STATUS  current
                    		DESCRIPTION
                    			"登陆失败提示语"
                    		::= { aaaGlobal 6 }

aaaAuthPwdPrompt    	OBJECT-TYPE
                    		SYNTAX  DisplayString(SIZE(0..255))
                    		MAX-ACCESS  read-write
                    		STATUS  current
                    		DESCRIPTION
                    			"认证登陆密码提示符"
                    		::= { aaaGlobal 7 }

aaaAuthUserPrompt   	OBJECT-TYPE
                    		SYNTAX  DisplayString(SIZE(0..255))
                    		MAX-ACCESS  read-write
                    		STATUS  current
                    		DESCRIPTION
                    			"认证登陆用户名提示符"
                    		::= { aaaGlobal 8 }

aaaAuthorConfCmd    	OBJECT-TYPE
                    		SYNTAX  EnabledStatus
                    		MAX-ACCESS  read-write
                    		STATUS  current
                    		DESCRIPTION
                    			"是否命令授权"
                    		::= { aaaGlobal 9 }


------------------------------------------------------------------------------
aaaList             	OBJECT IDENTIFIER ::= { aaaConf 2 }

aaaAuthenListTable  	OBJECT-TYPE
                    		SYNTAX  SEQUENCE OF   AaaAuthenListEntry
                    		MAX-ACCESS  not-accessible
                    		STATUS  current
                    		DESCRIPTION
                    			""
                    		::= { aaaList 1 }

aaaAuthenListEntry  	OBJECT-TYPE
                    		SYNTAX  AaaAuthenListEntry
                    		MAX-ACCESS  not-accessible
                    		STATUS  current
                    		DESCRIPTION
                    			""
                    		INDEX  { aaaAuthenListName, aaaAuthenListMode }
                    		::= { aaaAuthenListTable 1 }

AaaAuthenListEntry  	::= SEQUENCE {
                    			aaaAuthenListName      DisplayString,
                    			aaaAuthenListMode      INTEGER,
                    			aaaAuthenListOption1   INTEGER,
                    			aaaAuthenListGrpSrv1   DisplayString,
                    			aaaAuthenListOption2   INTEGER,
                    			aaaAuthenListGrpSrv2   DisplayString,
                    			aaaAuthenListOption3   INTEGER,
                    			aaaAuthenListGrpSrv3   DisplayString,
                    			aaaAuthenListOption4   INTEGER,
                    			aaaAuthenListGrpSrv4   DisplayString,
                    			aaaAuthenListRowStatus   RowStatus
                    	             }


aaaAuthenListName   	OBJECT-TYPE
                    		SYNTAX  DisplayString(SIZE(0..32))
                    		MAX-ACCESS  not-accessible
                    		STATUS  current
                    		DESCRIPTION
                    			"AAA认证列表名称
                    			 对于Login模式可以为default或自定义
                    			 对于Enable模式只能default
                    			 对于PPP模式只能自定义"
                    		::= { aaaAuthenListEntry 1 }

aaaAuthenListMode   	OBJECT-TYPE
                    		SYNTAX  INTEGER {
                    			         login(1),
                    			          enable(2),
                    			          ppp(3)
                    			        }
                    		MAX-ACCESS  not-accessible
                    		STATUS  current
                    		DESCRIPTION
                    			"AAA认证列表模式：
                    			 1——Login
                    			 2——Enable
                    			 3——PPP"
                    		::= { aaaAuthenListEntry 2 }

aaaAuthenListOption1	OBJECT-TYPE
                    		SYNTAX  INTEGER {
                    			         nomethod(0),
                    			          none(1),
                    			          local(2),
                    			          radius(3),
                    			          enable(4),
                    			          tacacs(5),
                    			          line(6),
                    			          grpSrv(7)
                    			        }
                    		MAX-ACCESS  read-write
                    		STATUS  current
                    		DESCRIPTION
                    			"AAA认证列表选项：
                    			 1——none
                    			 2——Local(enable模式无效)
                    			 3——Radius
                    			 4——Enable(ppp模式无效)
                    			 5——Tacacs
                    			 6——Line(ppp模式无效)
                    			 7——GrpSrv(服务器组)"
                    		::= { aaaAuthenListEntry 3 }

aaaAuthenListGrpSrv1	OBJECT-TYPE
                    		SYNTAX  DisplayString(SIZE(0..32))
                    		MAX-ACCESS  read-write
                    		STATUS  current
                    		DESCRIPTION
                    			"认证组服务器"
                    		::= { aaaAuthenListEntry 4 }

aaaAuthenListOption2	OBJECT-TYPE
                    		SYNTAX  INTEGER {
                    			         nomethod(0),
                    			          none(1),
                    			          local(2),
                    			          radius(3),
                    			          enable(4),
                    			          tacacs(5),
                    			          line(6),
                    			          grpSrv(7)
                    			        }
                    		MAX-ACCESS  read-write
                    		STATUS  current
                    		DESCRIPTION
                    			"和aaaAuthenListOption1相同"
                    		::= { aaaAuthenListEntry 5 }

aaaAuthenListGrpSrv2	OBJECT-TYPE
                    		SYNTAX  DisplayString(SIZE(0..32))
                    		MAX-ACCESS  read-write
                    		STATUS  current
                    		DESCRIPTION
                    			"认证组服务器2"
                    		::= { aaaAuthenListEntry 6 }

aaaAuthenListOption3	OBJECT-TYPE
                    		SYNTAX  INTEGER {
                    			         nomethod(0),
                    			          none(1),
                    			          local(2),
                    			          radius(3),
                    			          enable(4),
                    			          tacacs(5),
                    			          line(6),
                    			          grpSrv(7)
                    			        }
                    		MAX-ACCESS  read-write
                    		STATUS  current
                    		DESCRIPTION
                    			"和aaaAuthenListOption1相同"
                    		::= { aaaAuthenListEntry 7 }

aaaAuthenListGrpSrv3	OBJECT-TYPE
                    		SYNTAX  DisplayString(SIZE(0..32))
                    		MAX-ACCESS  read-write
                    		STATUS  current
                    		DESCRIPTION
                    			"认证组服务器3"
                    		::= { aaaAuthenListEntry 8 }

aaaAuthenListOption4	OBJECT-TYPE
                    		SYNTAX  INTEGER {
                    			         nomethod(0),
                    			          none(1),
                    			          local(2),
                    			          radius(3),
                    			          enable(4),
                    			          tacacs(5),
                    			          line(6),
                    			          grpSrv(7)
                    			        }
                    		MAX-ACCESS  read-write
                    		STATUS  current
                    		DESCRIPTION
                    			"和aaaAuthenListOption1相同"
                    		::= { aaaAuthenListEntry 9 }

aaaAuthenListGrpSrv4	OBJECT-TYPE
                    		SYNTAX  DisplayString(SIZE(0..32))
                    		MAX-ACCESS  read-write
                    		STATUS  current
                    		DESCRIPTION
                    			"认证组服务器4"
                    		::= { aaaAuthenListEntry 10 }

aaaAuthenListRowStatus	OBJECT-TYPE
                    		SYNTAX  RowStatus
                    		MAX-ACCESS  read-write
                    		STATUS  current
                    		DESCRIPTION
                    			""
                    		::= { aaaAuthenListEntry 11 }

aaaAuthorListTable  	OBJECT-TYPE
                    		SYNTAX  SEQUENCE OF   AaaAuthorListEntry
                    		MAX-ACCESS  not-accessible
                    		STATUS  current
                    		DESCRIPTION
                    			""
                    		::= { aaaList 2 }

aaaAuthorListEntry  	OBJECT-TYPE
                    		SYNTAX  AaaAuthorListEntry
                    		MAX-ACCESS  not-accessible
                    		STATUS  current
                    		DESCRIPTION
                    			""
                    		INDEX  { aaaAuthorListName, aaaAuthorListMode, aaaAuthorListCmdLvl }
                    		::= { aaaAuthorListTable 1 }

AaaAuthorListEntry  	::= SEQUENCE {
                    			aaaAuthorListName      DisplayString,
                    			aaaAuthorListMode      INTEGER,
                    			aaaAuthorListCmdLvl    INTEGER,
                    			aaaAuthorListOption1   INTEGER,
                    			aaaAuthorListGrpSrv1   DisplayString,
                    			aaaAuthorListOption2   INTEGER,
                    			aaaAuthorListGrpSrv2   DisplayString,
                    			aaaAuthorListOption3   INTEGER,
                    			aaaAuthorListGrpSrv3   DisplayString,
                    			aaaAuthorListOption4   INTEGER,
                    			aaaAuthorListGrpSrv4   DisplayString,
                    			aaaAuthorListRowStatus   RowStatus
                    	             }


aaaAuthorListName   	OBJECT-TYPE
                    		SYNTAX  DisplayString(SIZE(0..32))
                    		MAX-ACCESS  not-accessible
                    		STATUS  current
                    		DESCRIPTION
                    			"AAA授权列表名称
                    			 对于exec模式只能是default
                    			 对于network模式只能自定义名称"
                    		::= { aaaAuthorListEntry 1 }

aaaAuthorListMode   	OBJECT-TYPE
                    		SYNTAX  INTEGER {
                    			         exec(1),
                    			          network(2),
                    			          commands(4)
                    			        }
                    		MAX-ACCESS  not-accessible
                    		STATUS  current
                    		DESCRIPTION
                    			"AAA授权列表模式：
                    			 1——EXEC
                    			 2——network
                    			 3——commands(指定命令等级授权)"
                    		::= { aaaAuthorListEntry 2 }

aaaAuthorListCmdLvl 	OBJECT-TYPE
                    		SYNTAX  INTEGER(0..15)
                    		MAX-ACCESS  read-write
                    		STATUS  current
                    		DESCRIPTION
                    			"指定命令等级授权的命令等级"
                    		::= { aaaAuthorListEntry 3 }

aaaAuthorListOption1	OBJECT-TYPE
                    		SYNTAX  INTEGER {
                    			         nomethod(0),
                    			          none(1),
                    			          local(2),
                    			          radius(3),
                    			          tacacs(5),
                    			          grpSrv(7),
                    			          ifAuthenticated(16)
                    			        }
                    		MAX-ACCESS  read-write
                    		STATUS  current
                    		DESCRIPTION
                    			"AAA授权列表选项：
                    			 和认证选项类似，如配置数组 3 4 16 0 0 0 则表示授权顺序为radius tacacs if-authenticated
                    			 1——none
                    			 2——Local
                    			 3——Radius
                    			 5——Tacacs
                    			 7——SrvGrp(服务器组)
                    			 16——if-authenticated(如果通过认证就通过授权)"
                    		::= { aaaAuthorListEntry 4 }

aaaAuthorListGrpSrv1	OBJECT-TYPE
                    		SYNTAX  DisplayString(SIZE(0..32))
                    		MAX-ACCESS  read-write
                    		STATUS  current
                    		DESCRIPTION
                    			"授权组服务器选项"
                    		::= { aaaAuthorListEntry 5 }

aaaAuthorListOption2	OBJECT-TYPE
                    		SYNTAX  INTEGER {
                    			         nomethod(0),
                    			          none(1),
                    			          local(2),
                    			          radius(3),
                    			          tacacs(5),
                    			          grpSrv(7),
                    			          ifAuthenticated(16)
                    			        }
                    		MAX-ACCESS  read-write
                    		STATUS  current
                    		DESCRIPTION
                    			"和aaaAuthorListOption1相同"
                    		::= { aaaAuthorListEntry 6 }

aaaAuthorListGrpSrv2	OBJECT-TYPE
                    		SYNTAX  DisplayString(SIZE(0..32))
                    		MAX-ACCESS  read-write
                    		STATUS  current
                    		DESCRIPTION
                    			"和aaaAuthorListGrpSrv1相同"
                    		::= { aaaAuthorListEntry 7 }

aaaAuthorListOption3	OBJECT-TYPE
                    		SYNTAX  INTEGER {
                    			         nomethod(0),
                    			          none(1),
                    			          local(2),
                    			          radius(3),
                    			          tacacs(5),
                    			          grpSrv(7),
                    			          ifAuthenticated(16)
                    			        }
                    		MAX-ACCESS  read-write
                    		STATUS  current
                    		DESCRIPTION
                    			"和aaaAuthorListOption1相同"
                    		::= { aaaAuthorListEntry 8 }

aaaAuthorListGrpSrv3	OBJECT-TYPE
                    		SYNTAX  DisplayString(SIZE(0..32))
                    		MAX-ACCESS  read-write
                    		STATUS  current
                    		DESCRIPTION
                    			"和aaaAuthorListGrpSrv1相同"
                    		::= { aaaAuthorListEntry 9 }

aaaAuthorListOption4	OBJECT-TYPE
                    		SYNTAX  INTEGER {
                    			         nomethod(0),
                    			          none(1),
                    			          local(2),
                    			          radius(3),
                    			          tacacs(5),
                    			          grpSrv(7),
                    			          ifAuthenticated(16)
                    			        }
                    		MAX-ACCESS  read-write
                    		STATUS  current
                    		DESCRIPTION
                    			"和aaaAuthorListOption1相同"
                    		::= { aaaAuthorListEntry 10 }

aaaAuthorListGrpSrv4	OBJECT-TYPE
                    		SYNTAX  DisplayString(SIZE(0..32))
                    		MAX-ACCESS  read-write
                    		STATUS  current
                    		DESCRIPTION
                    			"和aaaAuthorListGrpSrv1相同"
                    		::= { aaaAuthorListEntry 11 }

aaaAuthorListRowStatus	OBJECT-TYPE
                    		SYNTAX  RowStatus
                    		MAX-ACCESS  read-write
                    		STATUS  current
                    		DESCRIPTION
                    			""
                    		::= { aaaAuthorListEntry 12 }

aaaAccountListTable 	OBJECT-TYPE
                    		SYNTAX  SEQUENCE OF   AaaAccountListEntry
                    		MAX-ACCESS  not-accessible
                    		STATUS  current
                    		DESCRIPTION
                    			""
                    		::= { aaaList 3 }

aaaAccountListEntry 	OBJECT-TYPE
                    		SYNTAX  AaaAccountListEntry
                    		MAX-ACCESS  not-accessible
                    		STATUS  current
                    		DESCRIPTION
                    			""
                    		INDEX  { aaaAccountListName, aaaAccountListMode, aaaAccountListCmdLvl }
                    		::= { aaaAccountListTable 1 }

AaaAccountListEntry 	::= SEQUENCE {
                    			aaaAccountListName     DisplayString,
                    			aaaAccountListMode     INTEGER,
                    			aaaAccountListCmdLvl   INTEGER,
                    			aaaAccountListMethod   INTEGER,
                    			aaaAccountListBroadcast   EnabledStatus,
                    			aaaAccountListOption1   INTEGER,
                    			aaaAccountListGrpSrv1   DisplayString,
                    			aaaAccountListOption2   INTEGER,
                    			aaaAccountListGrpSrv2   DisplayString,
                    			aaaAccountListOption3   INTEGER,
                    			aaaAccountListGrpSrv3   DisplayString,
                    			aaaAccountListOption4   Integer32,
                    			aaaAccountListGrpSrv4   DisplayString,
                    			aaaAccountListRowStatus   RowStatus
                    	             }


aaaAccountListName  	OBJECT-TYPE
                    		SYNTAX  DisplayString(SIZE(0..32))
                    		MAX-ACCESS  not-accessible
                    		STATUS  current
                    		DESCRIPTION
                    			"AAA计费列表名称
                    			 connection模式有default、dot1x、h323分别对应默认、dot1x应用、h323应用
                    			 exec模式只有default
                    			 network只有自定义名称"
                    		::= { aaaAccountListEntry 1 }

aaaAccountListMode  	OBJECT-TYPE
                    		SYNTAX  INTEGER {
                    			         exec(1),
                    			          network(2),
                    			          connection(3),
                    			          commands(4),
                    			          system(5)
                    			        }
                    		MAX-ACCESS  not-accessible
                    		STATUS  current
                    		DESCRIPTION
                    			"AAA计费列表模式：
                    			 1——EXEC
                    			 2——network
                    			 3——connection(用于dot1x、h323等)
                    			 4——commands(指定等级命令计费)
                    			 5——system(系统事件统计)"
                    		::= { aaaAccountListEntry 2 }

aaaAccountListCmdLvl	OBJECT-TYPE
                    		SYNTAX  INTEGER(0..15)
                    		MAX-ACCESS  read-write
                    		STATUS  current
                    		DESCRIPTION
                    			"指定等级命令进行计费"
                    		::= { aaaAccountListEntry 3 }

aaaAccountListMethod	OBJECT-TYPE
                    		SYNTAX  INTEGER {
                    			         none(1),
                    			          startStop(2),
                    			          stopOnly(3),
                    			          waitStart(4)
                    			        }
                    		MAX-ACCESS  read-write
                    		STATUS  current
                    		DESCRIPTION
                    			"AAA计费方法：
                    			 1——none
                    			 2——start-stop
                    			 3——stop-only
                    			 4——swait-start"
                    		::= { aaaAccountListEntry 4 }

aaaAccountListBroadcast	OBJECT-TYPE
                    		SYNTAX  EnabledStatus
                    		MAX-ACCESS  read-write
                    		STATUS  current
                    		DESCRIPTION
                    			"支持统计报文广播到各个服务器"
                    		::= { aaaAccountListEntry 5 }

aaaAccountListOption1	OBJECT-TYPE
                    		SYNTAX  INTEGER {
                    			         nomethod(0),
                    			          radius(3),
                    			          tacacs(5),
                    			          grpSrv(7)
                    			        }
                    		MAX-ACCESS  read-write
                    		STATUS  current
                    		DESCRIPTION
                    			"AAA计费列表选项：
                    			 和认证选项类似，并且计费选项只能配置为3 5 0 0 0 0或者5 3 0 0 0 0。
                    			 3——Radius
                    			 5——Tacacs
                    			 7——SrvGrp"
                    		::= { aaaAccountListEntry 6 }

aaaAccountListGrpSrv1	OBJECT-TYPE
                    		SYNTAX  DisplayString(SIZE(0..32))
                    		MAX-ACCESS  read-write
                    		STATUS  current
                    		DESCRIPTION
                    			"计费组服务器"
                    		::= { aaaAccountListEntry 7 }

aaaAccountListOption2	OBJECT-TYPE
                    		SYNTAX  INTEGER {
                    			         nomethod(0),
                    			          radius(3),
                    			          tacacs(5),
                    			          grpSrv(7)
                    			        }
                    		MAX-ACCESS  read-write
                    		STATUS  current
                    		DESCRIPTION
                    			"AAA计费列表选项：
                    			 和认证选项类似，并且计费选项只能配置为3 5 0 0 0 0或者5 3 0 0 0 0。
                    			 3——Radius
                    			 5——Tacacs
                    			 7——SrvGrp"
                    		::= { aaaAccountListEntry 8 }

aaaAccountListGrpSrv2	OBJECT-TYPE
                    		SYNTAX  DisplayString(SIZE(0..32))
                    		MAX-ACCESS  read-write
                    		STATUS  current
                    		DESCRIPTION
                    			"计费组服务器"
                    		::= { aaaAccountListEntry 9 }

aaaAccountListOption3	OBJECT-TYPE
                    		SYNTAX  INTEGER {
                    			         nomethod(0),
                    			          radius(3),
                    			          tacacs(5),
                    			          grpSrv(7)
                    			        }
                    		MAX-ACCESS  read-write
                    		STATUS  current
                    		DESCRIPTION
                    			"AAA计费列表选项：
                    			 和认证选项类似，并且计费选项只能配置为3 5 0 0 0 0或者5 3 0 0 0 0。
                    			 3——Radius
                    			 5——Tacacs
                    			 7——SrvGrp"
                    		::= { aaaAccountListEntry 10 }

aaaAccountListGrpSrv3	OBJECT-TYPE
                    		SYNTAX  DisplayString(SIZE(0..32))
                    		MAX-ACCESS  read-write
                    		STATUS  current
                    		DESCRIPTION
                    			"计费组服务器"
                    		::= { aaaAccountListEntry 11 }

aaaAccountListOption4	OBJECT-TYPE
                    		SYNTAX  Integer32 {
                    			         nomethod(0),
                    			          radius(3),
                    			          tacacs(5),
                    			          grpSrv(7)
                    			        }
                    		MAX-ACCESS  read-write
                    		STATUS  current
                    		DESCRIPTION
                    			""
                    		::= { aaaAccountListEntry 12 }

aaaAccountListGrpSrv4	OBJECT-TYPE
                    		SYNTAX  DisplayString(SIZE(0..32))
                    		MAX-ACCESS  read-write
                    		STATUS  current
                    		DESCRIPTION
                    			""
                    		::= { aaaAccountListEntry 13 }

aaaAccountListRowStatus	OBJECT-TYPE
                    		SYNTAX  RowStatus
                    		MAX-ACCESS  read-write
                    		STATUS  current
                    		DESCRIPTION
                    			""
                    		::= { aaaAccountListEntry 14 }


------------------------------------------------------------------------------
aaaGrpSrv           	OBJECT IDENTIFIER ::= { aaaConf 3 }

aaaGrpSrvTable      	OBJECT-TYPE
                    		SYNTAX  SEQUENCE OF   AaaGrpSrvEntry
                    		MAX-ACCESS  not-accessible
                    		STATUS  current
                    		DESCRIPTION
                    			""
                    		::= { aaaGrpSrv 1 }

aaaGrpSrvEntry      	OBJECT-TYPE
                    		SYNTAX  AaaGrpSrvEntry
                    		MAX-ACCESS  not-accessible
                    		STATUS  current
                    		DESCRIPTION
                    			""
                    		INDEX  { aaaGrpSrvName, aaaGrpSrvType }
                    		::= { aaaGrpSrvTable 1 }

AaaGrpSrvEntry      	::= SEQUENCE {
                    			aaaGrpSrvName          DisplayString,
                    			aaaGrpSrvType          INTEGER,
                    			aaaGrpSrvVrf           DisplayString,
                    			aaaGrpSrvRowStatus     RowStatus
                    	             }


aaaGrpSrvName       	OBJECT-TYPE
                    		SYNTAX  DisplayString(SIZE(0..32))
                    		MAX-ACCESS  not-accessible
                    		STATUS  current
                    		DESCRIPTION
                    			"组服务器名称"
                    		::= { aaaGrpSrvEntry 1 }

aaaGrpSrvType       	OBJECT-TYPE
                    		SYNTAX  INTEGER {
                    			         tacacs(1),
                    			          radius(2)
                    			        }
                    		MAX-ACCESS  not-accessible
                    		STATUS  current
                    		DESCRIPTION
                    			"组服务器类型"
                    		::= { aaaGrpSrvEntry 2 }

aaaGrpSrvVrf        	OBJECT-TYPE
                    		SYNTAX  DisplayString(SIZE(0..32))
                    		MAX-ACCESS  read-write
                    		STATUS  current
                    		DESCRIPTION
                    			""
                    		::= { aaaGrpSrvEntry 3 }

aaaGrpSrvRowStatus  	OBJECT-TYPE
                    		SYNTAX  RowStatus
                    		MAX-ACCESS  read-write
                    		STATUS  current
                    		DESCRIPTION
                    			""
                    		::= { aaaGrpSrvEntry 4 }

aaaGrpSrvReferenceTacacsIpTable	OBJECT-TYPE
                    		SYNTAX  SEQUENCE OF   AaaGrpSrvReferenceTacacsIpEntry
                    		MAX-ACCESS  not-accessible
                    		STATUS  current
                    		DESCRIPTION
                    			""
                    		::= { aaaGrpSrv 2 }

aaaGrpSrvReferenceTacacsIpEntry	OBJECT-TYPE
                    		SYNTAX  AaaGrpSrvReferenceTacacsIpEntry
                    		MAX-ACCESS  not-accessible
                    		STATUS  current
                    		DESCRIPTION
                    			""
                    		INDEX  { aaaGrpSrvPrivateTacacsIp, aaaGrpSrvPrivateTacacsIpName }
                    		::= { aaaGrpSrvReferenceTacacsIpTable 1 }

AaaGrpSrvReferenceTacacsIpEntry	::= SEQUENCE {
                    			aaaGrpSrvReferenceTacacsIp   IpAddress,
                    			aaaGrpSrvReferenceTacacsIpName   DisplayString,
                    			aaaGrpSrvReferenceTacacsIpStatus   INTEGER,
                    			aaaGrpSrvReferenceTacacsIpRowStatus   RowStatus
                    	             }


aaaGrpSrvReferenceTacacsIp	OBJECT-TYPE
                    		SYNTAX  IpAddress
                    		MAX-ACCESS  not-accessible
                    		STATUS  current
                    		DESCRIPTION
                    			""
                    		::= { aaaGrpSrvReferenceTacacsIpEntry 1 }

aaaGrpSrvReferenceTacacsIpName	OBJECT-TYPE
                    		SYNTAX  DisplayString(SIZE(0..32))
                    		MAX-ACCESS  accessible-for-notify
                    		STATUS  current
                    		DESCRIPTION
                    			""
                    		::= { aaaGrpSrvReferenceTacacsIpEntry 2 }

aaaGrpSrvReferenceTacacsIpStatus	OBJECT-TYPE
                    		SYNTAX  INTEGER {
                    			         define(1),
                    			          undefine(2)
                    			        }
                    		MAX-ACCESS  read-only
                    		STATUS  current
                    		DESCRIPTION
                    			""
                    		::= { aaaGrpSrvReferenceTacacsIpEntry 3 }

aaaGrpSrvReferenceTacacsIpRowStatus	OBJECT-TYPE
                    		SYNTAX  RowStatus
                    		MAX-ACCESS  read-create
                    		STATUS  current
                    		DESCRIPTION
                    			""
                    		::= { aaaGrpSrvReferenceTacacsIpEntry 4 }

aaaGrpSrvReferenceRadiusIpTable	OBJECT-TYPE
                    		SYNTAX  SEQUENCE OF   AaaGrpSrvReferenceRadiusIpEntry
                    		MAX-ACCESS  not-accessible
                    		STATUS  current
                    		DESCRIPTION
                    			""
                    		::= { aaaGrpSrv 3 }

aaaGrpSrvReferenceRadiusIpEntry	OBJECT-TYPE
                    		SYNTAX  AaaGrpSrvReferenceRadiusIpEntry
                    		MAX-ACCESS  not-accessible
                    		STATUS  current
                    		DESCRIPTION
                    			""
                    		INDEX  { aaaGrpSrvPrivateRadiusIp, aaaGrpSrvPrivateRadiusIpAuthPort, aaaGrpSrvPrivateRadiusIpAcctPort, aaaGrpSrvPrivateRadiusIpName }
                    		::= { aaaGrpSrvReferenceRadiusIpTable 1 }

AaaGrpSrvReferenceRadiusIpEntry	::= SEQUENCE {
                    			aaaGrpSrvReferenceRadiusIp   IpAddress,
                    			aaaGrpSrvReferenceRadiusIpAuthPort   INTEGER,
                    			aaaGrpSrvReferenceRadiusIpAcctPort   INTEGER,
                    			aaaGrpSrvReferenceRadiusIpName   DisplayString,
                    			aaaGrpSrvReferenceRadiusIpStatus   INTEGER,
                    			aaaGrpSrvReferenceRadiusIpRowStatus   RowStatus
                    	             }


aaaGrpSrvReferenceRadiusIp	OBJECT-TYPE
                    		SYNTAX  IpAddress
                    		MAX-ACCESS  not-accessible
                    		STATUS  current
                    		DESCRIPTION
                    			"组服务器IP地址"
                    		::= { aaaGrpSrvReferenceRadiusIpEntry 1 }

aaaGrpSrvReferenceRadiusIpAuthPort	OBJECT-TYPE
                    		SYNTAX  INTEGER(0..65535)
                    		MAX-ACCESS  not-accessible
                    		STATUS  current
                    		DESCRIPTION
                    			""
                    		::= { aaaGrpSrvReferenceRadiusIpEntry 2 }

aaaGrpSrvReferenceRadiusIpAcctPort	OBJECT-TYPE
                    		SYNTAX  INTEGER(0..65535)
                    		MAX-ACCESS  not-accessible
                    		STATUS  current
                    		DESCRIPTION
                    			""
                    		::= { aaaGrpSrvReferenceRadiusIpEntry 3 }

aaaGrpSrvReferenceRadiusIpName	OBJECT-TYPE
                    		SYNTAX  DisplayString(SIZE(0..32))
                    		MAX-ACCESS  not-accessible
                    		STATUS  current
                    		DESCRIPTION
                    			"IP所属的组"
                    		::= { aaaGrpSrvReferenceRadiusIpEntry 4 }

aaaGrpSrvReferenceRadiusIpStatus	OBJECT-TYPE
                    		SYNTAX  INTEGER {
                    			         define(1),
                    			          undefine(2)
                    			        }
                    		MAX-ACCESS  read-only
                    		STATUS  current
                    		DESCRIPTION
                    			""
                    		::= { aaaGrpSrvReferenceRadiusIpEntry 5 }

aaaGrpSrvReferenceRadiusIpRowStatus	OBJECT-TYPE
                    		SYNTAX  RowStatus
                    		MAX-ACCESS  read-write
                    		STATUS  current
                    		DESCRIPTION
                    			""
                    		::= { aaaGrpSrvReferenceRadiusIpEntry 6 }

aaaGrpSrvPrivateTacacsIpTable	OBJECT-TYPE
                    		SYNTAX  SEQUENCE OF   AaaGrpSrvPrivateTacacsIpEntry
                    		MAX-ACCESS  not-accessible
                    		STATUS  current
                    		DESCRIPTION
                    			""
                    		::= { aaaGrpSrv 4 }

aaaGrpSrvPrivateTacacsIpEntry	OBJECT-TYPE
                    		SYNTAX  AaaGrpSrvPrivateTacacsIpEntry
                    		MAX-ACCESS  not-accessible
                    		STATUS  current
                    		DESCRIPTION
                    			""
                    		INDEX  { aaaGrpSrvPrivateTacacsIp, aaaGrpSrvPrivateTacacsIpName }
                    		::= { aaaGrpSrvPrivateTacacsIpTable 1 }

AaaGrpSrvPrivateTacacsIpEntry	::= SEQUENCE {
                    			aaaGrpSrvPrivateTacacsIp   IpAddress,
                    			aaaGrpSrvPrivateTacacsIpName   DisplayString,
                    			aaaGrpSrvPrivateTacacsIpKey   DisplayString,
                    			aaaGrpSrvPrivateTacacsIpPort   INTEGER,
                    			aaaGrpSrvPrivateTacacsIpTimeout   INTEGER,
                    			aaaGrpSrvPrivateTacacsIpRowStatus   RowStatus
                    	             }


aaaGrpSrvPrivateTacacsIp	OBJECT-TYPE
                    		SYNTAX  IpAddress
                    		MAX-ACCESS  not-accessible
                    		STATUS  current
                    		DESCRIPTION
                    			""
                    		::= { aaaGrpSrvPrivateTacacsIpEntry 1 }

aaaGrpSrvPrivateTacacsIpName	OBJECT-TYPE
                    		SYNTAX  DisplayString(SIZE(0..32))
                    		MAX-ACCESS  not-accessible
                    		STATUS  current
                    		DESCRIPTION
                    			""
                    		::= { aaaGrpSrvPrivateTacacsIpEntry 2 }

aaaGrpSrvPrivateTacacsIpKey	OBJECT-TYPE
                    		SYNTAX  DisplayString(SIZE(0..127))
                    		MAX-ACCESS  read-create
                    		STATUS  current
                    		DESCRIPTION
                    			""
                    		::= { aaaGrpSrvPrivateTacacsIpEntry 3 }

aaaGrpSrvPrivateTacacsIpPort	OBJECT-TYPE
                    		SYNTAX  INTEGER(0.65535)
                    		MAX-ACCESS  read-create
                    		STATUS  current
                    		DESCRIPTION
                    			""
                    		::= { aaaGrpSrvPrivateTacacsIpEntry 4 }

aaaGrpSrvPrivateTacacsIpTimeout	OBJECT-TYPE
                    		SYNTAX  INTEGER(0..1000)
                    		MAX-ACCESS  read-create
                    		STATUS  current
                    		DESCRIPTION
                    			""
                    		::= { aaaGrpSrvPrivateTacacsIpEntry 5 }

aaaGrpSrvPrivateTacacsIpRowStatus	OBJECT-TYPE
                    		SYNTAX  RowStatus
                    		MAX-ACCESS  read-create
                    		STATUS  current
                    		DESCRIPTION
                    			""
                    		::= { aaaGrpSrvPrivateTacacsIpEntry 6 }

aaaGrpSrvPrivateRadiusIpTable	OBJECT-TYPE
                    		SYNTAX  SEQUENCE OF   AaaGrpSrvPrivateRadiusIpEntry
                    		MAX-ACCESS  not-accessible
                    		STATUS  current
                    		DESCRIPTION
                    			""
                    		::= { aaaGrpSrv 5 }

aaaGrpSrvPrivateRadiusIpEntry	OBJECT-TYPE
                    		SYNTAX  AaaGrpSrvPrivateRadiusIpEntry
                    		MAX-ACCESS  not-accessible
                    		STATUS  current
                    		DESCRIPTION
                    			""
                    		INDEX  { aaaGrpSrvPrivateRadiusIp, aaaGrpSrvPrivateRadiusIpName, aaaGrpSrvPrivateRadiusIpAuthPort, aaaGrpSrvPrivateRadiusIpAcctPort }
                    		::= { aaaGrpSrvPrivateRadiusIpTable 1 }

AaaGrpSrvPrivateRadiusIpEntry	::= SEQUENCE {
                    			aaaGrpSrvPrivateRadiusIp   IpAddress,
                    			aaaGrpSrvPrivateRadiusIpName   DisplayString,
                    			aaaGrpSrvPrivateRadiusIpAuthPort   INTEGER,
                    			aaaGrpSrvPrivateRadiusIpAcctPort   INTEGER,
                    			aaaGrpSrvPrivateRadiusIpPriority   INTEGER,
                    			aaaGrpSrvPrivateRadiusIpKey   DisplayString,
                    			aaaGrpSrvPrivateRadiusIpRowStatus   RowStatus
                    	             }


aaaGrpSrvPrivateRadiusIp	OBJECT-TYPE
                    		SYNTAX  IpAddress
                    		MAX-ACCESS  not-accessible
                    		STATUS  current
                    		DESCRIPTION
                    			""
                    		::= { aaaGrpSrvPrivateRadiusIpEntry 1 }

aaaGrpSrvPrivateRadiusIpName	OBJECT-TYPE
                    		SYNTAX  DisplayString(SIZE(0..32))
                    		MAX-ACCESS  accessible-for-notify
                    		STATUS  current
                    		DESCRIPTION
                    			""
                    		::= { aaaGrpSrvPrivateRadiusIpEntry 2 }

aaaGrpSrvPrivateRadiusIpAuthPort	OBJECT-TYPE
                    		SYNTAX  INTEGER(0..65535)
                    		MAX-ACCESS  not-accessible
                    		STATUS  current
                    		DESCRIPTION
                    			""
                    		::= { aaaGrpSrvPrivateRadiusIpEntry 3 }

aaaGrpSrvPrivateRadiusIpAcctPort	OBJECT-TYPE
                    		SYNTAX  INTEGER(0..65535)
                    		MAX-ACCESS  not-accessible
                    		STATUS  current
                    		DESCRIPTION
                    			""
                    		::= { aaaGrpSrvPrivateRadiusIpEntry 4 }

aaaGrpSrvPrivateRadiusIpPriority	OBJECT-TYPE
                    		SYNTAX  INTEGER(0..255)
                    		MAX-ACCESS  read-create
                    		STATUS  current
                    		DESCRIPTION
                    			""
                    		::= { aaaGrpSrvPrivateRadiusIpEntry 5 }

aaaGrpSrvPrivateRadiusIpKey	OBJECT-TYPE
                    		SYNTAX  DisplayString(SIZE(0..127))
                    		MAX-ACCESS  read-create
                    		STATUS  current
                    		DESCRIPTION
                    			""
                    		::= { aaaGrpSrvPrivateRadiusIpEntry 6 }

aaaGrpSrvPrivateRadiusIpRowStatus	OBJECT-TYPE
                    		SYNTAX  RowStatus
                    		MAX-ACCESS  read-create
                    		STATUS  current
                    		DESCRIPTION
                    			""
                    		::= { aaaGrpSrvPrivateRadiusIpEntry 7 }


------------------------------------------------------------------------------
radiusConf          	OBJECT IDENTIFIER ::= { mpAAAMib 2 }


------------------------------------------------------------------------------
radiusGlobal        	OBJECT IDENTIFIER ::= { radiusConf 1 }

radiusSvrDeadtime   	OBJECT-TYPE
                    		SYNTAX  INTEGER(0..1440)
                    		MAX-ACCESS  read-write
                    		STATUS  current
                    		DESCRIPTION
                    			"Time to stop using a server that does not respond
                    			 0 - don't stop
                    			 1..1440 - the time to stop"
                    		::= { radiusGlobal 1 }

radiusSvrKey        	OBJECT-TYPE
                    		SYNTAX  DisplayString(SIZE(0..127))
                    		MAX-ACCESS  read-write
                    		STATUS  current
                    		DESCRIPTION
                    			"Radius密钥"
                    		::= { radiusGlobal 2 }

radiusSvrRetrans    	OBJECT-TYPE
                    		SYNTAX  INTEGER(1..100)
                    		MAX-ACCESS  read-write
                    		STATUS  current
                    		DESCRIPTION
                    			"Raidus重传时间：default 3"
                    		::= { radiusGlobal 3 }

radiusSvrTimeout    	OBJECT-TYPE
                    		SYNTAX  INTEGER(1..1000)
                    		MAX-ACCESS  read-write
                    		STATUS  current
                    		DESCRIPTION
                    			"Radius等待服务器超时时间"
                    		::= { radiusGlobal 4 }

radiusSvrSrcIf      	OBJECT-TYPE
                    		SYNTAX  MInterfaceName
                    		MAX-ACCESS  read-write
                    		STATUS  current
                    		DESCRIPTION
                    			"Raidus使用的源接口"
                    		::= { radiusGlobal 5 }


------------------------------------------------------------------------------
radiusList          	OBJECT IDENTIFIER ::= { radiusConf 2 }

radiusHostTable     	OBJECT-TYPE
                    		SYNTAX  SEQUENCE OF  RadiusHostEntry
                    		MAX-ACCESS  not-accessible
                    		STATUS  current
                    		DESCRIPTION
                    			"The valid RadiusHost."
                    		::= { radiusList 1 }

radiusHostEntry     	OBJECT-TYPE
                    		SYNTAX  RadiusHostEntry
                    		MAX-ACCESS  not-accessible
                    		STATUS  current
                    		DESCRIPTION
                    			"The valid RadiusHost."
                    		INDEX  { radiusHostAddr, radiusHostAuthPort, radiusHostAcctPort }
                    		::= { radiusHostTable 1 }

RadiusHostEntry     	::= SEQUENCE {
                    			radiusHostAddr         IpAddress,
                    			radiusHostAuthPort     INTEGER,
                    			radiusHostAcctPort     INTEGER,
                    			radiusHostPriority     INTEGER,
                    			radiusHostKey          DisplayString,
                    			radiusHostStatus       RowStatus
                    	             }


radiusHostAddr      	OBJECT-TYPE
                    		SYNTAX  IpAddress
                    		MAX-ACCESS  not-accessible
                    		STATUS  current
                    		DESCRIPTION
                    			"Raidus服务器地址"
                    		::= { radiusHostEntry 1 }

radiusHostAuthPort  	OBJECT-TYPE
                    		SYNTAX  INTEGER(0..65535)
                    		MAX-ACCESS  not-accessible
                    		STATUS  current
                    		DESCRIPTION
                    			"Radius服务器认证端口"
                    		::= { radiusHostEntry 2 }

radiusHostAcctPort  	OBJECT-TYPE
                    		SYNTAX  INTEGER(0..65535)
                    		MAX-ACCESS  not-accessible
                    		STATUS  current
                    		DESCRIPTION
                    			"Radius服务器计费端口."
                    		::= { radiusHostEntry 3 }

radiusHostPriority  	OBJECT-TYPE
                    		SYNTAX  INTEGER(0..255)
                    		MAX-ACCESS  read-create
                    		STATUS  current
                    		DESCRIPTION
                    			"radius server's priority"
                    		::= { radiusHostEntry 4 }

radiusHostKey       	OBJECT-TYPE
                    		SYNTAX  DisplayString(SIZE(0..127))
                    		MAX-ACCESS  read-write
                    		STATUS  current
                    		DESCRIPTION
                    			""
                    		::= { radiusHostEntry 5 }

radiusHostStatus    	OBJECT-TYPE
                    		SYNTAX  RowStatus
                    		MAX-ACCESS  read-create
                    		STATUS  current
                    		DESCRIPTION
                    			"."
                    		::= { radiusHostEntry 6 }


------------------------------------------------------------------------------
tacacsConf          	OBJECT IDENTIFIER ::= { mpAAAMib 3 }


------------------------------------------------------------------------------
tacacsGlobal        	OBJECT IDENTIFIER ::= { tacacsConf 1 }

tacacsSvrKey        	OBJECT-TYPE
                    		SYNTAX  OCTET STRING(SIZE(0..127))
                    		MAX-ACCESS  read-write
                    		STATUS  current
                    		DESCRIPTION
                    			"Tacacs服务器密钥"
                    		::= { tacacsGlobal 1 }

tacacsSvrTimeout    	OBJECT-TYPE
                    		SYNTAX  INTEGER(1..1000)
                    		MAX-ACCESS  read-write
                    		STATUS  current
                    		DESCRIPTION
                    			"Tacacs服务器超时时间"
                    		::= { tacacsGlobal 2 }

tacacsSrcIf         	OBJECT-TYPE
                    		SYNTAX  MInterfaceName
                    		MAX-ACCESS  read-write
                    		STATUS  current
                    		DESCRIPTION
                    			"Tacacs客户端使用的源接口"
                    		::= { tacacsGlobal 3 }


------------------------------------------------------------------------------
tacacsList          	OBJECT IDENTIFIER ::= { tacacsConf 2 }

tacacsHostTable     	OBJECT-TYPE
                    		SYNTAX  SEQUENCE OF  TacacsHostEntry
                    		MAX-ACCESS  not-accessible
                    		STATUS  current
                    		DESCRIPTION
                    			"The valid tacacsHost."
                    		::= { tacacsList 1 }

tacacsHostEntry     	OBJECT-TYPE
                    		SYNTAX  TacacsHostEntry
                    		MAX-ACCESS  not-accessible
                    		STATUS  current
                    		DESCRIPTION
                    			"The valid tacacsHost."
                    		INDEX  { tacacsHostAddr }
                    		::= { tacacsHostTable 1 }

TacacsHostEntry     	::= SEQUENCE {
                    			tacacsHostAddr         IpAddress,
                    			tacacsHostKey          OCTET STRING,
                    			tacacsHostPort         INTEGER,
                    			tacacsHostTimeout      INTEGER,
                    			tacacsHostStatus       RowStatus
                    	             }


tacacsHostAddr      	OBJECT-TYPE
                    		SYNTAX  IpAddress
                    		MAX-ACCESS  not-accessible
                    		STATUS  current
                    		DESCRIPTION
                    			"Tacacs服务器地址"
                    		::= { tacacsHostEntry 1 }

tacacsHostKey       	OBJECT-TYPE
                    		SYNTAX  OCTET STRING(SIZE(0..127))
                    		MAX-ACCESS  read-create
                    		STATUS  current
                    		DESCRIPTION
                    			"Tacscs服务器私钥"
                    		::= { tacacsHostEntry 2 }

tacacsHostPort      	OBJECT-TYPE
                    		SYNTAX  INTEGER(1..65535)
                    		MAX-ACCESS  read-create
                    		STATUS  current
                    		DESCRIPTION
                    			"Tacscs服务器端口"
                    		::= { tacacsHostEntry 3 }

tacacsHostTimeout   	OBJECT-TYPE
                    		SYNTAX  INTEGER(1..1000)
                    		MAX-ACCESS  read-create
                    		STATUS  current
                    		DESCRIPTION
                    			"Tacscs等待服务器超时时间."
                    		::= { tacacsHostEntry 4 }

tacacsHostStatus    	OBJECT-TYPE
                    		SYNTAX  RowStatus
                    		MAX-ACCESS  read-create
                    		STATUS  current
                    		DESCRIPTION
                    			"."
                    		::= { tacacsHostEntry 5 }



END
------------------------------------------------------------------------------
-- ============================================================================
-- $Log: mpAAA.mib,v $
-- Revision 1.2  2010/08/12 05:50:06  xianggy
-- [product-30]合并AAA MIB
--
-- Revision 1.1  2010/06/21 11:18:46  liyh
-- first commit
--
--
--
-- ============================================================================
