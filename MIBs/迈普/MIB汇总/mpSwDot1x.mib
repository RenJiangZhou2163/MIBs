------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPSWDOT1X DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;


maipu               	OBJECT IDENTIFIER ::= { enterprises 5651 }
mpMgmt2             	OBJECT IDENTIFIER ::= { maipu 6 }
mpSwitchTech        	OBJECT IDENTIFIER ::= { mpMgmt2 3 }



mpSwDot1x           	MODULE-IDENTITY
                    		LAST-UPDATED 	"1104231645Z"
                    		ORGANIZATION 	"四川迈普数据通信股份有限公司,
                    		             	 Maipu (Sichuan) Communication Technology Co. LTD."
                    		CONTACT-INFO
                    			"编 写 人:  xupan
                    			 联系地址：四川省 成都市 高新区 九兴大道16号
                    			 邮    编：    610041
                    			 电    话：
                    			 传    真：
                    			 电子邮件： xpxpxpxpxp@263.net"
                    		DESCRIPTION
                      			""
                    		::= { mpSwitchTech  3 }




------------------------------------------------------------------------------
dot1xTraps          	OBJECT IDENTIFIER ::= { mpSwDot1x 0 }

dot1xMacAddTrap     	NOTIFICATION-TYPE
                    		OBJECTS {
                    		         dot1xMacAddress
                    		        }
                    		STATUS  current
                    		DESCRIPTION
                    			"notify when user online
                    			 param1: dot1xMacIndex;"
                    		::= { dot1xTraps 1 }

dot1xMacDelTrap     	NOTIFICATION-TYPE
                    		OBJECTS {
                    		         dot1xMacAddress
                    		        }
                    		STATUS  current
                    		DESCRIPTION
                    			"notify when user go-off
                    			 param1: dot1xMacIndex;"
                    		::= { dot1xTraps 2 }

mpMacChangeNotify   	NOTIFICATION-TYPE
                    		OBJECTS {
                    		         mpMacNotifyMsg,
                    		         mpTimeStamp
                    		        }
                    		STATUS  current
                    		DESCRIPTION
                    			"notify when mac added or deleted
                    			 param1: mpMacNotifyMsg
                    			 param2: mpTimeStamp"
                    		::= { dot1xTraps 3 }

dot1xPortTable      	OBJECT-TYPE
                    		SYNTAX  SEQUENCE OF   Dot1xPortEntry
                    		MAX-ACCESS  not-accessible
                    		STATUS  current
                    		DESCRIPTION
                    			"802.1x port configuration."
                    		::= { mpSwDot1x 1 }

dot1xPortEntry      	OBJECT-TYPE
                    		SYNTAX  Dot1xPortEntry
                    		MAX-ACCESS  not-accessible
                    		STATUS  current
                    		DESCRIPTION
                    			"802.1x port configuration."
                    		INDEX  { dot1xPortPortNo }
                    		::= { dot1xPortTable 1 }

Dot1xPortEntry      	::= SEQUENCE {
                    			dot1xPortPortNo        INTEGER,
                    			dot1xPortStatus        INTEGER,
                    			dot1xPortMaxUserNum    INTEGER,
                    			dot1xPortEapolRelay    INTEGER,
                    			dot1xPortUplinkPort    INTEGER,
                    			dot1xPortEapRelay      INTEGER,
                    			dot1xPortCurUserNum    INTEGER,
                    			dot1xPortGuestVlan     INTEGER,
                    			dot1xPortAutoVlan      INTEGER,
                    			dot1xPortQuietPeriod   INTEGER,
                    			dot1xPortReAuthPeriod   INTEGER,
                    			dot1xPortMaxAuthFail   INTEGER,
                    			dot1xPortMultiTrigger   INTEGER,
                    			dot1xPortReAuthEnable   INTEGER,
                    			dot1xPortPortMethod    INTEGER,
                    			dot1xPortRowStatus     RowStatus
                    	             }


dot1xPortPortNo     	OBJECT-TYPE
                    		SYNTAX  INTEGER
                    		MAX-ACCESS  read-only
                    		STATUS  current
                    		DESCRIPTION
                    			"port number"
                    		::= { dot1xPortEntry 1 }

dot1xPortStatus     	OBJECT-TYPE
                    		SYNTAX  INTEGER {
                    			         disable(1),
                    			          enable(2)
                    			        }
                    		MAX-ACCESS  read-create
                    		STATUS  current
                    		DESCRIPTION
                    			"enable or disable dot1x on the port."
                    		::= { dot1xPortEntry 2 }

dot1xPortMaxUserNum 	OBJECT-TYPE
                    		SYNTAX  INTEGER(1..4096)
                    		MAX-ACCESS  read-create
                    		STATUS  current
                    		DESCRIPTION
                    			"max user number on the port, default: 50"
                    		::= { dot1xPortEntry 3 }

dot1xPortEapolRelay 	OBJECT-TYPE
                    		SYNTAX  INTEGER {
                    			         disable(1),
                    			          enable(2)
                    			        }
                    		MAX-ACCESS  read-create
                    		STATUS  current
                    		DESCRIPTION
                    			"enable or disable eapol-relay on the port."
                    		::= { dot1xPortEntry 4 }

dot1xPortUplinkPort 	OBJECT-TYPE
                    		SYNTAX  INTEGER
                    		MAX-ACCESS  read-create
                    		STATUS  current
                    		DESCRIPTION
                    			"uplink port for eapol-relay"
                    		::= { dot1xPortEntry 5 }

dot1xPortEapRelay   	OBJECT-TYPE
                    		SYNTAX  INTEGER {
                    			         disable(1),
                    			          enable(2)
                    			        }
                    		MAX-ACCESS  read-create
                    		STATUS  current
                    		DESCRIPTION
                    			"enable or disable eap-relay on the port."
                    		::= { dot1xPortEntry 6 }

dot1xPortCurUserNum 	OBJECT-TYPE
                    		SYNTAX  INTEGER
                    		MAX-ACCESS  read-only
                    		STATUS  current
                    		DESCRIPTION
                    			"current user on the port."
                    		::= { dot1xPortEntry 7 }

dot1xPortGuestVlan  	OBJECT-TYPE
                    		SYNTAX  INTEGER(0..4094)
                    		MAX-ACCESS  read-create
                    		STATUS  current
                    		DESCRIPTION
                    			"guest vlan id, 0 for disable."
                    		::= { dot1xPortEntry 8 }

dot1xPortAutoVlan   	OBJECT-TYPE
                    		SYNTAX  INTEGER(0..4094)
                    		MAX-ACCESS  read-only
                    		STATUS  current
                    		DESCRIPTION
                    			"auto vlan id, 0 for disable."
                    		::= { dot1xPortEntry 9 }

dot1xPortQuietPeriod	OBJECT-TYPE
                    		SYNTAX  INTEGER(1..65535)
                    		MAX-ACCESS  read-create
                    		STATUS  current
                    		DESCRIPTION
                    			"quiet period following failed authentication."
                    		::= { dot1xPortEntry 10 }

dot1xPortReAuthPeriod	OBJECT-TYPE
                    		SYNTAX  INTEGER(1..3600)
                    		MAX-ACCESS  read-create
                    		STATUS  current
                    		DESCRIPTION
                    			"the time in seconds between re-authentication attempts."
                    		::= { dot1xPortEntry 11 }

dot1xPortMaxAuthFail	OBJECT-TYPE
                    		SYNTAX  INTEGER(1..10)
                    		MAX-ACCESS  read-create
                    		STATUS  current
                    		DESCRIPTION
                    			"retry times when authentication failed."
                    		::= { dot1xPortEntry 12 }

dot1xPortMultiTrigger	OBJECT-TYPE
                    		SYNTAX  INTEGER {
                    			         disable(1),
                    			          enable(2)
                    			        }
                    		MAX-ACCESS  read-create
                    		STATUS  current
                    		DESCRIPTION
                    			"enable or disable sending eap request/id packet periodic."
                    		::= { dot1xPortEntry 13 }

dot1xPortReAuthEnable	OBJECT-TYPE
                    		SYNTAX  INTEGER {
                    			         disable(1),
                    			          enable(2)
                    			        }
                    		MAX-ACCESS  read-create
                    		STATUS  current
                    		DESCRIPTION
                    			"enable or disable re-authentication."
                    		::= { dot1xPortEntry 14 }

dot1xPortPortMethod 	OBJECT-TYPE
                    		SYNTAX  INTEGER {
                    			         macbased(1),
                    			          portbased(2)
                    			        }
                    		MAX-ACCESS  read-create
                    		STATUS  current
                    		DESCRIPTION
                    			"authentication based on port or user."
                    		::= { dot1xPortEntry 15 }

dot1xPortRowStatus  	OBJECT-TYPE
                    		SYNTAX  RowStatus
                    		MAX-ACCESS  read-create
                    		STATUS  current
                    		DESCRIPTION
                    			"row status."
                    		::= { dot1xPortEntry 16 }

dot1xMacTable       	OBJECT-TYPE
                    		SYNTAX  SEQUENCE OF   Dot1xMacEntry
                    		MAX-ACCESS  not-accessible
                    		STATUS  current
                    		DESCRIPTION
                    			""
                    		::= { mpSwDot1x 2 }

dot1xMacEntry       	OBJECT-TYPE
                    		SYNTAX  Dot1xMacEntry
                    		MAX-ACCESS  not-accessible
                    		STATUS  current
                    		DESCRIPTION
                    			""
                    		INDEX  { dot1xMacAddress }
                    		::= { dot1xMacTable 1 }

Dot1xMacEntry       	::= SEQUENCE {
                    			dot1xMacAddress        MacAddress,
                    			dot1xMacPeriod         Unsigned32
                    	             }


dot1xMacAddress     	OBJECT-TYPE
                    		SYNTAX  MacAddress
                    		MAX-ACCESS  read-only
                    		STATUS  current
                    		DESCRIPTION
                    			"user's mac address"
                    		::= { dot1xMacEntry 1 }

dot1xMacPeriod      	OBJECT-TYPE
                    		SYNTAX  Unsigned32(1..30000000)
                    		MAX-ACCESS  read-write
                    		STATUS  current
                    		DESCRIPTION
                    			"forbidden time"
                    		::= { dot1xMacEntry 2 }

mpDot1xMacNotityTable	OBJECT-TYPE
                    		SYNTAX  SEQUENCE OF   MpDot1xMacNotityEntry
                    		MAX-ACCESS  not-accessible
                    		STATUS  current
                    		DESCRIPTION
                    			"This table will archive the MAC change notification events generated by this device. The MAC change notification events are archived here even if cmnMacChangesNotifications are not actually sent"
                    		::= { mpSwDot1x 3 }

mpDot1xMacNotityEntry	OBJECT-TYPE
                    		SYNTAX  MpDot1xMacNotityEntry
                    		MAX-ACCESS  not-accessible
                    		STATUS  current
                    		DESCRIPTION
                    			"This table will archive the MAC change notification events generated by this device. The MAC change notification events are archived here even if cmnMacChangesNotifications are not actually sent"
                    		INDEX  { mpMacNotityIndex }
                    		::= { mpDot1xMacNotityTable 1 }

MpDot1xMacNotityEntry	::= SEQUENCE {
                    			mpMacNotityIndex       Unsigned32,
                    			mpMacNotifyMsg         OCTET STRING,
                    			mpTimeStamp            TimeStamp
                    	             }


mpMacNotityIndex    	OBJECT-TYPE
                    		SYNTAX  Unsigned32(0..4294967295)
                    		MAX-ACCESS  read-only
                    		STATUS  current
                    		DESCRIPTION
                    			"An index that uniquely identifies a MAC change notification event previously generated by the device. This index starts at 1 and increases by one when a MAC change notification is 
                    			 generated.  When it reaches the maximum value, the agent wraps the value back to 1."
                    		::= { mpDot1xMacNotityEntry 1 }

mpMacNotifyMsg      	OBJECT-TYPE
                    		SYNTAX  OCTET STRING(SIZE(1..254))
                    		MAX-ACCESS  read-only
                    		STATUS  current
                    		DESCRIPTION
                    			"This object contains the information of a MAC change notification event. It consists of several tuples packed together in the format of '<tuple1><tuple2>...'.Each tuple consist of 11 octets in the format of '<operation><VLAN><MAC><dot1dBasePort>' 
                    			 where <operation> is of size 1 octet and supports the following values0 - End of MIB object.
                    			 1 - MAC learnt.
                    			 2 - MAC removed.
                    			 <VLAN> is VLAN number of the VLAN which the MAC address is
                    			 belonged to and has size of 2 octet.
                    			 <MAC> is the Layer2 Mac Address and has size of 6 octets.
                    			 <dot1dBasePort> is the value of dot1dBasePort for the interface from which the MAC address is learnt and has size of 2 octets.""
                    		::= { mpDot1xMacNotityEntry 2 }

mpTimeStamp         	OBJECT-TYPE
                    		SYNTAX  TimeStamp
                    		MAX-ACCESS  read-only
                    		STATUS  current
                    		DESCRIPTION
                    			"The value of sysUpTime when the cmnMacChangedNotification containing the information denoted by the cmnHistMacChangedMsg object in this entry was generated."
                    		::= { mpDot1xMacNotityEntry 3 }



END
------------------------------------------------------------------------------
-- ============================================================================
-- $Log: sysMib.mi2,v $
--
--
-- ============================================================================
