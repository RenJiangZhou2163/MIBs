-- *****************************************************************
-- mpIPsec.mib:  Maipu enterprise device IPsec MIB file
--
-- version 1.0.0.1, Mar 2, 2006 wang wenyu
--
-- Copyright (c)  by Maipu Communication Inc.
-- All rights reserved.
-- 
-- *****************************************************************

	
MAIPU-SECURITY-PKI-MIB DEFINITIONS ::= BEGIN

IMPORTS
        MODULE-IDENTITY, OBJECT-TYPE, Counter32,
       	IpAddress, Unsigned32		FROM SNMPv2-SMI
       	RowStatus			FROM SNMPv2-TC
       	mpSecurity			FROM MAIPU-SMI;
       
mpSecurityRouter 	MODULE-IDENTITY
        LAST-UPDATED "200603020932Z"      -- Thu Mar 2 09:32:35 PDT 2006
        ORGANIZATION "Maipu Communication"
        CONTACT-INFO
          	"       Wang wenyu
          	Postal: Maipu Inc
                  Tel: (028)85148048
          	E-Mail: office@maipu.com "
          
        DESCRIPTION
	 	"The MIB module describes the downlaod configuration file. "          
        ::= { mpSecurity 3 }

-- *****************************************************************

ConfigFileModule	OBJECT IDENTIFIER ::= { mpSecurityRouter 3 }

ConfigFileGroup	OBJECT IDENTIFIER ::= { ConfigFileModule 1 }

-- *****************************************************************

-- *****************************************************************
ConfigInitTraps		OBJECT IDENTIFIER ::= { ConfigFileGroup 0 }

ConfigReqTrap		NOTIFICATION-TYPE
	OBJECTS {
		cnUserID,
		cnVersion,
		cnHostName,
		cnOther,
		estabSaTrapRemoteAddress		
		}	
	STATUS current
    	DESCRIPTION
		"配置申请的TRAP."
    	::={ ConfigInitTraps 1 }
    	
EmbranceInitConfigTrap		NOTIFICATION-TYPE
	OBJECTS {
		cnUserID
		}	
	STATUS current
    	DESCRIPTION
		"分支设备SNMP配置成功的TRAP."
    	::={ ConfigInitTraps 2 }

PreKeyReqTrap				NOTIFICATION-TYPE
	OBJECTS {
		cnUserID,
		cnHostName
		}	
	STATUS current
    	DESCRIPTION
		"配置预共享密钥的TRAP."
    	::={ ConfigInitTraps 3 }
    	
-- *****************************************************************
    	
-- *****************************************************************
-- Config Node Table

ConfigFileTable		OBJECT-TYPE
    	SYNTAX SEQUENCE OF ConfigFileEntry
    	MAX-ACCESS not-accessible
    	STATUS current
    	DESCRIPTION
		"The table contains all the configuration of ca identity."
    	::={ ConfigFileGroup 1 }
    
ConfigFileEntry	OBJECT-TYPE
    	SYNTAX ConfigFileEntry
    	MAX-ACCESS not-accessible
    	STATUS current
    	DESCRIPTION
		"Each entry contains the attributes associated with configuration file.
		配置文件表"
    	INDEX { UserID, FragNum }
    	::= { ConfigFileTable 1 }
    
ConfigFileEntry	::=
	SEQUENCE {
		cfUserID		OCTET STRING,
		cfFragNum		INTEGER,
		cfFragLen		INTEGER,
		cfConfigNode		OCTET STRING,
		cfConfigFileRowStatus	RowStatus
		}	

cfUserID			OBJECT-TYPE
	SYNTAX	OCTET STRING
	MAX-ACCESS	read-write
	STATUS	current
	DESCRIPTION
		"This object defines the user name or identity.
		用户名称或ID"
	::= { ConfigFileEntry 1 }

cfFragNum			OBJECT-TYPE
	SYNTAX	INTEGER
	MAX-ACCESS	read-write
	STATUS	current
	DESCRIPTION
		"This object defines the fragment number of current configuration file.
		本表项属于特定配置文件中的分片号"
	::= { ConfigFileEntry 2 }

cfFragLen			OBJECT-TYPE
	SYNTAX	INTEGER
	MAX-ACCESS	read-write
	STATUS	current
	DESCRIPTION
		"This object defines the fragment length of current configuration file.
		本表项属于特定配置文件中的分片长度"
	::= { ConfigFileEntry 3 }
	
cfConfigNode		OBJECT-TYPE
	SYNTAX	OCTET STRING(SIZE(0..1024))
	MAX-ACCESS	read-write
	STATUS	current
	DESCRIPTION
		"This object defines the first node.
		配置节点"
	::= { ConfigFileEntry 4 }
	
cfConfigFileRowStatus	OBJECT-TYPE
	SYNTAX		RowStatus
	MAX-ACCESS 	read-create
	STATUS 		current
    	DESCRIPTION
    		"The object defines the status of the table entry."
	::= { ConfigFileEntry 5 }
	
-- *****************************************************************

-- *****************************************************************
ConfigNotifyGroup		OBJECT IDENTIFIER ::= { ConfigFileGroup 2 }

cnUserID			OBJECT-TYPE
	SYNTAX	OCTET STRING
	MAX-ACCESS	read-write
	STATUS	current
	DESCRIPTION
		"This object defines the user name or identity.
		用户名称或ID"
	::= { ConfigNotifyGroup 1 }	
	
cnFragCount		OBJECT-TYPE
	SYNTAX	INTEGER
	MAX-ACCESS	read-write
	STATUS	current
	DESCRIPTION
		"This object defines the fragment count.
		分片的总数"
	::= { ConfigNotifyGroup 2 }	

cnVersion		OBJECT-TYPE
	SYNTAX	INTEGER
	MAX-ACCESS	read-write
	STATUS	current
	DESCRIPTION
		"This object defines the version of configuration file.
		配置文件的版本"
	::= { ConfigNotifyGroup 3 }	

cnHostName		OBJECT-TYPE
	SYNTAX	INTEGER
	MAX-ACCESS	read-write
	STATUS	current
	DESCRIPTION
		"This object defines the hostname of router.
		设备的名称"
	::= { ConfigNotifyGroup 4 }		
	
cnOther		OBJECT-TYPE
	SYNTAX	OCTET STRING
	MAX-ACCESS	read-write
	STATUS	current
	DESCRIPTION
		"This object defines the informations used for bind vrc to hardware.
		硬件绑定信息"
	::= { ConfigNotifyGroup 5 }		
		
-- *****************************************************************		

-- *****************************************************************
-- Config Pre-Shared Key Node Table

ConfigPreKeyTable		OBJECT-TYPE
    	SYNTAX SEQUENCE OF ConfigPreKeyEntry
    	MAX-ACCESS not-accessible
    	STATUS current
    	DESCRIPTION
		"The table contains pre-shared key of ike id."
    	::={ ConfigFileGroup 3 }
    
ConfigPreKeyEntry	OBJECT-TYPE
    	SYNTAX ConfigPreKeyEntry
    	MAX-ACCESS not-accessible
    	STATUS current
    	DESCRIPTION
		"Each entry contains the pre-shared key of specified ike id."
    	INDEX { cfUserID }
    	::= { ConfigPreKeyTable 1 }
    
ConfigPreKeyEntry	::=
	SEQUENCE {
		cfUserID		OCTET STRING,
		cfPreKey		OCTET STRING,
		cfConfigPreKeyRowStatus	RowStatus
		}	

cfUserID			OBJECT-TYPE
	SYNTAX	OCTET STRING
	MAX-ACCESS	read-write
	STATUS	current
	DESCRIPTION
		"This object defines the user name or ike id."
	::= { ConfigPreKeyEntry 1 }

cfPreKey			OBJECT-TYPE
	SYNTAX	OCTET STRING
	MAX-ACCESS	read-write
	STATUS	current
	DESCRIPTION
		"This object defines the pre-shared key of ike id."
	::= { ConfigPreKeyEntry 2 }

cfConfigPreKeyRowStatus	OBJECT-TYPE
	SYNTAX		RowStatus
	MAX-ACCESS 	read-create
	STATUS 		current
    	DESCRIPTION
    		"The object defines the status of the table entry."
	::= { ConfigPreKeyEntry 3 }
	
END
