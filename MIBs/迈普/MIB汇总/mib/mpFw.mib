------------------------------------------------------------------------------
--
--  File         : mpFw.mib
--  Description  : 
--  Version      :  
--  Date         : March 20, 2006
-- 	Copyright    : 2006 by maipu (sichuan) communication technology co.,ltd.
--					All rights reserved.
--
-- $Id:
-- 
------------------------------------------------------------------------------

------------------------------------------------------------------------------
MPFWMIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;



mpFwMib             	MODULE-IDENTITY
                    		LAST-UPDATED 	"0603191042Z"
                    		ORGANIZATION 	"四川迈普数据通信股份有限公司,
                    		             	 Maipu (Sichuan) Communication Technology Co. LTD."
                    		CONTACT-INFO
                    			"编 写 人：huyq
                    			 联系地址：四川省 成都市 高新区 九兴大道16号
                    			 邮    编：610041
                    			 电    话：
                    			 传    真：
                    			 电子邮件："
                    		DESCRIPTION
                      			""
                    		::= { mpMgmt  35 }



mpFwIfTable         	OBJECT-TYPE
                    		SYNTAX  SEQUENCE OF   MpFwIfEntry
                    		MAX-ACCESS  not-accessible
                    		STATUS  current
                    		DESCRIPTION
                    			"接口的访问控制配置表."
                    		::= { mpFwMib 10 }

mpFwIfEntry         	OBJECT-TYPE
                    		SYNTAX  MpFwIfEntry
                    		MAX-ACCESS  not-accessible
                    		STATUS  current
                    		DESCRIPTION
                    			"接口的访问控制配置表."
                    		INDEX  { fwIfName, fwIfDirection }
                    		::= { mpFwIfTable 1 }

MpFwIfEntry         	::= SEQUENCE {
                    			fwIfName               DisplayString,
                    			fwIfDirection          INTEGER,
                    			fwIfGrpName            DisplayString,
                    			fwIfRowStatus          RowStatus
                    	             }


fwIfName            	OBJECT-TYPE
                    		SYNTAX  DisplayString(SIZE(1..39))
                    		MAX-ACCESS  read-create
                    		STATUS  current
                    		DESCRIPTION
                    			"配置访问控制的接口名称."
                    		::= { mpFwIfEntry 1 }

fwIfDirection       	OBJECT-TYPE
                    		SYNTAX  INTEGER {
                    			         in(1),
                    			          out(2)
                    			        }
                    		MAX-ACCESS  read-create
                    		STATUS  current
                    		DESCRIPTION
                    			"接口上访问控制应用的方向."
                    		::= { mpFwIfEntry 2 }

fwIfGrpName         	OBJECT-TYPE
                    		SYNTAX  DisplayString(SIZE(1..31))
                    		MAX-ACCESS  read-write
                    		STATUS  current
                    		DESCRIPTION
                    			"接口上配置的访问控制的名字或编号."
                    		::= { mpFwIfEntry 3 }

fwIfRowStatus       	OBJECT-TYPE
                    		SYNTAX  RowStatus
                    		MAX-ACCESS  read-create
                    		STATUS  current
                    		DESCRIPTION
                    			"接口的访问控制配置表的行状态."
                    		::= { mpFwIfEntry 4 }



END
------------------------------------------------------------------------------
-- ============================================================================
-- $Log: mpFw.mib,v $
-- Revision 1.1  2010/06/21 11:18:46  liyh
-- first commit
--
-- Revision 1.1  2006/03/30 09:24:28  huyq
-- 增加对SNMP的支持
--
--
--
-- ============================================================================
