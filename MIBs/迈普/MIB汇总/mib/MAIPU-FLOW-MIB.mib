--------------------------------------------------------------------
-- MAIPU-FLOW-MIB:  Maipu Flow Mgmt MIB file
--
-- Sept 2007, wangyg
-- Copyright (c) 2007 by MAIPU COMMUNICATION TECHNOLOGY CO.,LTD
-- All rights reserved.
-- 
--------------------------------------------------------------------

MAIPU-FLOW-MIB	DEFINITIONS ::= BEGIN
	IMPORTS
		RowStatus, DisplayString, TimeStamp
			FROM SNMPv2-TC
		DisplayString
			FROM RFC1213-MIB
		MODULE-IDENTITY, OBJECT-IDENTITY, OBJECT-TYPE, Unsigned32, IpAddress, enterprises, Integer32
			FROM SNMPv2-SMI
		InetAddress, InetPortNumber, InetAddressType
			FROM INET-ADDRESS-MIB
		InterfaceIndex
			FROM IF-MIB
		mpMgmt
			FROM MAIPU-SMI;

	mpFlowMib	MODULE-IDENTITY
		LAST-UPDATED	"200709080607Z"
		ORGANIZATION	"Maipu Communication Technology Co., LTD."
		CONTACT-INFO	"E-mail: office@maipu.com"
		DESCRIPTION		""
		REVISION		"200909061507Z"
		DESCRIPTION		"Initial version of this MIB module."
		::=  {  mpMgmt  603  }


	mpFlowMIBObjects	OBJECT IDENTIFIER	::=  {  mpFlowMib  1  }
	mpFlowConfigs	OBJECT IDENTIFIER	::=  {  mpFlowMIBObjects  1  }
	mpFlowInfo OBJECT IDENTIFIER	::=  {  mpFlowMIBObjects  2  }


-- flow table info

	mpFlowInfoTable	OBJECT-TYPE
		SYNTAX		SEQUENCE OF  MpFlowInfoEntry
		MAX-ACCESS	not-accessible
		STATUS		current
		DESCRIPTION	"流表。"
		::=  { mpFlowInfo  1 }

	mpFlowInfoEntry	OBJECT-TYPE
		SYNTAX		MpFlowInfoEntry
		MAX-ACCESS	not-accessible
		STATUS		current
		DESCRIPTION	"流表条目。"
		INDEX		{	mpFlowSourceIpAddrType, mpFlowSourceIpAddr, mpFlowSourcePort, 
						mpFlowDestIpAddrType, mpFlowDestIpAddr, mpFlowDestPort,
						mpFlowIpProtocols, mpFlowIpTos, mpFlowInInterface  }
		::=  { mpFlowInfoTable 1 }

	MpFlowInfoEntry  ::=  SEQUENCE {
		mpFlowSourceIpAddrType  InetAddressType,
		mpFlowSourceIpAddr  InetAddress,
		mpFlowSourcePort  InetPortNumber,
		mpFlowDestIpAddrType  InetAddressType,
		mpFlowDestIpAddr  InetAddress,
		mpFlowDestPort  InetPortNumber,
		mpFlowIpProtocols  INTEGER,
		mpFlowIpTos  INTEGER,
		mpFlowInInterface  InterfaceIndex,
		mpFlowOutInterface  InterfaceIndex,
		mpFlowTransPkts  Unsigned32,
		mpFlowTransOcts  Unsigned32,
		mpFlowStartTime  TimeStamp,
		mpFlowEndTime  TimeStamp,
		mpFlowSourceAs  Integer32,
		mpFlowDestAs  Integer32
		}


	mpFlowSourceIpAddrType	OBJECT-TYPE	
		SYNTAX			InetAddressType 
		MAX-ACCESS		read-only
		STATUS			current
		DESCRIPTION		"源端IP地址类型。"
		::=  {  mpFlowInfoEntry  1  }


	mpFlowSourceIpAddr	OBJECT-TYPE	
		SYNTAX			InetAddress 
		MAX-ACCESS		read-only
		STATUS			current
		DESCRIPTION		"源端地址。"
		::=  {  mpFlowInfoEntry  2  }

	mpFlowSourcePort	OBJECT-TYPE	
		SYNTAX			InetPortNumber 
		MAX-ACCESS		read-only
		STATUS			current
		DESCRIPTION		"源端端口。"
		::=  {  mpFlowInfoEntry  3  }


	mpFlowDestIpAddrType	OBJECT-TYPE	
		SYNTAX			InetAddressType
		MAX-ACCESS		read-only
		STATUS			current
		DESCRIPTION		"目的地址类型。"
		::=  {  mpFlowInfoEntry  4  }


	mpFlowDestIpAddr	OBJECT-TYPE	
		SYNTAX			InetAddress 
		MAX-ACCESS		read-only
		STATUS			current
		DESCRIPTION		"目的地址"
		::=  {  mpFlowInfoEntry  5  }


	mpFlowDestPort	OBJECT-TYPE	
		SYNTAX			InetPortNumber 
		MAX-ACCESS		read-only
		STATUS			current
		DESCRIPTION		"目的端口。"
		::=  {  mpFlowInfoEntry  6  }

		
	mpFlowIpProtocols	OBJECT-TYPE	
		SYNTAX			INTEGER   {
								other ( 1 ) , 
								tcp ( 2 ) , 
								udp ( 3 ) ,
								icmp ( 4 ) ,
								igmp ( 5 )
								} 
		MAX-ACCESS		read-only
		STATUS			current
		DESCRIPTION		"IP 协议类型。"
		::=  {  mpFlowInfoEntry  7  }


	mpFlowIpTos	OBJECT-TYPE	
		SYNTAX			INTEGER   ( SIZE ( 1 .. 3  ) ) 
		MAX-ACCESS		read-only
		STATUS			current
		DESCRIPTION		"IP服务类型。"
		::=  {  mpFlowInfoEntry  8  }


	mpFlowInInterface	OBJECT-TYPE	
		SYNTAX			InterfaceIndex
		MAX-ACCESS		read-only
		STATUS			current
		DESCRIPTION		"输入接口索引。"
		::=  {  mpFlowInfoEntry  9  }


	mpFlowOutInterface	OBJECT-TYPE	
		SYNTAX			InterfaceIndex
		MAX-ACCESS		read-only
		STATUS			current
		DESCRIPTION		"输出接口索引。"
		::=  {  mpFlowInfoEntry  10  }


	mpFlowTransPkts	OBJECT-TYPE	
		SYNTAX			Unsigned32
		MAX-ACCESS		read-only
		STATUS			current
		DESCRIPTION		"流传输报文数。"
		::=  {  mpFlowInfoEntry  11  }


	mpFlowTransOcts	OBJECT-TYPE	
		SYNTAX			Unsigned32
		MAX-ACCESS		read-only
		STATUS			current
		DESCRIPTION		"流传输字节数。"
		::=  {  mpFlowInfoEntry  12  }


	mpFlowStartTime	OBJECT-TYPE	
		SYNTAX			TimeStamp
		MAX-ACCESS		read-only
		STATUS			current
		DESCRIPTION		"流开始时间。"
		::=  {  mpFlowInfoEntry  13  }


	mpFlowEndTime	OBJECT-TYPE	
		SYNTAX			TimeStamp
		MAX-ACCESS		read-only
		STATUS			current
		DESCRIPTION		"流结束时间。"
		::=  {  mpFlowInfoEntry  14  }


	mpFlowSourceAs	OBJECT-TYPE	
		SYNTAX			Integer32
		MAX-ACCESS		read-only
		STATUS			current
		DESCRIPTION		"源端所属自治域。"
		::=  {  mpFlowInfoEntry  15  }


	mpFlowDestAs	OBJECT-TYPE	
		SYNTAX			Integer32
		MAX-ACCESS		read-only
		STATUS			current
		DESCRIPTION		"目的端所属自治域。"
		::=  {  mpFlowInfoEntry  16  }

-- mpFlowInfoTable end

END
