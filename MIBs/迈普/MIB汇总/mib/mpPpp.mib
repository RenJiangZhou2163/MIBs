-- *****************************************************************
-- MAIPU-PPP.mib:  Maipu enterprise device PPP MIB file
--
--version 1.0.0.0, Feb 13, 2001 Huanglulu
--version 2.0.0.0, Sep 12, 2002 Huanglulu
--
-- Copyright (c)  by Maipu DataComm Inc.
-- All rights reserved.
-- 
-- *****************************************************************
--

MAIPU-PPP-MIB DEFINITIONS ::= BEGIN

IMPORTS
    MODULE-IDENTITY, OBJECT-TYPE,
    IpAddress				               FROM SNMPv2-SMI
    mpMgmt                        	       FROM MAIPU-SMI;

mpPppMib MODULE-IDENTITY
    LAST-UPDATED "0102130000Z"
    ORGANIZATION "Maipu DataComm"
    CONTACT-INFO
	"   Maipu DataComm
		Customer Service

		Postal: Consulate Drive
			Chengdu, Sichuan  610041
			China

		Tel: 86-028-5161006

		E-mail: office@maipu.com"
    DESCRIPTION
		"The assignments for Maipu router's MIB of PPP infomation!"
    ::= {mpMgmt 5 }

pppConfTable OBJECT-TYPE
    SYNTAX SEQUENCE OF PppConfEntry
    MAX-ACCESS not-accessible
    STATUS current
    DESCRIPTION
		"PPP协议配置表."
    ::= { mpPppMib 1 }

pppConfEntry OBJECT-TYPE
    SYNTAX PppConfEntry
    MAX-ACCESS not-accessible
    STATUS current
    DESCRIPTION
		"PPP协议配置表条目."
    INDEX { pppIfIndex }    
    ::= { pppConfTable 1 }

PppConfEntry ::=
    SEQUENCE {
    	pppIfIndex		INTEGER,
    	pppIpNeg		INTEGER,
    	pppDefIpAddr	IpAddress,
    	pppDefIpDhcp	INTEGER,
    	pppDefIpPool	INTEGER,
	    pppIpPoolName	OCTET STRING,
    	pppAc			INTEGER,
    	pppAccountName	OCTET STRING,
    	pppAuthChap		INTEGER,
    	pppAuthChapName	OCTET STRING,
    	pppChapHostName	OCTET STRING,
    	pppAuthPap 		INTEGER,
    	pppAuthPapName	OCTET STRING,
    	pppPapUsername	OCTET STRING,
    	pppPapPassword	OCTET STRING,
    	pppAuthMsChap	INTEGER,
    	pppAuthMsChapName	OCTET STRING,
    	pppCallbackReq	INTEGER,
    	pppCallbackAcc	INTEGER,
    	pppCdp	 		INTEGER,
    	pppComprePredictor	INTEGER,
    	pppCompreStacker	INTEGER,
    	pppEncDesKey	OCTET STRING,
    	pppEnc3DesKey	OCTET STRING,
    	pppEncDesBisKey	OCTET STRING,
    	pppMultilink	INTEGER,
    	pppPc			INTEGER,
    	pppReliableLink	INTEGER,
    	pppTimeoutAuth	INTEGER,
    	pppTimeoutIpcp	INTEGER,
    	pppTimeoutRetry	INTEGER,
    	pppMultilinkBap INTEGER
		}
		
pppIfIndex	OBJECT-TYPE
	SYNTAX	INTEGER
	MAX-ACCESS	read-only
	STATUS	current
	DESCRIPTION
		"PPP配置表的索引,其值相应于接口的索引ifIndex."
	::= { pppConfEntry 1 }
	
pppIpNeg	OBJECT-TYPE
	SYNTAX	INTEGER {
				enable(1),
				disable(2)
					}
	MAX-ACCESS	read-write
	STATUS	current
	DESCRIPTION
		"是否设置接口为IP地址协商."
	::= { pppConfEntry 2 }

pppDefIpAddr	OBJECT-TYPE
	SYNTAX	IpAddress
	MAX-ACCESS	read-write
	STATUS	current
	DESCRIPTION
		"指定对端IP地址（当对端为地址协商时）."
	::= { pppConfEntry 3 }

pppDefIpDhcp	OBJECT-TYPE
	SYNTAX	INTEGER {
				enable(1),
				disable(2)
					}
	MAX-ACCESS	read-write
	STATUS	current
	DESCRIPTION
		"是否从DHCP服务器上为对端分配IP地址（当对端为地址协商时）."
	::= { pppConfEntry 4 }

pppDefIpPool	OBJECT-TYPE
	SYNTAX	INTEGER {
				enable(1),
				disable(2)
					}
	MAX-ACCESS	read-write
	STATUS	current
	DESCRIPTION
		"是否从默认地址池中为对端分配IP地址（当对端为地址协商时）."
	::= { pppConfEntry 5 }

pppDefIpPoolName	OBJECT-TYPE
	SYNTAX	OCTET STRING
	MAX-ACCESS	read-write
	STATUS	current
	DESCRIPTION
		"从指定地址池中为对端分配IP地址（当对端为地址协商时）."
	::= { pppConfEntry 6 }

pppAc	OBJECT-TYPE
	SYNTAX	INTEGER {
				enable(1),
				disable(2)
					}
	MAX-ACCESS	read-write
	STATUS	current
	DESCRIPTION
		"是否配置PPP地址/控制域压缩."
	::= { pppConfEntry 7 }

pppAccountName	OBJECT-TYPE
	SYNTAX	OCTET STRING
	MAX-ACCESS	read-write
	STATUS	current
	DESCRIPTION
		"."
	::= { pppConfEntry 8 }

pppAuthChap	OBJECT-TYPE
	SYNTAX	INTEGER {
				enable(1),
				disable(2)
					}
	MAX-ACCESS	read-write
	STATUS	current
	DESCRIPTION
		"是否配置CHAP认证."
	::= { pppConfEntry 9 }

pppAuthChapName	OBJECT-TYPE
	SYNTAX	OCTET STRING
	MAX-ACCESS	read-write
	STATUS	current
	DESCRIPTION
		"配置CHAP认证（使用AAA认证服务器）."
	::= { pppConfEntry 10 }

pppChapHostName	OBJECT-TYPE
	SYNTAX	OCTET STRING
	MAX-ACCESS	read-write
	STATUS	current
	DESCRIPTION
		"配置CHAP认证名."
	::= { pppConfEntry 11 }

pppAuthPap	OBJECT-TYPE
	SYNTAX	INTEGER {
				enable(1),
				disable(2)
					}
	MAX-ACCESS	read-write
	STATUS	current
	DESCRIPTION
		" 是否配置UPAP认证."
	::= { pppConfEntry 12 }

pppAuthPapName	OBJECT-TYPE
	SYNTAX	OCTET STRING
	MAX-ACCESS	read-write
	STATUS	current
	DESCRIPTION
		"配置UPAP认证（使用AAA认证服务器）."
	::= { pppConfEntry 13 }

pppPapUsername	OBJECT-TYPE
	SYNTAX	OCTET STRING
	MAX-ACCESS	read-write
	STATUS	current
	DESCRIPTION
		"配置PAP认证名."
	::= { pppConfEntry 14 }

pppPapPassword	OBJECT-TYPE
	SYNTAX	OCTET STRING
	MAX-ACCESS	read-write
	STATUS	current
	DESCRIPTION
		"配置PAP认证名."
	::= { pppConfEntry 15 }

pppAuthMsChap	OBJECT-TYPE
	SYNTAX	INTEGER {
				enable(1),
				disable(2)
					}
	MAX-ACCESS	read-write
	STATUS	current
	DESCRIPTION
		"是否配置MS-CHAP认证."
	::= { pppConfEntry 16 }

pppAuthMsChapName	OBJECT-TYPE
	SYNTAX	OCTET STRING
	MAX-ACCESS	read-write
	STATUS	current
	DESCRIPTION
		"配置MS-CHAP认证（使用AAA认证服务器）."
	::= { pppConfEntry 17 }

pppCallbackReq	OBJECT-TYPE
	SYNTAX	INTEGER {
				enable(1),
				disable(2)
					}
	MAX-ACCESS	read-write
	STATUS	current
	DESCRIPTION
		"是否配置回拨请求."
	::= { pppConfEntry 18 }

pppCallbackAcc	OBJECT-TYPE
	SYNTAX	INTEGER {
				enable(1),
				disable(2)
					}
	MAX-ACCESS	read-write
	STATUS	current
	DESCRIPTION
		"是否配置回拨接受."
	::= { pppConfEntry 19 }

pppCdp	OBJECT-TYPE
	SYNTAX	INTEGER {
				enable(1),
				disable(2)
					}
	MAX-ACCESS	read-write
	STATUS	current
	DESCRIPTION
		"是否配置CDP（在PPP接口上协商CDP报文）."
	::= { pppConfEntry 20 }

pppComprePredictor	OBJECT-TYPE
	SYNTAX	INTEGER {
				enable(1),
				disable(2)
					}
	MAX-ACCESS	read-write
	STATUS	current
	DESCRIPTION
		"是否配置PREDICTOR压缩."
	::= { pppConfEntry 21 }

pppCompreStacker	OBJECT-TYPE
	SYNTAX	INTEGER {
				enable(1),
				disable(2)
					}
	MAX-ACCESS	read-write
	STATUS	current
	DESCRIPTION
		"是否配置STACKER压缩."
	::= { pppConfEntry 22 }

pppEncDesKey	OBJECT-TYPE
	SYNTAX	OCTET STRING
	MAX-ACCESS	read-write
	STATUS	current
	DESCRIPTION
		"配置DES加密."
	::= { pppConfEntry 23 }

pppEnc3DesKey	OBJECT-TYPE
	SYNTAX	OCTET STRING
	MAX-ACCESS	read-write
	STATUS	current
	DESCRIPTION
		"配置3DES加密."
	::= { pppConfEntry 24 }

pppEncDesBisKey	OBJECT-TYPE
	SYNTAX	OCTET STRING
	MAX-ACCESS	read-write
	STATUS	current
	DESCRIPTION
		"配置DES-BIS加密."
	::= { pppConfEntry 25 }

pppMultilink	OBJECT-TYPE
	SYNTAX	INTEGER {
				enable(1),
				disable(2),
				bap(3)
					}
	MAX-ACCESS	read-write
	STATUS	current
	DESCRIPTION
		"是否配置PPP多链路，当其值为bap时，表示配置PPP多链路且使用BAP协议."
	::= { pppConfEntry 26 }

pppPc	OBJECT-TYPE
	SYNTAX	INTEGER {
				enable(1),
				disable(2)
					}
	MAX-ACCESS	read-write
	STATUS	current
	DESCRIPTION
		"是否配置PPP协议压缩."
	::= { pppConfEntry 27 }

pppReliableLink	OBJECT-TYPE
	SYNTAX	INTEGER {
				enable(1),
				disable(2)
					}
	MAX-ACCESS	read-write
	STATUS	current
	DESCRIPTION
		"是否配置可靠链路."
	::= { pppConfEntry 28 }

pppTimeoutAuth	OBJECT-TYPE
	SYNTAX	INTEGER (1..255)
	MAX-ACCESS	read-write
	STATUS	current
	DESCRIPTION
		"设置认证超时."
	::= { pppConfEntry 29 }

pppTimeoutIpcp	OBJECT-TYPE
	SYNTAX	INTEGER (1..255)
	MAX-ACCESS	read-write
	STATUS	current
	DESCRIPTION
		"设置IPCP协商超时."
	::= { pppConfEntry 30 }

pppTimeoutRetry	OBJECT-TYPE
	SYNTAX	INTEGER (1..255)
	MAX-ACCESS	read-write
	STATUS	current
	DESCRIPTION
		"设置LCP协商超时."
	::= { pppConfEntry 31 }

pppMultilinkBap	OBJECT-TYPE
	SYNTAX	INTEGER
	MAX-ACCESS	read-write
	STATUS	current
	DESCRIPTION
		"."
	::= { pppConfEntry 32 }


--//*********ppp show*********//
pppStatTable	OBJECT-TYPE
	SYNTAX	SEQUENCE OF PppStatEntry
	MAX-ACCESS	not-accessible
	STATUS	current
	DESCRIPTION
		"PPP统计信息表."
	::= { mpPppMib 2 }
	
pppStatEntry	OBJECT-TYPE
	SYNTAX	PppStatEntry
	MAX-ACCESS	not-accessible
	STATUS	current
	DESCRIPTION
		"PPP统计信息表条目."
	INDEX { pppStatIfIndex }
	::= { pppStatTable 1 }
	
PppStatEntry ::=
	SEQUENCE {
		pppStatIfIndex		INTEGER,
		pppLcpPhase			INTEGER,
		pppLcpState			INTEGER,
		pppLcpMru			INTEGER,
		pppLcpMtu			INTEGER,
		pppLcpAsyncMap		INTEGER,
		pppLcpLocalMagicNo	INTEGER,
		pppLcpProtoFieldComp	INTEGER,
		pppLcpACFieldComp	INTEGER,
		pppLcpEchoTimer		INTEGER,
		pppLcpEchoPend		INTEGER,
		pppLcpEchoNo		INTEGER,
		pppLcpEchoInter		INTEGER,
		pppLcpEchoFails		INTEGER,
		pppIpcpState		INTEGER,
		pppIpcpLocalIPAddr	IpAddress,
		pppIpcpRemIPAddr	IpAddress,
		pppIpcpVJCompProto	INTEGER,
		pppIpcpVJCompPassive	INTEGER,
		pppIpcpRtpCompProto	INTEGER,
		pppIpcpRtpCompPassive	INTEGER,
		pppCdpcpState		INTEGER,
		pppCcpState			INTEGER,
		pppEcpState			INTEGER,
		pppPapClientState	INTEGER,
		pppPapServerState	INTEGER,
		pppChapClientState	INTEGER,
		pppChapServerState	INTEGER,
		pppLzsdcpState		INTEGER,
		pppPredictor		INTEGER,
		pppDes				INTEGER,
		pppDesBis			INTEGER,
		ppp3Des				INTEGER
				}
				
pppStatIfIndex	OBJECT-TYPE
	SYNTAX	INTEGER
	MAX-ACCESS	read-only
	STATUS	current
	DESCRIPTION
		""
	::= { pppStatEntry 1 }
	
pppLcpPhase	OBJECT-TYPE
	SYNTAX	INTEGER {
				dead(1),
				establish(2),
				authenticate(3),
				network(4),
				terminate(5)
					}
	MAX-ACCESS	read-only
	STATUS	current
	DESCRIPTION
		"LCP阶段"
	::= { pppStatEntry 2 }

pppLcpState	OBJECT-TYPE
	SYNTAX	INTEGER {
				initial(1),
				starting(2),
				closed(3),
				stopped(4),
				closing(5),
				stopping(6),
				requestSent(7),
				ackReceived(8),
				ackSent(9),
				opened(10)
					}
	MAX-ACCESS	read-only
	STATUS	current
	DESCRIPTION
		"LCP状态"
	::= { pppStatEntry 3 }

pppLcpMru	OBJECT-TYPE
	SYNTAX	INTEGER
	MAX-ACCESS	read-only
	STATUS	current
	DESCRIPTION
		""
	::= { pppStatEntry 4 }

pppLcpMtu	OBJECT-TYPE
	SYNTAX	INTEGER
	MAX-ACCESS	read-only
	STATUS	current
	DESCRIPTION
		""
	::= { pppStatEntry 5 }

pppLcpAsyncMap	OBJECT-TYPE
	SYNTAX	INTEGER
	MAX-ACCESS	read-only
	STATUS	current
	DESCRIPTION
		"以十六进制数表示"
	::= { pppStatEntry 6 }

pppLcpLocalMagicNo	OBJECT-TYPE
	SYNTAX	INTEGER
	MAX-ACCESS	read-only
	STATUS	current
	DESCRIPTION
		"以十六进制数表示"
	::= { pppStatEntry 7 }

pppLcpProtoFieldComp	OBJECT-TYPE
	SYNTAX	INTEGER
	MAX-ACCESS	read-only
	STATUS	current
	DESCRIPTION
		""
	::= { pppStatEntry 8 }

pppLcpACFieldComp	OBJECT-TYPE
	SYNTAX	INTEGER
	MAX-ACCESS	read-only
	STATUS	current
	DESCRIPTION
		""
	::= { pppStatEntry 9 }

pppLcpEchoTimer	OBJECT-TYPE
	SYNTAX	INTEGER
	MAX-ACCESS	read-only
	STATUS	current
	DESCRIPTION
		""
	::= { pppStatEntry 10 }

pppLcpEchoPend	OBJECT-TYPE
	SYNTAX	INTEGER
	MAX-ACCESS	read-only
	STATUS	current
	DESCRIPTION
		""
	::= { pppStatEntry 11 }

pppLcpEchoNo	OBJECT-TYPE
	SYNTAX	INTEGER
	MAX-ACCESS	read-only
	STATUS	current
	DESCRIPTION
		""
	::= { pppStatEntry 12 }

pppLcpEchoInter	OBJECT-TYPE
	SYNTAX	INTEGER
	MAX-ACCESS	read-only
	STATUS	current
	DESCRIPTION
		""
	::= { pppStatEntry 13 }
	
pppLcpEchoFails	OBJECT-TYPE
	SYNTAX	INTEGER
	MAX-ACCESS	read-only
	STATUS	current
	DESCRIPTION
		""
	::= { pppStatEntry 14 }
	
pppIpcpState	OBJECT-TYPE
	SYNTAX	INTEGER {
				initial(1),
				starting(2),
				closed(3),
				stopped(4),
				closing(5),
				stopping(6),
				requestSent(7),
				ackReceived(8),
				ackSent(9),
				opened(10)
					}
	MAX-ACCESS	read-only
	STATUS	current
	DESCRIPTION
		"IPCP状态"
	::= { pppStatEntry 15 }
	
pppIpcpLocalIPAddr	OBJECT-TYPE
	SYNTAX	IpAddress
	MAX-ACCESS	read-only
	STATUS	current
	DESCRIPTION
		""
	::= { pppStatEntry 16 }
	
pppIpcpRemIPAddr	OBJECT-TYPE
	SYNTAX	IpAddress
	MAX-ACCESS	read-only
	STATUS	current
	DESCRIPTION
		""
	::= { pppStatEntry 17 }
	
pppIpcpVJCompProto	OBJECT-TYPE
	SYNTAX	INTEGER
	MAX-ACCESS	read-only
	STATUS	current
	DESCRIPTION
		""
	::= { pppStatEntry 18 }
	
pppIpcpVJCompPassive	OBJECT-TYPE
	SYNTAX	INTEGER
	MAX-ACCESS	read-only
	STATUS	current
	DESCRIPTION
		""
	::= { pppStatEntry 19 }
	
pppIpcpRtpCompProto	OBJECT-TYPE
	SYNTAX	INTEGER
	MAX-ACCESS	read-only
	STATUS	current
	DESCRIPTION
		""
	::= { pppStatEntry 20 }
	
pppIpcpRtpCompPassive	OBJECT-TYPE
	SYNTAX	INTEGER
	MAX-ACCESS	read-only
	STATUS	current
	DESCRIPTION
		""
	::= { pppStatEntry 21 }
	
pppCdpcpState	OBJECT-TYPE
	SYNTAX	INTEGER {
				initial(1),
				starting(2),
				closed(3),
				stopped(4),
				closing(5),
				stopping(6),
				requestSent(7),
				ackReceived(8),
				ackSent(9),
				opened(10)
					}
	MAX-ACCESS	read-only
	STATUS	current
	DESCRIPTION
		"CDPCP状态"
	::= { pppStatEntry 22 }
	
pppCcpState	OBJECT-TYPE
	SYNTAX	INTEGER {
				initial(1),
				starting(2),
				closed(3),
				stopped(4),
				closing(5),
				stopping(6),
				requestSent(7),
				ackReceived(8),
				ackSent(9),
				opened(10)
					}
	MAX-ACCESS	read-only
	STATUS	current
	DESCRIPTION
		"CCP状态"
	::= { pppStatEntry 23 }
	
pppEcpState	OBJECT-TYPE
	SYNTAX	INTEGER {
				initial(1),
				starting(2),
				closed(3),
				stopped(4),
				closing(5),
				stopping(6),
				requestSent(7),
				ackReceived(8),
				ackSent(9),
				opened(10)
					}
	MAX-ACCESS	read-only
	STATUS	current
	DESCRIPTION
		"ECP状态"
	::= { pppStatEntry 24 }
	
pppPapClientState	OBJECT-TYPE
	SYNTAX	INTEGER {
				initial(1),
				closed(2),
				pending(3),
				authenticationReq(4),
				open(5),
				badAuthentication(6)
					}
	MAX-ACCESS	read-only
	STATUS	current
	DESCRIPTION
		""
	::= { pppStatEntry 25 }

pppPapServerState	OBJECT-TYPE
	SYNTAX	INTEGER {
				initial(1),
				closed(2),
				pending(3),
				listen(4),
				open(5),
				badAuthentication(6)
					}
	MAX-ACCESS	read-only
	STATUS	current
	DESCRIPTION
		""
	::= { pppStatEntry 26 }

pppChapClientState	OBJECT-TYPE
	SYNTAX	INTEGER {
				initial(1),
				closed(2),
				pending(3),
				listen(4),
				response(5),
				open(6)
					}
	MAX-ACCESS	read-only
	STATUS	current
	DESCRIPTION
		""
	::= { pppStatEntry 27 }

pppChapServerState	OBJECT-TYPE
	SYNTAX	INTEGER {
				initial(1),
				closed(2),
				pending(3),
				initialChallenge(4),
				oepn(5),
				rechallenge(6),
				badAuthentication(7)
					}
	MAX-ACCESS	read-only
	STATUS	current
	DESCRIPTION
		""
	::= { pppStatEntry 28 }

pppLzsdcpState	OBJECT-TYPE
	SYNTAX	INTEGER
	MAX-ACCESS	read-only
	STATUS	current
	DESCRIPTION
		""
	::= { pppStatEntry 29 }

pppPredictor	OBJECT-TYPE
	SYNTAX	INTEGER
	MAX-ACCESS	read-only
	STATUS	current
	DESCRIPTION
		""
	::= { pppStatEntry 30 }

pppDes	OBJECT-TYPE
	SYNTAX	INTEGER
	MAX-ACCESS	read-only
	STATUS	current
	DESCRIPTION
		""
	::= { pppStatEntry 31 }

pppDesBis	OBJECT-TYPE
	SYNTAX	INTEGER
	MAX-ACCESS	read-only
	STATUS	current
	DESCRIPTION
		""
	::= { pppStatEntry 32 }

ppp3Des	OBJECT-TYPE
	SYNTAX	INTEGER
	MAX-ACCESS	read-only
	STATUS	current
	DESCRIPTION
		""
	::= { pppStatEntry 33 }


--//*********ppp compress show*********//
pppCompStatTable	OBJECT-TYPE
	SYNTAX	SEQUENCE OF PppCompStatEntry
	MAX-ACCESS	not-accessible
	STATUS	current
	DESCRIPTION
		"PPP压缩统计信息表."
	::= { mpPppMib 3 }
	
pppCompStatEntry	OBJECT-TYPE
	SYNTAX	PppCompStatEntry
	MAX-ACCESS	not-accessible
	STATUS	current
	DESCRIPTION
		"PPP压缩统计信息表条目."
	INDEX { pppCompStatIfIndex }
	::= { pppCompStatTable 1 }
	
PppCompStatEntry ::=
	SEQUENCE {
		pppCompStatIfIndex	INTEGER,
		pppCompType			INTEGER,
		pppUncompBytes		Counter32,
		pppUncompPkts		Counter32,
		pppCompBytes		Counter32,
		pppCompPkts			Counter32,
		pppIncompBytes		Counter32,
		pppIncompPkts		Counter32,
		pppRecvBytes		Counter32,
		pppTransBytes		Counter32,
		pppCompRatio		INTEGER
			}

pppCompStatIfIndex	OBJECT-TYPE
	SYNTAX	INTEGER
	MAX-ACCESS	read-only
	STATUS	current
	DESCRIPTION
		"压缩接口索引"
	::= { pppCompStatEntry 1 }

pppCompType	OBJECT-TYPE
	SYNTAX	INTEGER {
				stacker(1),
				predictor(2)
					}
	MAX-ACCESS	read-only
	STATUS	current
	DESCRIPTION
		"压缩类型"
	::= { pppCompStatEntry 2 }

pppUncompBytes	OBJECT-TYPE
	SYNTAX	Counter32
	MAX-ACCESS	read-only
	STATUS	current
	DESCRIPTION
		"未压缩字节数"
	::= { pppCompStatEntry 3 }

pppUncompPkts	OBJECT-TYPE
	SYNTAX	Counter32
	MAX-ACCESS	read-only
	STATUS	current
	DESCRIPTION
		"未压缩报文数"
	::= { pppCompStatEntry 4 }

pppCompBytes	OBJECT-TYPE
	SYNTAX	Counter32
	MAX-ACCESS	read-only
	STATUS	current
	DESCRIPTION
		"压缩字节数"
	::= { pppCompStatEntry 5 }

pppCompPkts	OBJECT-TYPE
	SYNTAX	Counter32
	MAX-ACCESS	read-only
	STATUS	current
	DESCRIPTION
		"压缩报文数"
	::= { pppCompStatEntry 6 }

pppIncompBytes	OBJECT-TYPE
	SYNTAX	Counter32
	MAX-ACCESS	read-only
	STATUS	current
	DESCRIPTION
		"不能压缩字节数"
	::= { pppCompStatEntry 7 }

pppIncompPkts	OBJECT-TYPE
	SYNTAX	Counter32
	MAX-ACCESS	read-only
	STATUS	current
	DESCRIPTION
		"不能压缩报文数"
	::= { pppCompStatEntry 8 }

pppRecvBytes	OBJECT-TYPE
	SYNTAX	Counter32
	MAX-ACCESS	read-only
	STATUS	current
	DESCRIPTION
		"接收字节数"
	::= { pppCompStatEntry 9 }

pppTransBytes	OBJECT-TYPE
	SYNTAX	Counter32
	MAX-ACCESS	read-only
	STATUS	current
	DESCRIPTION
		"传送字节数"
	::= { pppCompStatEntry 10 }

pppCompRatio	OBJECT-TYPE
	SYNTAX	INTEGER
	MAX-ACCESS	read-only
	STATUS	current
	DESCRIPTION
		"压缩率"
	::= { pppCompStatEntry 11 }


--//*********ppp Multilink show*********//
pppMultiTable	OBJECT-TYPE
	SYNTAX	SEQUENCE OF PppMultiEntry
	MAX-ACCESS	not-accessible
	STATUS	current
	DESCRIPTION
		"PPP多链路信息表."
	::= { mpPppMib 4 }
	
pppMultiEntry	OBJECT-TYPE
	SYNTAX	PppMultiEntry
	MAX-ACCESS	not-accessible
	STATUS	current
	DESCRIPTION
		"PPP多链路信息表条目."
	INDEX { pppVirtualAccInt }
	::= { pppMultiTable 1 }
	
PppMultiEntry ::=
	SEQUENCE {
		pppVirtualAccInt		OCTET STRING,
		pppLogicInt				OCTET STRING,
		pppLocalVirtualIpAddr	IpAddress,
		pppRemVirtuslIpAddr		IpAddress,
		pppMultiMemNum			INTEGER
			}

pppVirtualAccInt	OBJECT-TYPE
	SYNTAX	OCTET STRING
	MAX-ACCESS	read-only
	STATUS	current
	DESCRIPTION
		"Multilink的虚拟接口名"
	::= { pppMultiEntry 1 }

pppLogicInt	OBJECT-TYPE
	SYNTAX	OCTET STRING
	MAX-ACCESS	read-only
	STATUS	current
	DESCRIPTION
		"Multilink的虚拟接口对应的逻辑接口名"
	::= { pppMultiEntry 2 }

pppLocalVirtualIpAddr	OBJECT-TYPE
	SYNTAX	IpAddress
	MAX-ACCESS	read-only
	STATUS	current
	DESCRIPTION
		"Multilink本地虚拟接口的IP地址"
	::= { pppMultiEntry 3 }

pppRemVirtualIpAddr	OBJECT-TYPE
	SYNTAX	IpAddress
	MAX-ACCESS	read-only
	STATUS	current
	DESCRIPTION
		"Multilink对端虚拟接口的IP地址"
	::= { pppMultiEntry 4 }

pppMultiMemNum	OBJECT-TYPE
	SYNTAX	INTEGER
	MAX-ACCESS	read-only
	STATUS	current
	DESCRIPTION
		"该Multilink绑定的物理接口的个数"
	::= { pppMultiEntry 5 }


--//*********ppp Multilink show*********//
pppMultiIntTable	OBJECT-TYPE
	SYNTAX	SEQUENCE OF PppMultiIntEntry
	MAX-ACCESS	not-accessible
	STATUS	current
	DESCRIPTION
		"PPP多链路接口信息表."
	::= { mpPppMib 5 }
	
pppMultiIntEntry	OBJECT-TYPE
	SYNTAX	PppMultiIntEntry
	MAX-ACCESS	not-accessible
	STATUS	current
	DESCRIPTION
		"PPP多链路接口信息表条目."
	INDEX { pppMultiIntIfIndex }
	::= { pppMultiIntTable 1 }
	
PppMultiIntEntry ::=
	SEQUENCE {
		pppMultiIntIfIndex		INTEGER,
		pppMultiIntName			OCTET STRING,
		pppMultiIntBBandWidth	INTEGER,
		pppVirtualIntName		OCTET STRING
			}
			
pppMultiIntIfIndex	OBJECT-TYPE
	SYNTAX	INTEGER
	MAX-ACCESS	read-only
	STATUS	current
	DESCRIPTION
		"被绑定成Multilink的物理接口的索引"
	::= { pppMultiIntEntry 1 }

pppMultiIntName	OBJECT-TYPE
	SYNTAX	OCTET STRING
	MAX-ACCESS	read-only
	STATUS	current
	DESCRIPTION
		"被绑定成Multilink的物理接口的名字"
	::= { pppMultiIntEntry 2 }

pppMultiIntBBandWidth	OBJECT-TYPE
	SYNTAX	INTEGER
	MAX-ACCESS	read-only
	STATUS	current
	DESCRIPTION
		"该物理接口的带宽"
	::= { pppMultiIntEntry 3 }

pppVirtualIntName	OBJECT-TYPE
	SYNTAX	OCTET STRING
	MAX-ACCESS	read-only
	STATUS	current
	DESCRIPTION
		"所属的虚拟接口的名字"
	::= { pppMultiIntEntry 4 }

END
