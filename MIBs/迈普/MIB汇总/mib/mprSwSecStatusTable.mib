DEFINITIONS ::= BEGIN

mprSwSecStatusTable  OBJECT-TYPE
    SYNTAX  SEQUENCE OF mprSwSecStatusEntry
    ACCESS  not-accessible
    STATUS  5
    DESCRIPTION
            "Switch port security status table"
    ::= {mpSwPort 4}

mprSwSecStatusEntry  OBJECT-TYPE
    SYNTAX  mprSwSecStatusEntry
    ACCESS  not-accessible
    STATUS  5
    DESCRIPTION
            "Switch port security status table entry"
    INDEX   {mprSwSecStatusPortSlot, mprSwSecStatusPortIndex}
    ::= {mprSwSecStatusTable 1}

mprSwSecStatusPortSlot  OBJECT-TYPE
    SYNTAX  INTEGER
    ACCESS  read-only
    STATUS  5
    DESCRIPTION
            "table index, port's slot number"
    ::= {mprSwSecStatusEntry 1}

mprSwSecStatusPortIndex  OBJECT-TYPE
    SYNTAX  INTEGER
    ACCESS  read-only
    STATUS  5
    DESCRIPTION
            "table index, port's number"
    ::= {mprSwSecStatusEntry 2}

mprSwSecStatusEnabled  OBJECT-TYPE
    SYNTAX  INTEGER {
            disabled(1),
            enabled(2)
            }
    ACCESS  read-write
    STATUS  5
    DESCRIPTION
            "port's security started status, default is disabled"
    ::= {mprSwSecStatusEntry 3}

mprSwSecStatusMaxNum OBJECT-TYPE
    SYNTAX  INTEGER(0~4000)
    ACCESS  read-write
    STATUS  5
    DESCRIPTION
            "Mac max num that port can learn, default is 0"
    ::= {mprSwSecStatusEntry 4}

mprSwSecStatusRowStatus  OBJECT-TYPE
    SYNTAX  RowStatus
    ACCESS  read-create
    STATUS  5
    DESCRIPTION
            "row config status"
    ::= {mprSwSecStatusEntry 4}
END
