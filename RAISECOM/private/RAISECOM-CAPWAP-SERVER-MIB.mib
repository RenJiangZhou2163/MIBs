-- *****************************************************************
-- RAISECOM-CAPWAP-SERVER-MIB.mib:  Raisecom Capwap Server MIB file
--
-- Aug 2010, xueweiwen
--
-- Copyright (c) 2010 by Raisecom Networks Co.,Ltd.
-- All rights reserved.
-- 
-- *****************************************************************
--

RAISECOM-CAPWAP-SERVER-MIB DEFINITIONS ::= BEGIN

IMPORTS
    MODULE-IDENTITY,
    OBJECT-TYPE,
    Counter32,
    Unsigned32,
    IpAddress
            FROM SNMPv2-SMI
    InetAddressType, 
    InetAddress
            FROM INET-ADDRESS-MIB
    DisplayString,
    MacAddress,
    RowStatus
            FROM SNMPv2-TC
    MODULE-COMPLIANCE,
    OBJECT-GROUP
            FROM SNMPv2-CONF
    ruijieMgmt
            FROM RAISECOM-SMI;

ruijieCapwapSvrMIB MODULE-IDENTITY
    LAST-UPDATED "201008240000Z"
    ORGANIZATION "Raisecom Networks Co.,Ltd."
    CONTACT-INFO
           " 
           Tel: 4008-111-000 

           E-mail: service@raisecom.com.cn"
    DESCRIPTION
           "This module defines raisecom capwap server mibs."
    REVISION      "201008240000Z"
    DESCRIPTION
           "Initial version of this MIB module."
    ::= { ruijieMgmt 89 }


ruijieCapwapSvrMIBObjects OBJECT IDENTIFIER ::= { ruijieCapwapSvrMIB 1 }


-- capwap server white list url
ruijieCapwapSvrWhiteListURLTable OBJECT-TYPE
    SYNTAX  SEQUENCE OF RuijieCapwapSvrWhiteListURLEntry
    MAX-ACCESS  not-accessible
    STATUS  current
    DESCRIPTION
        "The table of Capwap server white list URL Info."
    ::= { ruijieCapwapSvrMIBObjects 1 }

ruijieCapwapSvrWhiteListURLEntry OBJECT-TYPE
    SYNTAX  RuijieCapwapSvrWhiteListURLEntry
    MAX-ACCESS  not-accessible
    STATUS  current
    DESCRIPTION
        "The entry of Capwap server white list URL info table."
    INDEX   { ruijieCapwapSvrWhiteListIndex }
    ::= { ruijieCapwapSvrWhiteListURLTable 1 }

RuijieCapwapSvrWhiteListURLEntry ::=
    SEQUENCE {
        ruijieCapwapSvrWhiteListIndex            Unsigned32,
        ruijieCapwapSvrWhiteListURL              DisplayString,
        ruijieCapwapSvrWhiteListURLParserStatus  DisplayString,
        ruijieCapwapSvrWhiteListURLRowStatus     RowStatus
    }

ruijieCapwapSvrWhiteListIndex OBJECT-TYPE
    SYNTAX       Unsigned32
    MAX-ACCESS   read-only
    STATUS       current
    DESCRIPTION
        "The index of the Capwap server white list url."    
    ::= { ruijieCapwapSvrWhiteListURLEntry 1 }

ruijieCapwapSvrWhiteListURL OBJECT-TYPE
    SYNTAX       DisplayString (SIZE (0..255))
    MAX-ACCESS   read-create
    STATUS       current
    DESCRIPTION
        "The URL of the Capwap server white list."    
    ::= { ruijieCapwapSvrWhiteListURLEntry 2 }

ruijieCapwapSvrWhiteListURLParserStatus OBJECT-TYPE
    SYNTAX       DisplayString (SIZE (0..255))
    MAX-ACCESS   read-only
    STATUS       current
    DESCRIPTION
        "The URL parser status of the Capwap server white list."    
    ::= { ruijieCapwapSvrWhiteListURLEntry 3 }

ruijieCapwapSvrWhiteListURLRowStatus OBJECT-TYPE
    SYNTAX       RowStatus
    MAX-ACCESS   read-create
    STATUS       current
    DESCRIPTION
        "The RowStatus of the Capwap server white list URL table."  
    ::= { ruijieCapwapSvrWhiteListURLEntry 4 }


-- capwap server white list ip
ruijieCapwapSvrWhiteListIPTable OBJECT-TYPE
    SYNTAX  SEQUENCE OF RuijieCapwapSvrWhiteListIPEntry
    MAX-ACCESS  not-accessible
    STATUS  current
    DESCRIPTION
        "The table of Capwap server white list IP Info."
    ::= { ruijieCapwapSvrMIBObjects 2 }

ruijieCapwapSvrWhiteListIPEntry OBJECT-TYPE
    SYNTAX  RuijieCapwapSvrWhiteListIPEntry
    MAX-ACCESS  not-accessible
    STATUS  current
    DESCRIPTION
        "The entry of Capwap server white list IP info table."
    INDEX   { ruijieCapwapSvrWhiteListIP }
    ::= { ruijieCapwapSvrWhiteListIPTable 1 }

RuijieCapwapSvrWhiteListIPEntry ::=
    SEQUENCE {
        ruijieCapwapSvrWhiteListIP            IpAddress,
        ruijieCapwapSvrWhiteListIPRowStatus   RowStatus
    }

ruijieCapwapSvrWhiteListIP OBJECT-TYPE
    SYNTAX       IpAddress
    MAX-ACCESS   read-only
    STATUS       current
    DESCRIPTION
        "The IP of the Capwap server white list."    
    ::= { ruijieCapwapSvrWhiteListIPEntry 1 }

ruijieCapwapSvrWhiteListIPRowStatus OBJECT-TYPE
    SYNTAX       RowStatus
    MAX-ACCESS   read-create
    STATUS       current
    DESCRIPTION
        "The RowStatus of the Capwap server white list IP table."    
    ::= { ruijieCapwapSvrWhiteListIPEntry 2 }


-- capwap server black list URL
ruijieCapwapSvrBlackListURLTable OBJECT-TYPE
    SYNTAX  SEQUENCE OF RuijieCapwapSvrBlackListURLEntry
    MAX-ACCESS  not-accessible
    STATUS  current
    DESCRIPTION
        "The table of Portal URL Info."
    ::= { ruijieCapwapSvrMIBObjects 3 }

ruijieCapwapSvrBlackListURLEntry OBJECT-TYPE
    SYNTAX  RuijieCapwapSvrBlackListURLEntry
    MAX-ACCESS  not-accessible
    STATUS  current
    DESCRIPTION
        "The entry of Portal URL info table."
    INDEX   { ruijieCapwapSvrBlackListIndex }
    ::= { ruijieCapwapSvrBlackListURLTable 1 }

RuijieCapwapSvrBlackListURLEntry ::=
    SEQUENCE {
        ruijieCapwapSvrBlackListIndex            Unsigned32,
        ruijieCapwapSvrBlackListURL              DisplayString,
        ruijieCapwapSvrBlackListURLParserStatus  DisplayString,
        ruijieCapwapSvrBlackListURLRowStatus     RowStatus
    }

ruijieCapwapSvrBlackListIndex OBJECT-TYPE
    SYNTAX       Unsigned32
    MAX-ACCESS   read-only
    STATUS       current
    DESCRIPTION
        "The URL of the Capwap server black list." 
    ::= { ruijieCapwapSvrBlackListURLEntry 1 }

ruijieCapwapSvrBlackListURL OBJECT-TYPE
    SYNTAX       DisplayString (SIZE (0..255))
    MAX-ACCESS   read-create
    STATUS       current
    DESCRIPTION
        "The URL of the Capwap server black list." 
    ::= { ruijieCapwapSvrBlackListURLEntry 2 }

ruijieCapwapSvrBlackListURLParserStatus OBJECT-TYPE
    SYNTAX       DisplayString (SIZE (0..255))
    MAX-ACCESS   read-only
    STATUS       current
    DESCRIPTION
        "The URL parser status of the Capwap server black list."   
    ::= { ruijieCapwapSvrBlackListURLEntry 3 }

ruijieCapwapSvrBlackListURLRowStatus OBJECT-TYPE
    SYNTAX       RowStatus
    MAX-ACCESS   read-create
    STATUS       current
    DESCRIPTION
        "The RowStatus of the Capwap server black list IP table."  
    ::= { ruijieCapwapSvrBlackListURLEntry 4 }

    
-- capwap server black list ip
ruijieCapwapSvrBlackListIPTable OBJECT-TYPE
    SYNTAX  SEQUENCE OF RuijieCapwapSvrBlackListIPEntry
    MAX-ACCESS  not-accessible
    STATUS  current
    DESCRIPTION
        "The table of Capwap server black list IP Info."
    ::= { ruijieCapwapSvrMIBObjects 4 }

ruijieCapwapSvrBlackListIPEntry OBJECT-TYPE
    SYNTAX  RuijieCapwapSvrBlackListIPEntry
    MAX-ACCESS  not-accessible
    STATUS  current
    DESCRIPTION
        "The entry of Capwap server black list IP info table."
    INDEX   { ruijieCapwapSvrBlackListIP }
    ::= { ruijieCapwapSvrBlackListIPTable 1 }

RuijieCapwapSvrBlackListIPEntry ::=
    SEQUENCE {
        ruijieCapwapSvrBlackListIP            IpAddress,
        ruijieCapwapSvrBlackListIPRowStatus   RowStatus
    }

ruijieCapwapSvrBlackListIP OBJECT-TYPE
    SYNTAX       IpAddress
    MAX-ACCESS   read-only
    STATUS       current
    DESCRIPTION
        "The IP of the Capwap server black list."   
    ::= { ruijieCapwapSvrBlackListIPEntry 1 }

ruijieCapwapSvrBlackListIPRowStatus OBJECT-TYPE
    SYNTAX       RowStatus
    MAX-ACCESS   read-create
    STATUS       current
    DESCRIPTION
        "The RowStatus of the Capwap server black list IP table."   
    ::= { ruijieCapwapSvrBlackListIPEntry 2 }    
    

-- capwap server black list port
ruijieCapwapSvrBlackListPortTable OBJECT-TYPE
    SYNTAX  SEQUENCE OF RuijieCapwapSvrBlackListPortEntry
    MAX-ACCESS  not-accessible
    STATUS  current
    DESCRIPTION
        "The table of Capwap server black list port Info."
    ::= { ruijieCapwapSvrMIBObjects 5 }

ruijieCapwapSvrBlackListPortEntry OBJECT-TYPE
    SYNTAX  RuijieCapwapSvrBlackListPortEntry
    MAX-ACCESS  not-accessible
    STATUS  current
    DESCRIPTION
        "The entry of Capwap server black list port info table."
    INDEX   { ruijieCapwapSvrBlackListPort }
    ::= { ruijieCapwapSvrBlackListPortTable 1 }

RuijieCapwapSvrBlackListPortEntry ::=
    SEQUENCE {
        ruijieCapwapSvrBlackListPort            INTEGER,
        ruijieCapwapSvrBlackListPortRowStatus   RowStatus
    }

ruijieCapwapSvrBlackListPort OBJECT-TYPE
    SYNTAX       INTEGER
    MAX-ACCESS   read-only
    STATUS       current
    DESCRIPTION
        "The port of the Capwap server black list."  
    ::= { ruijieCapwapSvrBlackListPortEntry 1 }

ruijieCapwapSvrBlackListPortRowStatus OBJECT-TYPE
    SYNTAX       RowStatus
    MAX-ACCESS   read-create
    STATUS       current
    DESCRIPTION
        "The RowStatus of the Capwap server black list port table." 
    ::= { ruijieCapwapSvrBlackListPortEntry 2 } 


-- capwap server white list mac
ruijieCapwapSvrWhiteListMacTable OBJECT-TYPE
    SYNTAX  SEQUENCE OF RuijieCapwapSvrWhiteListMacEntry
    MAX-ACCESS  not-accessible
    STATUS  current
    DESCRIPTION
        "The table of Capwap server white list Mac Info."
    ::= { ruijieCapwapSvrMIBObjects 6 }

ruijieCapwapSvrWhiteListMacEntry OBJECT-TYPE
    SYNTAX  RuijieCapwapSvrWhiteListMacEntry
    MAX-ACCESS  not-accessible
    STATUS  current
    DESCRIPTION
        "The entry of Capwap server white list Mac info table."
    INDEX   { ruijieCapwapSvrWhiteListMacIndex }
    ::= { ruijieCapwapSvrWhiteListMacTable 1 }

RuijieCapwapSvrWhiteListMacEntry ::=
    SEQUENCE {
        ruijieCapwapSvrWhiteListMacIndex            Unsigned32,
        ruijieCapwapSvrWhiteListMac              MacAddress,
        ruijieCapwapSvrWhiteListMacRowStatus     RowStatus
    }

ruijieCapwapSvrWhiteListMacIndex OBJECT-TYPE
    SYNTAX       Unsigned32
    MAX-ACCESS   read-only
    STATUS       current
    DESCRIPTION
        "The index of the Capwap server white list Mac." 
    ::= { ruijieCapwapSvrWhiteListMacEntry 1 }

ruijieCapwapSvrWhiteListMac OBJECT-TYPE
    SYNTAX       MacAddress
    MAX-ACCESS   read-create
    STATUS       current
    DESCRIPTION
        "The Mac of the Capwap server white list."   
    ::= { ruijieCapwapSvrWhiteListMacEntry 2 }

ruijieCapwapSvrWhiteListMacRowStatus OBJECT-TYPE
    SYNTAX       RowStatus
    MAX-ACCESS   read-create
    STATUS       current
    DESCRIPTION
        "The RowStatus of the Capwap server white list Mac table."   
    ::= { ruijieCapwapSvrWhiteListMacEntry 3 }


---
---compliance statements
---
ruijieCapwapSvrMIBConformance OBJECT IDENTIFIER ::= { ruijieCapwapSvrMIB 2 }
ruijieCapwapSvrMIBCompliances OBJECT IDENTIFIER ::= { ruijieCapwapSvrMIBConformance 1 }
ruijieCapwapSvrMIBGroups      OBJECT IDENTIFIER ::= { ruijieCapwapSvrMIBConformance 2 }

ruijieCapwapSvrMIBCompliance MODULE-COMPLIANCE
   STATUS  current
   DESCRIPTION
   			"The compliance statement for entities which implement
       	 the capwapServer MIB"
   MODULE
   GROUP ruijieCapwapSvrMIBGroup
 	 DESCRIPTION
        "This group is mandatory only for those system which support
         capwapServer function."          
   ::= { ruijieCapwapSvrMIBCompliances 1 }

ruijieCapwapSvrMIBGroup OBJECT-GROUP 
   OBJECTS { 
        ruijieCapwapSvrWhiteListURL,
        ruijieCapwapSvrWhiteListURLParserStatus,
        ruijieCapwapSvrWhiteListURLRowStatus,
        ruijieCapwapSvrWhiteListIP,
        ruijieCapwapSvrWhiteListIPRowStatus,
        ruijieCapwapSvrBlackListURL,
        ruijieCapwapSvrBlackListURLParserStatus,
        ruijieCapwapSvrBlackListURLRowStatus,        			
        ruijieCapwapSvrBlackListIP,
        ruijieCapwapSvrBlackListIPRowStatus,
        ruijieCapwapSvrBlackListPort,
        ruijieCapwapSvrBlackListPortRowStatus,
        ruijieCapwapSvrWhiteListMac,
        ruijieCapwapSvrWhiteListMacRowStatus
      } 
   STATUS  deprecated 
   DESCRIPTION 
         "The basic collection of objects providing management of capwapServer management." 
   ::= { ruijieCapwapSvrMIBGroups 1 } 

END
