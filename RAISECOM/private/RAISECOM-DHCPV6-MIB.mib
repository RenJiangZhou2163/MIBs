-- *****************************************************************
-- RAISECOM-DHCPv6-MIB.mib:  Raisecom DHCPv6 MIB file
--
-- March 2009, Chenfg
--
-- Copyright (c) 2009 by Raisecom Networks Co.,Ltd.
-- All rights reserved.
-- 
-- *****************************************************************

RAISECOM-DHCPv6-MIB  DEFINITIONS ::= BEGIN

IMPORTS
    MODULE-IDENTITY, 
    OBJECT-IDENTITY,
    OBJECT-TYPE, 
    Counter32,
    Unsigned32,	
    Counter64, 
    TimeTicks,
    Integer32
        FROM SNMPv2-SMI
    TimeInterval, 
    RowStatus,
    DisplayString
        FROM SNMPv2-TC
    MODULE-COMPLIANCE, 
    OBJECT-GROUP
        FROM SNMPv2-CONF
    Ipv6Address, 
    Ipv6AddressPrefix
        FROM IPV6-TC
    InetAddressIPv6
        FROM INET-ADDRESS-MIB
    InterfaceIndex
        FROM IF-MIB
    ruijieMgmt
        FROM RAISECOM-SMI;

ruijieDhcpv6MIB  MODULE-IDENTITY
    LAST-UPDATED "200903160000Z"
    ORGANIZATION "Raisecom Networks Co.,Ltd."
    CONTACT-INFO
        				" 
                Tel: 4008-111-000 

                E-mail: service@raisecom.com.cn"
    DESCRIPTION
        "This module defines raisecom DHCPv6 mibs."
    -- Revision History
    REVISION    "200903160000Z"
    DESCRIPTION
        "Initial version of this MIB module."
    ::= { ruijieMgmt 45 }


--
-- Declare top-level DHCPv6 MIB objects
--
ruijieDhcpv6MIBObjects OBJECT-IDENTITY 
    STATUS      current
    DESCRIPTION
        "DHCPv6 Server MIB objects are defined in this branch."
    ::= { ruijieDhcpv6MIB 1 }

--
-- DHCPv6 Server
--
ruijieDhcpv6ServerMIBObjects OBJECT-IDENTITY 
    STATUS      current
    DESCRIPTION
        "DHCPv6 Server MIB server identification objects are all defined
        in this branch."
    ::= { ruijieDhcpv6MIBObjects 1 }

ruijieDhcpv6ServerCounters OBJECT-IDENTITY
    STATUS      current
    DESCRIPTION
        "Group of objects that count various DHCPv6 events."
 ::= { ruijieDhcpv6ServerMIBObjects 1 }
 
ruijieDhcpv6ServerConfiguration OBJECT-IDENTITY
    STATUS      current
    DESCRIPTION
        "Objects that contain pre-configured and dynamic configuration
        information."
 ::= { ruijieDhcpv6ServerMIBObjects 2 }

--
-- DHCPv6 Server Counters
--
ruijieDhcpv6ServerHCountSolicits OBJECT-TYPE
    SYNTAX      Counter64
    MAX-ACCESS  read-only
    STATUS      current
    DESCRIPTION
        "The number of solicit packets received."
    ::= { ruijieDhcpv6ServerCounters 1 }

ruijieDhcpv6ServerHCountRequests OBJECT-TYPE
    SYNTAX      Counter64
    MAX-ACCESS  read-only
    STATUS      current
    DESCRIPTION
        "The number of request packets received."
    ::= { ruijieDhcpv6ServerCounters 2 }

ruijieDhcpv6ServerHCountRenews OBJECT-TYPE
    SYNTAX      Counter64
    MAX-ACCESS  read-only
    STATUS      current
    DESCRIPTION
        "The number of renew packets received."
    ::= { ruijieDhcpv6ServerCounters 3 }

ruijieDhcpv6ServerHCountDeclines OBJECT-TYPE
    SYNTAX      Counter64
    MAX-ACCESS  read-only
    STATUS      current
    DESCRIPTION
        "The number of decline packets received."
    ::= { ruijieDhcpv6ServerCounters 4 }

ruijieDhcpv6ServerHCountReleases OBJECT-TYPE
    SYNTAX      Counter64
    MAX-ACCESS  read-only
    STATUS      current
    DESCRIPTION
        "The number of release packets received."
    ::= { ruijieDhcpv6ServerCounters 5 }

ruijieDhcpv6ServerHCountInforms OBJECT-TYPE
    SYNTAX      Counter64
    MAX-ACCESS  read-only
    STATUS      current
    DESCRIPTION
        "The number of inform packets received."
    ::= { ruijieDhcpv6ServerCounters 6 }

ruijieDhcpv6ServerHCountConfirms OBJECT-TYPE
    SYNTAX      Counter64
    MAX-ACCESS  read-only
    STATUS      current
    DESCRIPTION
        "The number of confirm packets received."
    ::= { ruijieDhcpv6ServerCounters 7 }

ruijieDhcpv6ServerHCountRebinds OBJECT-TYPE
    SYNTAX      Counter64
    MAX-ACCESS  read-only
    STATUS      current
    DESCRIPTION
        "The number of rebind packets received."
    ::= { ruijieDhcpv6ServerCounters 8 }

ruijieDhcpv6ServerHCountAdvertises OBJECT-TYPE
    SYNTAX      Counter64
    MAX-ACCESS  read-only
    STATUS      current
    DESCRIPTION
        "The number of advertise packets sent."
    ::= { ruijieDhcpv6ServerCounters 9 }

ruijieDhcpv6ServerHCountSuccReplies OBJECT-TYPE
    SYNTAX      Counter64
    MAX-ACCESS  read-only
    STATUS      current
    DESCRIPTION
        "The number of success reply packets sent."
    ::= { ruijieDhcpv6ServerCounters 10 }

ruijieDhcpv6ServerHCountFailReplies OBJECT-TYPE
    SYNTAX      Counter64
    MAX-ACCESS  read-only
    STATUS      current
    DESCRIPTION
        "The number of failed reply packets sent."
    ::= { ruijieDhcpv6ServerCounters 11 }

ruijieDhcpv6ServerHCountInPkts OBJECT-TYPE
    SYNTAX      Counter64
    MAX-ACCESS  read-only
    STATUS      current
    DESCRIPTION
        "The number of input DHCPv6 packets."
    ::= { ruijieDhcpv6ServerCounters 12 }

ruijieDhcpv6ServerHCountOutPkts OBJECT-TYPE
    SYNTAX      Counter64
    MAX-ACCESS  read-only
    STATUS      current
    DESCRIPTION
        "The number of output DHCPv6 packets."
    ::= { ruijieDhcpv6ServerCounters 13 }

ruijieDhcpv6ServerHCountDroppedUnknown OBJECT-TYPE
    SYNTAX      Counter64
    MAX-ACCESS  read-only
    STATUS      current
    DESCRIPTION
        "The number of DHCPv6 packets dropped due to the server not
        recognizing received in the incoming packet."
    ::= { ruijieDhcpv6ServerCounters 14 }

ruijieDhcpv6ServerHCountDroppedError OBJECT-TYPE
    SYNTAX      Counter64
    MAX-ACCESS  read-only
    STATUS      current
    DESCRIPTION
        "The number of DHCPv6 packets dropped due to the server
        containing errors received in the incoming packet."
    ::= { ruijieDhcpv6ServerCounters 15 }
	
ruijieDhcpv6ServerHCountRelayforward OBJECT-TYPE
    SYNTAX      Counter64
    MAX-ACCESS  read-only
    STATUS      current
    DESCRIPTION
        "The number of Relay-forward packets received."
    ::= { ruijieDhcpv6ServerCounters 16 }
	
ruijieDhcpv6ServerHCountRelayreply OBJECT-TYPE
    SYNTAX      Counter64
    MAX-ACCESS  read-only
    STATUS      current
    DESCRIPTION
        "The number of Relay-reply packets sent."
    ::= { ruijieDhcpv6ServerCounters 17 }
    
ruijieDhcpv6ServerHCountReqtimes OBJECT-TYPE
    SYNTAX      Counter64
    MAX-ACCESS  read-only
    STATUS      current
    DESCRIPTION
        "The number of Discover packets recv."
    ::= { ruijieDhcpv6ServerCounters 18 }
    
ruijieDhcpv6ServerHCountReqSuctimes OBJECT-TYPE
    SYNTAX      Counter64
    MAX-ACCESS  read-only
    STATUS      current
    DESCRIPTION
        "The number of Ack packets send."
    ::= { ruijieDhcpv6ServerCounters 19 }

--
-- DHCPv6 Server Configuration
--
--
-- DHCPv6 Server Bindings Numbers
--
ruijieDhcpv6ServerNumBindings OBJECT-TYPE
    SYNTAX      Counter32
    MAX-ACCESS  read-only
    STATUS      current
    DESCRIPTION
        "The number of address bindings maintained by this server."
    ::= { ruijieDhcpv6ServerConfiguration 1 }

--
-- DHCPv6 Server Bindings Table
--
ruijieDhcpv6ServerBindingsTable OBJECT-TYPE
    SYNTAX      SEQUENCE OF RuijieDhcpv6ServerBindingsEntry
    MAX-ACCESS  not-accessible
    STATUS      current
    DESCRIPTION
        "A table of address bindings maintained by this DHCPv6 Server."
    ::= { ruijieDhcpv6ServerConfiguration 2 }

ruijieDhcpv6ServerBindingsEntry OBJECT-TYPE
    SYNTAX      RuijieDhcpv6ServerBindingsEntry
    MAX-ACCESS  not-accessible
    STATUS      current
    DESCRIPTION
        "An entry (conceptual row) representing an address binding maintained by
        this DHCPv6 Server."
    INDEX     { ruijieDhcpv6ServerBindingsPoolName,
                ruijieDhcpv6ServerBindingsClientDuid,
                ruijieDhcpv6ServerBindingsIaType,
                ruijieDhcpv6ServerBindingsIaId }
    ::= { ruijieDhcpv6ServerBindingsTable 1 }

RuijieDhcpv6ServerBindingsEntry ::= SEQUENCE {
    ruijieDhcpv6ServerBindingsPoolName      DisplayString,
    ruijieDhcpv6ServerBindingsClientDuid    OCTET STRING,
    ruijieDhcpv6ServerBindingsIaType        INTEGER,
    ruijieDhcpv6ServerBindingsIaId          Unsigned32,
    ruijieDhcpv6ServerBindingsAddress       Ipv6Address,
    ruijieDhcpv6ServerBindingsPrefix        Ipv6AddressPrefix,
    ruijieDhcpv6ServerBindingsPrefixLength  Integer32,
    ruijieDhcpv6ServerBindingsDuration      Unsigned32,
    ruijieDhcpv6ServerBindingsIfIndex       InterfaceIndex}

ruijieDhcpv6ServerBindingsPoolName OBJECT-TYPE
    SYNTAX      DisplayString (SIZE(1..32))
    MAX-ACCESS  read-only
    STATUS      current
    DESCRIPTION
        "The pool name associated with this entry in the bindings table."
    ::= { ruijieDhcpv6ServerBindingsEntry 1 }

ruijieDhcpv6ServerBindingsClientDuid OBJECT-TYPE
    SYNTAX      OCTET STRING (SIZE(0..130))
    MAX-ACCESS  read-only
    STATUS      current
    DESCRIPTION
        "The client DUID associated with this entry in the bindings table."
    ::= { ruijieDhcpv6ServerBindingsEntry 2 }

ruijieDhcpv6ServerBindingsIaType OBJECT-TYPE
    SYNTAX     INTEGER {
        iana(1),  -- IA-NA, Non-temporary Addresses
        iata(2),  -- IA-TA, Temporary Addresses
        iapd(3)   -- IA-PD, Prefix Delegation
    }
    MAX-ACCESS  read-only
    STATUS      current
    DESCRIPTION
        "The IA type associated with this entry in the bindings table."
    ::= { ruijieDhcpv6ServerBindingsEntry 3 }

ruijieDhcpv6ServerBindingsIaId OBJECT-TYPE
    SYNTAX      Unsigned32
    MAX-ACCESS  read-only
    STATUS      current
    DESCRIPTION
        "The IA index associated with this entry in the bindings table."
    ::= { ruijieDhcpv6ServerBindingsEntry 4 }

ruijieDhcpv6ServerBindingsAddress OBJECT-TYPE
    SYNTAX      Ipv6Address
    MAX-ACCESS  read-only
    STATUS      current
    DESCRIPTION
        "If IA type is IA_NA or IA_TA, then this is the IP Address associated
        with this entry in the bindings table."
    ::= { ruijieDhcpv6ServerBindingsEntry 5 }

ruijieDhcpv6ServerBindingsPrefix OBJECT-TYPE
    SYNTAX      Ipv6AddressPrefix
    MAX-ACCESS  read-only
    STATUS      current
    DESCRIPTION
        "If IA type is IA_PD, then this is IP Address Prefix Delegation 
        associated with this entry in the bindings table."
    ::= { ruijieDhcpv6ServerBindingsEntry 6 }

ruijieDhcpv6ServerBindingsPrefixLength OBJECT-TYPE
    SYNTAX      Integer32 (0..128)
    MAX-ACCESS  read-only
    STATUS      current
    DESCRIPTION
        "The IP Address Prefix Delegation length associated with this entry 
        in the bindings table."
    ::= { ruijieDhcpv6ServerBindingsEntry 7 }

ruijieDhcpv6ServerBindingsDuration OBJECT-TYPE
    SYNTAX      Unsigned32
    MAX-ACCESS  read-only
    STATUS      current
    DESCRIPTION
        "This is the time remaining prior to expiration of the address binding 
        associated with this entry. If the value is 4294967295 (i.e., 0xFFFFFFFF),
        this binding will be maintained indefinitely."
    ::= { ruijieDhcpv6ServerBindingsEntry 8 }

ruijieDhcpv6ServerBindingsIfIndex OBJECT-TYPE
    SYNTAX      InterfaceIndex
    MAX-ACCESS  read-only
    STATUS      current
    DESCRIPTION
        "The interface associated with this entry in the bindings table."
    ::= { ruijieDhcpv6ServerBindingsEntry 9 }

--
-- DHCPv6 Server Pool Usage Table
--
ruijieDhcpv6ServerPoolUsageTable OBJECT-TYPE
    SYNTAX      SEQUENCE OF RuijieDhcpv6ServerPoolEntry
    MAX-ACCESS  not-accessible
    STATUS      current
    DESCRIPTION
        "A table of pool usage maintained by this DHCPv6 Server."
    ::= { ruijieDhcpv6ServerConfiguration 3 }

ruijieDhcpv6ServerPoolEntry OBJECT-TYPE
    SYNTAX      RuijieDhcpv6ServerPoolEntry
    MAX-ACCESS  not-accessible
    STATUS      current
    DESCRIPTION
        "An entry (conceptual row) representing an pool maintained by
        this DHCPv6 Server."
    INDEX     { ruijieIPv6PoolUsageIndex}
    ::= { ruijieDhcpv6ServerPoolUsageTable 1 }
    
RuijieDhcpv6ServerPoolEntry ::= SEQUENCE {
    ruijieIPv6PoolUsageIndex     Unsigned32,
    ruijieIPv6PoolUsageName      DisplayString,
    ruijieIPv6DHCPIPPoolUsage    Unsigned32,
    ruijieIPv6PoolUsageRawStatus RowStatus
    }

ruijieIPv6PoolUsageIndex  OBJECT-TYPE
    SYNTAX      Unsigned32
    MAX-ACCESS  read-only
    STATUS      current
    DESCRIPTION
        "The pool index in the usage table."
    ::= { ruijieDhcpv6ServerPoolEntry 1 }
ruijieIPv6PoolUsageName OBJECT-TYPE
    SYNTAX      DisplayString (SIZE(1..32))
    MAX-ACCESS  read-create
    STATUS      current
    DESCRIPTION
        "The pool name associated with this entry in the bindings table."
    ::= { ruijieDhcpv6ServerPoolEntry 2 }

ruijieIPv6DHCPIPPoolUsage OBJECT-TYPE
    SYNTAX      Unsigned32
    MAX-ACCESS  read-only
    STATUS      current
    DESCRIPTION
        "This is the usage of the pool resource"
    ::= { ruijieDhcpv6ServerPoolEntry 3 }

ruijieIPv6PoolUsageRawStatus OBJECT-TYPE
    SYNTAX      RowStatus
    MAX-ACCESS  read-create
    STATUS      current
    DESCRIPTION
        "entry status of this entry. and the means in this enviraments can
            reffer to the text-convention definition of the RowStatus."
    ::= { ruijieDhcpv6ServerPoolEntry 4 }
--
-- DHCPv6 Server Pool Configure Table
--
ruijieDhcpv6ServerPoolConfigTable OBJECT-TYPE
    SYNTAX      SEQUENCE OF RuijieDhcpv6ServerPoolCfgEntry
    MAX-ACCESS  not-accessible
    STATUS      current
    DESCRIPTION
        "A table of configure pool maintained by this DHCPv6 Server."
    ::= { ruijieDhcpv6ServerConfiguration 4 }
ruijieDhcpv6ServerPoolCfgEntry OBJECT-TYPE
    SYNTAX      RuijieDhcpv6ServerPoolCfgEntry
    MAX-ACCESS  not-accessible
    STATUS      current
    DESCRIPTION
        "An entry (conceptual row) representing an pool maintained by
        this DHCPv6 Server."
    INDEX     { ruijieIPv6PoolCfgIndex}
    ::= { ruijieDhcpv6ServerPoolConfigTable 1 }
RuijieDhcpv6ServerPoolCfgEntry ::= SEQUENCE {
    ruijieIPv6PoolCfgIndex          Unsigned32,
    ruijieIPv6PoolName              DisplayString,
    ruijieIPv6PoolStartAddr         InetAddressIPv6,
    ruijieIPv6PoolStopAddr          InetAddressIPv6,
    ruijieIPv6NetPrefixLen          Unsigned32,
    ruijiePrimDNSServerIPv6Address  InetAddressIPv6,
    ruijieSeconDNSServerIPv6Address InetAddressIPv6,
    ruijieIPv6AddrLease             TimeTicks,
    ruijieIPv6RawStatus             RowStatus}
ruijieIPv6PoolCfgIndex  OBJECT-TYPE
    SYNTAX      Unsigned32
    MAX-ACCESS  read-only
    STATUS      current
    DESCRIPTION
        "The pool index associated with this entry in the bindings table."
    ::= { ruijieDhcpv6ServerPoolCfgEntry 1 }
ruijieIPv6PoolName OBJECT-TYPE
    SYNTAX      DisplayString (SIZE(1..32))
    MAX-ACCESS  read-create
    STATUS      current
    DESCRIPTION
        "The pool name associated with this entry in the bindings table."
    ::= { ruijieDhcpv6ServerPoolCfgEntry 2 }
ruijieIPv6PoolStartAddr OBJECT-TYPE
    SYNTAX      InetAddressIPv6
    MAX-ACCESS  read-create
    STATUS      current
    DESCRIPTION
        "This is the start address of the pool resource"
    ::= { ruijieDhcpv6ServerPoolCfgEntry 3 }
ruijieIPv6PoolStopAddr OBJECT-TYPE
    SYNTAX      InetAddressIPv6
    MAX-ACCESS  read-create
    STATUS      current
    DESCRIPTION
        "This is the stop address of the pool resource"
    ::= { ruijieDhcpv6ServerPoolCfgEntry 4 }
ruijieIPv6NetPrefixLen OBJECT-TYPE
    SYNTAX      Unsigned32
    MAX-ACCESS  read-create
    STATUS      current
    DESCRIPTION
        "This is the length of the prefix address resource"
    ::= { ruijieDhcpv6ServerPoolCfgEntry 5 }
ruijiePrimDNSServerIPv6Address OBJECT-TYPE
    SYNTAX      InetAddressIPv6
    MAX-ACCESS  read-create
    STATUS      current
    DESCRIPTION
        "This is the primary DNS address of the pool resource"
    ::= { ruijieDhcpv6ServerPoolCfgEntry 6 }
ruijieSeconDNSServerIPv6Address OBJECT-TYPE
    SYNTAX      InetAddressIPv6
    MAX-ACCESS  read-create
    STATUS      current
    DESCRIPTION
        "This is the second DNS address of the pool resource"
    ::= { ruijieDhcpv6ServerPoolCfgEntry 7 }
ruijieIPv6AddrLease OBJECT-TYPE
    SYNTAX      TimeTicks
    MAX-ACCESS  read-create
    STATUS      current
    DESCRIPTION
        "This is the lease time of the pool resource"
    ::= { ruijieDhcpv6ServerPoolCfgEntry 8 }
ruijieIPv6RawStatus OBJECT-TYPE
    SYNTAX RowStatus
    MAX-ACCESS read-create
    STATUS current
    DESCRIPTION
        "entry status of this entry. and the means in this enviraments can
        reffer to the text-convention definition of the RowStatus."
    ::= { ruijieDhcpv6ServerPoolCfgEntry 9 }
--
-- Conformance
--
ruijieDhcpv6MIBConformance   OBJECT-IDENTITY 
    STATUS      current
    DESCRIPTION
        "DHCPv6 server conformance objects are all defined in this
        branch."
    ::= { ruijieDhcpv6MIB 2 }
    
ruijieDhcpv6MIBCompliances   OBJECT IDENTIFIER ::= { ruijieDhcpv6MIBConformance 1 }
ruijieDhcpv6MIBGroups        OBJECT IDENTIFIER ::= { ruijieDhcpv6MIBConformance 2 }

--
-- Compliance groups
--
ruijieDhcpv6ServerCompliance MODULE-COMPLIANCE
    STATUS      current
    DESCRIPTION
        "This group describes the requirements for conformance to the
        DHCPv6 Server MIB."
    MODULE  -- this module
    MANDATORY-GROUPS {
        ruijieDhcpv6ServerCountersObjects,
        ruijieDhcpv6ServerConfigurationObjects
    }
    ::= { ruijieDhcpv6MIBCompliances 1 } 

--
-- Object groups
--
ruijieDhcpv6ServerCountersObjects  OBJECT-GROUP
    OBJECTS {
        ruijieDhcpv6ServerHCountSolicits,
        ruijieDhcpv6ServerHCountRenews,
        ruijieDhcpv6ServerHCountDeclines,
        ruijieDhcpv6ServerHCountReleases,
        ruijieDhcpv6ServerHCountInforms,
        ruijieDhcpv6ServerHCountConfirms,
        ruijieDhcpv6ServerHCountRebinds,
        ruijieDhcpv6ServerHCountAdvertises,
        ruijieDhcpv6ServerHCountSuccReplies,
        ruijieDhcpv6ServerHCountFailReplies,
        ruijieDhcpv6ServerHCountInPkts,
        ruijieDhcpv6ServerHCountOutPkts,
        ruijieDhcpv6ServerHCountDroppedUnknown,
        ruijieDhcpv6ServerHCountDroppedError,
        ruijieDhcpv6ServerHCountRelayforward,
        ruijieDhcpv6ServerHCountRelayreply,
        ruijieDhcpv6ServerHCountReqtimes,
        ruijieDhcpv6ServerHCountReqSuctimes
    }
    STATUS      current
    DESCRIPTION
        "The basic collection of objects providing management of DHCPv6
        Server functionality."
    ::= { ruijieDhcpv6MIBGroups 1 }

ruijieDhcpv6ServerConfigurationObjects  OBJECT-GROUP
    OBJECTS {
        ruijieDhcpv6ServerNumBindings,
        ruijieDhcpv6ServerBindingsPoolName,
        ruijieDhcpv6ServerBindingsClientDuid,
        ruijieDhcpv6ServerBindingsIaType,
        ruijieDhcpv6ServerBindingsIaId,
        ruijieDhcpv6ServerBindingsAddress,
        ruijieDhcpv6ServerBindingsPrefix,
        ruijieDhcpv6ServerBindingsPrefixLength,
        ruijieDhcpv6ServerBindingsDuration,
        ruijieDhcpv6ServerBindingsIfIndex }
    STATUS      current
    DESCRIPTION
        "The basic collection of objects providing management of DHCPv6
        Server functionality."
    ::= { ruijieDhcpv6MIBGroups 2 }

ruijieDhcpv6ServerPoolUsageTableObjects  OBJECT-GROUP
    OBJECTS {
        ruijieIPv6PoolUsageIndex,
        ruijieIPv6PoolName,
        ruijieIPv6DHCPIPPoolUsage,
        ruijieIPv6PoolUsageRawStatus
    }
    STATUS      current
    DESCRIPTION
        "The basic collection of objects providing management of DHCPv6
        Server functionality."
    ::= { ruijieDhcpv6MIBGroups 3 }

ruijieDhcpv6ServerPoolConfigGroup  OBJECT-GROUP
    OBJECTS {
    ruijieIPv6PoolCfgIndex,
    ruijieIPv6PoolName,
    ruijieIPv6PoolStartAddr,
    ruijieIPv6PoolStopAddr ,
    ruijieIPv6NetPrefixLen ,
    ruijiePrimDNSServerIPv6Address ,
    ruijieSeconDNSServerIPv6Address,
    ruijieIPv6AddrLease,
    ruijieIPv6RawStatus}
    STATUS      current
    DESCRIPTION
        "The basic collection of objects providing management of DHCPv6
        Server functionality."
    ::= { ruijieDhcpv6MIBGroups 4 }    
END
