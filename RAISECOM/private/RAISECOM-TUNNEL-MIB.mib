-- *****************************************************************
-- RAISECOM-TUNNEL-MIB.mib:  Raisecom Time MIB file
--
-- June 2012, zhangtao
--
-- Copyright (c) 2012 by Raisecom Networks Co.,Ltd.
-- All rights reserved.
-- 
-- *****************************************************************
--

RAISECOM-TUNNEL-MIB DEFINITIONS ::= BEGIN

    IMPORTS
        ruijieMgmt			
            FROM RAISECOM-SMI			
        IpAddress, Integer32, OBJECT-TYPE, MODULE-IDENTITY			
            FROM SNMPv2-SMI;

		-- 1.3.6.1.4.1.4881.1.1.10.2.1
    ruijieTunnelMib MODULE-IDENTITY 
        LAST-UPDATED "201206201634Z"		-- June 20, 2012 at 16:34 GMT
        ORGANIZATION 
            "Raisecom Networks Co.,Ltd."
        CONTACT-INFO 
            "
             Tel: 4008-111-000 
					
             E-mail: service@raisecom.com.cn"
        DESCRIPTION 
             "This module defines raisecom tunnel mibs."
        REVISION      
             "201206200000Z"
        DESCRIPTION
            "Initial version of this MIB module."
			::= { ruijieMgmt 114 }
			
--
-- Node definitions
--
	
		-- 1.3.6.1.4.1.4881.1.1.10.2.1.1
		ruijieTunnelObjects OBJECT IDENTIFIER ::= { ruijieTunnelMib 1 }
		
		-- 1.3.6.1.4.1.4881.1.1.10.2.1.1.1
		ruijieTunnelTable OBJECT-TYPE
			SYNTAX SEQUENCE OF RuijieTunnelEntry
			MAX-ACCESS not-accessible
			STATUS current
			DESCRIPTION
				"Description."
			::= { ruijieTunnelObjects 1 }
		
		-- 1.3.6.1.4.1.4881.1.1.10.2.1.1.1.1
		ruijieTunnelEntry OBJECT-TYPE
			SYNTAX RuijieTunnelEntry
			MAX-ACCESS not-accessible
			STATUS current
			DESCRIPTION
				"Description."
			INDEX { ruijieTunnelIp }
			::= { ruijieTunnelTable 1 }
		
		RuijieTunnelEntry ::=
			SEQUENCE { 
				ruijieTunnelIp
					IpAddress,
				ruijieTunnelOutIfindex
					Integer32
			 }

		-- 1.3.6.1.4.1.4881.1.1.10.2.1.1.1.1.1
		ruijieTunnelIp OBJECT-TYPE
			SYNTAX IpAddress
			MAX-ACCESS read-only
			STATUS current
			DESCRIPTION
				"Description."
			::= { ruijieTunnelEntry 1 }
		
		-- 1.3.6.1.4.1.4881.1.1.10.2.1.1.1.1.2
		ruijieTunnelOutIfindex OBJECT-TYPE
			SYNTAX Integer32
			MAX-ACCESS read-only
			STATUS current
			DESCRIPTION
				"Description."
			::= { ruijieTunnelEntry 2 }
	
	END

--
-- RAISECOM-TUNNEL-MIB.my
--
