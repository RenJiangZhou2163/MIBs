-- *****************************************************************
-- RAISECOM-BGP4-MIB.mib:  RAISECOM BGP4 MIB file
--
-- April 2003, HuangChongbin
--
-- Copyright (c) 2003 by Raisecom Networks Co.,Ltd.
-- All rights reserved.
-- 
-- *****************************************************************

RAISECOM-BGP4-MIB DEFINITIONS ::= BEGIN

IMPORTS
        MODULE-IDENTITY, 
        OBJECT-TYPE, 
        Unsigned32,
        Counter32
              FROM SNMPv2-SMI
        TruthValue,
        TEXTUAL-CONVENTION
              FROM SNMPv2-TC
        InetAutonomousSystemNumber 	
	            FROM INET-ADDRESS-MIB
        bgpPeerEntry,
        bgpPeerRemoteAddr
              FROM BGP4-MIB
        ruijieMgmt
              FROM RAISECOM-SMI;         

-- BEGIN：MODULE-IDENTITY
ruijieBgp4MIB MODULE-IDENTITY    
        LAST-UPDATED "200304010000Z"
        ORGANIZATION "Raisecom Networks Co.,Ltd."
        CONTACT-INFO
                " 
                Tel: 4008-111-000 
                
                E-mail: service@raisecom.com.cn"
        DESCRIPTION
                "This module defines raisecom bgp4 mibs."
        REVISION      "200304010000Z"
        DESCRIPTION
                "Initial version of this MIB module."
        ::= { ruijieMgmt 38}        
-- END：MODULE-IDENTITY


-- BEGIN：Noun definition 
RuijieBgpID ::= TEXTUAL-CONVENTION
	DISPLAY-HINT "1d."
	STATUS	     current
	DESCRIPTION
	    "The representation of a BGP Identifier.  The BGP
	     Identifier should be represented in the OCTET STRING
	     as with the first OCTET of the string containing
	     the first OCTET of the BGP Identifier received or sent
	     in the OPEN packet and so on.

	     Even though the BGP Identifier is trending away from
	     an IP address it is still displayed as if it was one,
	     even when it would be an illegal IP address."
	SYNTAX OCTET STRING(SIZE (4))                             
-- END：Noun definition 


-- BEGIN：ruijieBgpBaseScalars

ruijieBgpBaseScalars
	OBJECT IDENTIFIER ::= { ruijieBgp4MIB 1 }

-- BEGIN：ruijieBgpSupportedCapabilities
-- BGP Capabilities information

ruijieBgpSupportedCapabilities
        OBJECT IDENTIFIER ::= { ruijieBgpBaseScalars 1 }
        
ruijieBgpCapabilitySupportAvailable OBJECT-TYPE
	SYNTAX	   TruthValue
	MAX-ACCESS read-only
	STATUS	   current
	DESCRIPTION
	    "This value is TRUE if capability support is
	     available."
	::= { ruijieBgpSupportedCapabilities 1 }
	
ruijieBgpSupportedCapabilitiesTable OBJECT-TYPE
	SYNTAX	   SEQUENCE OF RuijieBgpSupportedCapabilityEntry
	MAX-ACCESS not-accessible
	STATUS	   current
	DESCRIPTION
	    "Table of supported BGP-4 capabilities."
	::= { ruijieBgpSupportedCapabilities 2 }
	
ruijieBgpSupportedCapabilitiesEntry OBJECT-TYPE
	SYNTAX	   RuijieBgpSupportedCapabilityEntry
	MAX-ACCESS not-accessible
	STATUS	   current
	DESCRIPTION
	    "Information about supported capabilities indexed
	     by capability number."
	INDEX {
	    ruijieBgpSupportedCapabilityCode
	}
	::= { ruijieBgpSupportedCapabilitiesTable 1 }
	
RuijieBgpSupportedCapabilityEntry ::= SEQUENCE {
	ruijieBgpSupportedCapabilityCode
	    Unsigned32,
	ruijieBgpSupportedCapability
	    TruthValue
    }
    
ruijieBgpSupportedCapabilityCode OBJECT-TYPE
	SYNTAX	   Unsigned32 (0..255)
	MAX-ACCESS read-only
	STATUS	   current
	DESCRIPTION
	    "Index of supported capability.  The index directly
	     corresponds with the BGP-4 Capability Advertisement
	     Capability Code."
	::= { ruijieBgpSupportedCapabilitiesEntry 1 }
	
ruijieBgpSupportedCapability OBJECT-TYPE
	SYNTAX	   TruthValue
	MAX-ACCESS read-only
	STATUS	   current
	DESCRIPTION
	    "This value is True if this capability is supported,
	     False otherwise."
	::= { ruijieBgpSupportedCapabilitiesEntry 2 }
	
-- END：ruijieBgpSupportedCapabilities

-- BEGIN：ruijieBgpBaseScalarExtensions
-- BGP Extensions

ruijieBgpBaseScalarExtensions
        OBJECT IDENTIFIER ::= { ruijieBgpBaseScalars 2 }
        
-- Base Scalar Route Reflection Extensions
ruijieBgpBaseScalarRouteReflectExts OBJECT IDENTIFIER ::=
	{ ruijieBgpBaseScalarExtensions 1 }

ruijieBgpRouteReflector OBJECT-TYPE
	SYNTAX	    TruthValue
	MAX-ACCESS  read-only
	STATUS	    current
	DESCRIPTION
	    "This value is TRUE if this implementation supports the
	     BGP Route Reflection Extension and is enabled as a
	     route reflector.  If the BGP Route Reflection extension
	     is not supported this value must be FALSE."
	REFERENCE
	    "RFC 2796 - BGP Route Reflection"
	::= { ruijieBgpBaseScalarRouteReflectExts 1 }

ruijieBgpClusterId OBJECT-TYPE
	SYNTAX	    RuijieBgpID
	MAX-ACCESS  read-only 
	STATUS	    current
	DESCRIPTION
	    "The configured Cluster-ID of the BGP Speaker.  This will
	     default to the BGP Speaker's ruijieBgpIdentifier if this
	     speaker is functioning as a route reflector and an
	     explicit Cluster-ID has not been configured.

	     A value of 0.0.0.0 will be present if Route Reflection is
	     not enabled."
	REFERENCE
	    "RFC 2796 - BGP Route Reflection"
	::= { ruijieBgpBaseScalarRouteReflectExts 2 }

-- Base Scalar AS Confederation Extensions
 
ruijieBgpBaseScalarASConfedExts OBJECT IDENTIFIER ::=
        { ruijieBgpBaseScalarExtensions 2 }

ruijieBgpConfederationRouter OBJECT-TYPE
	SYNTAX	   TruthValue
	MAX-ACCESS read-only
	STATUS	   current
	DESCRIPTION
	    "This value is TRUE if this implementation supports the
	     BGP AS Confederations Extension and this router is
	     configured to be in a confederation."
	REFERENCE
	    "RFC 3065 - Autonomous System Confederations for BGP"
	::= { ruijieBgpBaseScalarASConfedExts 1 }

ruijieBgpConfederationId OBJECT-TYPE
	SYNTAX	   InetAutonomousSystemNumber
	MAX-ACCESS read-only
	STATUS	   current
	DESCRIPTION
	    "The local Confederation Identification Number.
	    
	     This value will be zero (0) if this BGP Speaker is not
	     a confederation router."
	REFERENCE
	    "RFC 3065 - Autonomous System Confederations for BGP"
	    ::= { ruijieBgpBaseScalarASConfedExts 2 }

-- END：ruijieBgpBaseScalarExtensions

-- END：ruijieBgpBaseScalars

-- BEGIN：ruijieBgpPeer

ruijieBgpPeer
	OBJECT IDENTIFIER ::= { ruijieBgp4MIB 2 }

-- BEGIN：ruijieBgpPeerPrefixInfoTable

ruijieBgpPeerPrefixInfoTable OBJECT-TYPE
        SYNTAX     SEQUENCE OF RuijieBgpPeerPrefixInfoEntry
        MAX-ACCESS not-accessible
        STATUS     current
        DESCRIPTION
                "This table contains prefix info with peers,
                 One entry per BGP peer ."
        ::= { ruijieBgpPeer 1 }

ruijieBgpPeerPrefixInfoEntry  OBJECT-TYPE
        SYNTAX     RuijieBgpPeerPrefixInfoEntry
        MAX-ACCESS not-accessible
        STATUS     current
        DESCRIPTION
                "Entry containing information about the
                connection with a BGP peer."
        AUGMENTS {
	    bgpPeerEntry
	}
        ::= { ruijieBgpPeerPrefixInfoTable 1 }

RuijieBgpPeerPrefixInfoEntry ::= SEQUENCE {
        ruijieBgpPeerPrefixLimit       Unsigned32,
        ruijieBgpPeerPrefixAccepted    Counter32,
        ruijieBgpPeerPrefixAdvertised  Counter32
        }
    
ruijieBgpPeerPrefixLimit  OBJECT-TYPE
        SYNTAX      Unsigned32 (1..4294967295)
        MAX-ACCESS  read-only
        STATUS      deprecated
        DESCRIPTION
                "Max number of route prefixes accepted on this 
                 connection"
        ::= { ruijieBgpPeerPrefixInfoEntry 1 }
        
ruijieBgpPeerPrefixAccepted  OBJECT-TYPE  
        SYNTAX      Counter32
        MAX-ACCESS  read-only
        STATUS      deprecated
        DESCRIPTION
                "Number of Route prefixes received on this connnection,
                 which are accepted after applying filters. Possible
                 filters are route maps, prefix lists, distributed
                 lists, etc."
        ::= { ruijieBgpPeerPrefixInfoEntry 2 } 

ruijieBgpPeerPrefixAdvertised  OBJECT-TYPE
        SYNTAX      Counter32
        MAX-ACCESS  read-only
        STATUS      deprecated
        DESCRIPTION
                "Counter which gets incremented when a route prefix
                 is advertised on this connection. This object is
                 initialized to zero when the peer is configured or 
                 the router is rebooted"
        ::= { ruijieBgpPeerPrefixInfoEntry 3 }

-- END：ruijieBgpPeerPrefixInfoTable

-- BEGIN：ruijieBgpPeerCapabilities

ruijieBgpPeerCapabilities
	OBJECT IDENTIFIER ::= { ruijieBgpPeer 2 }

-- BEGIN：ruijieBgpPeerCapsAnnouncedTable
-- Announced Capabilities

ruijieBgpPeerCapsAnnouncedTable OBJECT-TYPE
	SYNTAX	   SEQUENCE OF RuijieBgpPeerCapsAnnouncedEntry
	MAX-ACCESS not-accessible
	STATUS	   current
	DESCRIPTION
	    "This table contains the capabilities
	     that are announced to a given peer."
	::= { ruijieBgpPeerCapabilities 1 }

ruijieBgpPeerCapsAnnouncedEntry OBJECT-TYPE
	SYNTAX	   RuijieBgpPeerCapsAnnouncedEntry
	MAX-ACCESS not-accessible
	STATUS	   current
	DESCRIPTION
	    "These entries are keyed by a BGP-4 peer remote
	     address and the BGP Capability Code"
	INDEX {
	    bgpPeerRemoteAddr,
	    ruijieBgpPeerCapAnnouncedCode
	}
	::= { ruijieBgpPeerCapsAnnouncedTable 1 }

RuijieBgpPeerCapsAnnouncedEntry ::= SEQUENCE {
	ruijieBgpPeerCapAnnouncedCode
	    Unsigned32,
	ruijieBgpPeerCapAnnouncedValue
	    OCTET STRING
    }

ruijieBgpPeerCapAnnouncedCode OBJECT-TYPE
	SYNTAX	   Unsigned32 (0..255)
	MAX-ACCESS read-only
	STATUS	   current
	DESCRIPTION
	    "The BGP Capability Advertisement Capability Code."
	::= { ruijieBgpPeerCapsAnnouncedEntry 1 }

ruijieBgpPeerCapAnnouncedValue OBJECT-TYPE
	SYNTAX	   OCTET STRING (SIZE(0..255))
	MAX-ACCESS read-only
	STATUS	   current
	DESCRIPTION
	    "The value of the announced capability."
	::= { ruijieBgpPeerCapsAnnouncedEntry 2 }

-- END：ruijieBgpPeerCapsAnnouncedTable

-- BEGIN：ruijieBgpPeerCapsReceivedTable
-- Received Capabilities

ruijieBgpPeerCapsReceivedTable OBJECT-TYPE
	SYNTAX	   SEQUENCE OF RuijieBgpPeerCapsReceivedEntry
	MAX-ACCESS not-accessible
	STATUS	   current
	DESCRIPTION
	    "This table contains the capabilities
	    that are supported for a given peer."
	::= { ruijieBgpPeerCapabilities 2 }

ruijieBgpPeerCapsReceivedEntry OBJECT-TYPE
	SYNTAX	   RuijieBgpPeerCapsReceivedEntry
	MAX-ACCESS not-accessible
	STATUS	   current
	DESCRIPTION
	    "These entries are keyed by a BGP-4 peer remote
	    address and the BGP Capability Code"
	INDEX {
	    bgpPeerRemoteAddr,
	    ruijieBgpPeerCapReceivedCode
	}
	::= { ruijieBgpPeerCapsReceivedTable 1 }

RuijieBgpPeerCapsReceivedEntry ::= SEQUENCE {
	ruijieBgpPeerCapReceivedCode
	    Unsigned32,
	ruijieBgpPeerCapReceivedValue
	    OCTET STRING
    }

ruijieBgpPeerCapReceivedCode OBJECT-TYPE
	SYNTAX	   Unsigned32 (0..255)
	MAX-ACCESS read-only
	STATUS	   current
	DESCRIPTION
	    "The BGP Capability Advertisement Capability Code."
	::= { ruijieBgpPeerCapsReceivedEntry 1 }

ruijieBgpPeerCapReceivedValue OBJECT-TYPE
	SYNTAX	   OCTET STRING (SIZE(0..255))
	MAX-ACCESS read-only
	STATUS	   current
	DESCRIPTION
	    "The value of the announced capability."
	::= { ruijieBgpPeerCapsReceivedEntry 3 }

-- END：ruijieBgpPeerCapsReceivedTable
	
-- END：ruijieBgpPeerCapabilities

-- BEGIN：ruijieBgpPeerExtensions

ruijieBgpPeerExtensions
	OBJECT IDENTIFIER ::= { ruijieBgpPeer 3 }

-- BEGIN：
-- Peer Route Reflection Extensions

ruijieBgpPeerRouteReflectionExts
	OBJECT IDENTIFIER ::= { ruijieBgpPeerExtensions 1 }

ruijieBgpPeerReflectorClientTable OBJECT-TYPE
	SYNTAX	   SEQUENCE OF RuijieBgpPeerReflectorClientEntry
	MAX-ACCESS not-accessible
	STATUS	   current
	DESCRIPTION
	    "Table of route reflection client settings on a per-peer
	     basis."
	REFERENCE
	    "RFC 2796 - BGP Route Reflection"
	::= { ruijieBgpPeerRouteReflectionExts 1 }

ruijieBgpPeerReflectorClientEntry OBJECT-TYPE
	SYNTAX	   RuijieBgpPeerReflectorClientEntry
	MAX-ACCESS not-accessible
	STATUS	   current
	DESCRIPTION
	    "Entry containing data on a per-peer basis on whether
	     the peer is configured as a route reflector client."
	REFERENCE
	    "RFC 2796 - BGP Route Reflection"
	AUGMENTS {
	    bgpPeerEntry
	}
	::= { ruijieBgpPeerReflectorClientTable 1 }

RuijieBgpPeerReflectorClientEntry ::= SEQUENCE {
	ruijieBgpPeerReflectorClient
	    INTEGER
    }

ruijieBgpPeerReflectorClient OBJECT-TYPE
	SYNTAX	  INTEGER {
	    nonClient(0),
	    client(1),
	    meshedClient(2)
	}
	MAX-ACCESS  read-only
	STATUS	    current
	DESCRIPTION
	    "This value indicates whether the given peer is a
	     reflector client of this router, or not.  A value of
	     nonClient indicates that this peer is not a reflector
	     client.  A value of client indicates that this peer is a
	     reflector client that is not fully meshed with other
	     reflector clients.	 A value of meshedClient indicates
	     that the peer is a reflector client and is fully meshed
	     with all other reflector clients.

	     This value must be nonClient (0) for BGP external peers."
	REFERENCE
	    "RFC 2796 - BGP Route Reflection"
	::= { ruijieBgpPeerReflectorClientEntry 1 }

-- Peer AS Confederations Extensions

ruijieBgpPeerASConfederationExts
	OBJECT IDENTIFIER ::= { ruijieBgpPeerExtensions 2 }

ruijieBgpPeerConfedMemberTable OBJECT-TYPE
	SYNTAX	   SEQUENCE OF RuijieBgpPeerConfedMemberEntry
	MAX-ACCESS not-accessible
	STATUS	   current
	DESCRIPTION
	    "Table of confederation member settings on a per-peer
	     basis."
	REFERENCE
	    "RFC 3065 - BGP Confederations"
	::= { ruijieBgpPeerASConfederationExts 1 }

ruijieBgpPeerConfedMemberEntry OBJECT-TYPE
	SYNTAX	   RuijieBgpPeerConfedMemberEntry
	MAX-ACCESS not-accessible
	STATUS	   current
	DESCRIPTION
	    "Entry containing data on a per-peer basis on whether
	     the peer is configured as a BGP confederation member."
	REFERENCE
	    "RFC 3065 - BGP Confederations"
	AUGMENTS {
	    bgpPeerEntry
	}
	::= { ruijieBgpPeerConfedMemberTable 1 }

RuijieBgpPeerConfedMemberEntry ::= SEQUENCE {
	ruijieBgpPeerConfedMember
	    TruthValue
    }
    
ruijieBgpPeerConfedMember OBJECT-TYPE
	SYNTAX	    TruthValue
	MAX-ACCESS  read-only
	STATUS	    current
	DESCRIPTION
	    "This value indicates whether the given peer is in our
	     confederation or not."
	REFERENCE
	    "RFC 3065 - BGP Confederations"
	::= { ruijieBgpPeerConfedMemberEntry 1 }
	
-- END：ruijieBgpPeerExtensions	 
	
-- END：ruijieBgpPeer

-- BEGIN：Conformance Information

ruijieBgpConformance
	OBJECT IDENTIFIER ::= { ruijieBgp4MIB 3 }

ruijieBgpMIBCompliances OBJECT IDENTIFIER ::=
	{ ruijieBgpConformance 1 }
ruijieBgpMIBGroups	OBJECT IDENTIFIER ::=
	{ ruijieBgpConformance 2 }

-- END：Conformance Information

END
