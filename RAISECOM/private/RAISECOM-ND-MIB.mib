-- *****************************************************************
-- RAISECOM-ND-MIB.mib:  Raisecom ND MIB file
--
--  2013.12.30, huangguohua@raisecom.com.cn
--
-- Copyright (c) 2013 by Raisecom Networks .
-- All rights reserved.
-- 
-- *****************************************************************
--

RAISECOM-ND-MIB DEFINITIONS ::= BEGIN

IMPORTS
        MODULE-IDENTITY,
        OBJECT-TYPE,
        NOTIFICATION-TYPE
                FROM SNMPv2-SMI
        Integer32
                FROM SNMPv2-SMI        
        MODULE-COMPLIANCE,
        OBJECT-GROUP,
        NOTIFICATION-GROUP
                FROM SNMPv2-CONF
        ruijieMgmt
                FROM RAISECOM-SMI;

ruijieNDMIB MODULE-IDENTITY
        LAST-UPDATED "201312300000Z"
        ORGANIZATION "Raisecom Networks."
        CONTACT-INFO
                " 
                Tel: 4008-111-000

                E-mail: service@raisecom.com.cn"
        DESCRIPTION
                "This module defines raisecom ND mibs."
        REVISION      "201312300000Z"
        DESCRIPTION
                "Initial version of this MIB module."
        ::= { ruijieMgmt 125}

ruijieNDMIBObjects OBJECT IDENTIFIER ::= { ruijieNDMIB 1 }     
          
   ruijieNDTotalActiveNeighbors OBJECT-TYPE
        SYNTAX Counter32
        MAX-ACCESS read-only
        STATUS current
        DESCRIPTION
            "Total active neighbors This system have"
        ::= { ruijieNDMIBObjects 1 }  
		
  ruijieNDTotalActiveDynamicNeighbors OBJECT-TYPE
          SYNTAX Counter32
          MAX-ACCESS read-only
          STATUS current
          DESCRIPTION
            "Total active dynamic neighbors This system have"
          ::= { ruijieNDMIBObjects 2} 
          
   ruijieNDTotalStaticNeighbors OBJECT-TYPE
        SYNTAX Counter32
        MAX-ACCESS read-only
        STATUS current
        DESCRIPTION
            "Total static neighbors This system configure"
        ::= { ruijieNDMIBObjects 3 } 
		
   ruijieNDTotalActiveStaticNeighbors OBJECT-TYPE
        SYNTAX Counter32
        MAX-ACCESS read-only
        STATUS current
        DESCRIPTION
            "Total active static neighbors This system have"
        ::= { ruijieNDMIBObjects 4 }        
                   

ruijieNDMIBConformance OBJECT IDENTIFIER ::= { ruijieNDMIB 2}
ruijieNDMIBCompliances OBJECT IDENTIFIER ::= { ruijieNDMIBConformance 1 }
ruijieNDMIBGroups      OBJECT IDENTIFIER ::= { ruijieNDMIBConformance 2 }

-- compliance statements

ruijieNDMIBCompliance MODULE-COMPLIANCE
        STATUS  current
        DESCRIPTION
                "The compliance statement for entities which implement
                the Raisecom ND MIB"
        MODULE  -- this module
                MANDATORY-GROUPS { 
                        ruijieNDObjectsGroup
                 }
         ::= { ruijieNDMIBCompliances 1 }
        
-- units of conformance

ruijieNDObjectsGroup OBJECT-GROUP
       OBJECTS {
	       ruijieNDTotalActiveNeighbors,
           ruijieNDTotalActiveDynamicNeighbors,
		   ruijieNDTotalStaticNeighbors,
		   ruijieNDTotalActiveStaticNeighbors
       }
       STATUS  current
       DESCRIPTION
                "A collection of objects providing ND information to a
                Raisecom agent."
       ::= { ruijieNDMIBGroups 1 }       

END
