-- *****************************************************************
-- RAISECOM-SMARTCLASS-SMI.mib: Raisecom Smart Class SMI File
-- 
-- Feb. 2017, panshiyong
--
-- Copyright (c) 2014 by Raisecom Networks Co.,Ltd.
-- All rights reserved.
-- 
-- *****************************************************************
--

RAISECOM-SMARTCLASS-SMI DEFINITIONS ::= BEGIN

IMPORTS
        MODULE-IDENTITY,
        OBJECT-IDENTITY
                FROM SNMPv2-SMI
        products
                FROM RAISECOM-SMI;
                
smartclass OBJECT IDENTIFIER ::= { products 8 }

smartclassMib MODULE-IDENTITY
        LAST-UPDATED "201702130000Z"
        ORGANIZATION "Raisecom Networks Co.,Ltd."
        CONTACT-INFO
                " 
                Tel: 4008-111-000 

                E-mail: service@raisecom.com.cn"
        DESCRIPTION
                "The Structure of Management Information for the
                 Raisecom enterprise."
        REVISION      "201702130000Z"
        DESCRIPTION
                "Initial version of this MIB module."
        ::= { smartclass 1 }        

ruijieSmartClassProducts OBJECT-IDENTITY
        STATUS  current
        DESCRIPTION
                "ruijieSmartClassProducts is the root OBJECT IDENTIFIER from
                 which sysObjectID values are assigned for smartclass.  Actual
                 values are defined in RAISECOM-PRODUCTS-MIB."
        ::= { smartclassMib 1 }
        
END
