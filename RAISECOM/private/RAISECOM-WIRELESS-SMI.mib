-- *****************************************************************
-- RAISECOM-WIRELESS-SMI.mib: Raisecom Wireless SMI File
-- 
-- July 2007, Wuzg
-- 
-- Copyright (c) 2007 by Raisecom Networks Co.,Ltd.
-- All rights reserved.
-- 
-- *****************************************************************
--

RAISECOM-WIRELESS-SMI DEFINITIONS ::= BEGIN

IMPORTS
        MODULE-IDENTITY,
        OBJECT-IDENTITY
                FROM SNMPv2-SMI
        products
                FROM RAISECOM-SMI;
                
wireless        OBJECT IDENTIFIER ::= { products 3 }

wirelessMib MODULE-IDENTITY
        LAST-UPDATED "200707040000Z"
        ORGANIZATION "Raisecom Networks Co.,Ltd."
        CONTACT-INFO
                " 
                Tel: 4008-111-000 

                E-mail: service@raisecom.com.cn"
        DESCRIPTION
                "The Structure of Management Information for the
                 Raisecom enterprise."
        REVISION      "200707040000Z"
        DESCRIPTION
                "Initial version of this MIB module."
        ::= { wireless 1 }        

ruijieWirelessProducts OBJECT-IDENTITY
        STATUS  current
        DESCRIPTION
                "ruijieWirelessProducts is the root OBJECT IDENTIFIER from
                which sysObjectID values are assigned for wireless product.
                Actual values are defined in RAISECOM-PRODUCTS-MIB."
        ::= { wirelessMib 1 }

ruijieWirelessMgmt OBJECT-IDENTITY
        STATUS  current
        DESCRIPTION
                "ruijieWirelessMgmt is the main subtree for those functional mib."
        ::= { wirelessMib 2 }
        
END
