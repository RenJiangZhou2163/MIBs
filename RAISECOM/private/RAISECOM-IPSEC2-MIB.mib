--
-- RAISECOM-IPSEC2-MIB.mib
-- MIB generated by MG-SOFT Visual MIB Builder Version 6.0  Build 88
-- Tuesday, February 14, 2012 at 13:07:15
--

	RAISECOM-IPSEC2-MIB DEFINITIONS ::= BEGIN
 
		IMPORTS		
			OBJECT-GROUP, MODULE-COMPLIANCE, NOTIFICATION-GROUP			
				FROM SNMPv2-CONF			
			IpAddress, Integer32, Unsigned32, Gauge32, Counter32, 
			Counter64, OBJECT-TYPE, NOTIFICATION-TYPE			
				FROM SNMPv2-SMI			
			DisplayString, TimeStamp, TEXTUAL-CONVENTION			
				FROM SNMPv2-TC
			ruijieMgmt
                                 FROM RAISECOM-SMI;
	
        ruijieIPSec2MibModule MODULE-IDENTITY
			LAST-UPDATED "201112191637Z"		-- December 19, 2011 at 16:37 GMT
			ORGANIZATION
				"Organization."
			CONTACT-INFO
				"Contact-info."
			DESCRIPTION
				"Description."
			::= { ruijieMgmt 108 }
	
	
--
-- Textual conventions
--
	
		RuijieIPSecNegoType ::= TEXTUAL-CONVENTION
			STATUS current
			DESCRIPTION 
				"The type of key used by an IPSec Phase-2 Tunnel. invalidType(2147483647)
				is defined as invalid value."
			SYNTAX INTEGER
				{
				ike(1),
				manual(2),
				invalidType(2147483647)
				}

		RuijieEncapMode ::= TEXTUAL-CONVENTION
			STATUS current
			DESCRIPTION 
				"The encapsulation mode used by an IPSec Phase-2 Tunnel."
			SYNTAX INTEGER
				{
				tunnel(1),
				transport(2),
				invalidMode(2147483647)
				}

		RuijieEncryptAlgo ::= TEXTUAL-CONVENTION
			STATUS current
			DESCRIPTION 
				"The encryption algorithm used in the IKE and IPSec negotiations.
				invalidAlg(2147483647) is defined as invalid value."
			SYNTAX INTEGER
				{
				none(0),
				desCbc(2),
				threedesCbc(3),
				aesCbc(12),
				sm1Cbc(128),
				invalidAlg(2147483647)
				}

		RuijieAuthAlgo ::= TEXTUAL-CONVENTION
			STATUS current
			DESCRIPTION 
				"The authentication algorithm used in the IKE negotiations.
				invalidAlg(2147483647) is defined as invalid value."
			SYNTAX INTEGER
				{
				none(0),
				md5(2),
				sha(3),
				invalidAlg(2147483647)
				}

		RuijieDiffHellmanGrp ::= TEXTUAL-CONVENTION
			STATUS current
			DESCRIPTION 
				"The Diffie Hellman Group used in the IKE and IPSec negotiations.
				invalidAlg(2147483647) is defined as invalid value."
			SYNTAX INTEGER
				{
				modp768(1),
				modp1024(2),
				invalidMode(2147483647)
				}

		RuijieIPSecTunnelState ::= TEXTUAL-CONVENTION
			STATUS current
			DESCRIPTION 
				"The state of IPSec tunnel."
			SYNTAX INTEGER
				{
				establishing(1),
				active(2),
				expiring(3)
				}

		RuijieSaProtocol ::= TEXTUAL-CONVENTION
			STATUS current
			DESCRIPTION 
				"The protocol of security association."
			SYNTAX INTEGER
				{
				reserved(0),
				isakmp(1),
				ah(2),
				esp(3)
				}

		RuijieTrafficType ::= TEXTUAL-CONVENTION
			STATUS current
			DESCRIPTION 
				"The type of the data flow."
			SYNTAX INTEGER
				{
				ipv4Addr(1),
				ipv4AddrSubnet(2),
				ipv6Addr(3),
				ipv6AddrSubnet(4),
				ipv4AddrRange(5),
				ipv6AddrRange(6)
				}

--  1.3.6.1.4.1.4881.1.1.10.2.108.1
-- December 19, 2011 at 16:37 GMT
-- 
-- Textual conventions
-- 
		RuijieIPSec2NegoType ::= TEXTUAL-CONVENTION
			STATUS current
			DESCRIPTION 
				"The type of key used by an IPSec Phase-2 Tunnel. invalidType(2147483647)
				is defined as invalid value."
			SYNTAX INTEGER
				{
				ike(1),
				manual(2),
				invalidType(2147483647)
				}

		RuijieIPSec2TunnelState ::= TEXTUAL-CONVENTION
			STATUS current
			DESCRIPTION 
				"The state of IPSec tunnel."
			SYNTAX INTEGER
				{
				establishing(1),
				active(2),
				expiring(3)
				}

	
--
-- Node definitions
--
	
		-- 1.3.6.1.4.1.4881.1.1.10.2.108.1
		ruijieIPSec2Objects OBJECT IDENTIFIER ::= { ruijieIPSec2MibModule 1 }

		
		-- 1.3.6.1.4.1.4881.1.1.10.2.108.1.1
		ruijieIPSec2TunnelTable OBJECT-TYPE
			SYNTAX SEQUENCE OF RuijieIPSec2TunnelEntry
			MAX-ACCESS not-accessible
			STATUS current
			DESCRIPTION
				"The IPSec Phase-2 Tunnel Table. There is one
				entry in this table for each active IPSec Phase-2 Tunnel."
			::= { ruijieIPSec2Objects 1 }

		
		-- 1.3.6.1.4.1.4881.1.1.10.2.108.1.1.1
		ruijieIPSec2TunnelEntry OBJECT-TYPE
			SYNTAX RuijieIPSec2TunnelEntry
			MAX-ACCESS not-accessible
			STATUS current
			DESCRIPTION
				"Information about RuijieIPSec2TunnelTable."
			INDEX { ruijieIPSec2TunIfIndex, ruijieIPSec2TunRemoteAddr, ruijieIPSec2TrafficLocalType, ruijieIPSec2TrafficLocalProtocol, ruijieIPSec2TrafficLocalAddr1, 
				ruijieIPSec2TrafficLocalAddr2, ruijieIPSec2TrafficLocalPort, ruijieIPSec2TrafficRemoteAddr1, ruijieIPSec2TrafficRemoteAddr2, ruijieIPSec2TrafficRemotePort
				 }
			::= { ruijieIPSec2TunnelTable 1 }

		
		RuijieIPSec2TunnelEntry ::=
			SEQUENCE { 
				ruijieIPSec2TunIfIndex
					Integer32,
				ruijieIPSec2TunnelTrafficIndex
					Integer32,
				ruijieIPSec2TunIndex
					Integer32,
				ruijieIPSec2TunIKETunnelIndex
					Integer32,
				ruijieIPSec2TunnelAhOutSaIndex
					Integer32,
				ruijieIPSec2TunnelAhInSaIndex
					Integer32,
				ruijieIPSec2TunnelEspOutSaIndex
					Integer32,
				ruijieIPSec2TunnelEspInSaIndex
					Integer32,
				ruijieIPSec2TunLocalAddr
					IpAddress,
				ruijieIPSec2TunRemoteAddr
					IpAddress,
				ruijieIPSec2TunLocalHostname
					DisplayString,
				ruijieIPSec2TunRemoteHostname
					DisplayString,
				ruijieIPSec2TunKeyType
					RuijieIPSec2NegoType,
				ruijieIPSec2TunEncapMode
					RuijieEncapMode,
				ruijieIPSec2TunInitiator
					INTEGER,
				ruijieIPSec2TunLifeSize
					Integer32,
				ruijieIPSec2TunLifeTime
					Integer32,
				ruijieIPSec2TunRemainTime
					Integer32,
				ruijieIPSec2TunActiveTime
					Integer32,
				ruijieIPSec2TunCreateTime
					TimeStamp,
				ruijieIPSec2TunRemainSize
					Integer32,
				ruijieIPSec2TunTotalRefreshes
					Counter32,
				ruijieIPSec2TunCurrentSaInstances
					Gauge32,
				ruijieIPSec2TunInSaEncryptAlgo
					RuijieEncryptAlgo,
				ruijieIPSec2TunInSaAhAuthAlgo
					RuijieAuthAlgo,
				ruijieIPSec2TunInSaEspAuthAlgo
					RuijieAuthAlgo,
				ruijieIPSec2TunDiffHellmanGrp
					RuijieDiffHellmanGrp,
				ruijieIPSec2TunOutSaEncryptAlgo
					RuijieEncryptAlgo,
				ruijieIPSec2TunOutSaAhAuthAlgo
					RuijieAuthAlgo,
				ruijieIPSec2TunOutSaEspAuthAlgo
					RuijieAuthAlgo,
				ruijieIPSec2TunMapName
					DisplayString,
				ruijieIPSec2TunSeqNum
					Integer32,
				ruijieIPSec2TunStatus
					RuijieIPSec2TunnelState
			 }

		-- 1.3.6.1.4.1.4881.1.1.10.2.108.1.1.1.1
		ruijieIPSec2TunIfIndex OBJECT-TYPE
			SYNTAX Integer32 (1..2147483647)
			MAX-ACCESS read-only
			STATUS current
			DESCRIPTION
				"The interface index( the ifIndex of ifTable )."
			::= { ruijieIPSec2TunnelEntry 1 }

		
		-- 1.3.6.1.4.1.4881.1.1.10.2.108.1.1.1.2
		ruijieIPSec2TunnelTrafficIndex OBJECT-TYPE
			SYNTAX Integer32
			MAX-ACCESS read-only
			STATUS current
			DESCRIPTION
				"Description."
			::= { ruijieIPSec2TunnelEntry 2 }

		
		-- 1.3.6.1.4.1.4881.1.1.10.2.108.1.1.1.3
		ruijieIPSec2TunIndex OBJECT-TYPE
			SYNTAX Integer32 (1..2147483647)
			MAX-ACCESS read-only
			STATUS current
			DESCRIPTION
				"The index of IPSec Phase-2 Tunnel Table. The value of
				the index is a number which begins at one and is
				incremented with each tunnel that is created. The
				value of this object will wrap at 2,147,483,647."
			::= { ruijieIPSec2TunnelEntry 3 }

		
		-- 1.3.6.1.4.1.4881.1.1.10.2.108.1.1.1.5
		ruijieIPSec2TunIKETunnelIndex OBJECT-TYPE
			SYNTAX Integer32 (1..2147483647)
			MAX-ACCESS read-only
			STATUS current
			DESCRIPTION
				"The index of the associated IPSec Phase-1 IKE Tunnel
				(IKETunIndex in the IKETunnelTable). 2147483647 is defined as
				invalid value. "
			::= { ruijieIPSec2TunnelEntry 5 }

		
		-- 1.3.6.1.4.1.4881.1.1.10.2.108.1.1.1.6
		ruijieIPSec2TunnelAhOutSaIndex OBJECT-TYPE
			SYNTAX Integer32
			MAX-ACCESS read-only
			STATUS current
			DESCRIPTION
				"Description."
			::= { ruijieIPSec2TunnelEntry 6 }

		
		-- 1.3.6.1.4.1.4881.1.1.10.2.108.1.1.1.7
		ruijieIPSec2TunnelAhInSaIndex OBJECT-TYPE
			SYNTAX Integer32 (1..2147483647)
			MAX-ACCESS read-only
			STATUS current
			DESCRIPTION
				"The index of the associated IPSec Phase-1 IKE Tunnel
				(IKETunIndex in the IKETunnelTable). 2147483647 is defined as
				invalid value. "
			::= { ruijieIPSec2TunnelEntry 7 }

		
		-- 1.3.6.1.4.1.4881.1.1.10.2.108.1.1.1.8
		ruijieIPSec2TunnelEspOutSaIndex OBJECT-TYPE
			SYNTAX Integer32 (1..2147483647)
			MAX-ACCESS read-only
			STATUS current
			DESCRIPTION
				"The index of the associated IPSec Phase-1 IKE Tunnel
				(IKETunIndex in the IKETunnelTable). 2147483647 is defined as
				invalid value. "
			::= { ruijieIPSec2TunnelEntry 8 }

		
		-- 1.3.6.1.4.1.4881.1.1.10.2.108.1.1.1.9
		ruijieIPSec2TunnelEspInSaIndex OBJECT-TYPE
			SYNTAX Integer32
			MAX-ACCESS read-only
			STATUS current
			DESCRIPTION
				"Description."
			::= { ruijieIPSec2TunnelEntry 9 }

		
		-- 1.3.6.1.4.1.4881.1.1.10.2.108.1.1.1.10
		ruijieIPSec2TunLocalAddr OBJECT-TYPE
			SYNTAX IpAddress
			MAX-ACCESS read-only
			STATUS current
			DESCRIPTION
				"The IP address of the local peer for the IPSec Phase-2
				Tunnel. 0.0.0.0 is defined as invalid value."
			::= { ruijieIPSec2TunnelEntry 10 }

		
		-- 1.3.6.1.4.1.4881.1.1.10.2.108.1.1.1.11
		ruijieIPSec2TunRemoteAddr OBJECT-TYPE
			SYNTAX IpAddress
			MAX-ACCESS read-only
			STATUS current
			DESCRIPTION
				"The IP address of the remote peer for the IPSec Phase-2
				Tunnel. 0.0.0.0 is defined as invalid value."
			::= { ruijieIPSec2TunnelEntry 11 }

		
		-- 1.3.6.1.4.1.4881.1.1.10.2.108.1.1.1.12
		ruijieIPSec2TunLocalHostname OBJECT-TYPE
			SYNTAX DisplayString
			MAX-ACCESS read-only
			STATUS current
			DESCRIPTION
				"The Hostname of the local peer for the IPSec Phase-2
				Tunnel."
			::= { ruijieIPSec2TunnelEntry 12 }

		
		-- 1.3.6.1.4.1.4881.1.1.10.2.108.1.1.1.13
		ruijieIPSec2TunRemoteHostname OBJECT-TYPE
			SYNTAX DisplayString
			MAX-ACCESS read-only
			STATUS current
			DESCRIPTION
				"The Hostname of the remote peer for the IPSec Phase-2
				Tunnel. "
			::= { ruijieIPSec2TunnelEntry 13 }

		
		-- 1.3.6.1.4.1.4881.1.1.10.2.108.1.1.1.14
		ruijieIPSec2TunKeyType OBJECT-TYPE
			SYNTAX RuijieIPSec2NegoType
			MAX-ACCESS read-only
			STATUS current
			DESCRIPTION
				"The key negotiate mode used by the IPSec Phase-2 Tunnel."
			::= { ruijieIPSec2TunnelEntry 14 }

		
		-- 1.3.6.1.4.1.4881.1.1.10.2.108.1.1.1.15
		ruijieIPSec2TunEncapMode OBJECT-TYPE
			SYNTAX RuijieEncapMode
			MAX-ACCESS read-only
			STATUS current
			DESCRIPTION
				"The encapsulation mode used by the IPSec Phase-2 Tunnel."
			::= { ruijieIPSec2TunnelEntry 15 }

		
		-- 1.3.6.1.4.1.4881.1.1.10.2.108.1.1.1.16
		ruijieIPSec2TunInitiator OBJECT-TYPE
			SYNTAX INTEGER
				{
				local(1),
				remote(2),
				none(2147483647)
				}
			MAX-ACCESS read-only
			STATUS current
			DESCRIPTION
				"The initiator of this IPSec tunnel. Value none is used for manual
				IPsec tunnel, for there is no initiator or responder in this method."
			::= { ruijieIPSec2TunnelEntry 16 }

		
		-- 1.3.6.1.4.1.4881.1.1.10.2.108.1.1.1.17
		ruijieIPSec2TunLifeSize OBJECT-TYPE
			SYNTAX Integer32 (1..2147483647)
			MAX-ACCESS read-only
			STATUS current
			DESCRIPTION
				"The negotiated LifeSize of the IPSec Phase-2 Tunnel in kilobytes.
				2147483647 is defined as invalid value."
			::= { ruijieIPSec2TunnelEntry 17 }

		
		-- 1.3.6.1.4.1.4881.1.1.10.2.108.1.1.1.18
		ruijieIPSec2TunLifeTime OBJECT-TYPE
			SYNTAX Integer32 (1..2147483647)
			MAX-ACCESS read-only
			STATUS current
			DESCRIPTION
				"The negotiated LifeTime of the IPSec Phase-2 Tunnel in seconds.
				2147483647 is defined as invalid value."
			::= { ruijieIPSec2TunnelEntry 18 }

		
		-- 1.3.6.1.4.1.4881.1.1.10.2.108.1.1.1.19
		ruijieIPSec2TunRemainTime OBJECT-TYPE
			SYNTAX Integer32 (0..2147483647)
			MAX-ACCESS read-only
			STATUS current
			DESCRIPTION
				"The remain time of SA in seconds. 2147483647 is defined as invalid
				value."
			::= { ruijieIPSec2TunnelEntry 19 }

		
		-- 1.3.6.1.4.1.4881.1.1.10.2.108.1.1.1.20
		ruijieIPSec2TunActiveTime OBJECT-TYPE
			SYNTAX Integer32 (0..2147483647)
			MAX-ACCESS read-only
			STATUS current
			DESCRIPTION
				"The duration the IPSec Phase-2 Tunnel has been active in
				hundredths of seconds. 2147483647 is defined as invalid value."
			::= { ruijieIPSec2TunnelEntry 20 }

		
		-- 1.3.6.1.4.1.4881.1.1.10.2.108.1.1.1.21
		ruijieIPSec2TunCreateTime OBJECT-TYPE
			SYNTAX TimeStamp
			MAX-ACCESS read-only
			STATUS current
			DESCRIPTION
				"The Time Stamp when the IPSec Phase-2 Tunnel created."
			::= { ruijieIPSec2TunnelEntry 21 }

		
		-- 1.3.6.1.4.1.4881.1.1.10.2.108.1.1.1.23
		ruijieIPSec2TunRemainSize OBJECT-TYPE
			SYNTAX Integer32 (0..2147483647)
			MAX-ACCESS read-only
			STATUS current
			DESCRIPTION
				"The remain LifeSize of SA in kilobytes. 2147483647 is defined as
				invalid value."
			::= { ruijieIPSec2TunnelEntry 23 }

		
		-- 1.3.6.1.4.1.4881.1.1.10.2.108.1.1.1.24
		ruijieIPSec2TunTotalRefreshes OBJECT-TYPE
			SYNTAX Counter32
			MAX-ACCESS read-only
			STATUS current
			DESCRIPTION
				"The total number of security association refreshing performed."
			::= { ruijieIPSec2TunnelEntry 24 }

		
		-- 1.3.6.1.4.1.4881.1.1.10.2.108.1.1.1.25
		ruijieIPSec2TunCurrentSaInstances OBJECT-TYPE
			SYNTAX Gauge32
			MAX-ACCESS read-only
			STATUS current
			DESCRIPTION
				"The number of security associations which are currently active
				or expiring."
			::= { ruijieIPSec2TunnelEntry 25 }

		
		-- 1.3.6.1.4.1.4881.1.1.10.2.108.1.1.1.26
		ruijieIPSec2TunInSaEncryptAlgo OBJECT-TYPE
			SYNTAX RuijieEncryptAlgo
			MAX-ACCESS read-only
			STATUS current
			DESCRIPTION
				"The encryption algorithm used by the inbound security association
				of the IPSec Phase-2 Tunnel."
			::= { ruijieIPSec2TunnelEntry 26 }

		
		-- 1.3.6.1.4.1.4881.1.1.10.2.108.1.1.1.27
		ruijieIPSec2TunInSaAhAuthAlgo OBJECT-TYPE
			SYNTAX RuijieAuthAlgo
			MAX-ACCESS read-only
			STATUS current
			DESCRIPTION
				"The authentication algorithm used by the inbound authentication
				header (AH) security association of the IPSec Phase-2 Tunnel."
			::= { ruijieIPSec2TunnelEntry 27 }

		
		-- 1.3.6.1.4.1.4881.1.1.10.2.108.1.1.1.28
		ruijieIPSec2TunInSaEspAuthAlgo OBJECT-TYPE
			SYNTAX RuijieAuthAlgo
			MAX-ACCESS read-only
			STATUS current
			DESCRIPTION
				"The authentication algorithm used by the inbound encapsulation
				security protocol(ESP) security association of the IPSec
				Phase-2 Tunnel."
			::= { ruijieIPSec2TunnelEntry 28 }

		
		-- 1.3.6.1.4.1.4881.1.1.10.2.108.1.1.1.29
		ruijieIPSec2TunDiffHellmanGrp OBJECT-TYPE
			SYNTAX RuijieDiffHellmanGrp
			MAX-ACCESS read-only
			STATUS current
			DESCRIPTION
				"The Diffie Hellman Group used by the security association of the
				IPSec Phase-2 Tunnel."
			::= { ruijieIPSec2TunnelEntry 29 }

		
		-- 1.3.6.1.4.1.4881.1.1.10.2.108.1.1.1.30
		ruijieIPSec2TunOutSaEncryptAlgo OBJECT-TYPE
			SYNTAX RuijieEncryptAlgo
			MAX-ACCESS read-only
			STATUS current
			DESCRIPTION
				"The encryption algorithm used by the outbound security
				association of the IPSec Phase-2 Tunnel."
			::= { ruijieIPSec2TunnelEntry 30 }

		
		-- 1.3.6.1.4.1.4881.1.1.10.2.108.1.1.1.31
		ruijieIPSec2TunOutSaAhAuthAlgo OBJECT-TYPE
			SYNTAX RuijieAuthAlgo
			MAX-ACCESS read-only
			STATUS current
			DESCRIPTION
				"The authentication algorithm used by the outbound
				authentication header (AH) security association of
				the IPSec Phase-2 Tunnel."
			::= { ruijieIPSec2TunnelEntry 31 }

		
		-- 1.3.6.1.4.1.4881.1.1.10.2.108.1.1.1.32
		ruijieIPSec2TunOutSaEspAuthAlgo OBJECT-TYPE
			SYNTAX RuijieAuthAlgo
			MAX-ACCESS read-only
			STATUS current
			DESCRIPTION
				"The authentication algorithm used by the outbound encapsulation
				security protocol(ESP) security association of the IPSec
				Phase-2 Tunnel."
			::= { ruijieIPSec2TunnelEntry 32 }

		
		-- 1.3.6.1.4.1.4881.1.1.10.2.108.1.1.1.33
		ruijieIPSec2TunMapName OBJECT-TYPE
			SYNTAX DisplayString
			MAX-ACCESS read-only
			STATUS current
			DESCRIPTION
				"The Map name used by this IPSec tunnel."
			::= { ruijieIPSec2TunnelEntry 33 }

		
		-- 1.3.6.1.4.1.4881.1.1.10.2.108.1.1.1.34
		ruijieIPSec2TunSeqNum OBJECT-TYPE
			SYNTAX Integer32 (1..2147483647)
			MAX-ACCESS read-only
			STATUS current
			DESCRIPTION
				"The sequence number of policy used by this IPSec tunnel."
			::= { ruijieIPSec2TunnelEntry 34 }

		
		-- 1.3.6.1.4.1.4881.1.1.10.2.108.1.1.1.35
		ruijieIPSec2TunStatus OBJECT-TYPE
			SYNTAX RuijieIPSec2TunnelState
			MAX-ACCESS read-write
			STATUS current
			DESCRIPTION
				"The status of the IPSec Tunnel."
			::= { ruijieIPSec2TunnelEntry 35 }

		
		-- 1.3.6.1.4.1.4881.1.1.10.2.108.1.2
		ruijieIPSec2TunnelStatTable OBJECT-TYPE
			SYNTAX SEQUENCE OF RuijieIPSec2TunnelStatEntry
			MAX-ACCESS not-accessible
			STATUS current
			DESCRIPTION
				"The IPSec Phase-2 Tunnel Statistics Table. "
			::= { ruijieIPSec2Objects 2 }

		
		-- 1.3.6.1.4.1.4881.1.1.10.2.108.1.2.1
		ruijieIPSec2TunnelStatEntry OBJECT-TYPE
			SYNTAX RuijieIPSec2TunnelStatEntry
			MAX-ACCESS not-accessible
			STATUS current
			DESCRIPTION
				"Information about RuijieIPSec2TunnelStatTable."
			INDEX { ruijieIPSec2TunIndex }
			::= { ruijieIPSec2TunnelStatTable 1 }

		
		RuijieIPSec2TunnelStatEntry ::=
			SEQUENCE { 
				ruijieIPSec2TunInOctets
					Counter64,
				ruijieIPSec2TunInDecompOctets
					Counter64,
				ruijieIPSec2TunInPkts
					Counter64,
				ruijieIPSec2TunInSpeed
					Counter64,
				ruijieIPSec2TunInDropPkts
					Counter64,
				ruijieIPSec2TunOutOctets
					Counter64,
				ruijieIPSec2TunOutUncompOctets
					Counter64,
				ruijieIPSec2TunOutPkts
					Counter64,
				ruijieIPSec2TunOutSpeed
					Counter64,
				ruijieIPSec2TunOutDropPkts
					Counter64
			 }

		-- 1.3.6.1.4.1.4881.1.1.10.2.108.1.2.1.1
		ruijieIPSec2TunInOctets OBJECT-TYPE
			SYNTAX Counter64
			MAX-ACCESS read-only
			STATUS current
			DESCRIPTION
				"The total number of octets received by this IPSec Phase-2 Tunnel.
				This value is accumulated BEFORE determining whether or not the
				packet should be decompressed."
			::= { ruijieIPSec2TunnelStatEntry 1 }

		
		-- 1.3.6.1.4.1.4881.1.1.10.2.108.1.2.1.2
		ruijieIPSec2TunInDecompOctets OBJECT-TYPE
			SYNTAX Counter64
			MAX-ACCESS read-only
			STATUS current
			DESCRIPTION
				"The total number of decompressed octets received by this IPSec
				Phase-2 Tunnel. This value is accumulated AFTER the packet
				is decompressed."
			::= { ruijieIPSec2TunnelStatEntry 2 }

		
		-- 1.3.6.1.4.1.4881.1.1.10.2.108.1.2.1.3
		ruijieIPSec2TunInPkts OBJECT-TYPE
			SYNTAX Counter64
			MAX-ACCESS read-only
			STATUS current
			DESCRIPTION
				"The total number of packets received by this IPSec Phase-2 Tunnel."
			::= { ruijieIPSec2TunnelStatEntry 3 }

		
		-- 1.3.6.1.4.1.4881.1.1.10.2.108.1.2.1.4
		ruijieIPSec2TunInSpeed OBJECT-TYPE
			SYNTAX Counter64
			MAX-ACCESS read-only
			STATUS current
			DESCRIPTION
				"The Speed(bps) of packets received by this IPSec Phase-2 Tunnel."
			::= { ruijieIPSec2TunnelStatEntry 4 }

		
		-- 1.3.6.1.4.1.4881.1.1.10.2.108.1.2.1.5
		ruijieIPSec2TunInDropPkts OBJECT-TYPE
			SYNTAX Counter64
			MAX-ACCESS read-only
			STATUS current
			DESCRIPTION
				"The total number of packets dropped during receiving process
				by this IPSec Phase-2 Tunnel."
			::= { ruijieIPSec2TunnelStatEntry 5 }

		
		-- 1.3.6.1.4.1.4881.1.1.10.2.108.1.2.1.6
		ruijieIPSec2TunOutOctets OBJECT-TYPE
			SYNTAX Counter64
			MAX-ACCESS read-only
			STATUS current
			DESCRIPTION
				"The total number of octets sent by this IPSec Phase-2 Tunnel.
				This value is accumulated AFTER determining whether or not
				the packet should be compressed."
			::= { ruijieIPSec2TunnelStatEntry 6 }

		
		-- 1.3.6.1.4.1.4881.1.1.10.2.108.1.2.1.7
		ruijieIPSec2TunOutUncompOctets OBJECT-TYPE
			SYNTAX Counter64
			MAX-ACCESS read-only
			STATUS current
			DESCRIPTION
				"The total number of uncompressed octets sent by this IPSec Phase-2
				Tunnel.This value is accumulated BEFORE the packet is compressed."
			::= { ruijieIPSec2TunnelStatEntry 7 }

		
		-- 1.3.6.1.4.1.4881.1.1.10.2.108.1.2.1.8
		ruijieIPSec2TunOutPkts OBJECT-TYPE
			SYNTAX Counter64
			MAX-ACCESS read-only
			STATUS current
			DESCRIPTION
				"The total number of packets sent by this IPSec Phase-2 Tunnel."
			::= { ruijieIPSec2TunnelStatEntry 8 }

		
		-- 1.3.6.1.4.1.4881.1.1.10.2.108.1.2.1.9
		ruijieIPSec2TunOutSpeed OBJECT-TYPE
			SYNTAX Counter64
			MAX-ACCESS read-only
			STATUS current
			DESCRIPTION
				"The Speed(bps) of packets sent by this IPSec Phase-2 Tunnel. "
			::= { ruijieIPSec2TunnelStatEntry 9 }

		
		-- 1.3.6.1.4.1.4881.1.1.10.2.108.1.2.1.10
		ruijieIPSec2TunOutDropPkts OBJECT-TYPE
			SYNTAX Counter64
			MAX-ACCESS read-only
			STATUS current
			DESCRIPTION
				"The total number of packets dropped during sending process
				by this IPSec Phase-2 Tunnel."
			::= { ruijieIPSec2TunnelStatEntry 10 }

		
		-- 1.3.6.1.4.1.4881.1.1.10.2.108.1.3
		ruijieIPSec2SaTable OBJECT-TYPE
			SYNTAX SEQUENCE OF RuijieIPSec2SaEntry
			MAX-ACCESS not-accessible
			STATUS current
			DESCRIPTION
				"The IPSec Phase-2 Security Protection Index Table.  This table
				contains an entry for each active and expiring security association."
			::= { ruijieIPSec2Objects 3 }

		
		-- 1.3.6.1.4.1.4881.1.1.10.2.108.1.3.1
		ruijieIPSec2SaEntry OBJECT-TYPE
			SYNTAX RuijieIPSec2SaEntry
			MAX-ACCESS not-accessible
			STATUS current
			DESCRIPTION
				"Information about RuijieIPSec2SaTable."
			INDEX { ruijieIPSec2SaIndex }
			::= { ruijieIPSec2SaTable 1 }

		
		RuijieIPSec2SaEntry ::=
			SEQUENCE { 
				ruijieIPSec2SaIndex
					Integer32,
				ruijieIPSec2SaDirection
					INTEGER,
				ruijieIPSec2SaValue
					Unsigned32,
				ruijieIPSec2SaProtocol
					RuijieSaProtocol,
				ruijieIPSec2SaEncryptAlgo
					RuijieEncryptAlgo,
				ruijieIPSec2SaAuthAlgo
					RuijieAuthAlgo,
				ruijieIPSec2SaStatus
					RuijieIPSec2TunnelState
			 }

		-- 1.3.6.1.4.1.4881.1.1.10.2.108.1.3.1.1
		ruijieIPSec2SaIndex OBJECT-TYPE
			SYNTAX Integer32 (1..2147483647)
			MAX-ACCESS read-only
			STATUS current
			DESCRIPTION
				"The number of the Sa associated with the Phase-2 Tunnel
				Table.  The value of this index is a number which begins
				at one and is incremented with each Sa associated with
				an IPSec Phase-2 Tunnel.  The value of this object will
				wrap at 2,147,483,647."
			::= { ruijieIPSec2SaEntry 1 }

		
		-- 1.3.6.1.4.1.4881.1.1.10.2.108.1.3.1.2
		ruijieIPSec2SaDirection OBJECT-TYPE
			SYNTAX INTEGER
				{
				in(1),
				out(2)
				}
			MAX-ACCESS read-only
			STATUS current
			DESCRIPTION
				"The direction of the SA."
			::= { ruijieIPSec2SaEntry 2 }

		
		-- 1.3.6.1.4.1.4881.1.1.10.2.108.1.3.1.3
		ruijieIPSec2SaValue OBJECT-TYPE
			SYNTAX Unsigned32 (1..4294967295)
			MAX-ACCESS read-only
			STATUS current
			DESCRIPTION
				"The value of the SPI."
			::= { ruijieIPSec2SaEntry 3 }

		
		-- 1.3.6.1.4.1.4881.1.1.10.2.108.1.3.1.4
		ruijieIPSec2SaProtocol OBJECT-TYPE
			SYNTAX RuijieSaProtocol
			MAX-ACCESS read-only
			STATUS current
			DESCRIPTION
				"The security protocol of the SA."
			::= { ruijieIPSec2SaEntry 4 }

		
		-- 1.3.6.1.4.1.4881.1.1.10.2.108.1.3.1.5
		ruijieIPSec2SaEncryptAlgo OBJECT-TYPE
			SYNTAX RuijieEncryptAlgo
			MAX-ACCESS read-only
			STATUS current
			DESCRIPTION
				"The encryption algorithm used by the security association
				of the IPSec Phase-2 Tunnel."
			::= { ruijieIPSec2SaEntry 5 }

		
		-- 1.3.6.1.4.1.4881.1.1.10.2.108.1.3.1.6
		ruijieIPSec2SaAuthAlgo OBJECT-TYPE
			SYNTAX RuijieAuthAlgo
			MAX-ACCESS read-only
			STATUS current
			DESCRIPTION
				"The authentication algorithm used by the SA."
			::= { ruijieIPSec2SaEntry 6 }

		
		-- 1.3.6.1.4.1.4881.1.1.10.2.108.1.3.1.7
		ruijieIPSec2SaStatus OBJECT-TYPE
			SYNTAX RuijieIPSec2TunnelState
			MAX-ACCESS read-only
			STATUS current
			DESCRIPTION
				"The status of the SA."
			::= { ruijieIPSec2SaEntry 7 }

		
		-- 1.3.6.1.4.1.4881.1.1.10.2.108.1.4
		ruijieIPSec2TrafficTable OBJECT-TYPE
			SYNTAX SEQUENCE OF RuijieIPSec2TrafficEntry
			MAX-ACCESS not-accessible
			STATUS current
			DESCRIPTION
				"The IPSec Phase-2 Tunnel Traffic Table. "
			::= { ruijieIPSec2Objects 4 }

		
		-- 1.3.6.1.4.1.4881.1.1.10.2.108.1.4.1
		ruijieIPSec2TrafficEntry OBJECT-TYPE
			SYNTAX RuijieIPSec2TrafficEntry
			MAX-ACCESS not-accessible
			STATUS current
			DESCRIPTION
				"Information about RuijieIPSec2TrafficTable."
			INDEX { ruijieIPSec2TunnelTrafficIndex }
			::= { ruijieIPSec2TrafficTable 1 }

		
		RuijieIPSec2TrafficEntry ::=
			SEQUENCE { 
				ruijieIPSec2TrafficIndex
					Integer32,
				ruijieIPSec2TrafficLocalType
					RuijieTrafficType,
				ruijieIPSec2TrafficLocalAddr1
					IpAddress,
				ruijieIPSec2TrafficLocalAddr2
					IpAddress,
				ruijieIPSec2TrafficLocalProtocol
					Integer32,
				ruijieIPSec2TrafficLocalPort
					Integer32,
				ruijieIPSec2TrafficLocalHostname
					DisplayString,
				ruijieIPSec2TrafficRemoteType
					RuijieTrafficType,
				ruijieIPSec2TrafficRemoteAddr1
					IpAddress,
				ruijieIPSec2TrafficRemoteAddr2
					IpAddress,
				ruijieIPSec2TrafficRemoteProtocol
					Integer32,
				ruijieIPSec2TrafficRemotePort
					Integer32,
				ruijieIPSec2TrafficRemoteHostname
					DisplayString
			 }

		-- 1.3.6.1.4.1.4881.1.1.10.2.108.1.4.1.1
		ruijieIPSec2TrafficIndex OBJECT-TYPE
			SYNTAX Integer32
			MAX-ACCESS read-only
			STATUS current
			DESCRIPTION
				"Description."
			::= { ruijieIPSec2TrafficEntry 1 }

		
		-- 1.3.6.1.4.1.4881.1.1.10.2.108.1.4.1.2
		ruijieIPSec2TrafficLocalType OBJECT-TYPE
			SYNTAX RuijieTrafficType
			MAX-ACCESS read-only
			STATUS current
			DESCRIPTION
				"The type of local peer. Possible values are: a single
				IP address, or an IP address range, or an IP subnet."
			::= { ruijieIPSec2TrafficEntry 2 }

		
		-- 1.3.6.1.4.1.4881.1.1.10.2.108.1.4.1.3
		ruijieIPSec2TrafficLocalAddr1 OBJECT-TYPE
			SYNTAX IpAddress
			MAX-ACCESS read-only
			STATUS current
			DESCRIPTION
				"The first specification of local peer's IP address. If
				the local peer type is single IP address, then this is the
				value of the IP address. If the local peer type is IP subnet,
				then this is the value of the subnet. If the local peer type
				is IP address range, then this is the value of beginning IP
				address of the range."
			::= { ruijieIPSec2TrafficEntry 3 }

		
		-- 1.3.6.1.4.1.4881.1.1.10.2.108.1.4.1.4
		ruijieIPSec2TrafficLocalAddr2 OBJECT-TYPE
			SYNTAX IpAddress
			MAX-ACCESS read-only
			STATUS current
			DESCRIPTION
				"The second specification of local peer's IP address. If the local
				peer type is single IP address, then this is the value of the
				IP address. If the local peer type is IP subnet, then this is
				the value of the subnet mask. If the local peer type is IP
				address range, then this is the value of ending IP address of
				the range."
			::= { ruijieIPSec2TrafficEntry 4 }

		
		-- 1.3.6.1.4.1.4881.1.1.10.2.108.1.4.1.5
		ruijieIPSec2TrafficLocalProtocol OBJECT-TYPE
			SYNTAX Integer32 (0..255)
			MAX-ACCESS read-only
			STATUS current
			DESCRIPTION
				"The protocol number of the local peer's traffic."
			::= { ruijieIPSec2TrafficEntry 5 }

		
		-- 1.3.6.1.4.1.4881.1.1.10.2.108.1.4.1.6
		ruijieIPSec2TrafficLocalPort OBJECT-TYPE
			SYNTAX Integer32 (0..65535)
			MAX-ACCESS read-only
			STATUS current
			DESCRIPTION
				"The port number of the local peer's traffic."
			::= { ruijieIPSec2TrafficEntry 6 }

		
		-- 1.3.6.1.4.1.4881.1.1.10.2.108.1.4.1.7
		ruijieIPSec2TrafficLocalHostname OBJECT-TYPE
			SYNTAX DisplayString
			MAX-ACCESS read-only
			STATUS current
			DESCRIPTION
				"The Hostname of local peer's IP address."
			::= { ruijieIPSec2TrafficEntry 7 }

		
		-- 1.3.6.1.4.1.4881.1.1.10.2.108.1.4.1.8
		ruijieIPSec2TrafficRemoteType OBJECT-TYPE
			SYNTAX RuijieTrafficType
			MAX-ACCESS read-only
			STATUS current
			DESCRIPTION
				"The type of remote peer. Possible values are: a single
				IP address, or an IP address range, or an IP subnet."
			::= { ruijieIPSec2TrafficEntry 8 }

		
		-- 1.3.6.1.4.1.4881.1.1.10.2.108.1.4.1.9
		ruijieIPSec2TrafficRemoteAddr1 OBJECT-TYPE
			SYNTAX IpAddress
			MAX-ACCESS read-only
			STATUS current
			DESCRIPTION
				"The first specification of remote peer's IP address.
				If the remote peer type is single IP address, then
				this is the value of the IP address. If the remote
				peer type is IP subnet, then this is the value
				of the subnet. If the remote peer type is IP
				address range, then this is the value of beginning
				IP address of the range."
			::= { ruijieIPSec2TrafficEntry 9 }

		
		-- 1.3.6.1.4.1.4881.1.1.10.2.108.1.4.1.10
		ruijieIPSec2TrafficRemoteAddr2 OBJECT-TYPE
			SYNTAX IpAddress
			MAX-ACCESS read-only
			STATUS current
			DESCRIPTION
				"Single IP address, then this is the value of the IP
				address. If the remote peer type is IP subnet,
				then this is the value of the subnet mask. If the
				remote peer type is IP address range, then this
				is the value of ending IP address of the range."
			::= { ruijieIPSec2TrafficEntry 10 }

		
		-- 1.3.6.1.4.1.4881.1.1.10.2.108.1.4.1.11
		ruijieIPSec2TrafficRemoteProtocol OBJECT-TYPE
			SYNTAX Integer32 (0..255)
			MAX-ACCESS read-only
			STATUS current
			DESCRIPTION
				"The protocol number of the remote peer's traffic."
			::= { ruijieIPSec2TrafficEntry 11 }

		
		-- 1.3.6.1.4.1.4881.1.1.10.2.108.1.4.1.12
		ruijieIPSec2TrafficRemotePort OBJECT-TYPE
			SYNTAX Integer32 (0..65535)
			MAX-ACCESS read-only
			STATUS current
			DESCRIPTION
				"The port number of the remote peer's traffic."
			::= { ruijieIPSec2TrafficEntry 12 }

		
		-- 1.3.6.1.4.1.4881.1.1.10.2.108.1.4.1.13
		ruijieIPSec2TrafficRemoteHostname OBJECT-TYPE
			SYNTAX DisplayString
			MAX-ACCESS read-only
			STATUS current
			DESCRIPTION
				"The Hostname of remote peer's IP address."
			::= { ruijieIPSec2TrafficEntry 13 }

		
		-- 1.3.6.1.4.1.4881.1.1.10.2.108.1.5
		ruijieIPSec2GlobalStats OBJECT IDENTIFIER ::= { ruijieIPSec2Objects 5 }

		
		-- 1.3.6.1.4.1.4881.1.1.10.2.108.1.5.1
		ruijieIPSec2GlobalActiveTunnels OBJECT-TYPE
			SYNTAX Gauge32
			MAX-ACCESS read-only
			STATUS current
			DESCRIPTION
				"The total number of currently active  IPSec Phase-2 Tunnels."
			::= { ruijieIPSec2GlobalStats 1 }

		
		-- 1.3.6.1.4.1.4881.1.1.10.2.108.1.5.2
		ruijieIPSec2GlobalActiveSas OBJECT-TYPE
			SYNTAX Gauge32
			MAX-ACCESS read-only
			STATUS current
			DESCRIPTION
				"The total number of currently active or expiring IPSec Phase-2 SA."
			::= { ruijieIPSec2GlobalStats 2 }

		
		-- 1.3.6.1.4.1.4881.1.1.10.2.108.1.5.3
		ruijieIPSec2GlobalInOctets OBJECT-TYPE
			SYNTAX Counter64
			MAX-ACCESS read-only
			STATUS current
			DESCRIPTION
				"The total number of octets received by all current and previous
				IPSec Phase-2 Tunnels. This value is accumulated BEFORE determining
				whether or not the packet should be decompressed."
			::= { ruijieIPSec2GlobalStats 3 }

		
		-- 1.3.6.1.4.1.4881.1.1.10.2.108.1.5.4
		ruijieIPSec2GlobalInPkts OBJECT-TYPE
			SYNTAX Counter64
			MAX-ACCESS read-only
			STATUS current
			DESCRIPTION
				"The total number of packets received by all current and
				previous IPSec Phase-2 Tunnels."
			::= { ruijieIPSec2GlobalStats 4 }

		
		-- 1.3.6.1.4.1.4881.1.1.10.2.108.1.5.5
		ruijieIPSec2GlobalInSpeed OBJECT-TYPE
			SYNTAX Counter64
			MAX-ACCESS read-only
			STATUS current
			DESCRIPTION
				"The total speed(bps) of packets received by all current and
				previous IPSec Phase-2 Tunnels."
			::= { ruijieIPSec2GlobalStats 5 }

		
		-- 1.3.6.1.4.1.4881.1.1.10.2.108.1.5.6
		ruijieIPSec2GlobalInDrops OBJECT-TYPE
			SYNTAX Counter64
			MAX-ACCESS read-only
			STATUS current
			DESCRIPTION
				"The total number of packets dropped during receiving
				process by all current and previous IPSec Phase-2
				Tunnels. "
			::= { ruijieIPSec2GlobalStats 6 }

		
		-- 1.3.6.1.4.1.4881.1.1.10.2.108.1.5.7
		ruijieIPSec2GlobalOutOctets OBJECT-TYPE
			SYNTAX Counter64
			MAX-ACCESS read-only
			STATUS current
			DESCRIPTION
				"The total number of octets sent by all current and previous
				IPSec Phase-2 Tunnels. This value is accumulated AFTER
				determining whether or not the packet should be compressed."
			::= { ruijieIPSec2GlobalStats 7 }

		
		-- 1.3.6.1.4.1.4881.1.1.10.2.108.1.5.8
		ruijieIPSec2GlobalOutPkts OBJECT-TYPE
			SYNTAX Counter64
			MAX-ACCESS read-only
			STATUS current
			DESCRIPTION
				"The total number of packets sent by all current and previous
				IPSec Phase-2 Tunnels."
			::= { ruijieIPSec2GlobalStats 8 }

		
		-- 1.3.6.1.4.1.4881.1.1.10.2.108.1.5.9
		ruijieIPSec2GlobalOutSpeed OBJECT-TYPE
			SYNTAX Counter64
			MAX-ACCESS read-only
			STATUS current
			DESCRIPTION
				"The total speed(bps) of packets sent by all current and previous
				IPSec Phase-2 Tunnels."
			::= { ruijieIPSec2GlobalStats 9 }

		
		-- 1.3.6.1.4.1.4881.1.1.10.2.108.1.5.10
		ruijieIPSec2GlobalOutDrops OBJECT-TYPE
			SYNTAX Counter64
			MAX-ACCESS read-only
			STATUS current
			DESCRIPTION
				"The total number of packets dropped during sending process
				by all current and previous IPSec Phase-2 Tunnels."
			::= { ruijieIPSec2GlobalStats 10 }

		
		-- 1.3.6.1.4.1.4881.1.1.10.2.108.1.6
		ruijieIPSec2TrapObject OBJECT IDENTIFIER ::= { ruijieIPSec2Objects 6 }

		
		-- 1.3.6.1.4.1.4881.1.1.10.2.108.1.6.1
		ruijieIPSec2MapName OBJECT-TYPE
			SYNTAX DisplayString
			MAX-ACCESS accessible-for-notify
			STATUS current
			DESCRIPTION
				"The IPSec map name with a trap."
			::= { ruijieIPSec2TrapObject 1 }

		
		-- 1.3.6.1.4.1.4881.1.1.10.2.108.1.6.2
		ruijieIPSec2SeqNum OBJECT-TYPE
			SYNTAX Integer32
			MAX-ACCESS accessible-for-notify
			STATUS current
			DESCRIPTION
				"The IPSec map sequence number with a trap."
			::= { ruijieIPSec2TrapObject 2 }

		
		-- 1.3.6.1.4.1.4881.1.1.10.2.108.1.6.3
		ruijieIPSec2SpiValue OBJECT-TYPE
			SYNTAX Integer32
			MAX-ACCESS accessible-for-notify
			STATUS current
			DESCRIPTION
				"The SPI value associated with a trap."
			::= { ruijieIPSec2TrapObject 3 }

		
		-- 1.3.6.1.4.1.4881.1.1.10.2.108.1.7
		ruijieIPSec2Trap OBJECT IDENTIFIER ::= { ruijieIPSec2Objects 7 }

		
		-- 1.3.6.1.4.1.4881.1.1.10.2.108.1.7.1
		ruijieIPSec2Notifications OBJECT IDENTIFIER ::= { ruijieIPSec2Trap 1 }

		
		-- 1.3.6.1.4.1.4881.1.1.10.2.108.1.7.1.1
		ruijieIPSec2TunnelStart NOTIFICATION-TYPE
			OBJECTS { ruijieIPSec2TunIfIndex, ruijieIPSec2TunRemoteAddr, ruijieIPSec2TrafficLocalType, ruijieIPSec2TrafficLocalAddr1, ruijieIPSec2TrafficLocalAddr2, 
				ruijieIPSec2TrafficLocalProtocol, ruijieIPSec2TrafficLocalPort, ruijieIPSec2TrafficRemoteAddr1, ruijieIPSec2TrafficRemoteAddr2, ruijieIPSec2TrafficRemotePort
				 }
			STATUS current
			DESCRIPTION 
				"This notification is generated when an IPSec Phase-2
				Tunnel is created."
			::= { ruijieIPSec2Notifications 1 }

		
		-- 1.3.6.1.4.1.4881.1.1.10.2.108.1.7.1.2
		ruijieIPSec2TunnelStop NOTIFICATION-TYPE
			OBJECTS { ruijieIPSec2TunIfIndex, ruijieIPSec2TunRemoteAddr, ruijieIPSec2TrafficLocalType, ruijieIPSec2TrafficLocalAddr1, ruijieIPSec2TrafficLocalAddr2, 
				ruijieIPSec2TrafficLocalProtocol, ruijieIPSec2TrafficLocalPort, ruijieIPSec2TrafficRemoteAddr1, ruijieIPSec2TrafficRemoteAddr2, ruijieIPSec2TrafficRemotePort
				 }
			STATUS current
			DESCRIPTION 
				"This notification is generated when an IPSec Phase-2
				Tunnel is deleted."
			::= { ruijieIPSec2Notifications 2 }

		
		-- 1.3.6.1.4.1.4881.1.1.10.2.108.2
		ruijieIPSec2Conformance OBJECT IDENTIFIER ::= { ruijieIPSec2MibModule 2 }

		
		-- 1.3.6.1.4.1.4881.1.1.10.2.108.2.1
		ruijieIPSec2Compliances OBJECT IDENTIFIER ::= { ruijieIPSec2Conformance 1 }

		
		-- 1.3.6.1.4.1.4881.1.1.10.2.108.2.1.1
		ruijieIPSec2Compliance MODULE-COMPLIANCE
			STATUS current
			DESCRIPTION 
				" "
			MODULE -- this module
				MANDATORY-GROUPS { ruijieIPSec2TunnelTableGroup, ruijieIPSec2TunnelStatGroup, ruijieIPSec2SaGroup, ruijieIPSec2TrafficTableGroup, ruijieIPSec2GlobalStatsGroup, 
					ruijieIPSec2TrapObjectGroup, ruijieIPSec2TrapGroup }
			::= { ruijieIPSec2Compliances 1 }

		
		-- 1.3.6.1.4.1.4881.1.1.10.2.108.2.2
		ruijieIPSec2Groups OBJECT IDENTIFIER ::= { ruijieIPSec2Conformance 2 }

		
		-- 1.3.6.1.4.1.4881.1.1.10.2.108.2.2.1
		ruijieIPSec2TunnelTableGroup OBJECT-GROUP
			OBJECTS { ruijieIPSec2TunIfIndex, ruijieIPSec2TunLocalAddr, ruijieIPSec2TunRemoteAddr, ruijieIPSec2TunLocalHostname, ruijieIPSec2TunRemoteHostname, 
				ruijieIPSec2TunKeyType, ruijieIPSec2TunEncapMode, ruijieIPSec2TunInitiator, ruijieIPSec2TunLifeSize, ruijieIPSec2TunLifeTime, 
				ruijieIPSec2TunRemainTime, ruijieIPSec2TunActiveTime, ruijieIPSec2TunCreateTime, ruijieIPSec2TunRemainSize, ruijieIPSec2TunTotalRefreshes, 
				ruijieIPSec2TunCurrentSaInstances, ruijieIPSec2TunInSaEncryptAlgo, ruijieIPSec2TunInSaAhAuthAlgo, ruijieIPSec2TunInSaEspAuthAlgo, ruijieIPSec2TunDiffHellmanGrp, 
				ruijieIPSec2TunOutSaEncryptAlgo, ruijieIPSec2TunOutSaAhAuthAlgo, ruijieIPSec2TunOutSaEspAuthAlgo, ruijieIPSec2TunMapName, ruijieIPSec2TunSeqNum, 
				ruijieIPSec2TunStatus, ruijieIPSec2TunInOctets, ruijieIPSec2TunInDecompOctets, ruijieIPSec2TunInPkts, ruijieIPSec2TunInSpeed, 
				ruijieIPSec2TunInDropPkts, ruijieIPSec2TunOutOctets, ruijieIPSec2TunOutUncompOctets, ruijieIPSec2TunOutPkts, ruijieIPSec2TunOutSpeed, 
				ruijieIPSec2TunOutDropPkts }
			STATUS current
			DESCRIPTION 
				"The group contains the IPSec tunnel's property information."
			::= { ruijieIPSec2Groups 1 }

		
		-- 1.3.6.1.4.1.4881.1.1.10.2.108.2.2.2
		ruijieIPSec2TunnelStatGroup OBJECT-GROUP
			OBJECTS { ruijieIPSec2TunInOctets, ruijieIPSec2TunInDecompOctets, ruijieIPSec2TunInPkts, ruijieIPSec2TunInSpeed, ruijieIPSec2TunInDropPkts, 
				ruijieIPSec2TunOutOctets, ruijieIPSec2TunOutUncompOctets, ruijieIPSec2TunOutPkts, ruijieIPSec2TunOutSpeed, ruijieIPSec2TunOutDropPkts
				 }
			STATUS current
			DESCRIPTION 
				"The group contains the IPSec tunnel's statistic information."
			::= { ruijieIPSec2Groups 2 }

		
		-- 1.3.6.1.4.1.4881.1.1.10.2.108.2.2.3
		ruijieIPSec2SaGroup OBJECT-GROUP
			OBJECTS { ruijieIPSec2SaIndex, ruijieIPSec2SaDirection, ruijieIPSec2SaValue, ruijieIPSec2SaProtocol, ruijieIPSec2SaEncryptAlgo, 
				ruijieIPSec2SaAuthAlgo, ruijieIPSec2SaStatus }
			STATUS current
			DESCRIPTION 
				"The group contains the SA's property information."
			::= { ruijieIPSec2Groups 3 }

		
		-- 1.3.6.1.4.1.4881.1.1.10.2.108.2.2.4
		ruijieIPSec2TrafficTableGroup OBJECT-GROUP
			OBJECTS { ruijieIPSec2TrafficLocalType, ruijieIPSec2TrafficLocalAddr1, ruijieIPSec2TrafficLocalAddr2, ruijieIPSec2TrafficLocalProtocol, ruijieIPSec2TrafficLocalPort, 
				ruijieIPSec2TrafficRemoteAddr1, ruijieIPSec2TrafficRemoteAddr2, ruijieIPSec2TrafficRemotePort, ruijieIPSec2TrafficLocalHostname, ruijieIPSec2TrafficRemoteType, 
				ruijieIPSec2TrafficRemoteProtocol, ruijieIPSec2TrafficRemoteHostname }
			STATUS current
			DESCRIPTION 
				"The group contains the property information of the
				data flow protected by IPSec tunnel."
			::= { ruijieIPSec2Groups 4 }

		
		-- 1.3.6.1.4.1.4881.1.1.10.2.108.2.2.5
		ruijieIPSec2GlobalStatsGroup OBJECT-GROUP
			OBJECTS { ruijieIPSec2GlobalActiveTunnels, ruijieIPSec2GlobalActiveSas, ruijieIPSec2GlobalInOctets, ruijieIPSec2GlobalInPkts, ruijieIPSec2GlobalInSpeed, 
				ruijieIPSec2GlobalInDrops, ruijieIPSec2GlobalOutOctets, ruijieIPSec2GlobalOutPkts, ruijieIPSec2GlobalOutSpeed, ruijieIPSec2GlobalOutDrops
				 }
			STATUS current
			DESCRIPTION 
				"The group contains all of the IPSec tunnel's statistic
				information."
			::= { ruijieIPSec2Groups 5 }

		
		-- 1.3.6.1.4.1.4881.1.1.10.2.108.2.2.6
		ruijieIPSec2TrapObjectGroup OBJECT-GROUP
			OBJECTS { ruijieIPSec2MapName, ruijieIPSec2SeqNum, ruijieIPSec2SpiValue }
			STATUS current
			DESCRIPTION 
				"The group contains all of trap objects of IPSec tunnels."
			::= { ruijieIPSec2Groups 6 }

		
		-- 1.3.6.1.4.1.4881.1.1.10.2.108.2.2.7
		ruijieIPSec2TrapGroup NOTIFICATION-GROUP
			NOTIFICATIONS { ruijieIPSec2TunnelStart, ruijieIPSec2TunnelStop }
			STATUS current
			DESCRIPTION 
				"The group contains all of trap of IPSec tunnels."
			::= { ruijieIPSec2Groups 7 }

		
	
	END

--
-- RAISECOM-IPSEC2-MIB.mib
--
