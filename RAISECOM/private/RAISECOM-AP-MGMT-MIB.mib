-- *****************************************************************
-- RAISECOM-AP-MGMT-MIB.mib:  Raisecom AP MGMT MIB file
--
-- July 2013, linwei4
-- 
-- Copyright (c) 2012 by Raisecom Networks Co.,Ltd.
-- All rights reserved.
-- *****************************************************************
--
RAISECOM-AP-MGMT-MIB DEFINITIONS ::= BEGIN

IMPORTS
        OBJECT-TYPE,
        Integer32,
        MODULE-IDENTITY
                FROM SNMPv2-SMI
        ruijieMgmt
                FROM RAISECOM-SMI; 
                
ruijieApMgmtMIB MODULE-IDENTITY
    LAST-UPDATED "201307230000Z"
    ORGANIZATION "Raisecom Networks Co.,Ltd."
    CONTACT-INFO
        " 
    Tel: 4008-111-000

    E-mail: service@raisecom.com.cn"
    DESCRIPTION
        "This module defines ac management mibs."
    REVISION      "201307230000Z"
    DESCRIPTION
        "Initial version of this MIB module."
    ::= { ruijieMgmt 124}

--***************** define the AP root nodes *****************
ruijieApMgmtMIBObjects OBJECT IDENTIFIER      ::= { ruijieApMgmtMIB 1 }
ruijieApMgmt     OBJECT IDENTIFIER ::= { ruijieApMgmtMIBObjects 1 }

--********************************************************************
--                                                                  **
--                  AP nodes                                        **
--                                                                  **
--********************************************************************

-- 1.ap_mode, the ap's mode
ruijieApMode OBJECT-TYPE
    SYNTAX  INTEGER (0..1)
    MAX-ACCESS  read-only
    STATUS  current
    DESCRIPTION
            "The ap mode:
            0--fit
            1--fat"
    ::= { ruijieApMgmt 1 }

END
