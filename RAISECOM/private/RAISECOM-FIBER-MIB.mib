-- *****************************************************************
-- RAISECOM-FIBER-MIB.mib:  Raisecom FIBER MIB file
--
-- January 2012, wangyouliang
--
-- Copyright (c) 2012 by Raisecom Networks Co.,Ltd.
-- All rights reserved.
-- 
-- *****************************************************************
--

RAISECOM-FIBER-MIB DEFINITIONS ::= BEGIN

IMPORTS
        MODULE-IDENTITY,
        OBJECT-TYPE
                FROM SNMPv2-SMI
        TruthValue,
        DisplayString
                FROM SNMPv2-TC
        MODULE-COMPLIANCE,
        OBJECT-GROUP
                FROM SNMPv2-CONF
        IfIndex
                FROM RAISECOM-TC
        ruijieMgmt
                FROM RAISECOM-SMI;

ruijieFiberMIB MODULE-IDENTITY
        LAST-UPDATED "201111280000Z"
        ORGANIZATION "Raisecom Networks Co.,Ltd."
        CONTACT-INFO
                " 
                Tel: 4008-111-000 

                E-mail: service@raisecom.com.cn"
        DESCRIPTION
                "This module defines raisecom fiber module information mibs."
        REVISION      "201111280000Z"
        DESCRIPTION
                "Initial version of this MIB module."
        ::= { ruijieMgmt 105}

ruijieFiberMIBObjects OBJECT IDENTIFIER ::= { ruijieFiberMIB 1 }


-- ---------------------------------------------------------- --
-- A table for getting Fiber port information.
-- ---------------------------------------------------------- -- 
ruijieFiberTable OBJECT-TYPE
        SYNTAX SEQUENCE OF RuijieFiberEntry
        MAX-ACCESS not-accessible
        STATUS current
        DESCRIPTION
            "A table for getting Fiber Module information"
        ::= { ruijieFiberMIBObjects 1 }
    
ruijieFiberEntry OBJECT-TYPE
        SYNTAX RuijieFiberEntry
        MAX-ACCESS not-accessible
        STATUS current
        DESCRIPTION
            "Entry of a Fiber Module information."
        INDEX { ruijieFiberPortIndex }
        ::= { ruijieFiberTable 1 }
    
RuijieFiberEntry ::=
        SEQUENCE {
                ruijieFiberPortIndex IfIndex,
                ruijieFiberPortDescr DisplayString,
                ruijieFiberTransceiverType INTEGER,
                ruijieFiberConnectorType INTEGER,
                ruijieFiberWavelength INTEGER,
                ruijieFiberTransferDistanceSMF INTEGER,
                ruijieFiberTransferDistance62point5umOM1 INTEGER,
                ruijieFiberTransferDistance62point5um INTEGER,
                ruijieFiberTransferDistance50umOM2 INTEGER,
                ruijieFiberTransferDistance50um INTEGER,
                ruijieFiberTransferDistance50umOM3 INTEGER,
                ruijieFiberTransferDistanceEBW50um INTEGER,
                ruijieFiberTransferDistanceCopper INTEGER,
                ruijieFiberTransferDistanceCableAssembly INTEGER,
                ruijieFiberDDMSupportStatus TruthValue,
                ruijieFiberSerialNumber DisplayString,
                ruijieFiberTemp INTEGER,
                ruijieFiberTempStatus INTEGER,
                ruijieFiberVoltage INTEGER,
                ruijieFiberVoltageStatus INTEGER,
                ruijieFiberBias INTEGER,
                ruijieFiberBiasStatus INTEGER,
                ruijieFiberChannel1Bias INTEGER,
                ruijieFiberChannel1BiasStatus INTEGER,
                ruijieFiberChannel2Bias INTEGER,
                ruijieFiberChannel2BiasStatus INTEGER,
                ruijieFiberChannel3Bias INTEGER,
                ruijieFiberChannel3BiasStatus INTEGER,
                ruijieFiberChannel4Bias INTEGER,
                ruijieFiberChannel4BiasStatus INTEGER,
                ruijieFiberRXpowerIntegerpart INTEGER,
                ruijieFiberRXpowerDecimalpart INTEGER,
                ruijieFiberRXpowertype INTEGER,
                ruijieFiberRXpowerStatus INTEGER,
                ruijieFiberChannel1RXpowerIntegerpart INTEGER,
                ruijieFiberChannel1RXpowerDecimalpart INTEGER,
                ruijieFiberChannel1RXpowertype INTEGER,
                ruijieFiberChannel1RXpowerStatus INTEGER,
                ruijieFiberChannel2RXpowerIntegerpart INTEGER,
                ruijieFiberChannel2RXpowerDecimalpart INTEGER,
                ruijieFiberChannel2RXpowertype INTEGER,
                ruijieFiberChannel2RXpowerStatus INTEGER,
                ruijieFiberChannel3RXpowerIntegerpart INTEGER,
                ruijieFiberChannel3RXpowerDecimalpart INTEGER,
                ruijieFiberChannel3RXpowertype INTEGER,
                ruijieFiberChannel3RXpowerStatus INTEGER,
                ruijieFiberChannel4RXpowerIntegerpart INTEGER,
                ruijieFiberChannel4RXpowerDecimalpart INTEGER,
                ruijieFiberChannel4RXpowertype INTEGER,
                ruijieFiberChannel4RXpowerStatus INTEGER,
                ruijieFiberTXpowerIntegerpart INTEGER,
                ruijieFiberTXpowerDecimalpart INTEGER,
                ruijieFiberTXpowerStatus INTEGER,
                ruijieFiberChannel1TXpowerIntegerpart INTEGER,
                ruijieFiberChannel1TXpowerDecimalpart INTEGER,
                ruijieFiberChannel1TXpowerStatus INTEGER,
                ruijieFiberChannel2TXpowerIntegerpart INTEGER,
                ruijieFiberChannel2TXpowerDecimalpart INTEGER,
                ruijieFiberChannel2TXpowerStatus INTEGER,
                ruijieFiberChannel3TXpowerIntegerpart INTEGER,
                ruijieFiberChannel3TXpowerDecimalpart INTEGER,
                ruijieFiberChannel3TXpowerStatus INTEGER,
                ruijieFiberChannel4TXpowerIntegerpart INTEGER,
                ruijieFiberChannel4TXpowerDecimalpart INTEGER,
                ruijieFiberChannel4TXpowerStatus INTEGER,
                ruijieFiberRXpowerSign INTEGER,
                ruijieFiberChannel1RXpowerSign INTEGER,
                ruijieFiberChannel2RXpowerSign INTEGER,
                ruijieFiberChannel3RXpowerSign INTEGER,
                ruijieFiberChannel4RXpowerSign INTEGER,
                ruijieFiberTXpowerSign INTEGER,
                ruijieFiberChannel1TXpowerSign INTEGER,
                ruijieFiberChannel2TXpowerSign INTEGER,
                ruijieFiberChannel3TXpowerSign INTEGER,
                ruijieFiberChannel4TXpowerSign INTEGER,                 
        }
        
ruijieFiberPortIndex OBJECT-TYPE
        SYNTAX IfIndex
        MAX-ACCESS not-accessible
        STATUS current
        DESCRIPTION
            "Port index of the port."
        ::= { ruijieFiberEntry 1 }

ruijieFiberPortDescr OBJECT-TYPE
        SYNTAX DisplayString (SIZE(1..32))
        MAX-ACCESS read-only
        STATUS current
        DESCRIPTION
            "Discription of the port."
        ::= { ruijieFiberEntry 2 }

ruijieFiberTransceiverType OBJECT-TYPE
        SYNTAX INTEGER {
            unknown(1),
            fiber100BASEGTSFP(2),
            fiber100BASESXSFP(3),
            fiber100BASELXSFP(4),
            fiber100BASELHSFP(5),
	    fiber100BASEZXSFP(6),
            fiber100CopperSFP(7),
            fiber1000BASEGTSFP(8),
            fiber1000BASESXSFP(9),
            fiber1000BASELXSFP(10),
            fiber1000BASELHSFP(11),
	    fiber1000BASEZXSFP(12),
            fiber1000CopperSFP(13),
            fiber10GCopperSFPPlus(14),
            fiber10GBASESRSFPPlus(15),
            fiber10GBASELRSFPPlus(16),
            fiber10GBASEERSFPPlus(17),
            fiber10GBASEZRSFPPlus(18),
            fiber10GCopperXFP(19),
            fiber10GBASESRXFP(20),
            fiber10GBASELRXFP(21),
            fiber10GBASEERXFP(22),
            fiber10GBASEZRXFP(23),
            fiber40GActiveCableQSFPPlus(24),
            fiber40GLR4QSFPPlus(25),
            fiber40GCopperQSFPPlus(26),
            fiber40GSR4QSFPPlus(27),
            fiber2500CopperSFP(28),
            fiberFC16G(29),
            fiberFC8G(30),
            fiberFC4G(31),
            fiberFC2G(32),
            fiber10GActiveCableSFPPlus(33),
            fiber40GER4QSFPPlus(34),
            fiber40GZR4QSFPPlus(35),
            fiber100GCABLEQSFP28(36),
            fiber100GLR4QSFP28(37),  
            fiber100GSR4QSFP28(38),
            fiber100GER4QSFP28(39),
            fiber100GZR4QSFP28(40),
            fiber100GCR4QSFP28(41),
            fiber100GPSM4QSFP28(42),    
            fiber25GSRSFP28    (43),
            fiber25GLRSFP28    (44),
            fiber25GERSFP28    (45),
            fiber25GZRSFP28    (46),
            fiber25GCOPPERSFP28 (47),
            fiber25GACTIVECABLESFP28 (48),            
        }
        MAX-ACCESS read-only
        STATUS current
        DESCRIPTION
            "Transceiver type of the Fiber module insered into the port."
        ::= { ruijieFiberEntry 3 }

ruijieFiberConnectorType OBJECT-TYPE
        SYNTAX INTEGER {
	    meaningless(0),
            unknownorunspecified(1),
            vendorspecific(2),
            sc(3),
            fiberChannelStyle1CopperConnector(4),
            fiberChannelStyle2CopperConnector(5),
            bncortnc(6),
            fiberChannelCoaxialHeaders(7),
            fiberJack(8),
            lc(9),
            mtrj(10),
            mu(11),
            sg(12),
            opticalPigtail(13),
            hssdcII(14),
            copperPigtail(15),
	    mpo(16),
	    rj45(17),
            noSparableConnector(18)
        }
        MAX-ACCESS read-only
        STATUS current
        DESCRIPTION
            "Connector type of the Fiber module insered into the port.
	     If the transceiver type of Fiber module is unknown(1), then this
             object contains a zero value."
        ::= { ruijieFiberEntry 4 }

ruijieFiberWavelength OBJECT-TYPE
        SYNTAX INTEGER
        MAX-ACCESS read-only
        STATUS current
        DESCRIPTION
            "The value of wavelength of the Fiber module insered into the port.
	     If the transceiver type of Fiber module is either fiber100CopperSFP(7)  
	     or fiber1000CopperSFP(13) (or fiber10GCopperSFPPlus(14), 
	     or fiber10GCopperXFP(19), or fiber40GCopperQSFPPlus(26), or fiber2500CopperSFP(28), or unknown(1)), then this
             object contains a zero value."
        ::= { ruijieFiberEntry 5 }

ruijieFiberTransferDistanceSMF OBJECT-TYPE
        SYNTAX INTEGER
        MAX-ACCESS read-only
        STATUS current
        DESCRIPTION
            "The value of transfer distance of the Fiber module insered into the port.
	     This value specifies the link length that is supported by the 
	     transceiver while operating in compliance with the applicable 
	     standards using single mode fiber for. The value is in units of kilometers.
	     A value of zero means that the transceiver does not support single mode fiber."
        ::= { ruijieFiberEntry 6 }

ruijieFiberTransferDistance62point5umOM1 OBJECT-TYPE
        SYNTAX INTEGER
        MAX-ACCESS read-only
        STATUS current
        DESCRIPTION
            "The value of transfer distance of the Fiber module insered into the port.
	     This value specifies the link length that is supported by the 
	     transceiver while operating in compliance with the applicable 
	     standards using 62.5 micron multimode (200 MHz*Km at 850 nm, 500 MHz*Km 
	     at 1310 nm) fiber. The value is in units of meters.
	     A value of zero means that the transceiver does not 
	     support 62.5 micron multimode fiber or the Fiber module type 
	     is neither SFP/SFP+ nor QSFP+."
        ::= { ruijieFiberEntry 7 }

ruijieFiberTransferDistance62point5um OBJECT-TYPE
        SYNTAX INTEGER
        MAX-ACCESS read-only
        STATUS current
        DESCRIPTION
            "The value of transfer distance of the Fiber module insered into the port.
	     This value specifies the link length that is supported by the 
	     transceiver while operating in compliance with the applicable 
	     standards using 62.5 micron core multimode (200 MHz*Km at 850 nm, 500 MHz*Km 
	     at 1310 nm) fiber. The value is in units of meters.
	     A value of zero means that the transceiver does not 
	     support 62.5 micron multimode fiber or the Fiber module type is not XFP."
        ::= { ruijieFiberEntry 8 }

ruijieFiberTransferDistance50umOM2 OBJECT-TYPE
        SYNTAX INTEGER
        MAX-ACCESS read-only
        STATUS current
        DESCRIPTION
            "The value of transfer distance of the Fiber module insered into the port.
	     This value specifies the link length that is supported by the 
	     transceiver while operating in compliance with the applicable 
	     standards using 50 micron multimode (500 MHz*Km at 850 nm for SFP module 
	     or at 850 nm and 1310 nm for QSFP+ module) fiber. The value is in units of meters.
	     A value of zero means that the transceiver does not 
	     support 50 micron multimode fiber or the Fiber module type 
	     is neither SFP/SFP+ nor QSFP+."
        ::= { ruijieFiberEntry 9 }

ruijieFiberTransferDistance50um OBJECT-TYPE
        SYNTAX INTEGER
        MAX-ACCESS read-only
        STATUS current
        DESCRIPTION
            "The value of transfer distance of the Fiber module insered into the port.
	     This value specifies the link length that is supported by the 
	     transceiver while operating in compliance with the applicable 
	     standards using 50 micron core multimode (500 MHz*Km at 850 nm and 1310 nm) fiber. 
	     The value is in units of meters.
	     A value of zero means that the transceiver does not 
	     support 50 micron core multimode fiber or the Fiber module type 
	     is not XFP."
        ::= { ruijieFiberEntry 10 }

ruijieFiberTransferDistance50umOM3 OBJECT-TYPE
        SYNTAX INTEGER
        MAX-ACCESS read-only
        STATUS current
        DESCRIPTION
            "The value of transfer distance of the Fiber module insered into the port.
	     This value specifies the link length that is supported by the 
	     transceiver while operating in compliance with the applicable 
	     standards using 50 micron multimode OM3(2000 MHz*Km) fiber. 
	     The value is in units of meters.
	     A value of zero means that the transceiver does not 
	     support 50 micron multimode fiber or the Fiber module type 
	     is neither SFP/SFP+ nor QSFP+."
        ::= { ruijieFiberEntry 11 }

ruijieFiberTransferDistanceEBW50um OBJECT-TYPE
        SYNTAX INTEGER
        MAX-ACCESS read-only
        STATUS current
        DESCRIPTION
            "The value of transfer distance of the Fiber module insered into the port.
	     This value specifies the link length that is supported by the 
	     transceiver while operating in compliance with the applicable 
	     standards using 2000 MHz*Km (850nm) extended bandwidth 50 
	     micron core multimode fiber. The value is in units of meters.  
	     A value of zero means that the transceiver does not support 
	     extended bandwidth 50 micron multimode fiber or the Fiber module type is not XFP."
        ::= { ruijieFiberEntry 12 }

ruijieFiberTransferDistanceCopper OBJECT-TYPE
        SYNTAX INTEGER
        MAX-ACCESS read-only
        STATUS current
        DESCRIPTION
            "The value of transfer distance of the Fiber module insered into the port.
	     This value specifies the link length that is supported by the 
	     transceiver while operating in compliance with the applicable 
	     standards using copper cables. The value is in units of meters.
	     A value of zero means that the transceiver does not support copper cables
	     or the Fiber module type is neither SFP/SFP+ nor XFP."
        ::= { ruijieFiberEntry 13 }

ruijieFiberTransferDistanceCableAssembly OBJECT-TYPE
        SYNTAX INTEGER
        MAX-ACCESS read-only
        STATUS current
        DESCRIPTION
            "The value of transfer distance of the Fiber module insered into the port.
	     This value specifies the link length of the Cable assembly passive. 
	     The value is in units of meters.
	     A value of zero means that the transceiver is not a cable assemblyor
	     or the Fiber module type is not QSFP+."
        ::= { ruijieFiberEntry 14 }

ruijieFiberDDMSupportStatus OBJECT-TYPE
        SYNTAX        TruthValue
        MAX-ACCESS    read-only
        STATUS        current
        DESCRIPTION
        "This object indicates that whether the Digital Diagnostic Monitors is implemeted."
    ::= { ruijieFiberEntry 15 }

ruijieFiberSerialNumber OBJECT-TYPE
        SYNTAX DisplayString (SIZE(1..32))
        MAX-ACCESS read-only
        STATUS current
        DESCRIPTION
            "The serial number of the Fiber module insered into the port."
        ::= { ruijieFiberEntry 16 }

ruijieFiberTemp OBJECT-TYPE
        SYNTAX INTEGER
        MAX-ACCESS read-only
        STATUS current
        DESCRIPTION
            "The temperature of the Fiber module insered into the port.
	    The value is in units of degrees Celsius.
	    If the ruijieFiberDDMSupportStatus is false, the temperature value is 0."
        ::= { ruijieFiberEntry 17 }

ruijieFiberTempStatus OBJECT-TYPE
        SYNTAX INTEGER {
            unknown(1),
            ok(2),
            warning(3),
            alarm(4)
        }
        MAX-ACCESS read-only
        STATUS current
        DESCRIPTION
            "The status ok(2) indicates that the temperature of the Fiber module is in
	    the normal level. The status warning(3) indicates that the temperature of 
	    the Fiber module exceeds high warning level or is below low warning level. 
            The status alarm(4) indicates that the temperature of 
	    the Fiber module exceeds high alarm level or is below low alarm level. 
	    If the ruijieFiberDDMSupportStatus is false or the Fiber module type is 
	    neither SFP/SFP+ nor XFP(or not QSFP+), the status is unknown(1)."
        ::= { ruijieFiberEntry 18 }

ruijieFiberVoltage OBJECT-TYPE
        SYNTAX INTEGER
        MAX-ACCESS read-only
        STATUS current
        DESCRIPTION
            "The voltage of the Fiber module insered into the port.
	    The value is in units of mVolts.
	    If the ruijieFiberDDMSupportStatus is false, the voltage value is 0."
        ::= { ruijieFiberEntry 19 }

ruijieFiberVoltageStatus OBJECT-TYPE
        SYNTAX INTEGER {
            unknown(1),
            ok(2),
            warning(3),
            alarm(4)
        }
        MAX-ACCESS read-only
        STATUS current
        DESCRIPTION
            "The status ok(2) indicates that the voltage of the Fiber module is in
	    the normal level. The status warning(3) indicates that the voltage of 
	    the Fiber module exceeds high warning level or is below low warning level. 
            The status alarm(4) indicates that the voltage of 
	    the Fiber module exceeds high alarm level or is below low alarm level. 
	    If the ruijieFiberDDMSupportStatus is false or the Fiber module type is 
	    neither SFP/SFP+ nor XFP(or not QSFP+), the status is unknown(1)."
        ::= { ruijieFiberEntry 20 }

ruijieFiberBias OBJECT-TYPE
        SYNTAX INTEGER
        MAX-ACCESS read-only
        STATUS current
        DESCRIPTION
            "The bias of the Fiber module insered into the port.
	    The value is in units of uA.
	    If the ruijieFiberDDMSupportStatus is false or the Fiber module type is 
	    neither SFP/SFP+ nor XFP, the bias value is 0."
        ::= { ruijieFiberEntry 21 }

ruijieFiberBiasStatus OBJECT-TYPE
        SYNTAX INTEGER {
            unknown(1),
            ok(2),
            warning(3),
            alarm(4)
        }
        MAX-ACCESS read-only
        STATUS current
        DESCRIPTION
            "The status ok(2) indicates that the bias of the Fiber module is in
	    the normal level. The status warning(3) indicates that the bias of 
	    the Fiber module exceeds high warning level or is below low warning level. 
            The status alarm(4) indicates that the bias of 
	    the Fiber module exceeds high alarm level or is below low alarm level. 
	    If the ruijieFiberDDMSupportStatus is false or the Fiber module type is 
	    neither SFP/SFP+ nor XFP, the status is unknown(1)."
        ::= { ruijieFiberEntry 22 }

ruijieFiberChannel1Bias OBJECT-TYPE
        SYNTAX INTEGER
        MAX-ACCESS read-only
        STATUS current
        DESCRIPTION
            "The bias in Channel 1 of the QSFP+ Fiber module insered into the port.
	    The value is in units of uA.
	    If the ruijieFiberDDMSupportStatus is false or the Fiber module type is 
	    not QSFP+, the bias value in Channel 1 is 0."
        ::= { ruijieFiberEntry 23 }

ruijieFiberChannel1BiasStatus OBJECT-TYPE
        SYNTAX INTEGER {
            unknown(1),
            ok(2),
            warning(3),
            alarm(4)
        }
        MAX-ACCESS read-only
        STATUS current
        DESCRIPTION
            "The status ok(2) indicates that the bias in the Channel 1 of QSFP+ is in
	    the normal level. The status warning(3) indicates 
	    that the bias in the Channel 1 exceeds high warning level or is 
	    below low warning level. The status alarm(4) indicates that the bias in 
	    the Channel 1 exceeds high alarm level or is below low alarm level. 
	    If the ruijieFiberDDMSupportStatus is false or the Fiber module type is 
	    not QSFP+, the status is unknown(1)."
        ::= { ruijieFiberEntry 24 }

ruijieFiberChannel2Bias OBJECT-TYPE
        SYNTAX INTEGER
        MAX-ACCESS read-only
        STATUS current
        DESCRIPTION
            "The bias in Channel 2 of the QSFP+ Fiber module insered into the port.
	    The value is in units of uA.
	    If the ruijieFiberDDMSupportStatus is false or the Fiber module type is 
	    not QSFP+, the bias value in Channel 2 is 0."
        ::= { ruijieFiberEntry 25 }

ruijieFiberChannel2BiasStatus OBJECT-TYPE
        SYNTAX INTEGER {
            unknown(1),
            ok(2),
            warning(3),
            alarm(4)
        }
        MAX-ACCESS read-only
        STATUS current
        DESCRIPTION
            "The status ok(2) indicates that the bias in the Channel 2 of QSFP+ is in
	    the normal level. The status warning(3) indicates 
	    that the bias in the Channel 2 exceeds high warning level or is 
	    below low warning level. The status alarm(4) indicates that the bias in 
	    the Channel 2 exceeds high alarm level or is below low alarm level. 
	    If the ruijieFiberDDMSupportStatus is false or the Fiber module type is 
	    not QSFP+, the status is unknown(1)."
        ::= { ruijieFiberEntry 26 }

ruijieFiberChannel3Bias OBJECT-TYPE
        SYNTAX INTEGER
        MAX-ACCESS read-only
        STATUS current
        DESCRIPTION
            "The bias in Channel 3 of the QSFP+ Fiber module insered into the port.
	    The value is in units of uA.
	    If the ruijieFiberDDMSupportStatus is false or the Fiber module type is 
	    not QSFP+, the bias value in Channel 3 is 0."
        ::= { ruijieFiberEntry 27 }

ruijieFiberChannel3BiasStatus OBJECT-TYPE
        SYNTAX INTEGER {
            unknown(1),
            ok(2),
            warning(3),
            alarm(4)
        }
        MAX-ACCESS read-only
        STATUS current
        DESCRIPTION
            "The status ok(2) indicates that the bias in the Channel 3 of QSFP+ is in
	    the normal level. The status warning(3) indicates 
	    that the bias in the Channel 3 exceeds high warning level or is 
	    below low warning level. The status alarm(4) indicates that the bias in 
	    the Channel 3 exceeds high alarm level or is below low alarm level. 
	    If the ruijieFiberDDMSupportStatus is false or the Fiber module type is 
	    not QSFP+, the status is unknown(1)."
        ::= { ruijieFiberEntry 28 }

ruijieFiberChannel4Bias OBJECT-TYPE
        SYNTAX INTEGER
        MAX-ACCESS read-only
        STATUS current
        DESCRIPTION
            "The bias in Channel 4 of the QSFP+ Fiber module insered into the port.
	    The value is in units of uA.
	    If the ruijieFiberDDMSupportStatus is false or the Fiber module type is 
	    not QSFP+, the bias value in Channel 4 is 0."
        ::= { ruijieFiberEntry 29 }

ruijieFiberChannel4BiasStatus OBJECT-TYPE
        SYNTAX INTEGER {
            unknown(1),
            ok(2),
            warning(3),
            alarm(4)
        }
        MAX-ACCESS read-only
        STATUS current
        DESCRIPTION
            "The status ok(2) indicates that the bias in the Channel 4 of QSFP+ is in
	    the normal level. The status warning(3) indicates 
	    that the bias in the Channel 4 exceeds high warning level or is 
	    below low warning level. The status alarm(4) indicates that the bias in 
	    the Channel 4 exceeds high alarm level or is below low alarm level. 
	    If the ruijieFiberDDMSupportStatus is false or the Fiber module type is 
	    not QSFP+, the status is unknown(1)."
        ::= { ruijieFiberEntry 30 }

ruijieFiberRXpowerIntegerpart OBJECT-TYPE
        SYNTAX INTEGER
        MAX-ACCESS read-only
        STATUS current
        DESCRIPTION
            "The integer part of Rx power of the Fiber module insered into the port.
	    The value is in units of dbm.
	    If the ruijieFiberDDMSupportStatus is false or the Fiber module type is 
	    neither SFP/SFP+ nor XFP, the integer part of Rx power value 
	    is -100(means that the value is invalid)."
        ::= { ruijieFiberEntry 31 }

ruijieFiberRXpowerDecimalpart OBJECT-TYPE
        SYNTAX INTEGER
        MAX-ACCESS read-only
        STATUS current
        DESCRIPTION
            "The decimal part of Rx power of the Fiber module insered into the port.
	    The value is in units of dbm.
	    If the ruijieFiberDDMSupportStatus is false or the Fiber module type is 
	    neither SFP/SFP+ nor XFP, the decimal part of Rx power value 
	    is -100(means that the value is invalid)."
        ::= { ruijieFiberEntry 32 }

ruijieFiberRXpowertype OBJECT-TYPE
        SYNTAX INTEGER {
            unknown(1),
            average(2),
            oma(3)
        }
        MAX-ACCESS read-only
        STATUS current
        DESCRIPTION
            "The value indicates whether the received power measurement 
	     represents average input optical power(2) or oma(3). 
	     If the ruijieFiberDDMSupportStatus is false or the Fiber module type is 
	     neither SFP/SFP+ nor XFP (or not QSFP+), the value is unknown(1)."
        ::= { ruijieFiberEntry 33 }

ruijieFiberRXpowerStatus OBJECT-TYPE
        SYNTAX INTEGER {
            unknown(1),
            ok(2),
            warning(3),
            alarm(4)
        }
        MAX-ACCESS read-only
        STATUS current
        DESCRIPTION
            "The status ok(2) indicates that the Rx power of the Fiber module is in
	    the normal level. The status warning(3) indicates that the Rx power of 
	    the Fiber module exceeds high warning level or is below low warning level. 
            The status alarm(4) indicates that the Rx power of 
	    the Fiber module exceeds high alarm level or is below low alarm level. 
	    If the ruijieFiberDDMSupportStatus is false or the Fiber module type is 
	    neither SFP/SFP+ nor XFP, the status is unknown(1)."
        ::= { ruijieFiberEntry 34 }

ruijieFiberChannel1RXpowerIntegerpart OBJECT-TYPE
        SYNTAX INTEGER
        MAX-ACCESS read-only
        STATUS current
        DESCRIPTION
            "The integer part of Rx power in Channel 1 of the QSFP+ 
	    Fiber module insered into the port. The value is in units of dbm.
	    If the ruijieFiberDDMSupportStatus is false or the Fiber module type is 
	    not QSFP+, the integer part of Rx power value in Channel 1 
	    is -100(means the value is invalid)."
        ::= { ruijieFiberEntry 35 }

ruijieFiberChannel1RXpowerDecimalpart OBJECT-TYPE
        SYNTAX INTEGER
        MAX-ACCESS read-only
        STATUS current
        DESCRIPTION
            "The decimal part of Rx power in Channel 1 of the QSFP+ 
	    Fiber module insered into the port. The value is in units of dbm.
	    If the ruijieFiberDDMSupportStatus is false or the Fiber module type is 
	    not QSFP+, the decimal part of Rx power value in Channel 1 
	    is -100(means the value is invalid)."
        ::= { ruijieFiberEntry 36 }

ruijieFiberChannel1RXpowertype OBJECT-TYPE
        SYNTAX INTEGER {
            unknown(1),
            average(2),
            oma(3)
        }
        MAX-ACCESS read-only
        STATUS current
        DESCRIPTION
            "The value indicates whether the received power measurement 
	     represents average input optical power(2) or oma(3) in Channel 1 of QSFP+. 
	     If the ruijieFiberDDMSupportStatus is false or the Fiber module type is 
	     not QSFP+, the value is unknown(1)."
        ::= { ruijieFiberEntry 37 }

ruijieFiberChannel1RXpowerStatus OBJECT-TYPE
        SYNTAX INTEGER {
            unknown(1),
            ok(2),
            warning(3),
            alarm(4)
        }
        MAX-ACCESS read-only
        STATUS current
        DESCRIPTION
            "The status ok(2) indicates that the Rx power in the Channel 1 of QSFP+ is in
	    the normal level. The status warning(3) indicates that 
	    the Rx power in the Channel 1 exceeds high warning level or is below 
	    low warning level. The status alarm(4) indicates that the Rx power in the
	    Channel 1 exceeds high alarm level or is below low alarm level. 
	    If the ruijieFiberDDMSupportStatus is false or the Fiber module type is 
	    not QSFP+, the status is unknown(1)."
        ::= { ruijieFiberEntry 38 }

ruijieFiberChannel2RXpowerIntegerpart OBJECT-TYPE
        SYNTAX INTEGER
        MAX-ACCESS read-only
        STATUS current
        DESCRIPTION
            "The integer part of Rx power in Channel 1 of the QSFP+ 
	    Fiber module insered into the port. The value is in units of dbm.
	    If the ruijieFiberDDMSupportStatus is false or the Fiber module type is 
	    not QSFP+, the integer part of Rx power value in Channel 1 
	    is -100(means the value is invalid)."
        ::= { ruijieFiberEntry 39 }

ruijieFiberChannel2RXpowerDecimalpart OBJECT-TYPE
        SYNTAX INTEGER
        MAX-ACCESS read-only
        STATUS current
        DESCRIPTION
            "The decimal part of Rx power in Channel 1 of the QSFP+ 
	    Fiber module insered into the port. The value is in units of dbm.
	    If the ruijieFiberDDMSupportStatus is false or the Fiber module type is 
	    not QSFP+, the decimal part of Rx power value in Channel 2 
	    is -100(means the value is invalid)."
        ::= { ruijieFiberEntry 40 }

ruijieFiberChannel2RXpowertype OBJECT-TYPE
        SYNTAX INTEGER {
            unknown(1),
            average(2),
            oma(3)
        }
        MAX-ACCESS read-only
        STATUS current
        DESCRIPTION
            "The value indicates whether the received power measurement 
	     represents average input optical power(2) or oma(3) in Channel 2 of QSFP+. 
	     If the ruijieFiberDDMSupportStatus is false or the Fiber module type is 
	     not QSFP+, the value is unknown(1)."
        ::= { ruijieFiberEntry 41 }

ruijieFiberChannel2RXpowerStatus OBJECT-TYPE
        SYNTAX INTEGER {
            unknown(1),
            ok(2),
            warning(3),
            alarm(4)
        }
        MAX-ACCESS read-only
        STATUS current
        DESCRIPTION
            "The status ok(2) indicates that the Rx power in the Channel 2 of QSFP+ is in
	    the normal level. The status warning(3) indicates that 
	    the Rx power in the Channel 2 exceeds high warning level or is below 
	    low warning level. The status alarm(4) indicates that the Rx power in the
	    Channel 2 exceeds high alarm level or is below low alarm level. 
	    If the ruijieFiberDDMSupportStatus is false or the Fiber module type is 
	    not QSFP+, the status is unknown(1)."
        ::= { ruijieFiberEntry 42 }

ruijieFiberChannel3RXpowerIntegerpart OBJECT-TYPE
        SYNTAX INTEGER
        MAX-ACCESS read-only
        STATUS current
        DESCRIPTION
            "The integer part of Rx power in Channel 3 of the QSFP+ 
	    Fiber module insered into the port. The value is in units of dbm.
	    If the ruijieFiberDDMSupportStatus is false or the Fiber module type is 
	    not QSFP+, the integer part of Rx power value in Channel 3 
	    is -100(means the value is invalid)."
        ::= { ruijieFiberEntry 43 }

ruijieFiberChannel3RXpowerDecimalpart OBJECT-TYPE
        SYNTAX INTEGER
        MAX-ACCESS read-only
        STATUS current
        DESCRIPTION
            "The decimal part of Rx power in Channel 3 of the QSFP+ 
	    Fiber module insered into the port. The value is in units of dbm.
	    If the ruijieFiberDDMSupportStatus is false or the Fiber module type is 
	    not QSFP+, the decimal part of Rx power value in Channel 3 
	    is -100(means the value is invalid)."
        ::= { ruijieFiberEntry 44 }

ruijieFiberChannel3RXpowertype OBJECT-TYPE
        SYNTAX INTEGER {
            unknown(1),
            average(2),
            oma(3)
        }
        MAX-ACCESS read-only
        STATUS current
        DESCRIPTION
            "The value indicates whether the received power measurement 
	     represents average input optical power(2) or oma(3) in Channel 3 of QSFP+. 
	     If the ruijieFiberDDMSupportStatus is false or the Fiber module type is 
	     not QSFP+, the value is unknown(1)."
        ::= { ruijieFiberEntry 45 }

ruijieFiberChannel3RXpowerStatus OBJECT-TYPE
        SYNTAX INTEGER {
            unknown(1),
            ok(2),
            warning(3),
            alarm(4)
        }
        MAX-ACCESS read-only
        STATUS current
        DESCRIPTION
            "The status ok(2) indicates that the Rx power in the Channel 3 of QSFP+ is in
	    the normal level. The status warning(3) indicates that 
	    the Rx power in the Channel 3 exceeds high warning level or is below 
	    low warning level. The status alarm(4) indicates that the Rx power in the
	    Channel 3 exceeds high alarm level or is below low alarm level. 
	    If the ruijieFiberDDMSupportStatus is false or the Fiber module type is 
	    not QSFP+, the status is unknown(1)."
        ::= { ruijieFiberEntry 46 }

ruijieFiberChannel4RXpowerIntegerpart OBJECT-TYPE
        SYNTAX INTEGER
        MAX-ACCESS read-only
        STATUS current
        DESCRIPTION
            "The integer part of Rx power in Channel 4 of the QSFP+ 
	    Fiber module insered into the port. The value is in units of dbm.
	    If the ruijieFiberDDMSupportStatus is false or the Fiber module type is 
	    not QSFP+, the integer part of Rx power value in Channel 4 
	    is -100(means the value is invalid)."
        ::= { ruijieFiberEntry 47 }

ruijieFiberChannel4RXpowerDecimalpart OBJECT-TYPE
        SYNTAX INTEGER
        MAX-ACCESS read-only
        STATUS current
        DESCRIPTION
            "The decimal part of Rx power in Channel 4 of the QSFP+ 
	    Fiber module insered into the port. The value is in units of dbm.
	    If the ruijieFiberDDMSupportStatus is false or the Fiber module type is 
	    not QSFP+, the decimal part of Rx power value in Channel 4 
	    is -100(means the value is invalid)."
        ::= { ruijieFiberEntry 48 }

ruijieFiberChannel4RXpowertype OBJECT-TYPE
        SYNTAX INTEGER {
            unknown(1),
            average(2),
            oma(3)
        }
        MAX-ACCESS read-only
        STATUS current
        DESCRIPTION
            "The value indicates whether the received power measurement 
	     represents average input optical power(2) or oma(3) in Channel 4 of QSFP+. 
	     If the ruijieFiberDDMSupportStatus is false or the Fiber module type is 
	     not QSFP+, the value is unknown(1)."
        ::= { ruijieFiberEntry 49 }

ruijieFiberChannel4RXpowerStatus OBJECT-TYPE
        SYNTAX INTEGER {
            unknown(1),
            ok(2),
            warning(3),
            alarm(4)
        }
        MAX-ACCESS read-only
        STATUS current
        DESCRIPTION
            "The status ok(2) indicates that the Rx power in the Channel 4 of QSFP+ is in
	    the normal level. The status warning(3) indicates that 
	    the Rx power in the Channel 4 exceeds high warning level or is below 
	    low warning level. The status alarm(4) indicates that the Rx power in the
	    Channel 4 exceeds high alarm level or is below low alarm level. 
	    If the ruijieFiberDDMSupportStatus is false or the Fiber module type is 
	    not QSFP+, the status is unknown(1)."
        ::= { ruijieFiberEntry 50 }

ruijieFiberTXpowerIntegerpart OBJECT-TYPE
        SYNTAX INTEGER
        MAX-ACCESS read-only
        STATUS current
        DESCRIPTION
            "The integer part of Tx power of the Fiber module insered into the port.
	    The value is in units of dbm.
	    If the ruijieFiberDDMSupportStatus is false or the Fiber module type is 
	    neither SFP/SFP+ nor XFP, the integer part of Tx power value 
	    is -100(means that the value is invalid)."
        ::= { ruijieFiberEntry 51 }

ruijieFiberTXpowerDecimalpart OBJECT-TYPE
        SYNTAX INTEGER
        MAX-ACCESS read-only
        STATUS current
        DESCRIPTION
            "The decimal part of Tx power of the Fiber module insered into the port.
	    The value is in units of dbm.
	    If the ruijieFiberDDMSupportStatus is false or the Fiber module type is 
	    neither SFP/SFP+ nor XFP, the decimal part of Tx power value 
	    is -100(means that the value is invalid)."
        ::= { ruijieFiberEntry 52 }

ruijieFiberTXpowerStatus OBJECT-TYPE
        SYNTAX INTEGER {
            unknown(1),
            ok(2),
            warning(3),
            alarm(4)
        }
        MAX-ACCESS read-only
        STATUS current
        DESCRIPTION
            "The status ok(2) indicates that the Tx power of the Fiber module is in
	    the normal level. The status warning(3) indicates that the Tx power of 
	    the Fiber module exceeds high warning level or is below low warning level. 
            The status alarm(4) indicates that the Tx power of 
	    the Fiber module exceeds high alarm level or is below low alarm level. 
	    If the ruijieFiberDDMSupportStatus is false or the Fiber module type is 
	    neither SFP/SFP+ nor XFP, the status is unknown(1)."
        ::= { ruijieFiberEntry 53 }

ruijieFiberChannel1TXpowerIntegerpart OBJECT-TYPE
        SYNTAX INTEGER
        MAX-ACCESS read-only
        STATUS current
        DESCRIPTION
            "The integer part of Tx power in Channel 1 of the QSFP+ 
	    Fiber module insered into the port. The value is in units of dbm.
	    If the ruijieFiberDDMSupportStatus is false or the Fiber module type is 
	    not QSFP+, the integer part of Tx power value in Channel 1 
	    is -100(means the value is invalid)."
        ::= { ruijieFiberEntry 54 }

ruijieFiberChannel1TXpowerDecimalpart OBJECT-TYPE
        SYNTAX INTEGER
        MAX-ACCESS read-only
        STATUS current
        DESCRIPTION
            "The decimal part of Tx power in Channel 1 of the QSFP+ 
	    Fiber module insered into the port. The value is in units of dbm.
	    If the ruijieFiberDDMSupportStatus is false or the Fiber module type is 
	    not QSFP+, the decimal part of Tx power value in Channel 1 
	    is -100(means the value is invalid)."
        ::= { ruijieFiberEntry 55 }

ruijieFiberChannel1TXpowerStatus OBJECT-TYPE
        SYNTAX INTEGER {
            unknown(1),
            ok(2),
            warning(3),
            alarm(4)
        }
        MAX-ACCESS read-only
        STATUS current
        DESCRIPTION
            "The status ok(2) indicates that the Tx power in the Channel 1 of QSFP+ is in
	    the normal level. The status warning(3) indicates that 
	    the Tx power in the Channel 1 exceeds high warning level or is below 
	    low warning level. The status alarm(4) indicates that the Tx power in the
	    Channel 1 exceeds high alarm level or is below low alarm level. 
	    If the ruijieFiberDDMSupportStatus is false or the Fiber module type is 
	    not QSFP+, the status is unknown(1)."
        ::= { ruijieFiberEntry 56 }

ruijieFiberChannel2TXpowerIntegerpart OBJECT-TYPE
        SYNTAX INTEGER
        MAX-ACCESS read-only
        STATUS current
        DESCRIPTION
            "The integer part of Tx power in Channel 1 of the QSFP+ 
	    Fiber module insered into the port. The value is in units of dbm.
	    If the ruijieFiberDDMSupportStatus is false or the Fiber module type is 
	    not QSFP+, the integer part of Tx power value in Channel 1 
	    is -100(means the value is invalid)."
        ::= { ruijieFiberEntry 57 }

ruijieFiberChannel2TXpowerDecimalpart OBJECT-TYPE
        SYNTAX INTEGER
        MAX-ACCESS read-only
        STATUS current
        DESCRIPTION
            "The decimal part of Tx power in Channel 1 of the QSFP+ 
	    Fiber module insered into the port. The value is in units of dbm.
	    If the ruijieFiberDDMSupportStatus is false or the Fiber module type is 
	    not QSFP+, the decimal part of Tx power value in Channel 2 
	    is -100(means the value is invalid)."
        ::= { ruijieFiberEntry 58 }

ruijieFiberChannel2TXpowerStatus OBJECT-TYPE
        SYNTAX INTEGER {
            unknown(1),
            ok(2),
            warning(3),
            alarm(4)
        }
        MAX-ACCESS read-only
        STATUS current
        DESCRIPTION
            "The status ok(2) indicates that the Tx power in the Channel 2 of QSFP+ is in
	    the normal level. The status warning(3) indicates that 
	    the Tx power in the Channel 2 exceeds high warning level or is below 
	    low warning level. The status alarm(4) indicates that the Tx power in the
	    Channel 2 exceeds high alarm level or is below low alarm level. 
	    If the ruijieFiberDDMSupportStatus is false or the Fiber module type is 
	    not QSFP+, the status is unknown(1)."
        ::= { ruijieFiberEntry 59 }

ruijieFiberChannel3TXpowerIntegerpart OBJECT-TYPE
        SYNTAX INTEGER
        MAX-ACCESS read-only
        STATUS current
        DESCRIPTION
            "The integer part of Tx power in Channel 3 of the QSFP+ 
	    Fiber module insered into the port. The value is in units of dbm.
	    If the ruijieFiberDDMSupportStatus is false or the Fiber module type is 
	    not QSFP+, the integer part of Tx power value in Channel 3 
	    is -100(means the value is invalid)."
        ::= { ruijieFiberEntry 60 }

ruijieFiberChannel3TXpowerDecimalpart OBJECT-TYPE
        SYNTAX INTEGER
        MAX-ACCESS read-only
        STATUS current
        DESCRIPTION
            "The decimal part of Tx power in Channel 3 of the QSFP+ 
	    Fiber module insered into the port. The value is in units of dbm.
	    If the ruijieFiberDDMSupportStatus is false or the Fiber module type is 
	    not QSFP+, the decimal part of Tx power value in Channel 3 
	    is -100(means the value is invalid)."
        ::= { ruijieFiberEntry 61 }

ruijieFiberChannel3TXpowerStatus OBJECT-TYPE
        SYNTAX INTEGER {
            unknown(1),
            ok(2),
            warning(3),
            alarm(4)
        }
        MAX-ACCESS read-only
        STATUS current
        DESCRIPTION
            "The status ok(2) indicates that the Tx power in the Channel 3 of QSFP+ is in
	    the normal level. The status warning(3) indicates that 
	    the Tx power in the Channel 3 exceeds high warning level or is below 
	    low warning level. The status alarm(4) indicates that the Tx power in the
	    Channel 3 exceeds high alarm level or is below low alarm level. 
	    If the ruijieFiberDDMSupportStatus is false or the Fiber module type is 
	    not QSFP+, the status is unknown(1)."
        ::= { ruijieFiberEntry 62 }

ruijieFiberChannel4TXpowerIntegerpart OBJECT-TYPE
        SYNTAX INTEGER
        MAX-ACCESS read-only
        STATUS current
        DESCRIPTION
            "The integer part of Tx power in Channel 4 of the QSFP+ 
	    Fiber module insered into the port. The value is in units of dbm.
	    If the ruijieFiberDDMSupportStatus is false or the Fiber module type is 
	    not QSFP+, the integer part of Tx power value in Channel 4 
	    is -100(means the value is invalid)."
        ::= { ruijieFiberEntry 63 }

ruijieFiberChannel4TXpowerDecimalpart OBJECT-TYPE
        SYNTAX INTEGER
        MAX-ACCESS read-only
        STATUS current
        DESCRIPTION
            "The decimal part of Tx power in Channel 4 of the QSFP+ 
	    Fiber module insered into the port. The value is in units of dbm.
	    If the ruijieFiberDDMSupportStatus is false or the Fiber module type is 
	    not QSFP+, the decimal part of Tx power value in Channel 4 
	    is -100(means the value is invalid)."
        ::= { ruijieFiberEntry 64 }

ruijieFiberChannel4TXpowerStatus OBJECT-TYPE
        SYNTAX INTEGER {
            unknown(1),
            ok(2),
            warning(3),
            alarm(4)
        }
        MAX-ACCESS read-only
        STATUS current
        DESCRIPTION
            "The status ok(2) indicates that the Tx power in the Channel 4 of QSFP+ is in
	    the normal level. The status warning(3) indicates that 
	    the Tx power in the Channel 4 exceeds high warning level or is below 
	    low warning level. The status alarm(4) indicates that the Tx power in the
	    Channel 4 exceeds high alarm level or is below low alarm level. 
	    If the ruijieFiberDDMSupportStatus is false or the Fiber module type is 
	    not QSFP+, the status is unknown(1)."
        ::= { ruijieFiberEntry 65 }

ruijieFiberRXpowerSign OBJECT-TYPE
        SYNTAX INTEGER
        MAX-ACCESS read-only
        STATUS current
        DESCRIPTION
            "The sign (-1) indicates that the Rx power value is lower than 0, while sign (1) is higher than 0."
        ::= { ruijieFiberEntry 66 }

ruijieFiberChannel1RXpowerSign OBJECT-TYPE
        SYNTAX INTEGER
        MAX-ACCESS read-only
        STATUS current
        DESCRIPTION
            "The sign (-1) indicates that the Rx power value is lower than 0, while sign (1) is higher than 0."
        ::= { ruijieFiberEntry 67 }

ruijieFiberChannel2RXpowerSign OBJECT-TYPE
        SYNTAX INTEGER
        MAX-ACCESS read-only
        STATUS current
        DESCRIPTION
            "The sign (-1) indicates that the Rx power value is lower than 0, while sign (1) is higher than 0."
        ::= { ruijieFiberEntry 68 }

ruijieFiberChannel3RXpowerSign OBJECT-TYPE
        SYNTAX INTEGER
        MAX-ACCESS read-only
        STATUS current
        DESCRIPTION
            "The sign (-1) indicates that the Rx power value is lower than 0, while sign (1) is higher than 0."
        ::= { ruijieFiberEntry 69 }

ruijieFiberChannel4RXpowerSign OBJECT-TYPE
        SYNTAX INTEGER
        MAX-ACCESS read-only
        STATUS current
        DESCRIPTION
            "The sign (-1) indicates that the Rx power value is lower than 0, while sign (1) is higher than 0."
        ::= { ruijieFiberEntry 70 }

ruijieFiberTXpowerSign OBJECT-TYPE
        SYNTAX INTEGER
        MAX-ACCESS read-only
        STATUS current
        DESCRIPTION
            "The sign (-1) indicates that the Tx power value is lower than 0, while sign (1) is higher than 0."
        ::= { ruijieFiberEntry 71 }

ruijieFiberChannel1TXpowerSign OBJECT-TYPE
        SYNTAX INTEGER
        MAX-ACCESS read-only
        STATUS current
        DESCRIPTION
            "The sign (-1) indicates that the Tx power value is lower than 0, while sign (1) is higher than 0."
        ::= { ruijieFiberEntry 72 }

ruijieFiberChannel2TXpowerSign OBJECT-TYPE
        SYNTAX INTEGER
        MAX-ACCESS read-only
        STATUS current
        DESCRIPTION
            "The sign (-1) indicates that the Tx power value is lower than 0, while sign (1) is higher than 0."
        ::= { ruijieFiberEntry 73 }

ruijieFiberChannel3TXpowerSign OBJECT-TYPE
        SYNTAX INTEGER
        MAX-ACCESS read-only
        STATUS current
        DESCRIPTION
            "The sign (-1) indicates that the Tx power value is lower than 0, while sign (1) is higher than 0."
        ::= { ruijieFiberEntry 74 }

ruijieFiberChannel4TXpowerSign OBJECT-TYPE
        SYNTAX INTEGER
        MAX-ACCESS read-only
        STATUS current
        DESCRIPTION
            "The sign (-1) indicates that the Tx power value is lower than 0, while sign (1) is higher than 0."
        ::= { ruijieFiberEntry 75 }

ruijieFiberAntifakeMIBTraps OBJECT IDENTIFIER ::= { ruijieFiberMIB 2 }      

ruijieFiberAntifakeIntfNameDesc OBJECT-TYPE
        SYNTAX DisplayString (SIZE(0..255))
        MAX-ACCESS accessible-for-notify
        STATUS current
        DESCRIPTION
          "The description of the interface."
        ::= { ruijieFiberAntifakeMIBTraps 1 }

ruijieFiberAntifakeSerialNumberDesc OBJECT-TYPE
        SYNTAX DisplayString (SIZE(0..255))
        MAX-ACCESS accessible-for-notify
        STATUS current
        DESCRIPTION
          "The description of the serial number of the fiber module." 
        ::= { ruijieFiberAntifakeMIBTraps 2 }
        
ruijieFiberAntifakeTrap NOTIFICATION-TYPE
        OBJECTS   {ruijieFiberAntifakeIntfNameDesc, ruijieFiberAntifakeSerialNumberDesc}
        STATUS     current
        DESCRIPTION
          "When detect the fiber module is not original raisecom fiber module, then this trap will be sent."
        ::= { ruijieFiberAntifakeMIBTraps 3 }                    

ruijieFiberMIBConformance OBJECT IDENTIFIER ::= { ruijieFiberMIB 3 }
ruijieFiberMIBCompliances OBJECT IDENTIFIER ::= { ruijieFiberMIBConformance 1 }
ruijieFiberMIBGroups      OBJECT IDENTIFIER ::= { ruijieFiberMIBConformance 2 }

-- ---------------------------------------------------------- --
-- compliance statements
-- ---------------------------------------------------------- --
ruijieFiberMIBConpliance MODULE-COMPLIANCE
        STATUS  current
        DESCRIPTION
                "The compliance statement for entities which implement
                the Raisecom Fiber MIB"
        MODULE  -- this module
                MANDATORY-GROUPS { 
                        ruijieFiberMIBGroup  
                }

                GROUP      ruijieFiberAntifakeIntfNameDescGroup
                DESCRIPTION
                     "This group is mandatory only for those system which support fiber antifake notification." 

                GROUP      ruijieFiberAntifakeSerialNumberDescGroup
                DESCRIPTION
                     "This group is mandatory only for those system which support fiber antifake notification." 

         ::= { ruijieFiberMIBCompliances 1 }
         
ruijieFiberMIBGroup OBJECT-GROUP
        OBJECTS {
                ruijieFiberPortDescr,
                ruijieFiberTransceiverType,
                ruijieFiberConnectorType,
                ruijieFiberWavelength,
                ruijieFiberTransferDistanceSMF,
                ruijieFiberTransferDistance62point5umOM1,
                ruijieFiberTransferDistance62point5um,
                ruijieFiberTransferDistance50umOM2,
                ruijieFiberTransferDistance50um,
                ruijieFiberTransferDistance50umOM3,
                ruijieFiberTransferDistanceEBW50um,
                ruijieFiberTransferDistanceCopper,
                ruijieFiberTransferDistanceCableAssembly,
                ruijieFiberDDMSupportStatus,
                ruijieFiberSerialNumber,
                ruijieFiberTemp,
                ruijieFiberTempStatus,
                ruijieFiberVoltage,
                ruijieFiberVoltageStatus,
                ruijieFiberBias,
                ruijieFiberBiasStatus,
                ruijieFiberChannel1Bias,
                ruijieFiberChannel1BiasStatus,
                ruijieFiberChannel2Bias,
                ruijieFiberChannel2BiasStatus,
                ruijieFiberChannel3Bias,
                ruijieFiberChannel3BiasStatus,
                ruijieFiberChannel4Bias,
                ruijieFiberChannel4BiasStatus,
                ruijieFiberRXpowerIntegerpart,
                ruijieFiberRXpowerDecimalpart,
                ruijieFiberRXpowertype,
                ruijieFiberRXpowerStatus,
                ruijieFiberChannel1RXpowerIntegerpart,
                ruijieFiberChannel1RXpowerDecimalpart,
                ruijieFiberChannel1RXpowertype,
                ruijieFiberChannel1RXpowerStatus,
                ruijieFiberChannel2RXpowerIntegerpart,
                ruijieFiberChannel2RXpowerDecimalpart,
                ruijieFiberChannel2RXpowertype,
                ruijieFiberChannel2RXpowerStatus,
                ruijieFiberChannel3RXpowerIntegerpart,
                ruijieFiberChannel3RXpowerDecimalpart,
                ruijieFiberChannel3RXpowertype,
                ruijieFiberChannel3RXpowerStatus,
                ruijieFiberChannel4RXpowerIntegerpart,
                ruijieFiberChannel4RXpowerDecimalpart,
                ruijieFiberChannel4RXpowertype,
                ruijieFiberChannel4RXpowerStatus,
                ruijieFiberTXpowerIntegerpart,
                ruijieFiberTXpowerDecimalpart,
                ruijieFiberTXpowerStatus,
                ruijieFiberChannel1TXpowerIntegerpart,
                ruijieFiberChannel1TXpowerDecimalpart,
                ruijieFiberChannel1TXpowerStatus,
                ruijieFiberChannel2TXpowerIntegerpart,
                ruijieFiberChannel2TXpowerDecimalpart,
                ruijieFiberChannel2TXpowerStatus,
                ruijieFiberChannel3TXpowerIntegerpart,
                ruijieFiberChannel3TXpowerDecimalpart,
                ruijieFiberChannel3TXpowerStatus,
                ruijieFiberChannel4TXpowerIntegerpart,
                ruijieFiberChannel4TXpowerDecimalpart,
                ruijieFiberChannel4TXpowerStatus,
                ruijieFiberRXpowerSign INTEGER,
                ruijieFiberChannel1RXpowerSign INTEGER,
                ruijieFiberChannel2RXpowerSign INTEGER,
                ruijieFiberChannel3RXpowerSign INTEGER,
                ruijieFiberChannel4RXpowerSign INTEGER,
                ruijieFiberTXpowerSign INTEGER,
                ruijieFiberChannel1TXpowerSign INTEGER,
                ruijieFiberChannel2TXpowerSign INTEGER,
                ruijieFiberChannel3TXpowerSign INTEGER,
                ruijieFiberChannel4TXpowerSign INTEGER, 
        }
        STATUS  current
        DESCRIPTION
                "A collection of objects providing Fiber managment."
        ::= { ruijieFiberMIBGroups 1 }

ruijieFiberAntifakeIntfNameDescGroup OBJECT-GROUP
        OBJECTS {ruijieFiberAntifakeIntfNameDesc}
        STATUS  current
        DESCRIPTION
                "Objects that providing a literal description of the interface."
        ::= { ruijieFiberMIBGroups 2 } 
	
ruijieFiberAntifakeSerialNumberDescGroup OBJECT-GROUP
        OBJECTS {ruijieFiberAntifakeSerialNumberDesc}
        STATUS  current
        DESCRIPTION
                "Objects that providing a literal description of the fiber module serial number."
        ::= { ruijieFiberMIBGroups 3 }
END
