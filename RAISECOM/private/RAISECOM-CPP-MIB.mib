-- *****************************************************************
-- RAISECOM-CPP-MIB.mib:  Raisecom CPP MIB file
--
-- Dec 2014, Linxiaojie
--
-- Copyright (c) 2012 by Raisecom Networks Co.,Ltd.
-- All rights reserved.
-- 
-- *****************************************************************
--

RAISECOM-CPP-MIB DEFINITIONS ::= BEGIN

IMPORTS
        MODULE-IDENTITY,
        OBJECT-TYPE,
        NOTIFICATION-TYPE,
        Integer32,
        OBJECT-TYPE
                FROM SNMPv2-SMI
        TruthValue,
        DisplayString
                FROM SNMPv2-TC
        MODULE-COMPLIANCE,
        OBJECT-GROUP
                FROM SNMPv2-CONF
        ruijieMgmt
                FROM RAISECOM-SMI;

ruijieCPPMIB MODULE-IDENTITY
        LAST-UPDATED "201412192100Z"
        ORGANIZATION "Raisecom Networks Co.,Ltd."
        CONTACT-INFO
                " 
                Tel: 4008-111-000 

                E-mail: service@raisecom.com.cn"
        DESCRIPTION
                "This module defines raisecom cpp mibs."
        REVISION      "201412192100Z"
        DESCRIPTION
                "Add a table about cpp."
        REVISION      "201412192100Z"
        DESCRIPTION
                "Initial version of this MIB module."
        ::= { ruijieMgmt 132 }

ruijieCPPMIBObjects OBJECT IDENTIFIER ::= { ruijieCPPMIB 1 }

ruijieCPPTable OBJECT-TYPE
        SYNTAX 			SEQUENCE OF RuijieCPPEntry
        MAX-ACCESS 	not-accessible
        STATUS 			current
        DESCRIPTION
            " "
        ::= { ruijieCPPMIBObjects 1 }

ruijieCPPEntry OBJECT-TYPE
        SYNTAX 			RuijieCPPEntry
        MAX-ACCESS 	not-accessible
        STATUS 			current
        DESCRIPTION
            " "
        INDEX { cppIndex }
        ::= { ruijieCPPTable 1 }

RuijieCPPEntry ::=
        SEQUENCE {
            cppIndex			Integer32,
            cppDeviceId			Integer32,
            cppSlotId			Integer32,
            cppCardIndex		DisplayString,
            cppPacketType		DisplayString,
            cppTrafficClass		Integer32,
            cppBandwidth		Integer32,
            cppRate			Integer32,
            cppDrop			Integer32,
            cppTotal			Integer32,
            cppTotalDrop		Integer32
        }
cppIndex OBJECT-TYPE
        SYNTAX 			Integer32 (1..2147483647)
        MAX-ACCESS 	read-only
        STATUS 			current
        DESCRIPTION
            " "
        ::= { ruijieCPPEntry 1 }

cppDeviceId OBJECT-TYPE
        SYNTAX 			Integer32 (1..2147483647)
        MAX-ACCESS 	read-only
        STATUS 			current
        DESCRIPTION
            " "
        ::= { ruijieCPPEntry 2 }

cppSlotId OBJECT-TYPE
        SYNTAX 			Integer32 (1..2147483647)
        MAX-ACCESS 	read-only
        STATUS 			current
        DESCRIPTION
            " "
        ::= { ruijieCPPEntry 3 }

cppCardIndex OBJECT-TYPE
        SYNTAX DisplayString(SIZE (1..32))
        MAX-ACCESS read-only
        STATUS current
        DESCRIPTION
            " "
        ::= { ruijieCPPEntry 4 }

cppPacketType OBJECT-TYPE
        SYNTAX DisplayString(SIZE (1..32))
        MAX-ACCESS read-only
        STATUS current
        DESCRIPTION
            " "
        ::= { ruijieCPPEntry 5 }

cppTrafficClass OBJECT-TYPE
        SYNTAX 			Integer32 (1..2147483647)
        MAX-ACCESS 	read-only
        STATUS 			current
        DESCRIPTION
            " "
        ::= { ruijieCPPEntry 6 }

cppBandwidth OBJECT-TYPE
        SYNTAX 			Integer32 (1..2147483647)
        MAX-ACCESS 	read-only
        STATUS 			current
        DESCRIPTION
            " "
        ::= { ruijieCPPEntry 7 }

cppRate OBJECT-TYPE
        SYNTAX 			Integer32 (1..2147483647)
        MAX-ACCESS 	read-only
        STATUS 			current
        DESCRIPTION
            " "
        ::= { ruijieCPPEntry 8 }

cppDrop OBJECT-TYPE
        SYNTAX 			Integer32 (1..2147483647)
        MAX-ACCESS 	read-only
        STATUS 			current
        DESCRIPTION
            " "
        ::= { ruijieCPPEntry 9 }

cppTotal OBJECT-TYPE
        SYNTAX 			Integer32 (1..2147483647)
        MAX-ACCESS 	read-only
        STATUS 			current
        DESCRIPTION
            " "
        ::= { ruijieCPPEntry 10 }

cppTotalDrop OBJECT-TYPE
        SYNTAX 			Integer32 (1..2147483647)
        MAX-ACCESS 	read-only
        STATUS 			current
        DESCRIPTION
            " "
        ::= { ruijieCPPEntry 11 }

END
