-- *****************************************************************
-- RAISECOM-PATCH-MIB.mib:  Raisecom patch MIB file
--
-- Sep 2016, gaojinli
--
-- Copyright (c) 2016 by Raisecom Networks Co.,Ltd.
-- All rights reserved.
-- 
-- *****************************************************************
--

RAISECOM-PATCH-MIB DEFINITIONS ::= BEGIN

IMPORTS
        MODULE-IDENTITY,
        OBJECT-TYPE,
        Integer32,
        Unsigned32,
        Counter64,
        IpAddress
                FROM SNMPv2-SMI
        TruthValue,
        DisplayString,
        RowStatus,
        MacAddress
                FROM SNMPv2-TC
        MODULE-COMPLIANCE,
        OBJECT-GROUP
                FROM SNMPv2-CONF
        IfIndex,
        ConfigStatus
                FROM RAISECOM-TC        
        ruijieMgmt
                FROM RAISECOM-SMI;
				
ruijiePatchMIB MODULE-IDENTITY
        LAST-UPDATED "201609230000Z"
        ORGANIZATION "Raisecom Networks Co.,Ltd."
        CONTACT-INFO
                " 
                Tel: 4008-111-000 

                E-mail: service@raisecom.com.cn"
        DESCRIPTION
                "This module defines raisecom system patch mibs."
        REVISION      "201609230000Z"
        DESCRIPTION
                "Initial version of this MIB module."
        ::= { ruijieMgmt 151}

ruijiePatchMIBObjects OBJECT IDENTIFIER ::= { ruijiePatchMIB 1 }

ruijiePatchTable OBJECT-TYPE
        SYNTAX SEQUENCE OF RuijiePatchEntry
        MAX-ACCESS not-accessible
        STATUS current
        DESCRIPTION
               "A table of patch entries."
        ::= { ruijiePatchMIBObjects 1 }

ruijiePatchEntry OBJECT-TYPE
        SYNTAX RuijiePatchEntry
        MAX-ACCESS not-accessible
        STATUS current
        DESCRIPTION
                "Entry contains patch details."  
        INDEX { ruijiePatchDevIndex,
                ruijiePatchCmpntIndex}
        ::= { ruijiePatchTable 1 }

RuijiePatchEntry ::=
        SEQUENCE {
                ruijiePatchDevIndex Integer32,
                ruijiePatchCmpntIndex  Integer32,
                ruijiePatchDevId Integer32,
                ruijiePatchSlotId  Integer32,
                ruijiePatchCpuId Integer32,
                ruijiePatchExist DisplayString,
                ruijiePatchName DisplayString,
                ruijiePatchBranch DisplayString,
                ruijiePatchCmpntName DisplayString,
                ruijiePatchSize Counter64,
                ruijiePatchStatus DisplayString,
                ruijiePatchVersion  DisplayString,
                ruijiePatchInstallTime DisplayString,
                ruijiePatchDescription DisplayString
        }

ruijiePatchDevIndex OBJECT-TYPE
        SYNTAX        Integer32
        MAX-ACCESS read-only
        STATUS current
        DESCRIPTION
            "An index that represents a Devices."
        ::= { ruijiePatchEntry 1 }
		
ruijiePatchCmpntIndex OBJECT-TYPE
        SYNTAX        Integer32
        MAX-ACCESS read-only
        STATUS current
        DESCRIPTION
            "An index that represents a Patch Component."
        ::= { ruijiePatchEntry 2 }

ruijiePatchDevId OBJECT-TYPE
        SYNTAX        Integer32
        MAX-ACCESS read-only
        STATUS current
        DESCRIPTION
            "Device Identification."
        ::= { ruijiePatchEntry 3 }
		
ruijiePatchSlotId OBJECT-TYPE
        SYNTAX        Integer32
        MAX-ACCESS read-only
        STATUS current
        DESCRIPTION
            "Slot Identification."
        ::= { ruijiePatchEntry 4 }
		
ruijiePatchCpuId OBJECT-TYPE
        SYNTAX        Integer32
        MAX-ACCESS read-only
        STATUS current
        DESCRIPTION
            "Cpu Identification."
        ::= { ruijiePatchEntry 5 }
		
ruijiePatchExist OBJECT-TYPE
        SYNTAX        DisplayString
        MAX-ACCESS read-only
        STATUS current
        DESCRIPTION
            "Whether there is a Patch exist in the system."
        ::= { ruijiePatchEntry 6 }

ruijiePatchName OBJECT-TYPE
        SYNTAX        DisplayString
        MAX-ACCESS    read-only
        STATUS        current
        DESCRIPTION
            "The Patch Name."
        ::= { ruijiePatchEntry 7 }
		
ruijiePatchBranch OBJECT-TYPE
        SYNTAX        DisplayString
        MAX-ACCESS    read-only
        STATUS        current
        DESCRIPTION
            "The Patch Branch."
        ::= { ruijiePatchEntry 8 }
		
ruijiePatchCmpntName OBJECT-TYPE
        SYNTAX        DisplayString
        MAX-ACCESS    read-only
        STATUS        current
        DESCRIPTION
            "The Component name of a Patch."
        ::= { ruijiePatchEntry 9 }
		
ruijiePatchSize OBJECT-TYPE
        SYNTAX        Counter64
        MAX-ACCESS    read-only
        STATUS        current
        DESCRIPTION
            "The size of the Patch Component."
        ::= { ruijiePatchEntry 10 }
		
ruijiePatchStatus OBJECT-TYPE
        SYNTAX        DisplayString
        MAX-ACCESS    read-only
        STATUS        current
        DESCRIPTION
            "Currtent status of the Patch."
        ::= { ruijiePatchEntry 11 }
		
ruijiePatchVersion OBJECT-TYPE
        SYNTAX        DisplayString
        MAX-ACCESS    read-only
        STATUS        current
        DESCRIPTION
            "The Patch Version."
        ::= { ruijiePatchEntry 12 }
		
ruijiePatchInstallTime OBJECT-TYPE
        SYNTAX        DisplayString
        MAX-ACCESS    read-only
        STATUS        current
        DESCRIPTION
            "The Patch Install time."
        ::= { ruijiePatchEntry 13 }
		
ruijiePatchDescription OBJECT-TYPE
        SYNTAX        DisplayString
        MAX-ACCESS    read-only
        STATUS        current
        DESCRIPTION
            "The Patch Description."
        ::= { ruijiePatchEntry 14 }

END
