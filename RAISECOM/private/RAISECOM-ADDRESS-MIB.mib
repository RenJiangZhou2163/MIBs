-- *****************************************************************
-- RAISECOM-ADDRESS-MIB.mib:  Raisecom Address MIB file
--
-- March 2002, Wuzg
--
-- Copyright (c) 2002 by Raisecom Networks Co.,Ltd.
-- All rights reserved.
-- 
-- *****************************************************************
--

RAISECOM-ADDRESS-MIB DEFINITIONS ::= BEGIN

IMPORTS
        MODULE-IDENTITY,
        OBJECT-TYPE,
        NOTIFICATION-TYPE,
        Integer32,
        Unsigned32
                FROM SNMPv2-SMI
        RowStatus,
        TimeStamp,
        MacAddress
                FROM SNMPv2-TC
        MODULE-COMPLIANCE,
        OBJECT-GROUP
                FROM SNMPv2-CONF
        IfIndex
                FROM RAISECOM-TC
        EnabledStatus 
                FROM P-BRIDGE-MIB
        ruijieMgmt
                FROM RAISECOM-SMI;

ruijieAddressMIB MODULE-IDENTITY
        LAST-UPDATED "200203200000Z"
        ORGANIZATION "Raisecom Networks Co.,Ltd."
        CONTACT-INFO
                " 
                Tel: 4008-111-000 

                E-mail: service@raisecom.com.cn"
        DESCRIPTION
                "This module defines raisecom address mibs."
        REVISION      "200203200000Z"
        DESCRIPTION
                "Initial version of this MIB module."
        ::= { ruijieMgmt 22}

ruijieAddressMIBObjects OBJECT IDENTIFIER ::= { ruijieAddressMIB 1 }

ruijieAddressManagementObjects OBJECT IDENTIFIER ::= { ruijieAddressMIBObjects 1 }

ruijieAddressNotificationObjects OBJECT IDENTIFIER ::= { ruijieAddressMIBObjects 2 }

 
--
-- raisecom Address Filter 
--
ruijieDynamicAddressCurrentNum OBJECT-TYPE
        SYNTAX Integer32
        MAX-ACCESS read-only
        STATUS current
        DESCRIPTION
              "The currunt number of dynamic MAC address ."
    ::= { ruijieAddressManagementObjects 1 } 
    
ruijieStaticAddressCurrentNum OBJECT-TYPE
        SYNTAX Integer32
        MAX-ACCESS read-only
        STATUS current
        DESCRIPTION
              "The currunt number of static MAC address ."
    ::= { ruijieAddressManagementObjects 2 }

ruijieFilterAddressCurrentNum OBJECT-TYPE
        SYNTAX Integer32
        MAX-ACCESS read-only
        STATUS current
        DESCRIPTION
              "Current number of the filtering MAC address."
    ::= { ruijieAddressManagementObjects 3 }

ruijieAddressAvailableNum OBJECT-TYPE
        SYNTAX Integer32
        MAX-ACCESS read-only
        STATUS current
        DESCRIPTION
              "Total Mac Address Space Available."
    ::= { ruijieAddressManagementObjects 4 }

ruijieMacAddressTable OBJECT-TYPE
        SYNTAX  SEQUENCE OF RuijieMacAddressEntry
        MAX-ACCESS  not-accessible
        STATUS  current
        DESCRIPTION
              "The table of address MAC address include dynamic mac address,
               static mac address and filter mac address."
    ::= { ruijieAddressManagementObjects 5 }

ruijieMacAddressEntry OBJECT-TYPE
        SYNTAX  RuijieMacAddressEntry
        MAX-ACCESS  not-accessible
        STATUS  current
        DESCRIPTION
              "The entry of MAC address table."
        INDEX   { ruijieMacAddressFdbId,ruijieMacAddress}
    ::= { ruijieMacAddressTable 1 }

 RuijieMacAddressEntry ::=
     SEQUENCE {
             ruijieMacAddressFdbId Unsigned32,
             ruijieMacAddress MacAddress,
             ruijieMacAddressPort IfIndex,
             ruijieMacAddressType INTEGER,      
             ruijieMacAddressStatus RowStatus                    
   }

ruijieMacAddressFdbId OBJECT-TYPE
        SYNTAX       Unsigned32
        MAX-ACCESS   read-only
        STATUS       current
        DESCRIPTION
            "The VID of vlan which the Address address blongs to."
    ::= { ruijieMacAddressEntry 1 }
    
ruijieMacAddress OBJECT-TYPE
        SYNTAX  MacAddress
        MAX-ACCESS  read-only
        STATUS  current
        DESCRIPTION
              "The MAC address which will be address static address."
    ::= { ruijieMacAddressEntry 2 }

ruijieMacAddressPort OBJECT-TYPE
        SYNTAX       IfIndex
        MAX-ACCESS   read-create
        STATUS       current
        DESCRIPTION
            "Interface(port or trunk) number of the port from which a frame must
             be received in order  for this entry's filtering information to apply."
    ::= { ruijieMacAddressEntry 3 }
    
ruijieMacAddressType OBJECT-TYPE
        SYNTAX  INTEGER {
                  dynamic(1),
                  static(2),
                  filter(3)                   
              }
        MAX-ACCESS  read-create
        STATUS  current
        DESCRIPTION
              "Only 'static' and 'filter' allow to be set to this object."
    ::= { ruijieMacAddressEntry 4 }
        
ruijieMacAddressStatus OBJECT-TYPE
        SYNTAX RowStatus
        MAX-ACCESS read-create
        STATUS current
        DESCRIPTION
            "entry status of this entry. and the means in this enviraments can
            reffer to the text-convention definition of the RowStatus."
    ::= { ruijieMacAddressEntry 5 }


--Address Notification
ruijieMacNotiGlobalEnabled  OBJECT-TYPE
    SYNTAX        EnabledStatus
    MAX-ACCESS    read-write
    STATUS        current
    DESCRIPTION
        "Indicates whether the MAC notification feature is currently 
         running in the device.

        Setting this object to disabled(2) disables the MAC notification
        feature globally thus disabling the feature at each interface.

        Setting this object to enabled(1) will start the MAC notification
        feature running in the device. If the feature is already
        running, setting to enabled(1) has no effect. Once the MAC
        notification is enabled, whether the feature is running at each
        interface is controlled by the ruijieMacNotiIfCfgTable."   
        
    ::= { ruijieAddressNotificationObjects 1 }

ruijieMacNotificationInterval  OBJECT-TYPE
    SYNTAX        Unsigned32 (0..3600)
    MAX-ACCESS    read-write
    STATUS        current
    DESCRIPTION
        "This object specifies the maximum interval of time in units of seconds
         between MacChangedNotifications being generated by the device.
        
        If the value of ruijieMacNotiGlobalEnabled is eanbled(1), the
        device will send out the generated MacChangedNotifications
        and archive the MAC change notification events in the
        RuijieMacNotiHisTable.  
        
        If the value of this object is equal to 0, the device will 
        generate MacChangedNotifications and archive the MAC 
        change notification events in the RuijieMacNotiHisTable as soon as
        there is MAC address learnt or removed by the device.

        If the value of this object is greater than 0, the device will
        wait for a period of time equal to the value of this object
        before generate the MacChangedNotifications and archive
        the MAC change notification events in the RuijieMacNotiHisTable."
    DEFVAL { 1 }
    ::= { ruijieAddressNotificationObjects 2 }

ruijieMacNotiHisTableMaxLength OBJECT-TYPE
    SYNTAX          Unsigned32 (0..200)
    MAX-ACCESS      read-write
    STATUS          current
    DESCRIPTION
        "The upper limit on the number of entries that the
        RuijieMacNotiHisTable may contain.  A value of 0 will
        prevent any history from being retained. When this
        table is full, the oldest entry will be deleted and
        a new one will be created."
    DEFVAL  { 50 }
    ::= { ruijieAddressNotificationObjects 3 }
    
ruijieMacNotiHisTableCurrentLength OBJECT-TYPE
    SYNTAX          Unsigned32   
    MAX-ACCESS      read-only
    STATUS          current
    DESCRIPTION
        "The number of entries that the RuijieMacNotiHisTable contain currently."
    ::= { ruijieAddressNotificationObjects 4 }    

ruijieMacNotiHisTable OBJECT-TYPE
    SYNTAX     SEQUENCE OF RuijieMacNotiHisEntry
    MAX-ACCESS not-accessible
    STATUS     current
    DESCRIPTION
        "This table will archive the dynamic MAC change notification events 
        generated by this device."
    ::= { ruijieAddressNotificationObjects 5 }

ruijieMacNotiHisEntry OBJECT-TYPE
    SYNTAX     RuijieMacNotiHisEntry
    MAX-ACCESS not-accessible
    STATUS     current
    DESCRIPTION
        "A dynamic MAC change notification message that was previously
        generated by this device.  Each entry is indexed by a message
        index."
    INDEX   { ruijieMacNotiHisIndex }
    ::= { ruijieMacNotiHisTable 1 }

RuijieMacNotiHisEntry ::=
    SEQUENCE {
        ruijieMacNotiHisIndex
                Unsigned32,
        ruijieMacNotiHisMacChangedMsg
                OCTET STRING,
        ruijieMacNotiHisTimestamp
                TimeStamp
    }

ruijieMacNotiHisIndex OBJECT-TYPE
    SYNTAX          Unsigned32 (1..4294967295)
    MAX-ACCESS      read-only
    STATUS          current
    DESCRIPTION
        "An index that uniquely identifies a MAC change notification
        event previously generated by the device. This index ruijies at
        1 and increases by one when a MAC change notification is 
        generated.  When it reaches the maximum value, the agent wraps
        the value back to 1."
    ::= { ruijieMacNotiHisEntry 1 }

ruijieMacNotiHisMacChangedMsg OBJECT-TYPE
    SYNTAX        OCTET STRING (SIZE(1..254))
    MAX-ACCESS    read-only
    STATUS        current
    DESCRIPTION
        "This object contains the information of a MAC change
        notification event. It consists of several sections packed
        together in the format of '<section1><section2>...'.
        
        Each tuple consist of 11 octets in the format of
        '<operation><VLAN><MAC><Interface>' where 

        <operation> is of size 1 octet and supports the following values
          0 - End of MIB object.
          1 - MAC learnt.
          2 - MAC removed.

        <VLAN> is vlan number of the VLAN which the MAC address is
        belonged to and has size of 2 octet.

        <MAC> is the Layer2 Mac Address and has size of 6 octets.

        <Interface> is the value for the interface from which the MAC 
        address is learnt and has size of 2 octets."
    ::= { ruijieMacNotiHisEntry 2 }

ruijieMacNotiHisTimestamp  OBJECT-TYPE
    SYNTAX          TimeStamp
    MAX-ACCESS      read-only
    STATUS          current
    DESCRIPTION
        "The value of sysUpTime when the MacChangedNotification
        containing the information denoted by the ruijieMacNotiHisMacChangedMsg
        object in this entry was generated."
    ::= { ruijieMacNotiHisEntry 3 }


-- Raisecom Mac Notification Interface Config Table

ruijieMacNotiIfCfgTable  OBJECT-TYPE
    SYNTAX        SEQUENCE OF RuijieMacNotiIfCfgEntry
    MAX-ACCESS    not-accessible
    STATUS        current
    DESCRIPTION
        "This table enables or disables the generation of notification
        at each interface when MAC address is learnt or removed." 
    ::= { ruijieAddressNotificationObjects 6 }

ruijieMacNotiIfCfgEntry  OBJECT-TYPE
    SYNTAX        RuijieMacNotiIfCfgEntry
    MAX-ACCESS    not-accessible
    STATUS        current
    DESCRIPTION
        "Each entry contains the configuration for enabling the
        MAC notification at each interface that supports this
        feature." 
    INDEX { ruijieMacNotiIfIndex }
    ::= { ruijieMacNotiIfCfgTable 1 }

RuijieMacNotiIfCfgEntry  ::= SEQUENCE {
    ruijieMacNotiIfIndex IfIndex,
    ruijieIfMacAddrLearntEnable    EnabledStatus, 
    ruijieIfMacAddrRemovedEnable   EnabledStatus 
}

ruijieMacNotiIfIndex OBJECT-TYPE
     SYNTAX   IfIndex
     MAX-ACCESS   read-only
     STATUS   current
     DESCRIPTION
            "IfIndex vale of interface."
    ::= { ruijieMacNotiIfCfgEntry 1 }
       
ruijieIfMacAddrLearntEnable OBJECT-TYPE
    SYNTAX        EnabledStatus 
    MAX-ACCESS    read-write
    STATUS        current
    DESCRIPTION
        "Indicates whether this interface is enabled to send 
        MacChangedNotification when it learns a new MAC address. This
        variable has no effect when the value of ruijieMacNotiGlobalEnabled
        object is disabled(2).

        Setting this object to enabled(1) enables the sending of
        MacChangedNotification when this interface learns a 
        new MAC address.

        Setting this object to disabled(2) disables the sending
        of MacChangedNotification when this interface learns
        a new MAC address."      
    DEFVAL { disabled }
    ::= { ruijieMacNotiIfCfgEntry 2 }

ruijieIfMacAddrRemovedEnable OBJECT-TYPE
    SYNTAX        EnabledStatus 
    MAX-ACCESS    read-write
    STATUS        current
    DESCRIPTION
        "Indicates whether this interface is enabled to send 
        MacChangedNotification when a MAC address which it learnt
        previously is removed from the forwarding table. This variable
        has no effect when the value of ruijieMacNotiGlobalEnabled object
        is disabled(2). 

        Setting this object to enabled(1) enables the sending of
        MacChangedNotification when a MAC address which this
        interface learnt previously is removed from the forwarding
        table.

        Setting this object to disabled(2) disables the sending of
        MacChangedNotification when a MAC address which this
        interface learnt previously is removed from the forwarding
        table."
    DEFVAL { disabled }
    ::= { ruijieMacNotiIfCfgEntry 3 }


ruijieMacIfLearnTable  OBJECT-TYPE
    SYNTAX        SEQUENCE OF RuijieMacIfLearnEntry
    MAX-ACCESS    not-accessible
    STATUS        current
    DESCRIPTION
        "This table enables or disables the generation of notification
        at each interface when MAC address learning enable or disable." 
    ::= { ruijieAddressNotificationObjects 7 }

ruijieMacIfLearnEntry  OBJECT-TYPE
    SYNTAX        RuijieMacIfLearnEntry
    MAX-ACCESS    not-accessible
    STATUS        current
    DESCRIPTION
        "The configuration of each entry illustrates whether each 
         interface supports the MAC address-learning ability." 
    INDEX { ruijieMacIfLearnIfIndex }
    ::= { ruijieMacIfLearnTable 1 }

RuijieMacIfLearnEntry  ::= SEQUENCE {
    ruijieMacIfLearnIfIndex IfIndex,
    ruijieMacIfLearnEnable  EnabledStatus 
}

ruijieMacIfLearnIfIndex OBJECT-TYPE
     SYNTAX   IfIndex
     MAX-ACCESS   read-only
     STATUS   current
     DESCRIPTION
            "IfIndex vale of interface."
    ::= { ruijieMacIfLearnEntry 1 }
       
ruijieMacIfLearnEnable OBJECT-TYPE
    SYNTAX        EnabledStatus 
    MAX-ACCESS    read-write
    STATUS        current
    DESCRIPTION
        "Indicates whether this interface is enabled to learn MAC address. 
         This variable has no effect when the value of ruijieMacIfLearnEnable
         object is disabled(2).

        Setting this object to be enabled(1) enables the interface to learn MAC address.

        Setting this object to be disabled(2) disables the interface to learn MAC address."      
    DEFVAL { enabled }
    ::= { ruijieMacIfLearnEntry 2 }

ruijieMacGlobalLearnEnabled  OBJECT-TYPE
    SYNTAX        EnabledStatus
    MAX-ACCESS    read-write
    STATUS        current
    DESCRIPTION
        "Indicates whether this device is enabled to learn MAC address. 
        Setting this object to be enabled(1) enables the device to learn MAC address.
        Setting this object to be disabled(2) disables the device to learn MAC address."      
    DEFVAL { enabled }
    ::= { ruijieAddressNotificationObjects 8 }
    
--
-- Notification 
--

ruijieAddressTraps      OBJECT IDENTIFIER ::= { ruijieAddressMIB 2 }

macChangedNotification NOTIFICATION-TYPE
    OBJECTS { ruijieMacNotiHisMacChangedMsg} 
    STATUS  current
    DESCRIPTION
        "This notification is generated when there is enough MAC
        address information to fully occupy a maximum size SNMP trap
        message. This notification is also generated when there
        is at least one MAC address changed or removed and the amount
        of time elapsed from the previous notification is greater
        than the maximum wait time denoted by ruijieMacNotificationInterval object. 

        If there are more MAC addresses information than can fit into
        one ruijieMacNotiHisMacChangedMsg object, then multiple notifications
        will be generated." 
    ::= { ruijieAddressTraps 1 } 
    
    
ruijieAddressMIBConformance OBJECT IDENTIFIER ::= { ruijieAddressMIB 3 }
ruijieAddressMIBCompliances OBJECT IDENTIFIER ::= { ruijieAddressMIBConformance 1 }
ruijieAddressMIBGroups      OBJECT IDENTIFIER ::= { ruijieAddressMIBConformance 2 }


-- compliance statements

ruijieAddressMIBCompliance MODULE-COMPLIANCE
        STATUS  current
        DESCRIPTION
                "The compliance statement for entities which implement
                the Raisecom MAC Address MIB"
        MODULE  -- this module
                MANDATORY-GROUPS { ruijieMacAddressMIBGroup,
                                   ruijieAddressNotificationMIBGroup
                 }
        ::= { ruijieAddressMIBCompliances 1 }
                
-- units of conformance
       
ruijieMacAddressMIBGroup OBJECT-GROUP
        OBJECTS {
                ruijieDynamicAddressCurrentNum,
                ruijieStaticAddressCurrentNum,
                ruijieFilterAddressCurrentNum,
                ruijieAddressAvailableNum,       
                ruijieMacAddressFdbId,
                ruijieMacAddress,
                ruijieMacAddressPort,
                ruijieMacAddressType,      
                ruijieMacAddressStatus
        }
        STATUS  current
        DESCRIPTION
                "A collection of objects providing address address to a
                Raisecom agent."
        ::= { ruijieAddressMIBGroups 1 }                         
        
ruijieAddressNotificationMIBGroup OBJECT-GROUP
        OBJECTS {
                ruijieMacNotiGlobalEnabled,
                ruijieMacNotificationInterval,
                ruijieMacNotiHisTableMaxLength,
                ruijieMacNotiHisTableCurrentLength,
                ruijieMacNotiHisIndex,
                ruijieMacNotiHisMacChangedMsg,
                ruijieMacNotiHisTimestamp,
                ruijieMacNotiIfIndex,
                ruijieIfMacAddrLearntEnable, 
                ruijieIfMacAddrRemovedEnable
        }
        STATUS  current
        DESCRIPTION
                "A collection of objects providing port address to a
                Raisecom agent."
        ::= { ruijieAddressMIBGroups 2 }                                         
        
END
