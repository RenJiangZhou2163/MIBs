-- *****************************************************************
-- RAISECOM-GATEWAY-SMI.mib: Raisecom GATEWAY SMI File
-- 
-- May. 2010, panshiyong
--
-- Copyright (c) 2010 by Raisecom Networks Co.,Ltd.
-- All rights reserved.
-- 
-- *****************************************************************
--

RAISECOM-GATEWAY-SMI DEFINITIONS ::= BEGIN

IMPORTS
        MODULE-IDENTITY,
        OBJECT-IDENTITY
                FROM SNMPv2-SMI
        products
                FROM RAISECOM-SMI;
                
gateway          OBJECT IDENTIFIER ::= { products 5 }

gatewayMib MODULE-IDENTITY
        LAST-UPDATED "201005250000Z"
        ORGANIZATION "Raisecom Networks Co.,Ltd."
        CONTACT-INFO
                " 
                Tel: 4008-111-000 

                E-mail: service@raisecom.com.cn"
        DESCRIPTION
                "The Structure of Management Information for the
                 Raisecom enterprise."
        REVISION      "201005250000Z"
        DESCRIPTION
                "Initial version of this MIB module."
        ::= { gateway 1 }        

ruijieGatewayProducts OBJECT-IDENTITY
        STATUS  current
        DESCRIPTION
                "ruijieGatewayProducts is the root OBJECT IDENTIFIER from
                 which sysObjectID values are assigned for gateway.  Actual
                 values are defined in RAISECOM-PRODUCTS-MIB."
        ::= { gatewayMib 1 }
        
END
