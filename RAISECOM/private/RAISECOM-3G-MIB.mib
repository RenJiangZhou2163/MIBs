-- ====================================================================
-- Copyright (c) 2011 by Raisecom Networks Co.,Ltd. All rights reserved.
--
-- Description: The MIB is designed to get 3G wireless safenet solution statistic information.
-- Reference: rujie Enterprise MIB
-- =====================================================================

RAISECOM-3G-MIB DEFINITIONS ::= BEGIN

    IMPORTS
        DisplayString,TEXTUAL-CONVENTION,TimeStamp
            FROM SNMPv2-TC
        IpAddress, Integer32, Counter32, Counter64, OBJECT-TYPE,
        MODULE-IDENTITY, Gauge32, NOTIFICATION-TYPE, Unsigned32
            FROM SNMPv2-SMI
        MODULE-COMPLIANCE, OBJECT-GROUP, NOTIFICATION-GROUP
            FROM SNMPv2-CONF
        ruijieMgmt
            FROM RAISECOM-SMI;

    ruijie3GMonitor MODULE-IDENTITY
        LAST-UPDATED "201102220000Z"            
        ORGANIZATION
            "Raisecom Networks Co.,Ltd."
        CONTACT-INFO
            "Tel: 4008-111-000 
             E-mail: service@raisecom.com.cn"  
        DESCRIPTION
            "The MIB is designed to get statistic information of
             3G wireless safenet. With this MIB, we can get information of a certain
             3G user or all users."
        REVISION      "201102220000Z"
        DESCRIPTION
                "Initial version of this MIB module."
        ::= { ruijieMgmt 95 }       
                               
                       
-- ========================================================================
-- Node definitions
-- ========================================================================
--Begin the node of ruijie3GObjects.

    ruijie3GObjects OBJECT IDENTIFIER ::= { ruijie3GMonitor 1 }

-- ===============================================
-- Begin the table of ruijie3GTable.
-- ===============================================

    ruijie3GTable OBJECT-TYPE
        SYNTAX SEQUENCE OF Ruijie3GEntry
        MAX-ACCESS not-accessible
        STATUS current
        DESCRIPTION
            "The 3G connection infomation fot every user. There is one
             entry in this table for each active 3G connection."
        ::= { ruijie3GObjects 1 }

    ruijie3GEntry OBJECT-TYPE
        SYNTAX Ruijie3GEntry
        MAX-ACCESS not-accessible
        STATUS current
        DESCRIPTION
            "Information about ruijie3GTunnelTable."
        INDEX { ruijie3GIPAddr }
        ::= { ruijie3GTable 1 }
    
    Ruijie3GEntry ::=
        SEQUENCE {
            ruijie3gUsername
                DisplayString,
            ruijie3GOnlineStatus
            	INTEGER, 
            ruijie3GIMEI
                DisplayString,
            ruijie3GIPAddrType
            	INTEGER,
            ruijie3GIPAddr
            	IpAddress,
            ruijie3GUplineTime
                TimeStamp,
            ruijie3GActiveTime
           	    Integer32,
            ruijie3GSignalStrength
           	    Integer32,
            ruijie3GISP
           	    INTEGER,
            ruijie3GSysMode
           	    INTEGER,
            ruijie3GServiceStatus        		
            	INTEGER,
            ruijie3GRoamingStatus
                INTEGER,
            ruijie3GDomain        
            	INTEGER,
            ruijie3GSIMStatus
                INTEGER,
   	    ruijie3GSignalStrengthPercent
                Integer32,
            ruijie3GApn
                DisplayString,
            ruijie3GCellID
                Integer32,
            ruijie3GLAC
                Integer32,
            ruijie3GBSID
                Integer32,
            ruijie3GSID
                Integer32,
            ruijie3GNID 
                Integer32,
            ruijie3GIMSI
                DisplayString,
            ruijie3GESN
                DisplayString,
            ruijie3GPhoneNumber
                DisplayString,
            ruijie3GifIndex
                INTEGER,
            ruijie3GBSLONG
                Integer32,
            ruijie3GBSLAT
                Integer32,
	    ruijie3GBackupInfo
	            INTEGER,
            ruijie3GSerialNumber
                DisplayString,
	    ruijie3GBackupIMSI
                DisplayString,
            ruijie3GGatewayIPAddr
            	IpAddress,
	    ruijie3GLineDownCause
	            Integer32,
	    ruijie3GModemType
	            INTEGER
        }
        
    ruijie3gUsername OBJECT-TYPE
        SYNTAX DisplayString
        MAX-ACCESS read-only
        STATUS current
        DESCRIPTION
            "The Username  of 3G User."
        ::= { ruijie3GEntry 1 }
   
    ruijie3GOnlineStatus OBJECT-TYPE
        SYNTAX INTEGER
            {
                lpm(0),
		online(1),
                offline(4),
		ftm(5),
		reset(6),
		rfOff(7)          
            }
        MAX-ACCESS read-only
        STATUS current
        DESCRIPTION
            "the status of 3G user. online or offline"
        ::= { ruijie3GEntry 2 }
    
    ruijie3GIMEI OBJECT-TYPE
        SYNTAX DisplayString
        MAX-ACCESS read-only
        STATUS current
        DESCRIPTION
            "the IMEI number of 3G user."
        ::= { ruijie3GEntry 3 }
    
    ruijie3GIPAddrType OBJECT-TYPE
         SYNTAX INTEGER {
            ipv4Addr(1),
            ipv6Addr(2)
         }
        MAX-ACCESS read-only
        STATUS current
        DESCRIPTION
            "The IP Address type of remote user."
        ::= { ruijie3GEntry 4 }
    
    ruijie3GIPAddr OBJECT-TYPE
        SYNTAX IpAddress
        MAX-ACCESS read-only
        STATUS current
        DESCRIPTION
            "The 3G remote users's IP address."
        ::= { ruijie3GEntry 5 }
    
    ruijie3GUplineTime OBJECT-TYPE
        SYNTAX TimeStamp
        MAX-ACCESS read-only
        STATUS current
        DESCRIPTION
            "The value of up line time for this 3G user."
        ::= { ruijie3GEntry 6 } 

		
        -- 1.3.6.1.4.1.4881.1.1.10.2.95.1.1.1.7
        ruijie3GActiveTime OBJECT-TYPE
			SYNTAX Integer32 (0..2147483647)
			MAX-ACCESS read-only
			STATUS current
			DESCRIPTION
				"The duration of the 3G connection has been active for one user. 
				2147483647 is defined as invalid value."
			::= { ruijie3GEntry 7 }

		
		-- 1.3.6.1.4.1.4881.1.1.10.2.95.1.1.1.8
		ruijie3GSignalStrength OBJECT-TYPE
			SYNTAX Integer32 (-150..0)
			MAX-ACCESS read-only
			STATUS current
			DESCRIPTION
				"The signal strength of the 3G connection for this user."
			::= { ruijie3GEntry 8 }

		
		-- 1.3.6.1.4.1.4881.1.1.10.2.95.1.1.1.9
		ruijie3GISP OBJECT-TYPE
			SYNTAX INTEGER
				{
				chinaUnicom(1),
				chinaTelecom(2),
				chinaMobile(3)
				}
			MAX-ACCESS read-only
			STATUS current
			DESCRIPTION
				"the ISP of 3G networsk."
			::= { ruijie3GEntry 9 }

		
		-- 1.3.6.1.4.1.4881.1.1.10.2.95.1.1.1.10
		ruijie3GSysMode OBJECT-TYPE
			SYNTAX INTEGER
				{
				noService(0),
				amps(1),
				cdma(2),
				gsmGprs(3),
				hdr(4),
				wcdma(5),
				gps(6),
				gsmCdma(7),
				cdmaHdrHybrid(8),
				tdscdma(15),
				td-1te(100),
				fdd-lte(101)
				}
			MAX-ACCESS read-only
			STATUS current
			DESCRIPTION
				"the system mode of 3G networsk."
			::= { ruijie3GEntry 10 }

		
		-- 1.3.6.1.4.1.4881.1.1.10.2.95.1.1.1.11
		ruijie3GServiceStatus OBJECT-TYPE
			SYNTAX INTEGER
				{
				noService(0),
				restricted(1),
				valid(2),
				restrictedRegional(3),
				powerSavingAndDeepSleepState(4)
				}
			MAX-ACCESS read-only
			STATUS current
			DESCRIPTION
				"the sevice status of 3G user."
			::= { ruijie3GEntry 11 }

		
		-- 1.3.6.1.4.1.4881.1.1.10.2.95.1.1.1.12
		ruijie3GRoamingStatus OBJECT-TYPE
			SYNTAX INTEGER
				{
				noRoaming(0),
				roaming(1)
				}
			MAX-ACCESS read-only
			STATUS current
			DESCRIPTION
				"the roaming status of 3G  user."
			::= { ruijie3GEntry 12 }

		
		-- 1.3.6.1.4.1.4881.1.1.10.2.95.1.1.1.13
		ruijie3GDomain OBJECT-TYPE
			SYNTAX INTEGER
				{
				noService(0),
				onlyCS(1),
				onlyPS(2),
				pSCS(3),
				pSCSnotRegistered(4),
				ePSService(100),
				cdmaNotSupport(255)
				}
			MAX-ACCESS read-only
			STATUS current
			DESCRIPTION
				"the Domain status of 3G user ."
			::= { ruijie3GEntry 13 }

		
		-- 1.3.6.1.4.1.4881.1.1.10.2.95.1.1.1.14
		ruijie3GSIMStatus OBJECT-TYPE
			SYNTAX INTEGER
				{
				invalidUsimCard(0),
				validUsimCard(1),
				invalidForCS(2),
				invalidForPS(3),
				invalidForCSPS(4),
				noUsimCard(255)
				}
			MAX-ACCESS read-only
			STATUS current
			DESCRIPTION
				"the SIM card status of 3G user."
			::= { ruijie3GEntry 14 }

		
		-- 1.3.6.1.4.1.4881.1.1.10.2.95.1.1.1.15
		ruijie3GSignalStrengthPercent OBJECT-TYPE
			SYNTAX Integer32 (0..100)
			MAX-ACCESS read-only
			STATUS current
			DESCRIPTION
				"The percent of signal strength of the 3G connection for this user."
			::= { ruijie3GEntry 15 }

		
		-- 1.3.6.1.4.1.4881.1.1.10.2.95.1.1.1.16
		ruijie3GApn OBJECT-TYPE
			SYNTAX DisplayString
			MAX-ACCESS read-only
			STATUS current
			DESCRIPTION
				"The access-point  of 3G User(only used in TD-SCDMA and WCDMA)."
			::= { ruijie3GEntry 16 }

		
		-- 1.3.6.1.4.1.4881.1.1.10.2.95.1.1.1.17
		ruijie3GCellID OBJECT-TYPE
			SYNTAX Integer32 (0..100)
			MAX-ACCESS read-only
			STATUS current
			DESCRIPTION
				"The access Cell id  of 3G User(only used in TD-SCDMA and WCDMA)."
			::= { ruijie3GEntry 17 }

		
		-- 1.3.6.1.4.1.4881.1.1.10.2.95.1.1.1.18
		ruijie3GLAC OBJECT-TYPE
			SYNTAX Integer32 (0..100)
			MAX-ACCESS read-only
			STATUS current
			DESCRIPTION
				"The Location Area Code  of 3G User(only used in TD-SCDMA and WCDMA)."
			::= { ruijie3GEntry 18 }

		
		-- 1.3.6.1.4.1.4881.1.1.10.2.95.1.1.1.19
		ruijie3GBSID OBJECT-TYPE
			SYNTAX Integer32 (0..100)
			MAX-ACCESS read-only
			STATUS current
			DESCRIPTION
				"The Base Station ID  of 3G User(only used in CDMA2000)."
			::= { ruijie3GEntry 19 }

		
		-- 1.3.6.1.4.1.4881.1.1.10.2.95.1.1.1.20
		ruijie3GNID OBJECT-TYPE
			SYNTAX Integer32 (0..100)
			MAX-ACCESS read-only
			STATUS current
			DESCRIPTION
				"The Network ID  of 3G User(only used in CDMA2000)."
			::= { ruijie3GEntry 20 }

		
		-- 1.3.6.1.4.1.4881.1.1.10.2.95.1.1.1.21
		ruijie3GSID OBJECT-TYPE
			SYNTAX Integer32 (0..100)
			MAX-ACCESS read-only
			STATUS current
			DESCRIPTION
				"The System ID  of 3G User(only used in CDMA2000)."
			::= { ruijie3GEntry 21 }

		
		-- 1.3.6.1.4.1.4881.1.1.10.2.95.1.1.1.22
		ruijie3GIMSI OBJECT-TYPE
			SYNTAX DisplayString
			MAX-ACCESS read-only
			STATUS current
			DESCRIPTION
				"The IMSI  of 3G User."
			::= { ruijie3GEntry 22 }

		
		-- 1.3.6.1.4.1.4881.1.1.10.2.95.1.1.1.23
		ruijie3GESN OBJECT-TYPE
			SYNTAX DisplayString
			MAX-ACCESS read-only
			STATUS current
			DESCRIPTION
				"The ESN  of 3G User(only used in CDMA2000)."
			::= { ruijie3GEntry 23 }

		
		-- 1.3.6.1.4.1.4881.1.1.10.2.95.1.1.1.24
		ruijie3GPhoneNumber OBJECT-TYPE
			SYNTAX DisplayString
			MAX-ACCESS read-only
			STATUS current
			DESCRIPTION
				"The Phone Number of 3G User."
			::= { ruijie3GEntry 24 }

		
		-- 1.3.6.1.4.1.4881.1.1.10.2.95.1.1.1.25
		ruijie3GifIndex OBJECT-TYPE
			SYNTAX INTEGER
			MAX-ACCESS read-only
			STATUS current
			DESCRIPTION
				"The Index of 3G Interface."
			::= { ruijie3GEntry 25 }

		
		-- 1.3.6.1.4.1.4881.1.1.10.2.95.1.1.1.26
		ruijie3GBSLONG OBJECT-TYPE
			SYNTAX Integer32
			MAX-ACCESS read-only
			STATUS current
			DESCRIPTION
				"The longitude of 3G User(only used in CDMA2000)."
			::= { ruijie3GEntry 26 }

		
		-- 1.3.6.1.4.1.4881.1.1.10.2.95.1.1.1.27
		ruijie3GBSLAT OBJECT-TYPE
			SYNTAX Integer32
			MAX-ACCESS read-only
			STATUS current
			DESCRIPTION
				"The latitude of 3G User(only used in CDMA2000)."
			::= { ruijie3GEntry 27 }

		
		-- 1.3.6.1.4.1.4881.1.1.10.2.95.1.1.1.28
		ruijie3GBackupInfo OBJECT-TYPE
			SYNTAX INTEGER
				{
				no-backup(0),
				myself(1),
				master(2),
				slave(3)
				}
			MAX-ACCESS read-only
			STATUS current
			DESCRIPTION
				"The backup info of 3G line."
			::= { ruijie3GEntry 28 }

		
		-- 1.3.6.1.4.1.4881.1.1.10.2.95.1.1.1.29
		ruijie3GSerialNumber OBJECT-TYPE
			SYNTAX DisplayString
			MAX-ACCESS read-only
			STATUS current
			DESCRIPTION
				"The serial number of 3G router."
			::= { ruijie3GEntry 29 }

		
		-- 1.3.6.1.4.1.4881.1.1.10.2.95.1.1.1.30
		ruijie3GBackupIMSI OBJECT-TYPE
			SYNTAX DisplayString
			MAX-ACCESS read-only
			STATUS current
			DESCRIPTION
				"The IMSI of 3G backup line."
			::= { ruijie3GEntry 30 }

		
		-- 1.3.6.1.4.1.4881.1.1.10.2.95.1.1.1.31
		ruijie3GGatewayIPAddr OBJECT-TYPE
			SYNTAX IpAddress
			MAX-ACCESS read-only
			STATUS current
			DESCRIPTION
				"The IP address of the 3g gateway."
			::= { ruijie3GEntry 31 }

		
		-- 1.3.6.1.4.1.4881.1.1.10.2.95.1.1.1.32
		ruijie3GLineDownCause OBJECT-TYPE
			SYNTAX Integer32
			MAX-ACCESS read-only
			STATUS current
			DESCRIPTION
				"The cause of line down."
			::= { ruijie3GEntry 32 }
	   
	       ruijie3GModemType OBJECT-TYPE
			SYNTAX INTEGER
				{
				modem-type-3G(1),
				modem-type-4G(2)
				}
			MAX-ACCESS read-only
			STATUS current
			DESCRIPTION
				"the type of modem used in router."
			::= { ruijie3GEntry 33 }

		
-- ===============================================
-- Begin the table of ruijie3GstatTable.
-- ===============================================

    ruijie3GStatTable OBJECT-TYPE
        SYNTAX SEQUENCE OF Ruijie3GStatEntry
        MAX-ACCESS not-accessible
        STATUS current
        DESCRIPTION
            "The 3G connection infomation fot every user. There is one
             entry in this table for each active 3G connection."
        ::= { ruijie3GObjects 2 }

    ruijie3GStatEntry OBJECT-TYPE
        SYNTAX Ruijie3GStatEntry
        MAX-ACCESS not-accessible
        STATUS current
        DESCRIPTION
            "Information about ruijie3GTunnelTable."
        INDEX { ruijie3GIPAddr }
        ::= { ruijie3GStatTable 1 }
 
    Ruijie3GStatEntry ::=
        SEQUENCE {
            ruijie3GInOctets
                Counter64,
            ruijie3GOutOctets
                Counter64,
            ruijie3GInSpeed
                Counter64,
            ruijie3GOutSpeed
                Counter64,
            ruijie3G2IMSI
                DisplayString,
            ruijie3G2ifIndex
                INTEGER
        }
        
    ruijie3GInOctets OBJECT-TYPE
        SYNTAX Counter64
        MAX-ACCESS read-only
        STATUS current
        DESCRIPTION
            "The total number of octets received by this 3G user."
        ::= { ruijie3GStatEntry 1 }

    ruijie3GOutOctets OBJECT-TYPE
        SYNTAX Counter64
        MAX-ACCESS read-only
        STATUS current
        DESCRIPTION
            "The total number of octets sent by this 3G user."
        ::= { ruijie3GStatEntry 2 } 
 
    ruijie3GInSpeed OBJECT-TYPE
        SYNTAX Counter64
        MAX-ACCESS read-only
        STATUS current
        DESCRIPTION
            "The Speed(bps) of packets received by this 3G user."
        ::= { ruijie3GStatEntry 3 }

    ruijie3GOutSpeed OBJECT-TYPE
        SYNTAX Counter64
        MAX-ACCESS read-only
        STATUS current
        DESCRIPTION
            "The Speed(bps) of packets snet by this 3G user."
        ::= { ruijie3GStatEntry 4 }
        
    ruijie3G2IMSI OBJECT-TYPE
        SYNTAX DisplayString
        MAX-ACCESS read-only
        STATUS current
        DESCRIPTION
            "The IMSI  of 3G User."
        ::= { ruijie3GStatEntry 5 } 
    
    ruijie3G2ifIndex OBJECT-TYPE
    SYNTAX  INTEGER
    MAX-ACCESS  read-only
    STATUS  current
    DESCRIPTION
            "The Index of 3G Interface."
    ::= { ruijie3GStatEntry 6 } 
 
-- ===============================================
-- Begin the ruijie3GTrapObject.
-- ===============================================

    ruijie3GTrap OBJECT IDENTIFIER ::= { ruijie3GObjects 3 }
    
    ruijie3GNotifications OBJECT IDENTIFIER ::= { ruijie3GTrap 1 }
    
    ruijie3GSignalThreshold NOTIFICATION-TYPE
        OBJECTS { 
                ruijie3GIPAddr, 
                ruijie3GSignalStrength,
                ruijie3GSignalStrengthPercent,
                ruijie3GIMSI 
        }
        STATUS current
        DESCRIPTION
            "This notification is generated when 3G signal is lower 
            than the specific Threshold value."
        ::= { ruijie3GNotifications 1 }
    
    ruijie3GUpLine NOTIFICATION-TYPE
        OBJECTS { 
                ruijie3GIPAddr,	
        	ruijie3gUsername,
        	ruijie3GIMSI,
                ruijie3GBackupInfo,
                ruijie3GSerialNumber,
                ruijie3GGatewayIPAddr							  
        }
        STATUS current
        DESCRIPTION
            "This notification is generated when 3G user up line."
        ::= { ruijie3GNotifications 2 }
    
    ruijie3GDownLine NOTIFICATION-TYPE
        OBJECTS { 
                ruijie3GLineDownCause,
		ruijie3GIPAddr,        		  
                ruijie3gUsername,
                ruijie3GIMSI 
        	}
        STATUS current
        DESCRIPTION
            "This notification is generated when 3G user down line."
        ::= { ruijie3GNotifications 3 }
        
      ruijie3GChangeAccessPoint NOTIFICATION-TYPE
        OBJECTS { 
                ruijie3GIPAddr,  
                ruijie3GApn,        		  
                ruijie3gUsername,
                ruijie3GIMSI 
                }
        STATUS current
        DESCRIPTION
            "This notification is generated when 3G change access point."
        ::= { ruijie3GNotifications 4 }
        
       ruijie3GBackupIntfSwitch NOTIFICATION-TYPE
        OBJECTS { 
                ruijie3GIPAddr,        		  
                ruijie3gUsername,
                ruijie3GIMSI,
                ruijie3GSerialNumber,
                ruijie3GBackupIMSI				  
                }
        STATUS current
        DESCRIPTION
            "This notification is generated when 3G switch to backup interface 
            in double card backup configuration."	
        ::= { ruijie3GNotifications 5 }
    
       ruijie3GBaseSationSwitch NOTIFICATION-TYPE
           OBJECTS {   
                   ruijie3GISP,
                   ruijie3GCellID,
                   ruijie3GLAC,
                   ruijie3GBSID,
                   ruijie3GSID,
                   ruijie3GNID,
                   ruijie3GIMSI,
                   ruijie3GPhoneNumber
                }
        STATUS current
        DESCRIPTION
            "This notification is generated when the access base station changes."	
        ::= { ruijie3GNotifications 6 }
		
	ruijie3GTrafficInformation NOTIFICATION-TYPE
        OBJECTS {    
                ruijie3GIPAddr,
		ruijie3GIMSI,
		ruijie3GSerialNumber,
		ruijie3GInOctets,
		ruijie3GOutOctets
	}
        STATUS current
        DESCRIPTION
            "This notification is used for reporting the traffic information of 3G user regularly. "
        ::= { ruijie3GNotifications 7 }

-- ===============================================
-- Begin the scalar parameters
-- ===============================================
    ruijie3GBsNumber OBJECT-TYPE
        SYNTAX Integer32
        MAX-ACCESS  read-only
        STATUS  current
        DESCRIPTION
            "The number of Base Station available on the system"
        ::= { ruijie3GObjects 4 }

-- ===============================================
-- Begin the table of ruijie3GBsTable.
-- ===============================================

    ruijie3GBsTable OBJECT-TYPE
        SYNTAX SEQUENCE OF Ruijie3GBsEntry
        MAX-ACCESS not-accessible
        STATUS current
        DESCRIPTION
            "The Base Station Information."
        ::= { ruijie3GObjects 5 }

    ruijie3GBsEntry OBJECT-TYPE
        SYNTAX Ruijie3GBsEntry
        MAX-ACCESS not-accessible
        STATUS current
        DESCRIPTION
            "Information about Base Station."
        INDEX { ruijie3GBsSN }
        ::= { ruijie3GBsTable 1 }
 
    Ruijie3GBsEntry ::=
        SEQUENCE {
            ruijie3GBsSN
                Integer32,
            ruijie3GBsISP
           	    INTEGER,
            ruijie3GBsMode
           	    INTEGER,
            ruijie3GBsIMSI
                DisplayString,
 	        ruijie3GBsLAC
                Integer32,
            ruijie3GBsCellID
                Integer32,
            ruijie3GBsBSID
                Integer32,
            ruijie3GBsSID
                Integer32,
            ruijie3GBsNID 
                Integer32,
            ruijie3GBsRssi
                Integer32,
            ruijie3GBsBSLONG
                Integer32,
            ruijie3GBsBSLAT
                Integer32
        }

    ruijie3GBsSN OBJECT-TYPE
        SYNTAX Integer32
        MAX-ACCESS read-only
        STATUS current
        DESCRIPTION
            "the Sequence Of The Base Station."
        ::= { ruijie3GBsEntry 1 }

    ruijie3GBsISP OBJECT-TYPE
        SYNTAX INTEGER
            {
            chinaUnicom(1),
            chinaTelecom(2),
            chinaMobile(3)
            }
        MAX-ACCESS read-only
        STATUS current
        DESCRIPTION
            "the ISP of 3G networsk."
        ::= { ruijie3GBsEntry 2 }
        
    ruijie3GBsMode OBJECT-TYPE
        SYNTAX INTEGER
            {
            sys2GMode(1),
            sys3GMode(2)
            }
        MAX-ACCESS read-only
        STATUS current
        DESCRIPTION
            "the sys mode of 3G networsk."
        ::= { ruijie3GBsEntry 3 }
        
     ruijie3GBsIMSI OBJECT-TYPE
        SYNTAX DisplayString
        MAX-ACCESS read-only
        STATUS current
        DESCRIPTION
            "The IMSI of 3G User."
        ::= { ruijie3GBsEntry 4 }
        
    ruijie3GBsLAC OBJECT-TYPE
        SYNTAX Integer32
        MAX-ACCESS read-only
        STATUS current
        DESCRIPTION
            "The Location Area Code  of 3G User(only used in TD-SCDMA and WCDMA)."
        ::= { ruijie3GBsEntry 5 }
               
     ruijie3GBsCellID OBJECT-TYPE
        SYNTAX Integer32
        MAX-ACCESS read-only
        STATUS current
        DESCRIPTION
            "The access Cell id  of 3G User(only used in TD-SCDMA and WCDMA)."
        ::= { ruijie3GBsEntry 6 }
                
    ruijie3GBsBSID OBJECT-TYPE
        SYNTAX Integer32
        MAX-ACCESS read-only
        STATUS current
        DESCRIPTION
            "The Base Station ID  of 3G User(only used in CDMA2000)."
        ::= { ruijie3GBsEntry 7 }

     ruijie3GBsSID OBJECT-TYPE
        SYNTAX Integer32
        MAX-ACCESS read-only
        STATUS current
        DESCRIPTION
            "The System ID  of 3G User(only used in CDMA2000)."
        ::= { ruijie3GBsEntry 8 }
	        
     ruijie3GBsNID OBJECT-TYPE
        SYNTAX Integer32
        MAX-ACCESS read-only
        STATUS current
        DESCRIPTION
            "The Network ID  of 3G User(only used in CDMA2000)."
        ::= { ruijie3GBsEntry 9 }

    ruijie3GBsRssi OBJECT-TYPE
        SYNTAX Integer32
        MAX-ACCESS read-only
        STATUS current
        DESCRIPTION
            "the strength of the connection."
        ::= { ruijie3GBsEntry 10 }

	ruijie3GBsBSLONG OBJECT-TYPE
        SYNTAX Integer32
        MAX-ACCESS read-only
        STATUS current
        DESCRIPTION
            "The longitude of 3G User(only used in CDMA2000)."
        ::= { ruijie3GBsEntry 11 }
		
	ruijie3GBsBSLAT OBJECT-TYPE
        SYNTAX Integer32
        MAX-ACCESS read-only
        STATUS current
        DESCRIPTION
            "The latitude of 3G User(only used in CDMA2000)."
        ::= { ruijie3GBsEntry 12 }
		
--  ===============================================
-- Begin the table of ruijie3GDeviceManagementTable.
-- ===============================================
		-- 1.3.6.1.4.1.4881.1.1.10.2.95.1.6
		ruijie3GDeviceManagementTable OBJECT-TYPE
			SYNTAX SEQUENCE OF Ruijie3GDeviceManagementEntry
			MAX-ACCESS not-accessible
			STATUS current
			DESCRIPTION
				"The 3G equipment infomation."
			::= { ruijie3GObjects 6 }
		
		-- 1.3.6.1.4.1.4881.1.1.10.2.95.1.6.1
		ruijie3GDeviceManagementEntry OBJECT-TYPE
			SYNTAX Ruijie3GDeviceManagementEntry
			MAX-ACCESS not-accessible
			STATUS current
			DESCRIPTION
				"Information about ruijie3GDeviceManagementTable."
			INDEX { ruijie3GRouterSlotNumber }
			::= { ruijie3GDeviceManagementTable 1 }

            Ruijie3GDeviceManagementEntry ::= 
                SEQUENCE { 
                    ruijie3GRouterType
                        DisplayString, 
                    ruijie3GRouterSN 
                        DisplayString, 
                    ruijie3GRouterSlotNumber
                        DisplayString, 
                    ruijie3GLineCardType 
                        DisplayString, 
                    ruijie3GCardIMSI
                        DisplayString, 
                    ruijie3GModemIMEI 
                        DisplayString, 
                    ruijie3GIntfIPAddr
                        IpAddress, 
                    ruijie3GCardPhoneNumber 
                        DisplayString, 
                    ruijie3GLineDetected
                        Unsigned32, 
                    ruijie3GLineDetectedResult 
                        INTEGER,
                    ruijie3GLineDetectedMainCause 
                        INTEGER, 
                    ruijie3GLineDetectedSubCause 
                        INTEGER,
                    ruijie3GDeviceBackupInfo 
                        INTEGER, 
                    ruijie3GRssiStrength 
                        Integer32,
      	            ruijie3GRssiStrengthPercent 
                        Integer32, 
                    ruijie3GNetworkISPMode 
                        INTEGER,
       	            ruijie3GNetworkSysMode 
                        INTEGER, 
                    ruijie3GNetworkServiceStatus 
                        INTEGER,
                    ruijie3GSIMCardStatus 
                        INTEGER, 
                    ruijie3GDailMode 
                        INTEGER,
                    ruijie3GDeviceBackupIMSI 
                        DisplayString, 
                    ruijie3GLineDetectedMode 
                        INTEGER,
                    ruijie3GPppUsername 
                        DisplayString, 
                    ruijie3GUserApn 
                        DisplayString,
                    ruijie3GModemOnlineStatus 
                        INTEGER, 
                    ruijie3GIntfIPAddrType 
                        INTEGER,
                    ruijie3GUserUplineTime 
                        TimeStamp, 
                    ruijie3GUserActiveTime 
                        Integer32,
                    ruijie3GSIMRoamingStatus 
                        INTEGER, 
                    ruijie3GAcessBSCellID 
                        Integer32,
                    ruijie3GAcessBSLAC 
                        Integer32, 
                    ruijie3GAcessBSLONG 
                        Integer32,
                    ruijie3GAcessBSLAT 
                        Integer32, 
                    ruijie3GDialOnDemandIfIndex 
                        Integer32,
                    ruijie3GTrafficPreventMode 
                        INTEGER, 
                    ruijie3GTrafficPreventIfIndex 
                        INTEGER,
                    ruijie3GTrafficPreventListID 
                        INTEGER,
                    ruijie3GTrafficPreventListName
                        DisplayString, 
                    ruijie3GDeviceModemType 
                        INTEGER, 
                    ruijie3GTrafficTrapInterval
                        Integer32, 
                    ruijie3GRssiThreshold 
                        Integer32, 
                    ruijie3GTrapFilterMode 
                        INTEGER,
                    ruijie3GEncrypt_type 
                        Integer32,
                    ruijie3GPassword 
                        DisplayString 
                }

		-- 1.3.6.1.4.1.4881.1.1.10.2.95.1.6.1.1
		ruijie3GRouterType OBJECT-TYPE
			SYNTAX DisplayString
			MAX-ACCESS read-only
			STATUS current
			DESCRIPTION
				"Equipment tpye of 3G router."
			::= { ruijie3GDeviceManagementEntry 1 }

		
		-- 1.3.6.1.4.1.4881.1.1.10.2.95.1.6.1.2
		ruijie3GRouterSN OBJECT-TYPE
			SYNTAX DisplayString
			MAX-ACCESS read-only
			STATUS current
			DESCRIPTION
				"The serial number of 3G router."
			::= { ruijie3GDeviceManagementEntry 2 }

		
		-- 1.3.6.1.4.1.4881.1.1.10.2.95.1.6.1.3
		ruijie3GRouterSlotNumber OBJECT-TYPE
			SYNTAX DisplayString
			MAX-ACCESS read-only
			STATUS current
			DESCRIPTION
				"The number of the activity slot in 3G router."
			::= { ruijie3GDeviceManagementEntry 3 }

		
		-- 1.3.6.1.4.1.4881.1.1.10.2.95.1.6.1.4
		ruijie3GLineCardType OBJECT-TYPE
			SYNTAX DisplayString
			MAX-ACCESS read-only
			STATUS current
			DESCRIPTION
				"The tpye of 3G router line card."
			::= { ruijie3GDeviceManagementEntry 4 }

		
		-- 1.3.6.1.4.1.4881.1.1.10.2.95.1.6.1.5
		ruijie3GCardIMSI OBJECT-TYPE
			SYNTAX DisplayString
			MAX-ACCESS read-only
			STATUS current
			DESCRIPTION
				"The IMSI  of 3G User."
			::= { ruijie3GDeviceManagementEntry 5 }

		
		-- 1.3.6.1.4.1.4881.1.1.10.2.95.1.6.1.6
		ruijie3GModemIMEI OBJECT-TYPE
			SYNTAX DisplayString
			MAX-ACCESS read-only
			STATUS current
			DESCRIPTION
				"The IMEI number of 3G user."
			::= { ruijie3GDeviceManagementEntry 6 }

		
		-- 1.3.6.1.4.1.4881.1.1.10.2.95.1.6.1.7
		ruijie3GIntfIPAddr OBJECT-TYPE
			SYNTAX IpAddress
			MAX-ACCESS read-only
			STATUS current
			DESCRIPTION
				"The IP Address of 3G interface."
			::= { ruijie3GDeviceManagementEntry 7 }

		
		-- 1.3.6.1.4.1.4881.1.1.10.2.95.1.6.1.8
		ruijie3GCardPhoneNumber OBJECT-TYPE
			SYNTAX DisplayString
			MAX-ACCESS read-only
			STATUS current
			DESCRIPTION
				"The Phone Number of 3G User."
			::= { ruijie3GDeviceManagementEntry 8 }

		
		-- 1.3.6.1.4.1.4881.1.1.10.2.95.1.6.1.9
		ruijie3GLineDetected OBJECT-TYPE
			SYNTAX Unsigned32
			MAX-ACCESS read-write
			STATUS current
			DESCRIPTION
				"The command is used for Detecting 3G line."
			::= { ruijie3GDeviceManagementEntry 9 }

		
		-- 1.3.6.1.4.1.4881.1.1.10.2.95.1.6.1.10
		ruijie3GLineDetectedResult OBJECT-TYPE
			SYNTAX INTEGER
				{
				noRsponse(0),
				pass(1),
				failed(2),
				using(3),
				detecting(4)
				}
			MAX-ACCESS read-only
			STATUS current
			DESCRIPTION
				"The result of 3G line detection."
			::= { ruijie3GDeviceManagementEntry 10 }

		
		-- 1.3.6.1.4.1.4881.1.1.10.2.95.1.6.1.11
		ruijie3GLineDetectedMainCause OBJECT-TYPE
			SYNTAX INTEGER
				{
				noGivenReason(0),
				dialFailed(1),
				pppFailed(2),
				ipsecSetupFailed(3)
				}
			MAX-ACCESS read-only
			STATUS current
			DESCRIPTION
				"The main cause of 3G line detection filed."
			::= { ruijie3GDeviceManagementEntry 11 }

		
		-- 1.3.6.1.4.1.4881.1.1.10.2.95.1.6.1.12
		ruijie3GLineDetectedSubCause OBJECT-TYPE
			SYNTAX INTEGER
				{
				noGivenReason(0),
				simCardInvalid(1),
				aPNInvalid(2),
				powerlower(3),
				userInfoError(4),
				ipsecSetupFailed(5)
				}
			MAX-ACCESS read-only
			STATUS current
			DESCRIPTION
				"The details cause of 3G line detection filed."
			::= { ruijie3GDeviceManagementEntry 12 }

		
		-- 1.3.6.1.4.1.4881.1.1.10.2.95.1.6.1.13
		ruijie3GDeviceBackupInfo OBJECT-TYPE
			SYNTAX INTEGER
				{
				no-backup(0),
				myself(1),
				master(2),
				slave(3)
				}
			MAX-ACCESS read-only
			STATUS current
			DESCRIPTION
				"The backup info of 3G line."
			::= { ruijie3GDeviceManagementEntry 13 }

		
		-- 1.3.6.1.4.1.4881.1.1.10.2.95.1.6.1.14
		ruijie3GRssiStrength OBJECT-TYPE
			SYNTAX Integer32 (-150..0)
			MAX-ACCESS read-only
			STATUS current
			DESCRIPTION
				"The signal strength of the 3G connection for this user."
			::= { ruijie3GDeviceManagementEntry 14 }

		
		-- 1.3.6.1.4.1.4881.1.1.10.2.95.1.6.1.15
		ruijie3GRssiStrengthPercent OBJECT-TYPE
			SYNTAX Integer32 (0..100)
			MAX-ACCESS read-only
			STATUS current
			DESCRIPTION
				"The percent of signal strength of the 3G connection for this user."
			::= { ruijie3GDeviceManagementEntry 15 }

		
		-- 1.3.6.1.4.1.4881.1.1.10.2.95.1.6.1.16
		ruijie3GNetworkISPMode OBJECT-TYPE
			SYNTAX INTEGER
				{
				chinaUnicom(1),
				chinaTelecom(2),
				chinaMobile(3)
				}
			MAX-ACCESS read-only
			STATUS current
			DESCRIPTION
				"the ISP of 3G networsk."
			::= { ruijie3GDeviceManagementEntry 16 }

		
		-- 1.3.6.1.4.1.4881.1.1.10.2.95.1.6.1.17
		ruijie3GNetworkSysMode OBJECT-TYPE
			SYNTAX INTEGER
				{
				noService(0),
				amps(1),
				cdma(2),
				gsmGprs(3),
				hdr(4),
				wcdma(5),
				gps(6),
				gsmCdma(7),
				cdmaHdrHybrid(8),
				td-scdma(15),
				td-1te(100),
				fdd-lte(101)
				}
			MAX-ACCESS read-write
			STATUS current
			DESCRIPTION
				"the system mode of 3G networsk."
			::= { ruijie3GDeviceManagementEntry 17 }

		
		-- 1.3.6.1.4.1.4881.1.1.10.2.95.1.6.1.18
		ruijie3GNetworkServiceStatus OBJECT-TYPE
			SYNTAX INTEGER
				{
				noService(0),
				restricted(1),
				valid(2),
				restrictedRegional(3),
				powerSavingAndDeepSleepState(4)
				}
			MAX-ACCESS read-only
			STATUS current
			DESCRIPTION
				"the sevice status of 3G user."
			::= { ruijie3GDeviceManagementEntry 18 }

		
		-- 1.3.6.1.4.1.4881.1.1.10.2.95.1.6.1.19
		ruijie3GSIMCardStatus OBJECT-TYPE
			SYNTAX INTEGER
				{
				invalidUsimCard(0),
				validUsimCard(1),
				invalidForCS(2),
				invalidForPS(3),
				invalidForCSPS(4),
				noUsimCard(255)
				}
			MAX-ACCESS read-only
			STATUS current
			DESCRIPTION
				"the SIM card status of 3G user."
			::= { ruijie3GDeviceManagementEntry 19 }

		
		-- 1.3.6.1.4.1.4881.1.1.10.2.95.1.6.1.20
		ruijie3GDailMode OBJECT-TYPE
			SYNTAX INTEGER
				{
				dialOnDemand(0),
				autoDail(1)
				}
			MAX-ACCESS read-write
			STATUS current
			DESCRIPTION
				"the dial mode of 3G user."
			::= { ruijie3GDeviceManagementEntry 20 }

		
		-- 1.3.6.1.4.1.4881.1.1.10.2.95.1.6.1.21
		ruijie3GDeviceBackupIMSI OBJECT-TYPE
			SYNTAX DisplayString
			MAX-ACCESS read-only
			STATUS current
			DESCRIPTION
				"The IMSI of 3G backup line."
			::= { ruijie3GDeviceManagementEntry 21 }

		
		-- 1.3.6.1.4.1.4881.1.1.10.2.95.1.6.1.22
		ruijie3GLineDetectedMode OBJECT-TYPE
			SYNTAX INTEGER
				{
				vpdnMode(0),
				ipsecMode(1)
				}
			MAX-ACCESS read-write
			STATUS current
			DESCRIPTION
				"The mode of 3G backup line detected."
			::= { ruijie3GDeviceManagementEntry 22 }

		
		-- 1.3.6.1.4.1.4881.1.1.10.2.95.1.6.1.23
		ruijie3GPppUsername OBJECT-TYPE
			SYNTAX DisplayString
			MAX-ACCESS read-write
			STATUS current
			DESCRIPTION
				"The Username of 3G or 4G User."
			::= { ruijie3GDeviceManagementEntry 23 }

		
		-- 1.3.6.1.4.1.4881.1.1.10.2.95.1.6.1.24
		ruijie3GUserApn OBJECT-TYPE
			SYNTAX DisplayString
			MAX-ACCESS read-write
			STATUS current
			DESCRIPTION
				"The access-point of 3G or 4G User."
			::= { ruijie3GDeviceManagementEntry 24 }

		
		-- 1.3.6.1.4.1.4881.1.1.10.2.95.1.6.1.25
		ruijie3GModemOnlineStatus OBJECT-TYPE
			SYNTAX INTEGER
				{
				minimum-function(0),
				fully-function(1),
				offline-mode(2),
				sim-activate(3),
				sim-deactivate(4)
				}
			MAX-ACCESS read-only
			STATUS current
			DESCRIPTION
				"The status of 3G or 4G user. online or offline."
			::= { ruijie3GDeviceManagementEntry 25 }

		
		-- 1.3.6.1.4.1.4881.1.1.10.2.95.1.6.1.26
		ruijie3GIntfIPAddrType OBJECT-TYPE
			SYNTAX INTEGER
				{
				ipv4Addr(1),
				ipv6Addr(2)
				}
			MAX-ACCESS read-only
			STATUS current
			DESCRIPTION
				"The IP Address type of remote user"
			::= { ruijie3GDeviceManagementEntry 26 }

		
		-- 1.3.6.1.4.1.4881.1.1.10.2.95.1.6.1.27
		ruijie3GUserUplineTime OBJECT-TYPE
			SYNTAX TimeStamp
			MAX-ACCESS read-only
			STATUS current
			DESCRIPTION
				"The upline time of the 3G or 4G user  after system start"
			::= { ruijie3GDeviceManagementEntry 27 }

		
		-- 1.3.6.1.4.1.4881.1.1.10.2.95.1.6.1.28
		ruijie3GUserActiveTime OBJECT-TYPE
			SYNTAX Integer32 (0..2147483647)
			MAX-ACCESS read-only
			STATUS current
			DESCRIPTION
				"The duration of the 3G or 4g connection has been active for one user."
			::= { ruijie3GDeviceManagementEntry 28 }

		
		-- 1.3.6.1.4.1.4881.1.1.10.2.95.1.6.1.29
		ruijie3GSIMRoamingStatus OBJECT-TYPE
			SYNTAX INTEGER
				{
				noRoaming(0),
				roaming(1)
				}
			MAX-ACCESS read-only
			STATUS current
			DESCRIPTION
				"the romain status of 3G user ."
			::= { ruijie3GDeviceManagementEntry 29 }

		
		-- 1.3.6.1.4.1.4881.1.1.10.2.95.1.6.1.30
		ruijie3GAcessBSCellID OBJECT-TYPE
			SYNTAX Integer32 (0..100)
			MAX-ACCESS read-only
			STATUS current
			DESCRIPTION
				"The access Cell id  of 3G or 4g User."
			::= { ruijie3GDeviceManagementEntry 30 }

		
		-- 1.3.6.1.4.1.4881.1.1.10.2.95.1.6.1.31
		ruijie3GAcessBSLAC OBJECT-TYPE
			SYNTAX Integer32 (0..100)
			MAX-ACCESS read-only
			STATUS current
			DESCRIPTION
				"The Location Area Code  of 3G User."
			::= { ruijie3GDeviceManagementEntry 31 }

		
		-- 1.3.6.1.4.1.4881.1.1.10.2.95.1.6.1.32
		ruijie3GAcessBSLONG OBJECT-TYPE
			SYNTAX Integer32
			MAX-ACCESS read-only
			STATUS current
			DESCRIPTION
				"The longitude of 3G User."
			::= { ruijie3GDeviceManagementEntry 32 }

		
		-- 1.3.6.1.4.1.4881.1.1.10.2.95.1.6.1.33
		ruijie3GAcessBSLAT OBJECT-TYPE
			SYNTAX Integer32
			MAX-ACCESS read-only
			STATUS current
			DESCRIPTION
				"The latitude of 3G User."
			::= { ruijie3GDeviceManagementEntry 33 }

		
		-- 1.3.6.1.4.1.4881.1.1.10.2.95.1.6.1.34
		ruijie3GDialOnDemandIfIndex OBJECT-TYPE
			SYNTAX Integer32
			MAX-ACCESS read-only
			STATUS current
			DESCRIPTION
				"The Index of trigger dial-up interface."
			::= { ruijie3GDeviceManagementEntry 34 }

		
		-- 1.3.6.1.4.1.4881.1.1.10.2.95.1.6.1.35
		ruijie3GTrafficPreventMode OBJECT-TYPE
			SYNTAX INTEGER
				{
				disable(0),
				enable(1)
				}
			MAX-ACCESS read-only
			STATUS current
			DESCRIPTION
				"The status of the traffic prevent function appliled currently "
			::= { ruijie3GDeviceManagementEntry 35 }

		
		-- 1.3.6.1.4.1.4881.1.1.10.2.95.1.6.1.36
		ruijie3GTrafficPreventIfIndex OBJECT-TYPE
			SYNTAX INTEGER
			MAX-ACCESS read-only
			STATUS current
			DESCRIPTION
				"The Index of traffic-prevent interface."
			::= { ruijie3GDeviceManagementEntry 36 }

		
		-- 1.3.6.1.4.1.4881.1.1.10.2.95.1.6.1.37
		ruijie3GTrafficPreventListID OBJECT-TYPE
			SYNTAX INTEGER
			MAX-ACCESS read-only
			STATUS current
			DESCRIPTION
				"The Index of traffic-prevent Acl list id."
			::= { ruijie3GDeviceManagementEntry 37 }

		
		-- 1.3.6.1.4.1.4881.1.1.10.2.95.1.6.1.38
		ruijie3GTrafficPreventListName OBJECT-TYPE
			SYNTAX DisplayString
			MAX-ACCESS read-only
			STATUS current
			DESCRIPTION
				"The Index of traffic-prevent Acl list name."
			::= { ruijie3GDeviceManagementEntry 38 }

		
		-- 1.3.6.1.4.1.4881.1.1.10.2.95.1.6.1.39
		ruijie3GDeviceModemType OBJECT-TYPE
			SYNTAX INTEGER
				{
				modem-type-3G(1),
				modem-type-4G(2)
				}
			MAX-ACCESS read-only
			STATUS current
			DESCRIPTION
				"the type of modem used in router."
			::= { ruijie3GDeviceManagementEntry 39 }
		
		-- 1.3.6.1.4.1.4881.1.1.10.2.95.1.6.1.40
		ruijie3GTrafficTrapInterval OBJECT-TYPE
			SYNTAX Integer32 (1..1440)
			MAX-ACCESS read-write
			STATUS current
			DESCRIPTION
				"The interval of traffic-info notification appliled currently."
			::= { ruijie3GDeviceManagementEntry 40 }
	   
	        -- 1.3.6.1.4.1.4881.1.1.10.2.95.1.6.1.41
		ruijie3GRssiThreshold OBJECT-TYPE
			SYNTAX Integer32 (-150..0)
			MAX-ACCESS read-write
			STATUS current
			DESCRIPTION
				"the threshold value of rssi notification appliled currently."
			::= { ruijie3GDeviceManagementEntry 41 }
		
		-- 1.3.6.1.4.1.4881.1.1.10.2.95.1.6.1.42
		ruijie3GTrapFilterMode OBJECT-TYPE
			SYNTAX INTEGER
				{
				disable(0),
				enable(1)
				}
			MAX-ACCESS read-write
			STATUS current
			DESCRIPTION
				"The status of the trap filter function appliled currently."
			::= { ruijie3GDeviceManagementEntry 42 }
			
	        -- 1.3.6.1.4.1.4881.1.1.10.2.95.1.6.1.43
		ruijie3GISPtimeout OBJECT-TYPE
			SYNTAX Integer32 (1..36000)
			MAX-ACCESS read-write
			STATUS current
			DESCRIPTION
				"The timeout parameter of trap filter function appliled currently."
			::= { ruijie3GDeviceManagementEntry 43 }
			
		-- 1.3.6.1.4.1.4881.1.1.10.2.95.1.6.1.44
		ruijie3GEncrypt_type OBJECT-TYPE
			SYNTAX INTEGER
				{
				ENCRYPT_NONE(0),
				ENCRYPT_TEMP(7)
				}
			MAX-ACCESS read-write
			STATUS current
			DESCRIPTION
				"The Encrypt type appliled currently."
			::= { ruijie3GDeviceManagementEntry 44 }
	  
		-- 1.3.6.1.4.1.4881.1.1.10.2.95.1.6.1.45
		ruijie3GPassword OBJECT-TYPE
			SYNTAX DisplayString
			MAX-ACCESS read-write
			STATUS current
			DESCRIPTION
				"The password appliled currently."
			::= { ruijie3GDeviceManagementEntry 45 }  
	  	
--  ===============================================
-- ADD new ruijie3GTrapObject.
-- ===============================================

    ruijie3GTrapNew OBJECT IDENTIFIER ::= { ruijie3GMonitor 2 }
    
    ruijie3GNotificationsNew OBJECT IDENTIFIER ::= { ruijie3GTrapNew 1 }
    
    ruijie3GLineDetectedNotification NOTIFICATION-TYPE
        OBJECTS {
                ruijie3GRouterSN,
	            ruijie3GCardIMSI,
                ruijie3GIntfIPAddr,				  
		        ruijie3GLineDetected, 
        	    ruijie3GLineDetectedResult,
        	    ruijie3GLineDetectedMainCause,
		        ruijie3GLineDetectedSubCause,
		        ruijie3GDeviceBackupInfo,
		        ruijie3GRssiStrength,
		        ruijie3GDeviceBackupIMSI
        	  }
        STATUS current
        DESCRIPTION
            "This notification is generated when user detecting 3g line."
        ::= { ruijie3GNotificationsNew 1 }

		
		-- 1.3.6.1.4.1.4881.1.1.10.2.95.2.1.2
		ruijie3GUserUpLine NOTIFICATION-TYPE
			OBJECTS { 
			        ruijie3GRouterSlotNumber, 
			        ruijie3GCardIMSI, 
			        ruijie3GIntfIPAddr, 
			        ruijie3GTrafficPreventListName, 
			        ruijie3GTrafficPreventListID, 
                                ruijie3GTrafficPreventIfIndex, 
                                ruijie3GTrafficPreventMode, 
                                ruijie3GPppUsername, 
                                ruijie3GRouterSN, 
                                ruijie3GCardPhoneNumber, 
                                ruijie3GDailMode, 
                                ruijie3GDialOnDemandIfIndex, 
                                ruijie3GDeviceModemType 
				}
			STATUS current
			DESCRIPTION 
				"This notification is generated when 4G user up line."
			::= { ruijie3GNotificationsNew 2 }

		
		-- 1.3.6.1.4.1.4881.1.1.10.2.95.2.1.3
		ruijie3GUserDownLine NOTIFICATION-TYPE
			OBJECTS { 
			        ruijie3GRouterSlotNumber, 
			        ruijie3GCardIMSI, 
			        ruijie3GIntfIPAddr, 
			        ruijie3GTrafficPreventListName, 
			        ruijie3GTrafficPreventListID, 
                                ruijie3GTrafficPreventIfIndex, 
                                ruijie3GTrafficPreventMode, 
                                ruijie3GPppUsername, ruijie3GRouterSN, 
                                ruijie3GCardPhoneNumber, 
                                ruijie3GDailMode, 
                                ruijie3GDialOnDemandIfIndex, 
                                ruijie3GDeviceModemType }
			STATUS current
			DESCRIPTION 
				"This notification is generated when 4G user down line."
			::= { ruijie3GNotificationsNew 3 }

		
		-- 1.3.6.1.4.1.4881.1.1.10.2.95.2.1.4
		ruijie3GRssiNotification NOTIFICATION-TYPE
			OBJECTS { 
			        ruijie3GRouterSlotNumber, 
			        ruijie3GCardIMSI, 
			        ruijie3GRouterSN, 
			        ruijie3GIntfIPAddr, 
			        ruijie3GRssiStrengthPercent, 
				ruijie3GRssiStrength, 
				ruijie3GDeviceModemType 
			}
			STATUS current
			DESCRIPTION 
				"This notification is generated when 4G signal is lower 
				than the specific threshold value."
			::= { ruijie3GNotificationsNew 4 }

		
		-- 1.3.6.1.4.1.4881.1.1.10.2.95.2.1.5
		ruijie3GTrafficInfoNotification NOTIFICATION-TYPE
			OBJECTS { 
			        ruijie3GRouterSlotNumber, 
			        ruijie3GCardIMSI, 
			        ruijie3GRouterSN, 
			        ruijie3GIntfIPAddr, 
			        ruijie3GOutOctets, 
				    ruijie3GInOctets, 
				    ruijie3GDeviceModemType, 
				    ruijie3GLineCardType, 
				    ruijie3GModemIMEI, 
				    ruijie3GCardPhoneNumber,
                    ruijie3GDeviceBackupInfo, 
                    ruijie3GRssiStrength, 
                    ruijie3GRssiStrengthPercent, 
                    ruijie3GNetworkISPMode, 
				    ruijie3GNetworkSysMode, 
				    ruijie3GSIMCardStatus, 
				    ruijie3GDailMode, 
				    ruijie3GPppUsername, 
				    ruijie3GUserActiveTime,
				    ruijie3GAcessBSCellID, 
				    ruijie3GAcessBSLAC, 
				    ruijie3GAcessBSLONG, 
				    ruijie3GAcessBSLAT, 
				    ruijie3GInSpeed, 
				    ruijie3GOutSpeed,
				    ruijie3G2ifIndex, 
				    ruijie3GTrafficTrapInterval,
				    ruijie3GRssiThreshold,
				    ruijie3GTrapFilterMode,
				    ruijie3GISPtimeout
				    }
			STATUS current
			DESCRIPTION 
				"This notification is used for reporting the traffic information of 4G user regularly. "
			::= { ruijie3GNotificationsNew 5 }

		
		-- 1.3.6.1.4.1.4881.1.1.10.2.95.2.1.6
		ruijie3GBackupMaster NOTIFICATION-TYPE
			OBJECTS { 
			        ruijie3GRouterSlotNumber, 
			        ruijie3GCardIMSI, 
			        ruijie3GIntfIPAddr, 
			        ruijie3GTrafficPreventListName, 
			        ruijie3GTrafficPreventListID, 
				    ruijie3GTrafficPreventIfIndex, 
				    ruijie3GTrafficPreventMode, 
                    ruijie3GPppUsername, 
                    ruijie3GRouterSN, 
                    ruijie3GCardPhoneNumber, 
                    ruijie3GDailMode, 
                    ruijie3GDialOnDemandIfIndex, 
                    ruijie3GDeviceModemType 
                    }
			STATUS current
			DESCRIPTION 
				"This notification is generated when 4G is switching to master line."
			::= { ruijie3GNotificationsNew 6 }

		
		-- 1.3.6.1.4.1.4881.1.1.10.2.95.2.1.7
		ruijie3GBackupSlave NOTIFICATION-TYPE
			OBJECTS { 
			        ruijie3GRouterSlotNumber, 
			        ruijie3GCardIMSI, 
			        ruijie3GIntfIPAddr, 
			        ruijie3GTrafficPreventListName, 
			        ruijie3GTrafficPreventListID, 
				    ruijie3GTrafficPreventIfIndex, 
				    ruijie3GTrafficPreventMode, 
				    ruijie3GPppUsername, 
				    ruijie3GRouterSN, 
				    ruijie3GCardPhoneNumber, 
				    ruijie3GDailMode, 
				    ruijie3GDialOnDemandIfIndex, 
				    ruijie3GDeviceModemType }
			STATUS current
			DESCRIPTION 
				"This notification is generated when 4G is switching to slave line."
			::= { ruijie3GNotificationsNew 7 }
			
	END

--
-- RAISECOM-3G-MIB.mib
--
