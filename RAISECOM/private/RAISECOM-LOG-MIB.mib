-- *****************************************************************
-- RAISECOM-LOG-MIB.mib:  Raisecom Log MIB file
--
-- March 2002, Wuzg
--
-- Copyright (c) 2002 by Raisecom Networks Co.,Ltd.
-- All rights reserved.
-- 
-- *****************************************************************
--

RAISECOM-LOG-MIB DEFINITIONS ::= BEGIN

IMPORTS
        MODULE-IDENTITY,
        OBJECT-TYPE,
        Integer32,
        IpAddress
                FROM SNMPv2-SMI
        DisplayString,
        DateAndTime,
        TimeStamp,
        TEXTUAL-CONVENTION
                FROM SNMPv2-TC
        EnabledStatus 
                FROM P-BRIDGE-MIB
        ConfigStatus,
        IfIndex
                FROM RAISECOM-TC
        MODULE-COMPLIANCE,
        OBJECT-GROUP
                FROM SNMPv2-CONF
        ruijieMgmt
                FROM RAISECOM-SMI;

ruijieLogMIB MODULE-IDENTITY
        LAST-UPDATED "200203200000Z"
        ORGANIZATION "Raisecom Networks Co.,Ltd."
        CONTACT-INFO
                " 
                Tel: 4008-111-000 

                E-mail: service@raisecom.com.cn"
        DESCRIPTION
                "This module defines raisecom event mibs."
        REVISION      "200203200000Z"
        DESCRIPTION
                "Initial version of this MIB module."
        ::= { ruijieMgmt 4}

ruijieLogMIBObjects OBJECT IDENTIFIER ::= { ruijieLogMIB 1 }

       
LogSeverity ::= TEXTUAL-CONVENTION
	STATUS	current
	DESCRIPTION
	       "The severity of a log message."
	SYNTAX	INTEGER {
			emergency(0),
			alert(1),
			critical(2),
			error(3),
			warning(4),
			notice(5),
			info(6),
			debug(7)
		}      
LogTimeStamp ::= TEXTUAL-CONVENTION
	STATUS	current
	DESCRIPTION
	       "The timestamp of a log message."
	SYNTAX	INTEGER {
			disabled(1),
			datetime(2),
			uptime(3)
	
		}     

LogSyslogFacility ::= TEXTUAL-CONVENTION
	STATUS	current
	DESCRIPTION
	       "The facility of a syslog message."
	SYNTAX	INTEGER {
                        kernel(0),                            
			user(1),                        
			mail(2),                              
			system(3),     
			security(4),                                                
			syslogd(5),    
			lineprinter(6),                      
			network(7),                      
			uUCP(8),                              
			clockdaemon(9),                     
			authorization(10),  
			fTP(11),                                  
			nTP(12),                               
			logaudit(13),                         
			logalert(14),                       
			clockdaemon2(15),                   
			localuse0(16),                      
			localuse1(17),                     
			localuse2(18),                       
			localuse3(19),                       
			localuse4(20),                       
			localuse5(21),                       
			localuse6(22),                       
			localuse7(23)                     
		}   		
--
-- Log 
--

ruijieLogGlobalStatus OBJECT-TYPE
        SYNTAX          EnabledStatus
        MAX-ACCESS      read-write
        STATUS          current
        DESCRIPTION
	       "Indicates whether the system logging feature is currently 
           running in the device."
	DEFVAL { enabled }
	::= { ruijieLogMIBObjects 1 }

ruijieLogSendConsoleStatus OBJECT-TYPE
        SYNTAX          EnabledStatus
        MAX-ACCESS      read-write
        STATUS          current
        DESCRIPTION
	       "Indicates whether the system log will be sent to console(out-band)."
        DEFVAL { enabled }
	::= { ruijieLogMIBObjects 2 }	
	
ruijieLogSendConsoleMaxSeverity OBJECT-TYPE
        SYNTAX          LogSeverity
        MAX-ACCESS      read-write
        STATUS          current
        DESCRIPTION
	       "Indicates which severity levels system log will be
      	  sent to console(out-band).  Any system log message with a severity value
      	  greater than this value will be ignored by the agent.Setting this value
      	  to 0 will prevent any log to send to console."
      	DEFVAL { debug }
	::= { ruijieLogMIBObjects 3 }	

ruijieLogSendMonitorStatus OBJECT-TYPE
        SYNTAX          EnabledStatus
        MAX-ACCESS      read-write
        STATUS          current
        DESCRIPTION
	       "Indicates whether the system log will be sent to monitor(telnet)."
        DEFVAL { disabled }
	::= { ruijieLogMIBObjects 4 }
	
ruijieLogSendMonitorMaxSeverity OBJECT-TYPE
        SYNTAX          LogSeverity
        MAX-ACCESS      read-write
        STATUS          current
        DESCRIPTION
	       "Indicates which severity levels system log will be
      	  sendt to monitor(telnet).  Any system log message with a severity value
      	  greater than this value will be ignored by the agent.Setting this value
      	  to 0 will prevent any log to send to telnet."
        DEFVAL { debug }
	::= { ruijieLogMIBObjects 5 }
  
ruijieLogSaveFileName OBJECT-TYPE
        SYNTAX DisplayString
        MAX-ACCESS read-write
        STATUS current
        DESCRIPTION
            "Setting this value to a non-null string will save all entries of event log 
             table into file which name is assigned by this value. Setting this value 
             to a null string will not save log to file."
        DEFVAL { ""}
        ::= { ruijieLogMIBObjects 6 }
			
ruijieLogFileMaxSeverity OBJECT-TYPE
        SYNTAX          LogSeverity
        MAX-ACCESS      read-write
        STATUS          current
        DESCRIPTION
	       "Indicates which severity levels system log will be
      	  sent to monitor(telnet).  Any system log message with a severity value
      	  greater than this value will be ignored by the agent.Setting this value
      	  to 0 will prevent any log to send to telnet."
        DEFVAL { notice } 	  
	::= { ruijieLogMIBObjects 7 }	
	
ruijieLogFileMaxSize OBJECT-TYPE
        SYNTAX Integer32(4096..2000000)
        MAX-ACCESS read-write
        STATUS current
        DESCRIPTION
            "The size of log file in units of byte."
        DEFVAL { 4096 }    
   ::= { ruijieLogMIBObjects 8 }      	
   
ruijieLogSendBufferStatus OBJECT-TYPE
        SYNTAX          EnabledStatus
        MAX-ACCESS      read-write
        STATUS          current
        DESCRIPTION
	       "Indicates whether the system log will be sent to buffer for retaining."
        DEFVAL { enabled }
	::= { ruijieLogMIBObjects 9 }
	
ruijieLogSendBufferMaxSeverity OBJECT-TYPE
        SYNTAX          LogSeverity
        MAX-ACCESS      read-write
        STATUS          current
        DESCRIPTION
	       "Indicates which severity levels system log will be
      	  sendt to monitor(telnet).  Any system log message with a severity value
      	  greater than this value will be ignored by the agent.Setting this value
      	  to 0 will prevent any log to send to telnet."
        DEFVAL { debug }
	::= { ruijieLogMIBObjects 10 }

ruijieLogClearBuffer OBJECT-TYPE
        SYNTAX Integer32
        MAX-ACCESS read-write
        STATUS current
        DESCRIPTION
            "It will clear logging buffer to set this object to any value but 0,
             Set its value to 0 will cause no action of agent,  
             when query always return value 0."
   ::= { ruijieLogMIBObjects 11 }      
	
--
-- log history table
--            
ruijieLogHisRecordMaxNum OBJECT-TYPE
        SYNTAX Integer32
        MAX-ACCESS read-only
        STATUS current
        DESCRIPTION
               "The upper limit on the number of entries that the
                log history table may contain."
        ::= { ruijieLogMIBObjects 12 }

ruijieLogHisTable OBJECT-TYPE
        SYNTAX SEQUENCE OF RuijieLogHisEntry
        MAX-ACCESS not-accessible
        STATUS current
        DESCRIPTION
            "A list of log history record , and when the table is full 
             the oldest entry will be deleted and a new one will be created."
    ::= { ruijieLogMIBObjects 13 }
    
ruijieLogHisEntry OBJECT-TYPE
        SYNTAX RuijieLogHisEntry
        MAX-ACCESS not-accessible
        STATUS current
        DESCRIPTION
            "Entry obtains history information of each logging."
        INDEX { ruijieLogHisIndex }
        ::= { ruijieLogHisTable 1 }
        
RuijieLogHisEntry ::=
        SEQUENCE {
           ruijieLogHisIndex Integer32,
           ruijieLogHisSeverity LogSeverity,
           ruijieLogHisMsgName DisplayString ,
           ruijieLogHisDescription DisplayString,
           ruijieLogHisTime DateAndTime,
           ruijieLogHisStamps TimeStamp
        }
    
ruijieLogHisIndex OBJECT-TYPE
        SYNTAX Integer32
        MAX-ACCESS read-only
        STATUS current
        DESCRIPTION
            "A unique vlaue for each log Entry."
        ::= { ruijieLogHisEntry 1 }
        
ruijieLogHisSeverity OBJECT-TYPE
        SYNTAX          LogSeverity
        MAX-ACCESS      read-only
        STATUS          current
        DESCRIPTION
	       "The severity of the log message."
	::= { ruijieLogHisEntry 2 }
    
ruijieLogHisMsgName OBJECT-TYPE
        SYNTAX          DisplayString (SIZE (1..30))
        MAX-ACCESS      read-only
        STATUS          current
        DESCRIPTION
	       "A textual identification for the log message type.  A 
		     facility name  uniquely identifies a message type."
	::= { ruijieLogHisEntry 3 }
        
ruijieLogHisDescription OBJECT-TYPE
        SYNTAX DisplayString (SIZE(1..80))
        MAX-ACCESS read-only
        STATUS current
        DESCRIPTION
            "Text description for this log message."
        ::= { ruijieLogHisEntry 4 }        

ruijieLogHisTime OBJECT-TYPE
        SYNTAX DateAndTime
        MAX-ACCESS read-only
        STATUS current
        DESCRIPTION
            "Date and time for this message was generated. "
        ::= { ruijieLogHisEntry 5 }

ruijieLogHisStamps OBJECT-TYPE
        SYNTAX TimeStamp
        MAX-ACCESS read-only
        STATUS current
        DESCRIPTION
            "The history timestamp that is multipled by 0.01s from the Startup to log print."
        ::= { ruijieLogHisEntry 6 }   
        
ruijieLogSequenceGlobalStatus OBJECT-TYPE
	SYNTAX          EnabledStatus
	MAX-ACCESS      read-write
	STATUS          current
	DESCRIPTION
	       "Indicates whether the  system log sequence  feature is currently 
	   running in the device."
	DEFVAL { disabled }
	::= { ruijieLogMIBObjects 14 }    
	      
ruijieLogTimeStampGlobalStatus OBJECT-TYPE
	SYNTAX          LogTimeStamp
	MAX-ACCESS      read-write
	STATUS          current
	DESCRIPTION
	       "Indicates whether the  system log timestamp date feature is currently 
	   running in the device."
	DEFVAL { datetime }
	::= { ruijieLogMIBObjects 15}  	
	
	
ruijieLogSyslogRelayGlobalStatus OBJECT-TYPE
	SYNTAX          EnabledStatus
	MAX-ACCESS      read-write
	STATUS          current
	DESCRIPTION
	       "Indicates whether the  syslog relay feature is currently 
	   running in the device."
	DEFVAL { disabled }
	::= { ruijieLogMIBObjects 16 }  


ruijieLogSyslogFacility OBJECT-TYPE
        SYNTAX          LogSyslogFacility
        MAX-ACCESS      read-write
        STATUS          current
        DESCRIPTION
	       "Indicates which Facility value syslog will be
      	  sent to syslog server. "
        DEFVAL { localuse7} 	  
	::= { ruijieLogMIBObjects 17 }	
	
ruijieLogSyslogSeverity OBJECT-TYPE
        SYNTAX          LogSeverity
        MAX-ACCESS      read-write
        STATUS          current
        DESCRIPTION
	       "Indicates which severity levels syslog will be
      	  sent to syslog server.  Any syslog message with a severity value
      	  greater than this value will be ignored."
      	DEFVAL { debug }
	::= { ruijieLogMIBObjects 18 }
	
ruijieLogSyslogServerTable OBJECT-TYPE
        SYNTAX SEQUENCE OF RuijieLogSyslogServerEntry
        MAX-ACCESS not-accessible
        STATUS current
        DESCRIPTION 
            "A list of the syslog server ."
        ::= { ruijieLogMIBObjects 19 }	
        

ruijieLogSyslogServerEntry OBJECT-TYPE
        SYNTAX RuijieLogSyslogServerEntry
        MAX-ACCESS not-accessible
        STATUS current
        DESCRIPTION
            "Entry obtains information of each syslog server ."
        INDEX { ruijieLogSyslogServerIpAddr }
        ::= { ruijieLogSyslogServerTable 1 }        

RuijieLogSyslogServerEntry ::=
        SEQUENCE {
           ruijieLogSyslogServerIpAddr IpAddress,
           ruijieLogSyslogServerIpStatus ConfigStatus
        }   

ruijieLogSyslogServerIpAddr OBJECT-TYPE
        SYNTAX IpAddress
        MAX-ACCESS read-only
        STATUS current
        DESCRIPTION
            "A ip address of a syslog server."
        ::= { ruijieLogSyslogServerEntry 1 }     
                                 
ruijieLogSyslogServerIpStatus OBJECT-TYPE
        SYNTAX ConfigStatus
        MAX-ACCESS read-write
        STATUS current
        DESCRIPTION
            "entry status. Setting this value to 'invalid' will remove this server"
        ::= { ruijieLogSyslogServerEntry 2 }
        
ruijieLogSyslogSendSrcIfindex OBJECT-TYPE
        SYNTAX IfIndex
        MAX-ACCESS read-write
        STATUS current
        DESCRIPTION
            "The source ifindex which syslog send ."
        ::= { ruijieLogMIBObjects 20 }  
   
ruijieLogSyslogSendSrcIp OBJECT-TYPE
        SYNTAX IpAddress
        MAX-ACCESS read-write
        STATUS current
        DESCRIPTION
            "The source Ip which syslog send ."
        ::= { ruijieLogMIBObjects 21}        
        

	  
        
ruijieLogMIBConformance OBJECT IDENTIFIER ::= { ruijieLogMIB 4 }
ruijieLogMIBCompliances OBJECT IDENTIFIER ::= { ruijieLogMIBConformance 1 }
ruijieLogMIBGroups      OBJECT IDENTIFIER ::= { ruijieLogMIBConformance 2 }


-- compliance statements

ruijieLogMIBCompliance MODULE-COMPLIANCE
        STATUS  current
        DESCRIPTION
                "The compliance statement for entities which implement
                the Raisecom Log MIB"
        MODULE  -- this module
                MANDATORY-GROUPS { ruijieLogMIBGroup
                 }
		

		GROUP ruijieLogHisStampsMIBGroup
		DESCRIPTION  
                     "This group is mandatory when the system has no RTC."  


        ::= { ruijieLogMIBCompliances 1 }
                
-- units of conformance
       
ruijieLogMIBGroup OBJECT-GROUP
        OBJECTS {
           ruijieLogGlobalStatus,
           ruijieLogSendConsoleStatus,
           ruijieLogSendConsoleMaxSeverity,
           ruijieLogSendMonitorStatus,
           ruijieLogSendMonitorMaxSeverity, 
           ruijieLogSaveFileName,
           ruijieLogFileMaxSeverity,
           ruijieLogFileMaxSize,
           ruijieLogSendBufferStatus,
           ruijieLogSendBufferMaxSeverity,
           ruijieLogClearBuffer,
           ruijieLogHisRecordMaxNum,
           ruijieLogHisIndex,
           ruijieLogHisSeverity,
           ruijieLogHisMsgName,
           ruijieLogHisDescription,
           ruijieLogHisTime,
           ruijieLogSequenceGlobalStatus,
           ruijieLogTimeStampGlobalStatus,
           ruijieLogSyslogRelayGlobalStatus,
           ruijieLogSyslogFacility,
           ruijieLogSyslogSeverity,
           ruijieLogSyslogServerIpAddr,
           ruijieLogSyslogServerIpStatus,
           ruijieLogSyslogSendSrcIfindex,
           ruijieLogSyslogSendSrcIp           
        }
        STATUS  current
        DESCRIPTION
                "A collection of objects providing logging to a
                 Raisecom agent."
        ::= { ruijieLogMIBGroups 1 }                 
                
ruijieLogHisStampsMIBGroup OBJECT-GROUP
        OBJECTS { 
           ruijieLogHisStamps
        }
        STATUS  current
        DESCRIPTION
                "Collection of log history timestamp."  
        ::= { ruijieLogMIBGroups 2 }                 
       
END
